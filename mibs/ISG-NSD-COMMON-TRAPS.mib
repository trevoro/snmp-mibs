-- Version 2.15.1.2 modified 2002-01-23 15:45:33-05

        ISG-NSD-COMMON-TRAPS DEFINITIONS ::= BEGIN
           
         IMPORTS
					enterprises FROM RFC1155-SMI
                TRAP-TYPE
                         FROM RFC-1215
                cdx6500SNMPLastTrap
                         FROM CDX-6500-COMMON-MIB
                ;

------ Object Identifiers. --------

        Counter16    ::=                        INTEGER (0..65535)

        Counter8    ::=                        INTEGER (0..255)

        MacAddress     ::= OCTET STRING (SIZE (6)) -- a 6 octet
        --     enterprises OBJECT IDENTIFIER ::= { private 1 }
        --     enterprises OBJECT IDENTIFIER ::= { private 1 }
        --     enterprises OBJECT IDENTIFIER ::= { private 1 }
               codex       OBJECT IDENTIFIER ::= { enterprises 449 }
    cdxProductSpecific     OBJECT IDENTIFIER ::= { codex 2 }
               cdx6500     OBJECT IDENTIFIER ::= { cdxProductSpecific 1 }
----------------------------------------------------------------------

      -- This object is defined to overcome HP Openview
      -- mib compiler error when no objects are defined
      -- in a module.
 
     -- cdx6520SysObjId OBJECT IDENTIFIER ::= { cdx6500 6520}

     -- TEMPLATE AFTER DESCRIPTION IS FOR HP OPENVIEW. THERE IS TOOL IN NETWORK MGMT
     -- GROUP WHICH CONVERTS THIS FILE TO HP OPENVIEW TRAP.CONF FORMAT.

        code-power-supply-down  TRAP-TYPE
		ENTERPRISE   cdx6500
		VARIABLES    { cdx6500SNMPLastTrap }
		DESCRIPTION
		     "POWER SUPPLY (%c) DOWN"
		     --#TYPE
		     --#SUMMARY "Trap #$G, specific: $S, arg(1) : $1"
		     --#ARGUMENTS {}
		     --#SEVERITY  CRITICAL
		     --#TIMEINDEX
		     --#HELP
		     --#HELPTAG
		     --#STATE
		::= 1000

        code-power-supply-up  TRAP-TYPE
		ENTERPRISE   cdx6500
		VARIABLES    { cdx6500SNMPLastTrap }
		DESCRIPTION
		     "POWER SUPPLY (%c) UP"
		     --#TYPE
		     --#SUMMARY "Trap #$G, specific: $S, arg(1) : $1"
		     --#ARGUMENTS {}
		     --#SEVERITY  CRITICAL
		     --#TIMEINDEX
		     --#HELP
		     --#HELPTAG
		     --#STATE
		::= 1001

        code-fan-failed  TRAP-TYPE
		ENTERPRISE   cdx6500
		VARIABLES    { cdx6500SNMPLastTrap }
		DESCRIPTION
		     "FAN FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 1002

        code-flash-checksum-error  TRAP-TYPE
		ENTERPRISE   cdx6500
		VARIABLES    { cdx6500SNMPLastTrap }
		DESCRIPTION
		     "FLASH CHECKSUM ERROR, %s (%04X/%04X)"
		     --#TYPE
		     --#SUMMARY "Trap #$G, specific: $S, arg(1) : $1"
		     --#ARGUMENTS {}
		     --#SEVERITY  CRITICAL
		     --#TIMEINDEX
		     --#HELP
		     --#HELPTAG
		     --#STATE
		::= 1003

        code-flash-checksum-ok  TRAP-TYPE
		ENTERPRISE   cdx6500
		VARIABLES    { cdx6500SNMPLastTrap }
		DESCRIPTION
		     "FLASH CHECKSUM OK, %s (%04X)"
		     --#TYPE
		     --#SUMMARY "Trap #$G, specific: $S, arg(1) : $1"
		     --#ARGUMENTS {}
		     --#SEVERITY  CRITICAL
		     --#TIMEINDEX
		     --#HELP
		     --#HELPTAG
		     --#STATE
		::= 1004

        code-error-detected  TRAP-TYPE
		ENTERPRISE   cdx6500
		VARIABLES    { cdx6500SNMPLastTrap }
		DESCRIPTION
		     "%d ERROR DETECTED AT 0x%x bit(s)0x%x.  CORRECTED."
		     --#TYPE
		     --#SUMMARY "Trap #$G, specific: $S, arg(1) : $1"
		     --#ARGUMENTS {}
		     --#SEVERITY  MAJOR
		     --#TIMEINDEX
		     --#HELP
		     --#HELPTAG
		     --#STATE
		::= 1005

	code1006-dram-code-c   TRAP-TYPE
		ENTERPRISE   cdx6500
		VARIABLES    { cdx6500SNMPLastTrap }
		DESCRIPTION
		     "DRAM CODE CHECKSUM ERROR - REPAIRED"
		     --#TYPE
		     --#SUMMARY "Trap #$G, specific: $S, arg(1) : $1"
		     --#ARGUMENTS {}
		     --#SEVERITY  MAJOR
		     --#TIMEINDEX
		     --#HELP
		     --#HELPTAG
		     --#STATE
		::= 1006

	code1007-dram-code-c   TRAP-TYPE
		ENTERPRISE   cdx6500
		VARIABLES    { cdx6500SNMPLastTrap }
		DESCRIPTION
		     "DRAM CODE CHECKSUM ERROR - UNABLE TO REPAIR - WRONG or NO FLASH"
		     --#TYPE
		     --#SUMMARY "Trap #$G, specific: $S, arg(1) : $1"
		     --#ARGUMENTS {}
		     --#SEVERITY  CRITICAL
		     --#TIMEINDEX
		     --#HELP
		     --#HELPTAG
		     --#STATE
		::= 1007

	code-dram-idata-c   TRAP-TYPE
		ENTERPRISE   cdx6500
		VARIABLES    { cdx6500SNMPLastTrap }
		DESCRIPTION
		     "DRAM IDATA CHECKSUM ERROR - RELOADING IDATA,"
		     --#TYPE	
		     --#SUMMARY "Trap #$G, specific: $S, arg(1) : $1"
		     --#ARGUMENTS {}
		     --#SEVERITY  MAJOR
		     --#TIMEINDEX
		     --#HELP
		     --#HELPTAG
		     --#STATE
		::= 1008

	code-dram-idata-reload-success   TRAP-TYPE
		ENTERPRISE   cdx6500
		VARIABLES    { cdx6500SNMPLastTrap }
		DESCRIPTION
		     "DRAM IDATA WAS RELOADED CORRECTLY, CONTACT MOTOROLA WITH ABOVE INFORMATION" 
		     --#TYPE	
		     --#SUMMARY "Trap #$G, specific: $S, arg(1) : $1"
		     --#ARGUMENTS {}
		     --#SEVERITY  MAJOR
		     --#TIMEINDEX
		     --#HELP
		     --#HELPTAG
		     --#STATE
		::= 1009

	code-dram-idata-reload-failure   TRAP-TYPE
		ENTERPRISE   cdx6500
		VARIABLES    { cdx6500SNMPLastTrap }
		DESCRIPTION
		     "DRAM IDATA COULD NOT BE RELOADED - OS-ABORT CALLED"
		     --#TYPE	
		     --#SUMMARY "Trap #$G, specific: $S, arg(1) : $1"
		     --#ARGUMENTS {}
		     --#SEVERITY  CRITICAL
		     --#TIMEINDEX
		     --#HELP
		     --#HELPTAG
		     --#STATE
		::= 1010

	code-dram-idata-sig-array   TRAP-TYPE
		ENTERPRISE   cdx6500
		VARIABLES    { cdx6500SNMPLastTrap }
		DESCRIPTION
		     "DRAM IDATA ARRAY BITS[%d - %d]: 0x%x 0x%x 0x%x 0x%x"
		     --#TYPE	
		     --#SUMMARY "Trap #$G, specific: $S, arg(1) : $1"
		     --#ARGUMENTS {}
		     --#SEVERITY  MAJOR
		     --#TIMEINDEX
		     --#HELP
		     --#HELPTAG
		     --#STATE
		::= 1011

        port-boot-complete  TRAP-TYPE
		ENTERPRISE   cdx6500
                VARIABLES    { cdx6500SNMPLastTrap }
                DESCRIPTION
                             " %02d - PORT BOOT COMPLETE "
                     --#TYPE
                     --#SUMMARY "Trap #$G, specific: $S, arg(1): $1"
                     --#ARGUMENTS {}
                     --#SEVERITY  INFORMATIONAL
                     --#TIMEINDEX
                     --#HELP
                     --#HELPTAG
                     --#STATE
                ::= 2000

        port-boot-failure  TRAP-TYPE
                ENTERPRISE   cdx6500
                VARIABLES    { cdx6500SNMPLastTrap }
                DESCRIPTION
                             " %02d - PORT BOOT FAILURE  (%d) "
                     --#TYPE
                     --#SUMMARY "Trap #$G, specific: $S, arg(1): $1"
                     --#ARGUMENTS {}
                     --#SEVERITY  INFORMATIONAL
                     --#TIMEINDEX
                     --#HELP
                     --#HELPTAG
                     --#STATE
                ::= 2001

        channel-boot-complete  TRAP-TYPE
                ENTERPRISE   cdx6500
                VARIABLES    { cdx6500SNMPLastTrap }
                DESCRIPTION
                             " %02d(%d) - CHANNEL BOOT COMPLETE "
                     --#TYPE
                     --#SUMMARY "Trap #$G, specific: $S, arg(1): $1"
                     --#ARGUMENTS {}
                     --#SEVERITY  INFORMATIONAL
                     --#TIMEINDEX
                     --#HELP
                     --#HELPTAG
                     --#STATE
                ::= 2002

        channel-boot-failure  TRAP-TYPE
                ENTERPRISE   cdx6500
                VARIABLES    { cdx6500SNMPLastTrap }
                DESCRIPTION
                             " %02d(%d) - CHANNEL BOOT FAILURE (%d) "
                     --#TYPE
                     --#SUMMARY "Trap #$G, specific: $S, arg(1): $1"
                     --#ARGUMENTS {}
                     --#SEVERITY  INFORMATIONAL
                     --#TIMEINDEX
                     --#HELP
                     --#HELPTAG
                     --#STATE
                ::= 2003

        code-port-boot-to-new-port-failu  TRAP-TYPE
		ENTERPRISE   cdx6500
		VARIABLES    { cdx6500SNMPLastTrap }
		DESCRIPTION
		     "PORT-%02d - BOOT TO NEW PORT FAILURE, PORT DOES NOT SUPPORT DYNAMIC CREATE"
		     --#TYPE
		     --#SUMMARY "Trap #$G, specific: $S, arg(1) : $1"
		     --#ARGUMENTS {}
		     --#SEVERITY  CRITICAL
		     --#TIMEINDEX
		     --#HELP
		     --#HELPTAG
		     --#STATE
		::= 2004

        code-port-insufficient-dynamic-m  TRAP-TYPE
		ENTERPRISE   cdx6500
		VARIABLES    { cdx6500SNMPLastTrap }
		DESCRIPTION
		     "PORT-%02d - INSUFFICIENT DYNAMIC MEMORY, PORT DOWN GRADED TO NULL PORT"
		     --#TYPE
		     --#SUMMARY "Trap #$G, specific: $S, arg(1) : $1"
		     --#ARGUMENTS {}
		     --#SEVERITY  CRITICAL
		     --#TIMEINDEX
		     --#HELP
		     --#HELPTAG
		     --#STATE
		::= 2005

	code2006-port-dynami   TRAP-TYPE
		ENTERPRISE   cdx6500
		VARIABLES    { cdx6500SNMPLastTrap }
		DESCRIPTION
		     "PORT-%02d - DYNAMIC PORT BOOT STARTED"
		     --#TYPE
		     --#SUMMARY "Trap #$G, specific: $S, arg(1) : $1"
		     --#ARGUMENTS {}
		     --#SEVERITY  CRITICAL
		     --#TIMEINDEX
		     --#HELP
		     --#HELPTAG
		     --#STATE
		::= 2006

	code2007-port-dynami   TRAP-TYPE
		ENTERPRISE   cdx6500
		VARIABLES    { cdx6500SNMPLastTrap }
		DESCRIPTION
		     "PORT-%02d - DYNAMIC PORT BEING CREATED"
		     --#TYPE
		     --#SUMMARY "Trap #$G, specific: $S, arg(1) : $1"
		     --#ARGUMENTS {}
		     --#SEVERITY  MAJOR
		     --#TIMEINDEX
		     --#HELP
		     --#HELPTAG
		     --#STATE
		::= 2007

	code2008-port-dynami   TRAP-TYPE
		ENTERPRISE   cdx6500
		VARIABLES    { cdx6500SNMPLastTrap }
		DESCRIPTION
		     "PORT-%02d - DYNAMIC PORT BOOT COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 2008

	code2009-port-failur   TRAP-TYPE
		ENTERPRISE   cdx6500
		VARIABLES    { cdx6500SNMPLastTrap }
		DESCRIPTION
		     "PORT-%02d - FAILURE PORT DOES NOT EXIST"
		     --#TYPE
		     --#SUMMARY "Trap #$G, specific: $S, arg(1) : $1"
		     --#ARGUMENTS {}
		     --#SEVERITY  CRITICAL
		     --#TIMEINDEX
		     --#HELP
		     --#HELPTAG
		     --#STATE
		::= 2009

        buff-pool-util-exceeded  TRAP-TYPE
                ENTERPRISE   cdx6500
                VARIABLES    { cdx6500SNMPLastTrap }
                DESCRIPTION
                             " BUFFER POOL UTILIZATION > THRESHOLD ON CARD %d"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 3000

        lib-lan-congestion-start  TRAP-TYPE
		ENTERPRISE   cdx6500
		VARIABLES    { cdx6500SNMPLastTrap }
		DESCRIPTION
		     "LAN CONGESTION START, %s, %s"
		     --#TYPE
		     --#SUMMARY "Trap #$G, specific: $S, arg(1) : $1"
		     --#ARGUMENTS {}
		     --#SEVERITY  MINOR
		     --#TIMEINDEX
		     --#HELP
		     --#HELPTAG
		     --#STATE
		::= 3001

        lib-lan-congestion-end  TRAP-TYPE
		ENTERPRISE   cdx6500
		VARIABLES    { cdx6500SNMPLastTrap }
		DESCRIPTION
		     "LAN CONGESTION END, %s, %s"
		     --#TYPE
		     --#SUMMARY "Trap #$G, specific: $S, arg(1) : $1"
		     --#ARGUMENTS {}
		     --#SEVERITY  MINOR
		     --#TIMEINDEX
		     --#HELP
		     --#HELPTAG
		     --#STATE
		::= 3002

        cmem-corrupted  TRAP-TYPE
                ENTERPRISE   cdx6500
                VARIABLES    { cdx6500SNMPLastTrap }
                DESCRIPTION
                             "CMEM CORRUPTION DETECTED ON BOARD %d"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 4000

        cmem-recovered  TRAP-TYPE
                ENTERPRISE   cdx6500
                VARIABLES    { cdx6500SNMPLastTrap }
                DESCRIPTION
                             "CMEM RECOVERED FROM BOARD %d"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 4001

        cmem-compression-fail  TRAP-TYPE
                ENTERPRISE   cdx6500
                VARIABLES    { cdx6500SNMPLastTrap }
                DESCRIPTION
                             "UNABLE TO COMPRESS CMEM - CMEM NOT WRITTEN"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 4002

        code-no-memory-tftp-upload-to-sc  TRAP-TYPE
		ENTERPRISE   cdx6500
		VARIABLES    { cdx6500SNMPLastTrap }
		DESCRIPTION
		     "NO MEMORY - TFTP UPLOAD TO SCRIPT FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 4003

        ctp-wrong-task-level  TRAP-TYPE
                ENTERPRISE   cdx6500
                VARIABLES    { cdx6500SNMPLastTrap }
                DESCRIPTION
                             "CTP - at wrong task, TCB = %x"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 5000

        ctp-help-msg-overflow  TRAP-TYPE
                ENTERPRISE   cdx6500
                VARIABLES    { cdx6500SNMPLastTrap }
                DESCRIPTION
                             "CTP HELP MESSAGE ARRAY OVERFLOW"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 5001

        eiaPort-handshake-incomplete  TRAP-TYPE
                ENTERPRISE   cdx6500
                VARIABLES    { cdx6500SNMPLastTrap }
                DESCRIPTION
                             " %s - EIA HANDSHAKE INCOMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6001

        eiaPort-handshake-complete  TRAP-TYPE
                ENTERPRISE   cdx6500
                VARIABLES    { cdx6500SNMPLastTrap }
                DESCRIPTION
                             " %s - EIA HANDSHAKE COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6002

        v25bis-proto-mismatch  TRAP-TYPE
                ENTERPRISE   cdx6500
                VARIABLES    { cdx6500SNMPLastTrap }
                DESCRIPTION
                             "%s - V.25 BIS PROTOCOL MISMATCH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6003

        v25bis-call-fail  TRAP-TYPE
                ENTERPRISE   cdx6500
                VARIABLES    { cdx6500SNMPLastTrap }
                DESCRIPTION
                             "%s - V.25 BIS CALL FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6004

        v25bis-error  TRAP-TYPE
                ENTERPRISE   cdx6500
                VARIABLES    { cdx6500SNMPLastTrap }
                DESCRIPTION
                             "%s - V.25 BIS ERROR - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6005

        v25bis-unknown-error  TRAP-TYPE
                ENTERPRISE   cdx6500
                VARIABLES    { cdx6500SNMPLastTrap }
                DESCRIPTION
                             "%s - V.25 BIS UNKNOWN ERROR - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6006

        sw56k-calling  TRAP-TYPE
                ENTERPRISE   cdx6500
                VARIABLES    { cdx6500SNMPLastTrap }
                DESCRIPTION
                             " %s - SW56K CALLING %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6007

        sw56k-connected  TRAP-TYPE
                ENTERPRISE   cdx6500
                VARIABLES    { cdx6500SNMPLastTrap }
                DESCRIPTION
                             " %s - SW56K CONNECTED TO %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6008

        sw56k-call-fail  TRAP-TYPE
                ENTERPRISE   cdx6500
                VARIABLES    { cdx6500SNMPLastTrap }
                DESCRIPTION
                             "%s - SW56K CALL TO %s FAILED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6009

        sw56k-incall-answered  TRAP-TYPE
                ENTERPRISE   cdx6500
                VARIABLES    { cdx6500SNMPLastTrap }
                DESCRIPTION
                             " %s - SW56K INCOMING CALL ANSWERED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6010

        sw56k-no-phone-num  TRAP-TYPE
                ENTERPRISE   cdx6500
                VARIABLES    { cdx6500SNMPLastTrap }
                DESCRIPTION
                             "%s - SW56K CALL FAILED - NO PHONE NUMBER"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6011

        sw56k-incall-ignored  TRAP-TYPE
                ENTERPRISE   cdx6500
                VARIABLES    { cdx6500SNMPLastTrap }
                DESCRIPTION
                             "%s - SW56K INCOMING CALL IGNORED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6012

        sw56k-disconnect-fail  TRAP-TYPE
                ENTERPRISE   cdx6500
                VARIABLES    { cdx6500SNMPLastTrap }
                DESCRIPTION
                             "%s - SW56K FAILED TO DISCONNECT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6013

        sw56k-line-out-of-service  TRAP-TYPE
                ENTERPRISE   cdx6500
                VARIABLES    { cdx6500SNMPLastTrap }
                DESCRIPTION
                             "%s - SW56K LINE NOT IN SERVICE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6014

        sw56k-line-in-service  TRAP-TYPE
                ENTERPRISE   cdx6500
                VARIABLES    { cdx6500SNMPLastTrap }
                DESCRIPTION
                             "%s - SW56K LINE IN SERVICE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6015

        sw56k-call-disconnected  TRAP-TYPE
                ENTERPRISE   cdx6500
                VARIABLES    { cdx6500SNMPLastTrap }
                DESCRIPTION
                             " %s - SW56K CALL DISCONNECTED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6016

        sw56k-in-channel-loopback  TRAP-TYPE
                ENTERPRISE   cdx6500
                VARIABLES    { cdx6500SNMPLastTrap }
                DESCRIPTION
                             "%s - SW56K IN CHANNEL LOOPBACK"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6017

        sw56k-in-dsu-loopback  TRAP-TYPE
                ENTERPRISE   cdx6500
                VARIABLES    { cdx6500SNMPLastTrap }
                DESCRIPTION
                             "%s - SW56K IN DSU LOOPBACK"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6018

        x32-dial-in-not-allowed  TRAP-TYPE
                ENTERPRISE   cdx6500
                VARIABLES    { cdx6500SNMPLastTrap }
                DESCRIPTION
                             " %s - DIAL IN NOT ALLOWED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6019

        x32-dial-out-not-allowed  TRAP-TYPE
                ENTERPRISE   cdx6500
                VARIABLES    { cdx6500SNMPLastTrap }
                DESCRIPTION
                             "%s - DIAL OUT NOT ALLOWED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6020

        x32-modem-faulty  TRAP-TYPE
                ENTERPRISE   cdx6500
                VARIABLES    { cdx6500SNMPLastTrap }
                DESCRIPTION
                             " %s - MODEM FAULTY OR NOT CONNECTED - %s - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6021

        x32-phone-num-busy  TRAP-TYPE
                ENTERPRISE   cdx6500
                VARIABLES    { cdx6500SNMPLastTrap }
                DESCRIPTION
                             " %s - PHONE NUMBER BUSY - %s - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6022

        x32-phone-line-busy  TRAP-TYPE
                ENTERPRISE   cdx6500
                VARIABLES    { cdx6500SNMPLastTrap }
                DESCRIPTION
                             " %s - PHONE LINE BUSY - %s - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6023

        x32-incompat-destination  TRAP-TYPE
                ENTERPRISE   cdx6500
                VARIABLES    { cdx6500SNMPLastTrap }
                DESCRIPTION
                             " %s - INCOMPATIBLE DESTINATION - %s - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 6024

	eia6025-port-dial-nu   TRAP-TYPE
		ENTERPRISE   cdx6500
		VARIABLES    { cdx6500SNMPLastTrap }
		DESCRIPTION
		     "Port %s - Dial Number one and two failed connection - %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 6025

	eia6026-port-modem-f   TRAP-TYPE
		ENTERPRISE   cdx6500
		VARIABLES    { cdx6500SNMPLastTrap }
		DESCRIPTION
		     "Port %s - Modem failed to Initialize, retrying..."
		     --#TYPE
		     --#SUMMARY "Trap #$G, specific: $S, arg(1) : $1"
		     --#ARGUMENTS {}
		     --#SEVERITY  MINOR
		     --#TIMEINDEX
		     --#HELP
		     --#HELPTAG
		     --#STATE
		::= 6026

	eia6027-port-modem-f   TRAP-TYPE
		ENTERPRISE   cdx6500
		VARIABLES    { cdx6500SNMPLastTrap }
		DESCRIPTION
		     "Port %s - Modem failed response to init, retrying..."
		     --#TYPE
		     --#SUMMARY "Trap #$G, specific: $S, arg(1) : $1"
		     --#ARGUMENTS {}
		     --#SEVERITY  MINOR
		     --#TIMEINDEX
		     --#HELP
		     --#HELPTAG
		     --#STATE
		::= 6027

	eia6028-port-modem-f   TRAP-TYPE
		ENTERPRISE   cdx6500
		VARIABLES    { cdx6500SNMPLastTrap }
		DESCRIPTION
		     "Port %s - Modem failed to respond to leads, reboot port."
		     --#TYPE
		     --#SUMMARY "Trap #$G, specific: $S, arg(1) : $1"
		     --#ARGUMENTS {}
		     --#SEVERITY  CRITICAL
		     --#TIMEINDEX
		     --#HELP
		     --#HELPTAG
		     --#STATE
		::= 6028

	eia6029-port-incomin   TRAP-TYPE
		ENTERPRISE   cdx6500
		VARIABLES    { cdx6500SNMPLastTrap }
		DESCRIPTION
		     "Port %s - Incoming call detected, cannot dial out"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 6029

	eia6030-port-no-dial   TRAP-TYPE
		ENTERPRISE   cdx6500
		VARIABLES    { cdx6500SNMPLastTrap }
		DESCRIPTION
		     "Port %s - No dial numbers configured"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 6030

	eia6031-port-could-n   TRAP-TYPE
		ENTERPRISE   cdx6500
		VARIABLES    { cdx6500SNMPLastTrap }
		DESCRIPTION
		     "Port %s - Could not disconnect modem, reboot port."
		     --#TYPE
		     --#SUMMARY "Trap #$G, specific: $S, arg(1) : $1"
		     --#ARGUMENTS {}
		     --#SEVERITY  INFORMATIONAL
		     --#TIMEINDEX
		     --#HELP
		     --#HELPTAG
		     --#STATE
		::= 6031

        code-software-failure-logged  TRAP-TYPE
		ENTERPRISE   cdx6500
		VARIABLES    { cdx6500SNMPLastTrap }
		DESCRIPTION
		     "SOFTWARE FAILURE LOGGED"
		     --#TYPE
		     --#SUMMARY "Trap #$G, specific: $S, arg(1) : $1"
		     --#ARGUMENTS {}
		     --#SEVERITY  CRITICAL
		     --#TIMEINDEX
		     --#HELP
		     --#HELPTAG
		     --#STATE
		::= 9000

	code9001-task-rescue   TRAP-TYPE
		ENTERPRISE   cdx6500
		VARIABLES    { cdx6500SNMPLastTrap }
		DESCRIPTION
		     "%s task rescued from possible deadlock"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 9001

	code9002-rescued-msg   TRAP-TYPE
		ENTERPRISE   cdx6500
		VARIABLES    { cdx6500SNMPLastTrap }
		DESCRIPTION
		     "%s rescued msg #%d\r\n%x/%x/%x %x/%x"
		     --#TYPE
		     --#SUMMARY "Trap #$G, specific: $S, arg(1) : $1"
		     --#ARGUMENTS {}
		     --#SEVERITY  CRITICAL
		     --#TIMEINDEX
		     --#HELP
		     --#HELPTAG
		     --#STATE
		::= 9002

	code9003-rescued-msg   TRAP-TYPE
		ENTERPRISE   cdx6500
		VARIABLES    { cdx6500SNMPLastTrap }
		DESCRIPTION
		     "%s rescued msg #%d\r\n%x:%x %x:%x %x:%x %x:%x %x:%x"
		     --#TYPE
		     --#SUMMARY "Trap #$G, specific: $S, arg(1) : $1"
		     --#ARGUMENTS {}
		     --#SEVERITY  CRITICAL
		     --#TIMEINDEX
		     --#HELP
		     --#HELPTAG
		     --#STATE
		::= 9003

        reports-lost  TRAP-TYPE
                ENTERPRISE   cdx6500
                VARIABLES    { cdx6500SNMPLastTrap }
                DESCRIPTION
                             "%d REPORTS LOST"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 15000

        report-log-cleared  TRAP-TYPE
                ENTERPRISE   cdx6500
                VARIABLES    { cdx6500SNMPLastTrap }
                DESCRIPTION
                             " LOG CLEARED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 15001

        vc-connected  TRAP-TYPE
                ENTERPRISE   cdx6500
                VARIABLES    { cdx6500SNMPLastTrap }
                DESCRIPTION
                             "%s CONNECTED TO %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 16000

        vc-disconnected  TRAP-TYPE
                ENTERPRISE   cdx6500
                VARIABLES    { cdx6500SNMPLastTrap }
                DESCRIPTION
                             "%s DISCONNECTED FROM %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 16001

        pvc-duplication  TRAP-TYPE
                ENTERPRISE   cdx6500
                VARIABLES    { cdx6500SNMPLastTrap }
                DESCRIPTION
                             " %02d(%d) - PVC DUPLICATED IN PVC TABLE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 16002

        pvc-not-connected  TRAP-TYPE
                ENTERPRISE   cdx6500
                VARIABLES    { cdx6500SNMPLastTrap }
                DESCRIPTION
                             " '%s' - PVC NOT CONNECTED TO '%s' - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 16003

        node-boot-for-rout-tables  TRAP-TYPE
                ENTERPRISE   cdx6500
                VARIABLES    { cdx6500SNMPLastTrap }
                DESCRIPTION
                             "Node boot required. The number of ROUT table entries in CMEM does not match the active number."
                     --#TYPE
                     --#SUMMARY "Trap #$G, specific: $S, arg(1): $1"
                     --#ARGUMENTS {}
                     --#SEVERITY  INFORMATIONAL
                     --#TIMEINDEX
                     --#HELP
                     --#HELPTAG
                     --#STATE
                ::= 16004

        node-boot-for-pvc  TRAP-TYPE
                ENTERPRISE   cdx6500
                VARIABLES    { cdx6500SNMPLastTrap }
                DESCRIPTION
                             "Node boot required. The number of PVC table entries in CMEM does not match the active number."
                     --#TYPE
                     --#SUMMARY "Trap #$G, specific: $S, arg(1): $1"
                     --#ARGUMENTS {}
                     --#SEVERITY  INFORMATIONAL
                     --#TIMEINDEX
                     --#HELP
                     --#HELPTAG
                     --#STATE
                ::= 16005

        rout-call-from-to-cleared-by-rou  TRAP-TYPE
		ENTERPRISE   cdx6500
		VARIABLES    { cdx6500SNMPLastTrap }
		DESCRIPTION
		     "CALL FROM %s TO %s CLEARED BY ROUT"
		     --#TYPE
		     --#SUMMARY "Trap #$G, specific: $S, arg(1) : $1"
		     --#ARGUMENTS {}
		     --#SEVERITY  CRITICAL
		     --#TIMEINDEX
		     --#HELP
		     --#HELPTAG
		     --#STATE
		::= 16006

	rout16007-routproclb-ss-rout-down   TRAP-TYPE
		ENTERPRISE   cdx6500
		VARIABLES    { cdx6500SNMPLastTrap }
		DESCRIPTION
		     " Rout-Proc-LBU : SS-ROUT-DOWN: Dont know how to frwd call: %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16007

	rout16008-routproclb-rout-not-found   TRAP-TYPE
		ENTERPRISE   cdx6500
		VARIABLES    { cdx6500SNMPLastTrap }
		DESCRIPTION
		     " Rout-Proc-LBU: SS-ROUT-DOWN:ROUT-NOT-FOUND:Cleared the Call: %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16008

	rout16009-routproclb-forwarding-call-req   TRAP-TYPE
		ENTERPRISE   cdx6500
		VARIABLES    { cdx6500SNMPLastTrap }
		DESCRIPTION
		     "Rout-Proc-LBU : SS-ROUT-DOWN : Forwarding Call Req : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16009

	rout16010-routproclb-ss-rout-up   TRAP-TYPE
		ENTERPRISE   cdx6500
		VARIABLES    { cdx6500SNMPLastTrap }
		DESCRIPTION
		     "Rout-Proc-LBU : SS-ROUT-UP: Call retry failed: Clearing: %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16010

	rout16011-routproclb-retry-calls   TRAP-TYPE
		ENTERPRISE   cdx6500
		VARIABLES    { cdx6500SNMPLastTrap }
		DESCRIPTION
		     "Rout-Proc-LBU : SS-ROUT-UP: Retry calls : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16011

	rout16012-rout-old-call-req   TRAP-TYPE
		ENTERPRISE   cdx6500
		VARIABLES    { cdx6500SNMPLastTrap }
		DESCRIPTION
		     "ROUT-Old-Call-Req: FROM %s TO %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16012

	rout16013-rout-call-req   TRAP-TYPE
		ENTERPRISE   cdx6500
		VARIABLES    { cdx6500SNMPLastTrap }
		DESCRIPTION
		     "ROUT-Call-Req: FROM %s TO %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16013

	rout16014-rout-call-acc   TRAP-TYPE
		ENTERPRISE   cdx6500
		VARIABLES    { cdx6500SNMPLastTrap }
		DESCRIPTION
		     "ROUT-Call-Acc: %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16014

	rout16015-rout-local-clear   TRAP-TYPE
		ENTERPRISE   cdx6500
		VARIABLES    { cdx6500SNMPLastTrap }
		DESCRIPTION
		     "ROUT-Local-Clear: %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16015

	rout16016-rout-clear-req   TRAP-TYPE
		ENTERPRISE   cdx6500
		VARIABLES    { cdx6500SNMPLastTrap }
		DESCRIPTION
		     "ROUT-Clear-Req: %s on %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16016

	rout16017-rout-clear-call-accept   TRAP-TYPE
		ENTERPRISE   cdx6500
		VARIABLES    { cdx6500SNMPLastTrap }
		DESCRIPTION
		     "ROUT-Clear-Call-Accept: %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16017

	rout16018-routclearcr   TRAP-TYPE
		ENTERPRISE   cdx6500
		VARIABLES    { cdx6500SNMPLastTrap }
		DESCRIPTION
		     "ROUT-Clear-CR: %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16018

	rout16019-rout-main   TRAP-TYPE
		ENTERPRISE   cdx6500
		VARIABLES    { cdx6500SNMPLastTrap }
		DESCRIPTION
		     "ROUT MAIN: Command: %d from %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16019

	rout16020-rout-socksel   TRAP-TYPE
		ENTERPRISE   cdx6500
		VARIABLES    { cdx6500SNMPLastTrap }
		DESCRIPTION
		     "%s RETURNED SAME SOCKET TO %s FOR CALL TO %s FROM %s. CALL CLEARED."
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16020

	rout16021-call-routi   TRAP-TYPE
		ENTERPRISE   cdx6500
		VARIABLES    { cdx6500SNMPLastTrap }
		DESCRIPTION
		     "%s CALL ROUTING ERROR: %s"
		     --#TYPE
		     --#SUMMARY "Trap #$G, specific: $S, arg(1) : $1"
		     --#ARGUMENTS {}
		     --#SEVERITY  CRITICAL
		     --#TIMEINDEX
		     --#HELP
		     --#HELPTAG
		     --#STATE
		::= 16021

	rout16022-routmain-p   TRAP-TYPE
		ENTERPRISE   cdx6500
		VARIABLES    { cdx6500SNMPLastTrap }
		DESCRIPTION
		     "rout-main: Packet Semaphore Locked %s: Event: %s, Pck Addr: 0x%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 16022

	rout16023-packet-poi   TRAP-TYPE
		ENTERPRISE   cdx6500
		VARIABLES    { cdx6500SNMPLastTrap }
		DESCRIPTION
		     "Packet pointer is NULL.  Can not process the call request"
		     --#TYPE
		     --#SUMMARY "Trap #$G, specific: $S, arg(1) : $1"
		     --#ARGUMENTS {}
		     --#SEVERITY  MINOR
		     --#TIMEINDEX
		     --#HELP
		     --#HELPTAG
		     --#STATE
		::= 16023

        port-util-exceeded  TRAP-TYPE
                ENTERPRISE   cdx6500
                VARIABLES    { cdx6500SNMPLastTrap }
                DESCRIPTION
                             " %02d - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 17000

        port-err-count-exceeded  TRAP-TYPE
                ENTERPRISE   cdx6500
                VARIABLES    { cdx6500SNMPLastTrap }
                DESCRIPTION
                             " %02d - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 17001

        cpu-util-exceeded  TRAP-TYPE
                ENTERPRISE   cdx6500
                VARIABLES    { cdx6500SNMPLastTrap }
                DESCRIPTION
                             " CPU UTILIZATION > THRESHOLD ON CARD %d"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 17002

        node-reset  TRAP-TYPE
                ENTERPRISE   cdx6500
                VARIABLES    { cdx6500SNMPLastTrap }
                DESCRIPTION
                             "NODE RESET DUE TO POWER-UP OR RESET SWITCH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19000

        watchdog-timeout-node-reset  TRAP-TYPE
                ENTERPRISE   cdx6500
                VARIABLES    { cdx6500SNMPLastTrap }
                DESCRIPTION
                             "NODE RESET DUE TO WATCHDOG TIMER TIMEOUT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19001

        node-boot  TRAP-TYPE
                ENTERPRISE   cdx6500
                VARIABLES    { cdx6500SNMPLastTrap }
                DESCRIPTION
                             "NODE BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19002

        crash-node-reset  TRAP-TYPE
                ENTERPRISE   cdx6500
                VARIABLES    { cdx6500SNMPLastTrap }
                DESCRIPTION
                             "NODE RESET DUE TO CRASH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19003

        debug-node-reset  TRAP-TYPE
                ENTERPRISE   cdx6500
                VARIABLES    { cdx6500SNMPLastTrap }
                DESCRIPTION
                             "NODE RESET DUE TO DEBUGGER COMMAND"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19004

        node-coldstart  TRAP-TYPE
                ENTERPRISE   cdx6500
                VARIABLES    { cdx6500SNMPLastTrap }
                DESCRIPTION
                             "NODE COLDSTARTED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19005

        node-warmstart  TRAP-TYPE
                ENTERPRISE   cdx6500
                VARIABLES    { cdx6500SNMPLastTrap }
                DESCRIPTION
                             "NODE WARMSTARTED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19006

        mboard-diag-fail  TRAP-TYPE
                ENTERPRISE   cdx6500
                VARIABLES    { cdx6500SNMPLastTrap }
                DESCRIPTION
                             "DIAGNOSTIC FAILURE ON BOARD 0, %s SECTION"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19007

        board-diag-fail  TRAP-TYPE
                ENTERPRISE   cdx6500
                VARIABLES    { cdx6500SNMPLastTrap }
                DESCRIPTION
                             "DIAGNOSTIC FAILURE ON BOARD %d"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19008

        port-diag-fail  TRAP-TYPE
                ENTERPRISE   cdx6500
                VARIABLES    { cdx6500SNMPLastTrap }
                DESCRIPTION
                             "DIAGNOSTIC FAILURE ON BOARD %d, PORT %02d"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19009

        missing-dim  TRAP-TYPE
                ENTERPRISE   cdx6500
                VARIABLES    { cdx6500SNMPLastTrap }
                DESCRIPTION
                             "MISSING DIM ON BOARD %d, PORT %02d"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19010

        flash-simm-diag-fail  TRAP-TYPE
                ENTERPRISE   cdx6500
                VARIABLES    { cdx6500SNMPLastTrap }
                DESCRIPTION
                             "DIAGNOSTIC FAILURE ON FLASH SIMM %d"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19011

        insufficient-ram  TRAP-TYPE
                ENTERPRISE   cdx6500
                VARIABLES    { cdx6500SNMPLastTrap }
                DESCRIPTION
                             "INSUFFICIENT RAM FOR CONFIGURATION"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19012

        port-boot-fail  TRAP-TYPE
                ENTERPRISE   cdx6500
                VARIABLES    { cdx6500SNMPLastTrap }
                DESCRIPTION
                             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19013

        local-dram-exhausted  TRAP-TYPE
                ENTERPRISE   cdx6500
                VARIABLES    { cdx6500SNMPLastTrap }
                DESCRIPTION
                             "LOCAL DRAM EXHAUSTED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19014

        bad-cmem-battery  TRAP-TYPE
                ENTERPRISE   cdx6500
                VARIABLES    { cdx6500SNMPLastTrap }
                DESCRIPTION
                             "CMEM BATTERY BAD"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19015

        unexpected-interrupt  TRAP-TYPE
                ENTERPRISE   cdx6500
                VARIABLES    { cdx6500SNMPLastTrap }
                DESCRIPTION
                             "UNEXPECTED INTERRUPT, SR/VECTNUM $%6.6x"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 19016

        code-port-insuffficient-dynamic  TRAP-TYPE
		ENTERPRISE   cdx6500
		VARIABLES    { cdx6500SNMPLastTrap }
		DESCRIPTION
		     "PORT-%02d - INSUFFFICIENT DYNAMIC MEMORY, PORT DOWN GRADED TO NULL PORT"
		     --#TYPE
		     --#SUMMARY "Trap #$G, specific: $S, arg(1) : $1"
		     --#ARGUMENTS {}
		     --#SEVERITY  CRITICAL
		     --#TIMEINDEX
		     --#HELP
		     --#HELPTAG
		     --#STATE
		::= 19017

        code-node-reset-with-default-pas  TRAP-TYPE
		ENTERPRISE   cdx6500
		VARIABLES    { cdx6500SNMPLastTrap }
		DESCRIPTION
		     "NODE RESET WITH DEFAULT PASSWORD"
		     --#TYPE
		     --#SUMMARY "Trap #$G, specific: $S, arg(1) : $1"
		     --#ARGUMENTS {}
		     --#SEVERITY  CRITICAL
		     --#TIMEINDEX
		     --#HELP
		     --#HELPTAG
		     --#STATE
		::= 19018

        cougar-reset-with-default-pas  TRAP-TYPE
		ENTERPRISE   cdx6500
		VARIABLES    { cdx6500SNMPLastTrap }
		DESCRIPTION
		     "NODE RESET WITH DEFAULT PASSWORD"
		     --#TYPE
		     --#SUMMARY "Trap #$G, specific: $S, arg(1) : $1"
		     --#ARGUMENTS {}
		     --#SEVERITY  CRITICAL
		     --#TIMEINDEX
		     --#HELP
		     --#HELPTAG
		     --#STATE
		::= 19019

	code19020-ctp-pad-setting-overridden   TRAP-TYPE
		ENTERPRISE   cdx6500
		VARIABLES    { cdx6500SNMPLastTrap }
		DESCRIPTION
		     "CTP PAD SETTING OVERRIDDEN DUE TO MISSING SOFTWARE"
		     --#TYPE
		     --#SUMMARY "Trap #$G, specific: $S, arg(1) : $1"
		     --#ARGUMENTS {}
		     --#SEVERITY  CRITICAL
		     --#TIMEINDEX
		     --#HELP
		     --#HELPTAG
		     --#STATE
		::= 19020

        node-boot-for-mnem  TRAP-TYPE
                ENTERPRISE   cdx6500
                VARIABLES    { cdx6500SNMPLastTrap }
                DESCRIPTION
                             "Node boot required. The number of MNEM table entries in CMEM does not match the active number."
                     --#TYPE
                     --#SUMMARY "Trap #$G, specific: $S, arg(1): $1"
                     --#ARGUMENTS {}
                     --#SEVERITY  INFORMATIONAL
                     --#TIMEINDEX
                     --#HELP
                     --#HELPTAG
                     --#STATE
                ::= 21000

        software-failure  TRAP-TYPE
                ENTERPRISE   cdx6500
                VARIABLES    { cdx6500SNMPLastTrap }
                DESCRIPTION
                             "SOFTWARE FAILURE LOGGED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 25000

        billing-records-lost  TRAP-TYPE
                ENTERPRISE   cdx6500
                VARIABLES    { cdx6500SNMPLastTrap }
                DESCRIPTION
                             " BILLING RECORD EXCEEDS LIMIT - BILLING RECORD LOST"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 32000

        dl-attempting-download  TRAP-TYPE
                ENTERPRISE   cdx6500
                VARIABLES    { cdx6500SNMPLastTrap }
                DESCRIPTION
                             "DLSV Loader: ATTEMPTING TO DOWNLOAD"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 33000

        dl-recvd-invalid-rec  TRAP-TYPE
                ENTERPRISE   cdx6500
                VARIABLES    { cdx6500SNMPLastTrap }
                DESCRIPTION
                             "DLSV Loader: RECEIVED AN INVALID RECORD TYPE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 33001

        dl-recvd-no-rec  TRAP-TYPE
                ENTERPRISE   cdx6500
                VARIABLES    { cdx6500SNMPLastTrap }
                DESCRIPTION
                             "DLSV Loader: RECEIVED NO RECORDS"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 33002

        dl-recvd-invalid-len-rec  TRAP-TYPE
                ENTERPRISE   cdx6500
                VARIABLES    { cdx6500SNMPLastTrap }
                DESCRIPTION
                             "DLSV Loader: RECEIVED RECORD WITH BAD LENGTH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 33003

        dl-recvd-invalid-chksum-rec  TRAP-TYPE
                ENTERPRISE   cdx6500
                VARIABLES    { cdx6500SNMPLastTrap }
                DESCRIPTION
                             "DLSV Loader: RECEIVED RECORD WITH BAD CHECKSUM"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 33004

        dl-download-complete  TRAP-TYPE
		ENTERPRISE   cdx6500
		VARIABLES    { cdx6500SNMPLastTrap }
		DESCRIPTION
			     "DLSV Loader: DOWNLOAD COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33005

        ds-conn-timeout  TRAP-TYPE
		ENTERPRISE   cdx6500
		VARIABLES    { cdx6500SNMPLastTrap }
		DESCRIPTION
			     "DLSV Server (%d): CONNECTION IDLE TOO LONG"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33006

        dl-invl-address  TRAP-TYPE
		ENTERPRISE   cdx6500
		VARIABLES    { cdx6500SNMPLastTrap }
		DESCRIPTION
			     "DLSV Server (%d): REQUEST WITH INVALID ADDRESS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33007

        ds-download-complete  TRAP-TYPE
		ENTERPRISE   cdx6500
		VARIABLES    { cdx6500SNMPLastTrap }
		DESCRIPTION
			     "DLSV Server (%d): DOWNLOAD COMPLETE TO %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33008

        ds-loading  TRAP-TYPE
		ENTERPRISE   cdx6500
		VARIABLES    { cdx6500SNMPLastTrap }
		DESCRIPTION
			     "DLSV Server (%d): LOADING TO ADDRESS %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33009

        ds-incompat-cpu  TRAP-TYPE
		ENTERPRISE   cdx6500
		VARIABLES    { cdx6500SNMPLastTrap }
		DESCRIPTION
			     "DLSV Server (%d): INCOMPATIBLE CPU TYPE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33010

        dl-invl-image-addr  TRAP-TYPE
		ENTERPRISE   cdx6500
		VARIABLES    { cdx6500SNMPLastTrap }
		DESCRIPTION
			     "DLSV Loader: INCOMPATIBLE IMAGE LOAD ADDRESS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33011

        dl-flash-erase-fail  TRAP-TYPE
		ENTERPRISE   cdx6500
		VARIABLES    { cdx6500SNMPLastTrap }
		DESCRIPTION
			     "DLSV Loader: CANNOT ERASE FLASH, %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33012

        dl-no-conf-server  TRAP-TYPE
		ENTERPRISE   cdx6500
		VARIABLES    { cdx6500SNMPLastTrap }
		DESCRIPTION
			     "DLSV Loader: NO CONFIGURED SERVER"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33013

        dl-flash-write-fail  TRAP-TYPE
		ENTERPRISE   cdx6500
		VARIABLES    { cdx6500SNMPLastTrap }
		DESCRIPTION
			     "DLSV Loader: CANNOT WRITE FLASH, %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33014

        ds-flash-read-fail  TRAP-TYPE
		ENTERPRISE   cdx6500
		VARIABLES    { cdx6500SNMPLastTrap }
		DESCRIPTION
			     "DLSV Server: CANNOT READ FLASH, %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33015

        dl-software-copy-fail  TRAP-TYPE
		ENTERPRISE   cdx6500
		VARIABLES    { cdx6500SNMPLastTrap }
		DESCRIPTION
			     "DLSV Loader: FAILED TO COPY SOFTWARE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33016

        ds-software-send-fail  TRAP-TYPE
		ENTERPRISE   cdx6500
		VARIABLES    { cdx6500SNMPLastTrap }
		DESCRIPTION
			     "DLSV Server: FAILED TO SEND SOFTWARE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33017

        dl-download-in-progress-err  TRAP-TYPE
		ENTERPRISE   cdx6500
		VARIABLES    { cdx6500SNMPLastTrap }
		DESCRIPTION
			     "DLSV Loader: SW DOWNLOAD ALREADY IN PROGRESS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33018

        ds-flash-bank-unavail  TRAP-TYPE
		ENTERPRISE   cdx6500
		VARIABLES    { cdx6500SNMPLastTrap }
		DESCRIPTION
			     "DLSV Server: F2F FLASH BANK UNAVAILABLE, %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33019

        ds-download-in-progress-err  TRAP-TYPE
		ENTERPRISE   cdx6500
		VARIABLES    { cdx6500SNMPLastTrap }
		DESCRIPTION
			     "DLSV Server: SW DOWNLOAD ALREADY IN PROGRESS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33020

        dl-copying-to-flash  TRAP-TYPE
		ENTERPRISE   cdx6500
		VARIABLES    { cdx6500SNMPLastTrap }
		DESCRIPTION
			     "DLSV Loader: COPYING SW TO FLASH, %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33021

        ds-no-mnemonic  TRAP-TYPE
		ENTERPRISE   cdx6500
		VARIABLES    { cdx6500SNMPLastTrap }
		DESCRIPTION
			     "DLSV Loader: MNEMONIC NOT CONFIGURED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 33022

        dlsv-flash-has-been-corrupted  TRAP-TYPE
		ENTERPRISE   cdx6500
		VARIABLES    { cdx6500SNMPLastTrap }
		DESCRIPTION
		     "DLSV Loader: FLASH HAS BEEN CORRUPTED"
		     --#TYPE
		     --#SUMMARY "Trap #$G, specific: $S, arg(1) : $1"
		     --#ARGUMENTS {}
		     --#SEVERITY  CRITICAL
		     --#TIMEINDEX
		     --#HELP
		     --#HELPTAG
		     --#STATE
		::= 33023

        nullPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 39000

        nullPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 39001

        nullPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 39002

        nullPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 39003

        async-iodrivers-port-error-thres  TRAP-TYPE
		ENTERPRISE   cdx6500
		VARIABLES    { cdx6500SNMPLastTrap }
		DESCRIPTION
		     "%s - PORT ERROR COUNT > THRESHOLD"
		     --#TYPE
		     --#SUMMARY "Trap #$G, specific: $S, arg(1) : $1"
		     --#ARGUMENTS {}
		     --#SEVERITY  MAJOR
		     --#TIMEINDEX
		     --#HELP
		     --#HELPTAG
		     --#STATE
		::= 40000

        async-iodrivers-unsupported-speed  TRAP-TYPE
		ENTERPRISE   cdx6500
		VARIABLES    { cdx6500SNMPLastTrap }
		DESCRIPTION
		     "%s - UNSUPPORTED SPEED: OPERATING AT %d BITS PER SECOND"
		     --#TYPE
		     --#SUMMARY "Trap #$G, specific: $S, arg(1) : $1"
		     --#ARGUMENTS {}
		     --#SEVERITY  MAJOR
		     --#TIMEINDEX
		     --#HELP
		     --#HELPTAG
		     --#STATE
		::= 40001

        bop-iodrivers-port-error-count-thres  TRAP-TYPE
		ENTERPRISE   cdx6500
		VARIABLES    { cdx6500SNMPLastTrap }
		DESCRIPTION
		     "%s - PORT ERROR COUNT > THRESHOLD"
		     --#TYPE
		     --#SUMMARY "Trap #$G, specific: $S, arg(1) : $1"
		     --#ARGUMENTS {}
		     --#SEVERITY  MAJOR
		     --#TIMEINDEX
		     --#HELP
		     --#HELPTAG
		     --#STATE
		::= 41000

        bop-iodrivers-unsupported-speed-oper  TRAP-TYPE
		ENTERPRISE   cdx6500
		VARIABLES    { cdx6500SNMPLastTrap }
		DESCRIPTION
		     "%s - UNSUPPORTED SPEED: OPERATING AT %d BITS PER SECOND"
		     --#TYPE
		     --#SUMMARY "Trap #$G, specific: $S, arg(1) : $1"
		     --#ARGUMENTS {}
		     --#SEVERITY  MAJOR
		     --#TIMEINDEX
		     --#HELP
		     --#HELPTAG
		     --#STATE
		::= 41001

        lapb-link-down  TRAP-TYPE
		ENTERPRISE   cdx6500
		VARIABLES    { cdx6500SNMPLastTrap }
		DESCRIPTION
		             "%s - LINK DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42000

        lapb-disc-received  TRAP-TYPE
		ENTERPRISE   cdx6500
		VARIABLES    { cdx6500SNMPLastTrap }
		DESCRIPTION
		             "%s - DISC RECEIVED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42001

        lapb-bad-frame-type  TRAP-TYPE
		ENTERPRISE   cdx6500
		VARIABLES    { cdx6500SNMPLastTrap }
		DESCRIPTION
		             " %s - BAD FRAME TYPE (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42002

        lapb-address-error  TRAP-TYPE
		ENTERPRISE   cdx6500
		VARIABLES    { cdx6500SNMPLastTrap }
		DESCRIPTION
		             " %s - ADDRESS ERROR (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42003

        lapb-bad-frame-len  TRAP-TYPE
		ENTERPRISE   cdx6500
		VARIABLES    { cdx6500SNMPLastTrap }
		DESCRIPTION
		             " %s - BAD FRAME LENGTH (%d)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42004

        lapb-extend-seq-frmr  TRAP-TYPE
		ENTERPRISE   cdx6500
		VARIABLES    { cdx6500SNMPLastTrap }
		DESCRIPTION
		             " %s - FRMR (%02X%02X/%02X%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42005

        lapb-norm-seq-frmr  TRAP-TYPE
		ENTERPRISE   cdx6500
		VARIABLES    { cdx6500SNMPLastTrap }
		DESCRIPTION
		             " %s - FRMR (%02X/%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42006

        lapb-link-up  TRAP-TYPE
		ENTERPRISE   cdx6500
		VARIABLES    { cdx6500SNMPLastTrap }
		DESCRIPTION
		             "%s - LINK UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42007

        lapb-link-blocked  TRAP-TYPE
		ENTERPRISE   cdx6500
		VARIABLES    { cdx6500SNMPLastTrap }
		DESCRIPTION
		             " %s - LINK BLOCKED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42008

        lapb-bad-n-r  TRAP-TYPE
		ENTERPRISE   cdx6500
		VARIABLES    { cdx6500SNMPLastTrap }
		DESCRIPTION
		             " %s - BAD N(R) (%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42009

        lapb-backup-activated  TRAP-TYPE
		ENTERPRISE   cdx6500
		VARIABLES    { cdx6500SNMPLastTrap }
		DESCRIPTION
		             "%s - BACKUP LINK ACTIVATED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42010

        lapb-extend-bad-frame-type  TRAP-TYPE
		ENTERPRISE   cdx6500
		VARIABLES    { cdx6500SNMPLastTrap }
		DESCRIPTION
		             " %s - BAD FRAME TYPE (%02X%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42011

        lapb-access-link-down  TRAP-TYPE
		ENTERPRISE   cdx6500
		VARIABLES    { cdx6500SNMPLastTrap }
		DESCRIPTION
		             " %s - ACCESS PORT DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42012

        lapb-access-link-up  TRAP-TYPE
		ENTERPRISE   cdx6500
		VARIABLES    { cdx6500SNMPLastTrap }
		DESCRIPTION
		             " %s - ACCESS PORT UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42013

        lapb-ovsize-frame  TRAP-TYPE
		ENTERPRISE   cdx6500
		VARIABLES    { cdx6500SNMPLastTrap }
		DESCRIPTION
		             " %s - OVERSIZE FRAME (%d) FROM REMOTE LINK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 42014

        hdlc-link-down  TRAP-TYPE
		ENTERPRISE   cdx6500
		VARIABLES    { cdx6500SNMPLastTrap }
		DESCRIPTION
		             "%s - LINK DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43000

        hdlc-disc-received  TRAP-TYPE
		ENTERPRISE   cdx6500
		VARIABLES    { cdx6500SNMPLastTrap }
		DESCRIPTION
		             "%s - DISC RECEIVED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43001

        hdlc-bad-frame-type  TRAP-TYPE
		ENTERPRISE   cdx6500
		VARIABLES    { cdx6500SNMPLastTrap }
		DESCRIPTION
		             " %s - BAD FRAME TYPE (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43002

        hdlc-address-error  TRAP-TYPE
		ENTERPRISE   cdx6500
		VARIABLES    { cdx6500SNMPLastTrap }
		DESCRIPTION
		             " %s - ADDRESS ERROR (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43003

        hdlc-bad-frame-len  TRAP-TYPE
		ENTERPRISE   cdx6500
		VARIABLES    { cdx6500SNMPLastTrap }
		DESCRIPTION
		             " %s - BAD FRAME LENGTH (%d)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43004

        hdlc-extend-seq-frmr  TRAP-TYPE
		ENTERPRISE   cdx6500
		VARIABLES    { cdx6500SNMPLastTrap }
		DESCRIPTION
		             " %s - FRMR (%02X%02X/%02X%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43005

        hdlc-norm-seq-frmr  TRAP-TYPE
		ENTERPRISE   cdx6500
		VARIABLES    { cdx6500SNMPLastTrap }
		DESCRIPTION
		             " %s - FRMR (%02X/%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43006

        hdlc-link-up  TRAP-TYPE
		ENTERPRISE   cdx6500
		VARIABLES    { cdx6500SNMPLastTrap }
		DESCRIPTION
		             "%s - LINK UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43007

        hdlc-line-blocked  TRAP-TYPE
		ENTERPRISE   cdx6500
		VARIABLES    { cdx6500SNMPLastTrap }
		DESCRIPTION
		             " %s - LINK BLOCKED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43008

        hdlc-bad-n-r  TRAP-TYPE
		ENTERPRISE   cdx6500
		VARIABLES    { cdx6500SNMPLastTrap }
		DESCRIPTION
		             " %s - BAD N(R) (%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43009

        hdlc-backup-activated  TRAP-TYPE
		ENTERPRISE   cdx6500
		VARIABLES    { cdx6500SNMPLastTrap }
		DESCRIPTION
		             "%s - BACKUP LINK ACTIVATED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43010

        hdlc-extend-bad-frame-type  TRAP-TYPE
		ENTERPRISE   cdx6500
		VARIABLES    { cdx6500SNMPLastTrap }
		DESCRIPTION
		             " %s - BAD FRAME TYPE (%02X%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43011

        hdlc-access-link-down  TRAP-TYPE
		ENTERPRISE   cdx6500
		VARIABLES    { cdx6500SNMPLastTrap }
		DESCRIPTION
		             " %s - ACCESS PORT DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43012

        hdlc-access-link-up  TRAP-TYPE
		ENTERPRISE   cdx6500
		VARIABLES    { cdx6500SNMPLastTrap }
		DESCRIPTION
		             " %s - ACCESS PORT UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43013

        hdlc-ovsize-frame  TRAP-TYPE
		ENTERPRISE   cdx6500
		VARIABLES    { cdx6500SNMPLastTrap }
		DESCRIPTION
		             " %s - OVERSIZE FRAME (%d) FROM REMOTE LINK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 43014

        apad-input-buf-overrun  TRAP-TYPE
		ENTERPRISE   cdx6500
		VARIABLES    { cdx6500SNMPLastTrap }
		DESCRIPTION
		             " %s - INPUT BUFFER OVERRUN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 44000

        apad-hpEnqack-timeout  TRAP-TYPE
		ENTERPRISE   cdx6500
		VARIABLES    { cdx6500SNMPLastTrap }
		DESCRIPTION
		             " %s - HP ENQ/ACK TIMEOUT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 44002

        apad-bcst-overrun  TRAP-TYPE
		ENTERPRISE   cdx6500
		VARIABLES    { cdx6500SNMPLastTrap }
		DESCRIPTION
		             " %s - BROADCAST OVERRUN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 44003

        apad-unauth-polled-async  TRAP-TYPE
		ENTERPRISE   cdx6500
		VARIABLES    { cdx6500SNMPLastTrap }
		DESCRIPTION
		             "%s - NOT AUTHORIZED TO USE POLLED ASYNC OPTION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 44004

        apad-x28-overrun  TRAP-TYPE
		ENTERPRISE   cdx6500
		VARIABLES    { cdx6500SNMPLastTrap }
		DESCRIPTION
		             " %s - X.28 SERVICE MESSAGE LOST"
                     --#TYPE
                     --#SUMMARY "Trap #$G, specific: $S, arg(1): $1"
                     --#ARGUMENTS {}
                     --#SEVERITY  INFORMATIONAL
                     --#TIMEINDEX
                     --#HELP
                     --#HELPTAG
                     --#STATE
		::= 44005

        apad-outputbuf-overrun  TRAP-TYPE
		ENTERPRISE   cdx6500
		VARIABLES    { cdx6500SNMPLastTrap }
		DESCRIPTION
		             " %s - OUTPUT BUFFER OVERRUN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 44006

        apad-stpa-frame-dropped  TRAP-TYPE
		ENTERPRISE   cdx6500
		VARIABLES    { cdx6500SNMPLastTrap }
		DESCRIPTION
		             " %s - TERM %d STPA FRAME DROPPED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 44007

        pad-violations-port-disconnected  TRAP-TYPE
		ENTERPRISE   cdx6500
		VARIABLES    { cdx6500SNMPLastTrap }
		DESCRIPTION
		     "%s - %d VIOLATIONS, PORT DISCONNECTED"
		     --#TYPE
		     --#SUMMARY "Trap #$G, specific: $S, arg(1) : $1"
		     --#ARGUMENTS {}
		     --#SEVERITY  MAJOR
		     --#TIMEINDEX
		     --#HELP
		     --#HELPTAG
		     --#STATE
		::= 44008

        pad-violations-port-locked  TRAP-TYPE
		ENTERPRISE   cdx6500
		VARIABLES    { cdx6500SNMPLastTrap }
		DESCRIPTION
		     "%s - %d VIOLATIONS, PORT LOCKED"
		     --#TYPE
		     --#SUMMARY "Trap #$G, specific: $S, arg(1) : $1"
		     --#ARGUMENTS {}
		     --#SEVERITY  MAJOR
		     --#TIMEINDEX
		     --#HELP
		     --#HELPTAG
		     --#STATE
		::= 44009

        pad-violations-port-degraded  TRAP-TYPE
		ENTERPRISE   cdx6500
		VARIABLES    { cdx6500SNMPLastTrap }
		DESCRIPTION
		     "%s - %d VIOLATIONS, PORT DEGRADED"
		     --#TYPE
		     --#SUMMARY "Trap #$G, specific: $S, arg(1) : $1"
		     --#ARGUMENTS {}
		     --#SEVERITY  MAJOR
		     --#TIMEINDEX
		     --#HELP
		     --#HELPTAG
		     --#STATE
		::= 44010

        pad-violations-no-action  TRAP-TYPE
		ENTERPRISE   cdx6500
		VARIABLES    { cdx6500SNMPLastTrap }
		DESCRIPTION
		     "%s - %d VIOLATIONS, NO ACTION"
		     --#TYPE
		     --#SUMMARY "Trap #$G, specific: $S, arg(1) : $1"
		     --#ARGUMENTS {}
		     --#SEVERITY  MAJOR
		     --#TIMEINDEX
		     --#HELP
		     --#HELPTAG
		     --#STATE
		::= 44011

        x25L3-pkt-lvl-restart  TRAP-TYPE
		ENTERPRISE   cdx6500
		VARIABLES    { cdx6500SNMPLastTrap }
		DESCRIPTION
		             " %s - PACKET LEVEL RESTART"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46000

        x25L3-no-response  TRAP-TYPE
		ENTERPRISE   cdx6500
		VARIABLES    { cdx6500SNMPLastTrap }
		DESCRIPTION
		             "%s - NO RESPONSE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46001

        x25L3-channel-reset-recv  TRAP-TYPE
		ENTERPRISE   cdx6500
		VARIABLES    { cdx6500SNMPLastTrap }
		DESCRIPTION
		             " %s - CHANNEL RESET RECEIVED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46002

        x25L3-rept-bad-p-k  TRAP-TYPE
		ENTERPRISE   cdx6500
		VARIABLES    { cdx6500SNMPLastTrap }
		DESCRIPTION
		             " %s - BAD P(K)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46003

        x25L3-bad-p-r  TRAP-TYPE
		ENTERPRISE   cdx6500
		VARIABLES    { cdx6500SNMPLastTrap }
		DESCRIPTION
		             " %s - BAD P(R)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46004

        x25L3-bad-p-s  TRAP-TYPE
		ENTERPRISE   cdx6500
		VARIABLES    { cdx6500SNMPLastTrap }
		DESCRIPTION
		             " %s - BAD P(S)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46005

        x25L3-pvc-not-connected  TRAP-TYPE
		ENTERPRISE   cdx6500
		VARIABLES    { cdx6500SNMPLastTrap }
		DESCRIPTION
		             " %s - PVC NOT CONNECTED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46006

        x25L3-unassigned-lcn  TRAP-TYPE
		ENTERPRISE   cdx6500
		VARIABLES    { cdx6500SNMPLastTrap }
		DESCRIPTION
		             " %s - UNASSIGNED LCN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46007

        x25L3-bad-pkt-len  TRAP-TYPE
		ENTERPRISE   cdx6500
		VARIABLES    { cdx6500SNMPLastTrap }
		DESCRIPTION
		             " %s - BAD PACKET LENGTH (%d)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46008

        x25L3-bad-pkt-type  TRAP-TYPE
		ENTERPRISE   cdx6500
		VARIABLES    { cdx6500SNMPLastTrap }
		DESCRIPTION
		             " %s - BAD PACKET TYPE (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46009

        x25L3-bcst-overrun  TRAP-TYPE
		ENTERPRISE   cdx6500
		VARIABLES    { cdx6500SNMPLastTrap }
		DESCRIPTION
		             " %s - BROADCAST OVERRUN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46010

        x25L3-input-overrun  TRAP-TYPE
		ENTERPRISE   cdx6500
		VARIABLES    { cdx6500SNMPLastTrap }
		DESCRIPTION
		             " %s - INPUT BUFFER OVERRUN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46011

        x25L3-tp-lvl-blocked  TRAP-TYPE
		ENTERPRISE   cdx6500
		VARIABLES    { cdx6500SNMPLastTrap }
		DESCRIPTION
		             " %s - %s PRIORITY QUEUE BLOCKED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46012

        x25L3-tp-all-lvls-blocked  TRAP-TYPE
		ENTERPRISE   cdx6500
		VARIABLES    { cdx6500SNMPLastTrap }
		DESCRIPTION
		             " %s - ALL PRIORITY QUEUES UNBLOCKED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46013

        x25L3-insuff-memory  TRAP-TYPE
		ENTERPRISE   cdx6500
		VARIABLES    { cdx6500SNMPLastTrap }
		DESCRIPTION
		             "IN-SUFFICIENT MEMORY FOR X25 CALL TRANSLATION TABLES"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46014

        x25L3-output-overrun  TRAP-TYPE
		ENTERPRISE   cdx6500
		VARIABLES    { cdx6500SNMPLastTrap }
		DESCRIPTION
		             " %s - OUTPUT BUFFER OVERRUN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 46015

	x2546016-bad-ccbptr   TRAP-TYPE
		ENTERPRISE   cdx6500
		VARIABLES    { cdx6500SNMPLastTrap }
		DESCRIPTION
		     "%s - BAD CCBPTR IN  %s, ch0ccbptr=%x, ccbptr=%x, ccb-index=%d, numchan=%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 46016

        padPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 49000

        padPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 49001

        padPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 49002

        padPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 49003

        padPort-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 49004

        padPort-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 49005

        padPort-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 49006

        x25Port-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 51000

        x25Port-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 51001

        x25Port-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 51002

        x25Port-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 51003

        x25Port-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 51004

        x25Port-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 51005

        x25Port-pkt-size-warning  TRAP-TYPE
		ENTERPRISE   cdx6500
		VARIABLES    { cdx6500SNMPLastTrap }
		DESCRIPTION
		             " %s - CONFIGURED PKT SIZE > MAX ALLOWED ISDN D-CHANNEL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 51006

        bsc2780Port-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 56000

        bsc2780Port-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 56001

        bsc2780Port-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 56002

        bsc2780Port-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 56003

        bsc2780Port-enable-fail  TRAP-TYPE
		ENTERPRISE   cdx6500
		VARIABLES    { cdx6500SNMPLastTrap }
		DESCRIPTION
		             "%s - PORT ENABLE FAILED - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 56004

        bsc2780Port-ses-rej  TRAP-TYPE
		ENTERPRISE   cdx6500
		VARIABLES    { cdx6500SNMPLastTrap }
		DESCRIPTION
		             "%s - NO RESPONSE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 56005

        bsc2780Port-line-error  TRAP-TYPE
		ENTERPRISE   cdx6500
		VARIABLES    { cdx6500SNMPLastTrap }
		DESCRIPTION
		             "%s - DISCONNECTED DUE TO LINE ERRORS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 56006

        bsc2780Port-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 56007

        bsc2780Port-warn-status  TRAP-TYPE
		ENTERPRISE   cdx6500
		VARIABLES    { cdx6500SNMPLastTrap }
		DESCRIPTION
		             "%s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 56008

        bsc3270Port-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57000

        bsc3270Port-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57001

        bsc3270Port-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57002

        bsc3270Port-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57003

        bsc3270Port-enable-fail  TRAP-TYPE
		ENTERPRISE   cdx6500
		VARIABLES    { cdx6500SNMPLastTrap }
		DESCRIPTION
		             "%s - PORT ENABLE FAILED - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57004

        bsc3270Port-inbound-err  TRAP-TYPE
		ENTERPRISE   cdx6500
		VARIABLES    { cdx6500SNMPLastTrap }
		DESCRIPTION
		             "%s(%02X%02X) NON-RECOVERABLE INBOUND ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57005

        bsc3270Port-outbound-err  TRAP-TYPE
		ENTERPRISE   cdx6500
		VARIABLES    { cdx6500SNMPLastTrap }
		DESCRIPTION
		             "%s(%02X%02X) NON-RECOVERABLE OUTBOUND ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57006

        bsc3270Port-line-down  TRAP-TYPE
		ENTERPRISE   cdx6500
		VARIABLES    { cdx6500SNMPLastTrap }
		DESCRIPTION
		             "%s - LINE DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57007

        bsc3270Port-line-up  TRAP-TYPE
		ENTERPRISE   cdx6500
		VARIABLES    { cdx6500SNMPLastTrap }
		DESCRIPTION
		             "%s - LINE OPERATIONAL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57008

        bsc3270Port-dev-down  TRAP-TYPE
		ENTERPRISE   cdx6500
		VARIABLES    { cdx6500SNMPLastTrap }
		DESCRIPTION
		             "%s - DEVICE DOWN - %02X %02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57009

        bsc3270Port-dev-up  TRAP-TYPE
		ENTERPRISE   cdx6500
		VARIABLES    { cdx6500SNMPLastTrap }
		DESCRIPTION
		             "%s - DEVICE OPERATIONAL - %02X %02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57010

        bsc3270Port-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 57011

        bsc3270-device-enabled  TRAP-TYPE
		ENTERPRISE   cdx6500
		VARIABLES    { cdx6500SNMPLastTrap }
		DESCRIPTION
		     "%s - DEVICE ENABLED - %02X %02X"
		     --#TYPE
		     --#SUMMARY "Trap #$G, specific: $S, arg(1) : $1"
		     --#ARGUMENTS {}
		     --#SEVERITY  CRITICAL
		     --#TIMEINDEX
		     --#HELP
		     --#HELPTAG
		     --#STATE
		::= 57012

        bsc3270-device-disabled  TRAP-TYPE
		ENTERPRISE   cdx6500
		VARIABLES    { cdx6500SNMPLastTrap }
		DESCRIPTION
		     "%s - DEVICE DISABLED - %02X %02X"
		     --#TYPE
		     --#SUMMARY "Trap #$G, specific: $S, arg(1) : $1"
		     --#ARGUMENTS {}
		     --#SEVERITY  CRITICAL
		     --#TIMEINDEX
		     --#HELP
		     --#HELPTAG
		     --#STATE
		::= 57013

        bsc3270-device-enable-failure  TRAP-TYPE
		ENTERPRISE   cdx6500
		VARIABLES    { cdx6500SNMPLastTrap }
		DESCRIPTION
		     "%s - DEVICE ENABLE FAILURE - %02X %02X"
		     --#TYPE
		     --#SUMMARY "Trap #$G, specific: $S, arg(1) : $1"
		     --#ARGUMENTS {}
		     --#SEVERITY  CRITICAL
		     --#TIMEINDEX
		     --#HELP
		     --#HELPTAG
		     --#STATE
		::= 57014

        bsc3270-device-disable-failure  TRAP-TYPE
		ENTERPRISE   cdx6500
		VARIABLES    { cdx6500SNMPLastTrap }
		DESCRIPTION
		     "%s - DEVICE DISABLE FAILURE - %02X %02X"
		     --#TYPE
		     --#SUMMARY "Trap #$G, specific: $S, arg(1) : $1"
		     --#ARGUMENTS {}
		     --#SEVERITY  CRITICAL
		     --#TIMEINDEX
		     --#HELP
		     --#HELPTAG
		     --#STATE
		::= 57015

	bsc327057016-device   TRAP-TYPE
		ENTERPRISE   cdx6500
		VARIABLES    { cdx6500SNMPLastTrap }
		DESCRIPTION
		     "%s - DEVICE BOOT COMPLETE - %02X %02X"
		     --#TYPE
		     --#SUMMARY "Trap #$G, specific: $S, arg(1) : $1"
		     --#ARGUMENTS {}
		     --#SEVERITY  CRITICAL
		     --#TIMEINDEX
		     --#HELP
		     --#HELPTAG
		     --#STATE
		::= 57016

	bsc327057017-device   TRAP-TYPE
		ENTERPRISE   cdx6500
		VARIABLES    { cdx6500SNMPLastTrap }
		DESCRIPTION
		     "%s - DEVICE BOOT FAILURE"
		     --#TYPE
		     --#SUMMARY "Trap #$G, specific: $S, arg(1) : $1"
		     --#ARGUMENTS {}
		     --#SEVERITY  CRITICAL
		     --#TIMEINDEX
		     --#HELP
		     --#HELPTAG
		     --#STATE
		::= 57017

        dsp3270-possible-data-loss  TRAP-TYPE
		ENTERPRISE   cdx6500
		VARIABLES    { cdx6500SNMPLastTrap }
		DESCRIPTION
		             "%s - POSSIBLE DATA LOSS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 59000

        cop-iodrivers-port-error-thres  TRAP-TYPE
		ENTERPRISE   cdx6500
		VARIABLES    { cdx6500SNMPLastTrap }
		DESCRIPTION
		     "%s - PORT ERROR COUNT > THRESHOLD"
		     --#TYPE
		     --#SUMMARY "Trap #$G, specific: $S, arg(1) : $1"
		     --#ARGUMENTS {}
		     --#SEVERITY  MAJOR
		     --#TIMEINDEX
		     --#HELP
		     --#HELPTAG
		     --#STATE
		::= 61000

        disk-bytes-loaded-from-nso-disk  TRAP-TYPE
		ENTERPRISE   cdx6500
		VARIABLES    { cdx6500SNMPLastTrap }
		DESCRIPTION
		     "%d BYTES LOADED FROM NSO DISK"
		     --#TYPE
		     --#SUMMARY "Trap #$G, specific: $S, arg(1) : $1"
		     --#ARGUMENTS {}
		     --#SEVERITY  CRITICAL
		     --#TIMEINDEX
		     --#HELP
		     --#HELPTAG
		     --#STATE
		::= 65000

        disk-cannot-read-from-nso-slot  TRAP-TYPE
		ENTERPRISE   cdx6500
		VARIABLES    { cdx6500SNMPLastTrap }
		DESCRIPTION
		     "CANNOT READ FROM NSO DISK, SLOT %d"
		     --#TYPE
		     --#SUMMARY "Trap #$G, specific: $S, arg(1) : $1"
		     --#ARGUMENTS {}
		     --#SEVERITY  CRITICAL
		     --#TIMEINDEX
		     --#HELP
		     --#HELPTAG
		     --#STATE
		::= 65001

        mx25L2-stn-up  TRAP-TYPE
		ENTERPRISE   cdx6500
		VARIABLES    { cdx6500SNMPLastTrap }
		DESCRIPTION
		             "%s - STATION UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68001

        mx25L2-multiple-masters  TRAP-TYPE
		ENTERPRISE   cdx6500
		VARIABLES    { cdx6500SNMPLastTrap }
		DESCRIPTION
		             "%s - TWO MASTERS ON MULTIPOINT LINK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68002

        mx25L2-bad-frame-type  TRAP-TYPE
		ENTERPRISE   cdx6500
		VARIABLES    { cdx6500SNMPLastTrap }
		DESCRIPTION
		             " %s - BAD FRAME TYPE (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68003

        mx25L2-norm-seq-frmr  TRAP-TYPE
		ENTERPRISE   cdx6500
		VARIABLES    { cdx6500SNMPLastTrap }
		DESCRIPTION
		             " %s - FRMR (%02X/%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68004

        mx25L2-addr-error  TRAP-TYPE
		ENTERPRISE   cdx6500
		VARIABLES    { cdx6500SNMPLastTrap }
		DESCRIPTION
		             " %s - ADDRESS ERROR (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68005

        mx25L2-master-polled-early  TRAP-TYPE
		ENTERPRISE   cdx6500
		VARIABLES    { cdx6500SNMPLastTrap }
		DESCRIPTION
		             "%s - MASTER POLLED EARLY"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68006

        mx25L2-link-up  TRAP-TYPE
		ENTERPRISE   cdx6500
		VARIABLES    { cdx6500SNMPLastTrap }
		DESCRIPTION
		             "%s - LINK UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68007

        mx25L2-bad-n-r  TRAP-TYPE
		ENTERPRISE   cdx6500
		VARIABLES    { cdx6500SNMPLastTrap }
		DESCRIPTION
		             " %s - BAD N(R) (%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68008

        mx25L2-bad-frame-len  TRAP-TYPE
		ENTERPRISE   cdx6500
		VARIABLES    { cdx6500SNMPLastTrap }
		DESCRIPTION
		             " %s - BAD FRAME LENGTH (%d)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68009

        mx25L2-stn-down  TRAP-TYPE
		ENTERPRISE   cdx6500
		VARIABLES    { cdx6500SNMPLastTrap }
		DESCRIPTION
		             "%s - STATION DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68010

        mx25L2-link-down  TRAP-TYPE
		ENTERPRISE   cdx6500
		VARIABLES    { cdx6500SNMPLastTrap }
		DESCRIPTION
		             "%s - LINK DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 68011

        mx25Port-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69000

        mx25Port-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69001

        mx25Port-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69002

        mx25Port-stn-boot  TRAP-TYPE
		ENTERPRISE   cdx6500
		VARIABLES    { cdx6500SNMPLastTrap }
		DESCRIPTION
		             "%s - STATION BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69003

        mx25Port-stn-disable  TRAP-TYPE
		ENTERPRISE   cdx6500
		VARIABLES    { cdx6500SNMPLastTrap }
		DESCRIPTION
		             "%s - STATION DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69004

        mx25Port-stn-enable  TRAP-TYPE
		ENTERPRISE   cdx6500
		VARIABLES    { cdx6500SNMPLastTrap }
		DESCRIPTION
		             "%s - STATION ENABLE COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69005

        mx25Port-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69006

        mx25Port-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69007

        mx25Port-stn-addr-dupl  TRAP-TYPE
		ENTERPRISE   cdx6500
		VARIABLES    { cdx6500SNMPLastTrap }
		DESCRIPTION
		             "%s - STATION ADDRESS DUPLICATED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69008

        mx25Port-stn-boot-fail  TRAP-TYPE
		ENTERPRISE   cdx6500
		VARIABLES    { cdx6500SNMPLastTrap }
		DESCRIPTION
		             "%s - STATION BOOT FAILED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69009

        mx25Port-stn-enable-fail  TRAP-TYPE
		ENTERPRISE   cdx6500
		VARIABLES    { cdx6500SNMPLastTrap }
		DESCRIPTION
		             "%s - STATION ENABLE FAILED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69010

        mx25Port-stn-disable-fail  TRAP-TYPE
		ENTERPRISE   cdx6500
		VARIABLES    { cdx6500SNMPLastTrap }
		DESCRIPTION
		             "%s - STATION DISABLE FAILED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69011

        mx25Port-stn-bsyout-fail  TRAP-TYPE
		ENTERPRISE   cdx6500
		VARIABLES    { cdx6500SNMPLastTrap }
		DESCRIPTION
		             "%s - STATION BUSY-OUT FAILED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69012

        mx25Port-boot-fail  TRAP-TYPE
		ENTERPRISE   cdx6500
		VARIABLES    { cdx6500SNMPLastTrap }
		DESCRIPTION
		             "%s - PORT BOOT FAILED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69013

        mx25Port-enable-fail  TRAP-TYPE
		ENTERPRISE   cdx6500
		VARIABLES    { cdx6500SNMPLastTrap }
		DESCRIPTION
		             "%s - PORT ENABLE FAILED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69014

        mx25Port-disable-fail  TRAP-TYPE
		ENTERPRISE   cdx6500
		VARIABLES    { cdx6500SNMPLastTrap }
		DESCRIPTION
		             "%s - PORT DISABLE FAILED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69015

        mx25Port-busyout-fail  TRAP-TYPE
		ENTERPRISE   cdx6500
		VARIABLES    { cdx6500SNMPLastTrap }
		DESCRIPTION
		             "%s - PORT BUSY-OUT FAILED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69016

        mx25Port-stn-bsyout  TRAP-TYPE
		ENTERPRISE   cdx6500
		VARIABLES    { cdx6500SNMPLastTrap }
		DESCRIPTION
		             "%s - STATION BUSY-OUT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69017

        mx25Port-busyout  TRAP-TYPE
		ENTERPRISE   cdx6500
		VARIABLES    { cdx6500SNMPLastTrap }
		DESCRIPTION
		             "%s - PORT BUSY-OUT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69018

        mx25Port-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 69019

        sdlcPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74000

        sdlcPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74001

        sdlcPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74002

        sdlcPort-disable-fail  TRAP-TYPE
		ENTERPRISE   cdx6500
		VARIABLES    { cdx6500SNMPLastTrap }
		DESCRIPTION
		             "%s - PORT DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74003

        sdlcPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74004

        sdlcPort-enable-fail  TRAP-TYPE
		ENTERPRISE   cdx6500
		VARIABLES    { cdx6500SNMPLastTrap }
		DESCRIPTION
		             "%s - PORT ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74005

        sdlcPort-stn-boot  TRAP-TYPE
		ENTERPRISE   cdx6500
		VARIABLES    { cdx6500SNMPLastTrap }
		DESCRIPTION
		             "%s - STATION BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74006

        sdlcPort-stn-boot-fail  TRAP-TYPE
		ENTERPRISE   cdx6500
		VARIABLES    { cdx6500SNMPLastTrap }
		DESCRIPTION
		             "%s - STATION BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74007

        sdlcPort-stn-disable  TRAP-TYPE
		ENTERPRISE   cdx6500
		VARIABLES    { cdx6500SNMPLastTrap }
		DESCRIPTION
		             "%s - STATION DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74008

        sdlcPort-stn-disable-fail  TRAP-TYPE
		ENTERPRISE   cdx6500
		VARIABLES    { cdx6500SNMPLastTrap }
		DESCRIPTION
		             "%s - STATION DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74009

        sdlcPort-stn-enable  TRAP-TYPE
		ENTERPRISE   cdx6500
		VARIABLES    { cdx6500SNMPLastTrap }
		DESCRIPTION
		             "%s - STATION ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74010

        sdlcPort-stn-enable-fail  TRAP-TYPE
		ENTERPRISE   cdx6500
		VARIABLES    { cdx6500SNMPLastTrap }
		DESCRIPTION
		             "%s - STATION ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74011

        sdlcPort-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74012

        sdlcPort-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74013

        sdlcPort-busyout  TRAP-TYPE
		ENTERPRISE   cdx6500
		VARIABLES    { cdx6500SNMPLastTrap }
		DESCRIPTION
		             "%s - PORT BUSY-OUT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74014

        sdlcPort-busyout-fail  TRAP-TYPE
		ENTERPRISE   cdx6500
		VARIABLES    { cdx6500SNMPLastTrap }
		DESCRIPTION
		             "%s - PORT BUSY-OUT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74015

        sdlcPort-stn-busy-out  TRAP-TYPE
		ENTERPRISE   cdx6500
		VARIABLES    { cdx6500SNMPLastTrap }
		DESCRIPTION
		             "%s - STATION BUSY-OUT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74016

        sdlcPort-stn-busyout-fail  TRAP-TYPE
		ENTERPRISE   cdx6500
		VARIABLES    { cdx6500SNMPLastTrap }
		DESCRIPTION
		             "%s - STATION BUSY-OUT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74017

        sdlcPort-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74018

        sdlcPort-insuff-mem  TRAP-TYPE
		ENTERPRISE   cdx6500
		VARIABLES    { cdx6500SNMPLastTrap }
		DESCRIPTION
		             "%s - INSUFFICIENT MEMORY TO PROTECT STATION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74019

        sdlcPort-unsup-frm-size  TRAP-TYPE
		ENTERPRISE   cdx6500
		VARIABLES    { cdx6500SNMPLastTrap }
		DESCRIPTION
		             " %s - UNSUPPORTED FRAME SIZE: OPERATING WITH 1024 BYTES"
                     --#TYPE
                     --#SUMMARY "Trap #$G, specific: $S, arg(1): $1"
                     --#ARGUMENTS {}
                     --#SEVERITY  INFORMATIONAL
                     --#TIMEINDEX
                     --#HELP
                     --#HELPTAG
                     --#STATE
		::= 74020

	sna74021-sdlc-s-dyna   TRAP-TYPE
		ENTERPRISE   cdx6500
		VARIABLES    { cdx6500SNMPLastTrap }
		DESCRIPTION
		     "SDLC-%dS%d - DYNAMIC STATION BOOT STARTED"
		     --#TYPE
		     --#SUMMARY "Trap #$G, specific: $S, arg(1) : $1"
		     --#ARGUMENTS {}
		     --#SEVERITY  CRITICAL
		     --#TIMEINDEX
		     --#HELP
		     --#HELPTAG
		     --#STATE
		::= 74021

	sna74022-sdlc-s-dyna   TRAP-TYPE
		ENTERPRISE   cdx6500
		VARIABLES    { cdx6500SNMPLastTrap }
		DESCRIPTION
		     "SDLC-%dS%d - DYNAMIC STATION BEING CREATED"
		     --#TYPE
		     --#SUMMARY "Trap #$G, specific: $S, arg(1) : $1"
		     --#ARGUMENTS {}
		     --#SEVERITY  MAJOR
		     --#TIMEINDEX
		     --#HELP
		     --#HELPTAG
		     --#STATE
		::= 74022

	sna74023-sdlc-s-dyna   TRAP-TYPE
		ENTERPRISE   cdx6500
		VARIABLES    { cdx6500SNMPLastTrap }
		DESCRIPTION
		     "SDLC-%dS%d - DYNAMIC STATION BOOT COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 74023

        sdlcL2-bad-frame-len  TRAP-TYPE
		ENTERPRISE   cdx6500
		VARIABLES    { cdx6500SNMPLastTrap }
		DESCRIPTION
		             " %s - BAD FRAME LENGTH (%d)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75001

        sdlcL2-bad-frame-type  TRAP-TYPE
		ENTERPRISE   cdx6500
		VARIABLES    { cdx6500SNMPLastTrap }
		DESCRIPTION
		             " %s - BAD FRAME TYPE (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75002

        sdlcL2-bad-n-r  TRAP-TYPE
		ENTERPRISE   cdx6500
		VARIABLES    { cdx6500SNMPLastTrap }
		DESCRIPTION
		             " %s - BAD N(R) (%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75003

        sdlcL2-master-polled-early  TRAP-TYPE
		ENTERPRISE   cdx6500
		VARIABLES    { cdx6500SNMPLastTrap }
		DESCRIPTION
		             "%s - MASTER POLLED EARLY"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75004

        sdlcL2-norm-seq-frmr  TRAP-TYPE
		ENTERPRISE   cdx6500
		VARIABLES    { cdx6500SNMPLastTrap }
		DESCRIPTION
		             " %s - FRMR (%02X/%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75005

        sdlcL2-stn-disconn  TRAP-TYPE
		ENTERPRISE   cdx6500
		VARIABLES    { cdx6500SNMPLastTrap }
		DESCRIPTION
		             "%s - STATION REQUESTED DISCONNECT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75006

        sdlcL2-stn-down  TRAP-TYPE
		ENTERPRISE   cdx6500
		VARIABLES    { cdx6500SNMPLastTrap }
		DESCRIPTION
		             "%s - STATION DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75007

        sdlcL2-stn-up  TRAP-TYPE
		ENTERPRISE   cdx6500
		VARIABLES    { cdx6500SNMPLastTrap }
		DESCRIPTION
		             "%s - STATION UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75008

        sdlcL2-addr-error  TRAP-TYPE
		ENTERPRISE   cdx6500
		VARIABLES    { cdx6500SNMPLastTrap }
		DESCRIPTION
		             " %s - ADDRESS ERROR (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75009

        sdlcL2-hpad-stn-down  TRAP-TYPE
		ENTERPRISE   cdx6500
		VARIABLES    { cdx6500SNMPLastTrap }
		DESCRIPTION
		             "%s - HPAD STATION DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75010

        sdlcL2-hpad-stn-up  TRAP-TYPE
		ENTERPRISE   cdx6500
		VARIABLES    { cdx6500SNMPLastTrap }
		DESCRIPTION
		             "%s - HPAD STATION UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75011

        sdlcL2-hpad-stn-active  TRAP-TYPE
		ENTERPRISE   cdx6500
		VARIABLES    { cdx6500SNMPLastTrap }
		DESCRIPTION
		             " %s - HPAD STATION ACTIVE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75012

        sdlcL2-hpad-stn-inactive  TRAP-TYPE
		ENTERPRISE   cdx6500
		VARIABLES    { cdx6500SNMPLastTrap }
		DESCRIPTION
		             " %s - HPAD STATION INACTIVE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75013

        sdlcL2-tpad-stn-active  TRAP-TYPE
		ENTERPRISE   cdx6500
		VARIABLES    { cdx6500SNMPLastTrap }
		DESCRIPTION
		             " %s - TPAD STATION ACTIVE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75014

        sdlcL2-tpad-stn-inactive  TRAP-TYPE
		ENTERPRISE   cdx6500
		VARIABLES    { cdx6500SNMPLastTrap }
		DESCRIPTION
		             " %s - TPAD STATION INACTIVE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75015

        sdlcL2-ovsize-frame  TRAP-TYPE
		ENTERPRISE   cdx6500
		VARIABLES    { cdx6500SNMPLastTrap }
		DESCRIPTION
		             " %s - OVERSIZE FRAME (%d) FROM REMOTE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 75016

        qllc-proto-error  TRAP-TYPE
		ENTERPRISE   cdx6500
		VARIABLES    { cdx6500SNMPLastTrap }
		DESCRIPTION
		             " %s - QLLC PROTOCOL ERROR (%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 76000

        qllc-bad-pkt-len  TRAP-TYPE
		ENTERPRISE   cdx6500
		VARIABLES    { cdx6500SNMPLastTrap }
		DESCRIPTION
		             " %s - QLLC BAD PACKET LENGTH (%d)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 76001

        qllc-illegal-pkt  TRAP-TYPE
		ENTERPRISE   cdx6500
		VARIABLES    { cdx6500SNMPLastTrap }
		DESCRIPTION
		             " %s - QLLC ILLEGAL PKT DETECTED (%02X/%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 76002

        qllc-qfrmr-receive  TRAP-TYPE
		ENTERPRISE   cdx6500
		VARIABLES    { cdx6500SNMPLastTrap }
		DESCRIPTION
		             " %s - QFRMR RECEIVED (%02X/%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 76003

        qllc-tpad-stn-up  TRAP-TYPE
		ENTERPRISE   cdx6500
		VARIABLES    { cdx6500SNMPLastTrap }
		DESCRIPTION
		             "%s - TPAD STATION UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 76004

        qllc-tpad-stn-down  TRAP-TYPE
		ENTERPRISE   cdx6500
		VARIABLES    { cdx6500SNMPLastTrap }
		DESCRIPTION
		             "%s - TPAD STATION DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 76005

        qllc-net-link-up  TRAP-TYPE
		ENTERPRISE   cdx6500
		VARIABLES    { cdx6500SNMPLastTrap }
		DESCRIPTION
		             " %s - NETWORK LINK UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 76006

        qllc-net-link-down  TRAP-TYPE
		ENTERPRISE   cdx6500
		VARIABLES    { cdx6500SNMPLastTrap }
		DESCRIPTION
		             " %s - NETWORK LINK DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 76007

        ncrbscPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86000

        ncrbscPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86001

        ncrbscPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86002

        ncrbscPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86003

        ncrbscPort-enable-fail  TRAP-TYPE
		ENTERPRISE   cdx6500
		VARIABLES    { cdx6500SNMPLastTrap }
		DESCRIPTION
		             "%s - PORT ENABLE FAILED - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86004

        ncrbscPort-inbound-err  TRAP-TYPE
		ENTERPRISE   cdx6500
		VARIABLES    { cdx6500SNMPLastTrap }
		DESCRIPTION
		             "%s - NON-RECOVERABLE INBOUND ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86005

        ncrbscPort-outbound-err  TRAP-TYPE
		ENTERPRISE   cdx6500
		VARIABLES    { cdx6500SNMPLastTrap }
		DESCRIPTION
		             "%s - NON-RECOVERABLE OUTBOUND ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86006

        ncrbscPort-line-down  TRAP-TYPE
		ENTERPRISE   cdx6500
		VARIABLES    { cdx6500SNMPLastTrap }
		DESCRIPTION
		             "%s - LINE DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86007

        ncrbscPort-line-up  TRAP-TYPE
		ENTERPRISE   cdx6500
		VARIABLES    { cdx6500SNMPLastTrap }
		DESCRIPTION
		             "%s - LINE OPERATIONAL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86008

        ncrbscPort-dev-down  TRAP-TYPE
		ENTERPRISE   cdx6500
		VARIABLES    { cdx6500SNMPLastTrap }
		DESCRIPTION
		             "%s - CONTROLLER DOWN - %02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86009

        ncrbscPort-dev-up  TRAP-TYPE
		ENTERPRISE   cdx6500
		VARIABLES    { cdx6500SNMPLastTrap }
		DESCRIPTION
		             "%s - CONTROLLER OPERATIONAL - %02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86010

        ncrbscPort-dev-unavail  TRAP-TYPE
		ENTERPRISE   cdx6500
		VARIABLES    { cdx6500SNMPLastTrap }
		DESCRIPTION
		             "%s - DEVICE UNAVAILABLE - %02X %02X - DATA LOSS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 86011

        ncrbsc-list-is-empty  TRAP-TYPE
		ENTERPRISE   cdx6500
		VARIABLES    { cdx6500SNMPLastTrap }
		DESCRIPTION
		     "%s - LIST IS EMPTY"
		     --#TYPE
		     --#SUMMARY "Trap #$G, specific: $S, arg(1) : $1"
		     --#ARGUMENTS {}
		     --#SEVERITY  CRITICAL
		     --#TIMEINDEX
		     --#HELP
		     --#HELPTAG
		     --#STATE
		::= 86012

        ncrbsc-list-is-not-empty  TRAP-TYPE
		ENTERPRISE   cdx6500
		VARIABLES    { cdx6500SNMPLastTrap }
		DESCRIPTION
		     "%s - LIST IS NOT EMPTY"
		     --#TYPE
		     --#SUMMARY "Trap #$G, specific: $S, arg(1) : $1"
		     --#ARGUMENTS {}
		     --#SEVERITY  CRITICAL
		     --#TIMEINDEX
		     --#HELP
		     --#HELPTAG
		     --#STATE
		::= 86013

        friL2-unconfigured-dlci  TRAP-TYPE
		ENTERPRISE   cdx6500
		VARIABLES    { cdx6500SNMPLastTrap }
		DESCRIPTION
		             " %s - FRAME RECEIVED FROM UNKNOWN DLCI: %04d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 87000

        friL2-pkt-for-disable-stn  TRAP-TYPE
		ENTERPRISE   cdx6500
		VARIABLES    { cdx6500SNMPLastTrap }
		DESCRIPTION
		             " %s - FRAME RECEIVED FOR DISABLED STATION: DLCI %04d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 87001

        friL2-bad-frame-len  TRAP-TYPE
		ENTERPRISE   cdx6500
		VARIABLES    { cdx6500SNMPLastTrap }
		DESCRIPTION
		             " %s - FRAME RECEIVED WITH BAD LENGTH: DLCI %04d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 87002

        friL2-annexd-error  TRAP-TYPE
		ENTERPRISE   cdx6500
		VARIABLES    { cdx6500SNMPLastTrap }
		DESCRIPTION
		             " %s - ANNEX D PROTOCOL ERROR THRESHOLD REACHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 87003

        friL2-lmi-error  TRAP-TYPE
		ENTERPRISE   cdx6500
		VARIABLES    { cdx6500SNMPLastTrap }
		DESCRIPTION
		             " %s - LMI PROTOCOL ERROR THRESHOLD REACHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 87004

        friL2-bypass-stn-link-up  TRAP-TYPE
		ENTERPRISE   cdx6500
		VARIABLES    { cdx6500SNMPLastTrap }
		DESCRIPTION
		             " %s - BYPASS STATION LINK UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 87005

        friL2-bypass-stn-link-down  TRAP-TYPE
		ENTERPRISE   cdx6500
		VARIABLES    { cdx6500SNMPLastTrap }
		DESCRIPTION
		             " %s - BYPASS STATION LINK DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 87006

        friL2-annexa-error  TRAP-TYPE
		ENTERPRISE   cdx6500
		VARIABLES    { cdx6500SNMPLastTrap }
		DESCRIPTION
		             " %s - ANNEX A PROTOCOL ERROR THRESHOLD REACHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 87007

        friL2-unused-net-dlci  TRAP-TYPE
		ENTERPRISE   cdx6500
		VARIABLES    { cdx6500SNMPLastTrap }
		DESCRIPTION
		             " %s - NETWORK DLCI UNASSIGNED: DLCI %04d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 87008

        fri-prot-detect-timeout  TRAP-TYPE
                ENTERPRISE   cdx6500
                VARIABLES    { cdx6500SNMPLastTrap }
                DESCRIPTION
                             "%s - NETWORK CTL PROTOCOL DETECTION TIMEOUT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 87009

        fri-prot-change  TRAP-TYPE
                ENTERPRISE   cdx6500
                VARIABLES    { cdx6500SNMPLastTrap }
                DESCRIPTION
                             "%s - NETWORK CTL PROTOCOL CHANGE DETECTED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 87010

        fri-frm-seg-down  TRAP-TYPE
                ENTERPRISE   cdx6500
                VARIABLES    { cdx6500SNMPLastTrap }
                DESCRIPTION
                             "%s - FRAME SEGMENTER LINK DOWN"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 87011

        fri-frm-seg-up  TRAP-TYPE
                ENTERPRISE   cdx6500
                VARIABLES    { cdx6500SNMPLastTrap }
                DESCRIPTION
                             "%s - FRAME SEGMENTER LINK UP"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 87012

        fri-rx-lmi-status-update-contain  TRAP-TYPE
		ENTERPRISE   cdx6500
		VARIABLES    { cdx6500SNMPLastTrap }
		DESCRIPTION
		     "%s - RX LMI STATUS UPDATE CONTAINING MORE THAN THE SUPPORTED # OF PVC'S. %04d"
		     --#TYPE
		     --#SUMMARY "Trap #$G, specific: $S, arg(1) : $1"
		     --#ARGUMENTS {}
		     --#SEVERITY  MAJOR
		     --#TIMEINDEX
		     --#HELP
		     --#HELPTAG
		     --#STATE
		::= 87013

        fri-frame-received-invalid-addre  TRAP-TYPE
		ENTERPRISE   cdx6500
		VARIABLES    { cdx6500SNMPLastTrap }
		DESCRIPTION
		     "%s - FRAME RECEIVED INVALID ADDRESS: %04d"
		     --#TYPE
		     --#SUMMARY "Trap #$G, specific: $S, arg(1) : $1"
		     --#ARGUMENTS {}
		     --#SEVERITY  MAJOR
		     --#TIMEINDEX
		     --#HELP
		     --#HELPTAG
		     --#STATE
		::= 87014

        fri-link-up  TRAP-TYPE
		ENTERPRISE   cdx6500
		VARIABLES    { cdx6500SNMPLastTrap }
		DESCRIPTION
		     "%s - LINK UP"
		     --#TYPE
		     --#SUMMARY "Trap #$G, specific: $S, arg(1) : $1"
		     --#ARGUMENTS {}
		     --#SEVERITY  CRITICAL
		     --#TIMEINDEX
		     --#HELP
		     --#HELPTAG
		     --#STATE
		::= 87015

        fri-link-down  TRAP-TYPE
		ENTERPRISE   cdx6500
		VARIABLES    { cdx6500SNMPLastTrap }
		DESCRIPTION
		     "%s - LINK DOWN"
		     --#TYPE
		     --#SUMMARY "Trap #$G, specific: $S, arg(1) : $1"
		     --#ARGUMENTS {}
		     --#SEVERITY  CRITICAL
		     --#TIMEINDEX
		     --#HELP
		     --#HELPTAG
		     --#STATE
		::= 87016

        fri-protocol-error-threshold-rea  TRAP-TYPE
		ENTERPRISE   cdx6500
		VARIABLES    { cdx6500SNMPLastTrap }
		DESCRIPTION
		     "%s - %s PROTOCOL ERROR THRESHOLD REACHED"
		     --#TYPE
		     --#SUMMARY "Trap #$G, specific: $S, arg(1) : $1"
		     --#ARGUMENTS {}
		     --#SEVERITY  MAJOR
		     --#TIMEINDEX
		     --#HELP
		     --#HELPTAG
		     --#STATE
		::= 87017

	fri87018-uni-segment   TRAP-TYPE
		ENTERPRISE   cdx6500
		VARIABLES    { cdx6500SNMPLastTrap }
		DESCRIPTION
		     "%s - UNI SEGMENTATION LINK DOWN"
		     --#TYPE
		     --#SUMMARY "Trap #$G, specific: $S, arg(1) : $1"
		     --#ARGUMENTS {}
		     --#SEVERITY  MAJOR
		     --#TIMEINDEX
		     --#HELP
		     --#HELPTAG
		     --#STATE
		::= 87018

	fri87019-uni-segment   TRAP-TYPE
		ENTERPRISE   cdx6500
		VARIABLES    { cdx6500SNMPLastTrap }
		DESCRIPTION
		     "%s - UNI SEGMENTATION LINK UP"
		     --#TYPE
		     --#SUMMARY "Trap #$G, specific: $S, arg(1) : $1"
		     --#ARGUMENTS {}
		     --#SEVERITY  MAJOR
		     --#TIMEINDEX
		     --#HELP
		     --#HELPTAG
		     --#STATE
		::= 87019

        friPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88000

        friPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88001

        friPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88002

        friPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88003

        friPort-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88004

        friPort-stn-disable  TRAP-TYPE
		ENTERPRISE   cdx6500
		VARIABLES    { cdx6500SNMPLastTrap }
		DESCRIPTION
		             "%s - STATION DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88005

        friPort-stn-enable  TRAP-TYPE
		ENTERPRISE   cdx6500
		VARIABLES    { cdx6500SNMPLastTrap }
		DESCRIPTION
		             "%s - STATION ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88006

        friPort-stn-boot  TRAP-TYPE
		ENTERPRISE   cdx6500
		VARIABLES    { cdx6500SNMPLastTrap }
		DESCRIPTION
		             "%s - STATION BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88007

        friPort-stn-boot-fail  TRAP-TYPE
		ENTERPRISE   cdx6500
		VARIABLES    { cdx6500SNMPLastTrap }
		DESCRIPTION
		             "%s - STATION BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88008

        friPort-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 88009

        fripPort-boot-Stn-novbd  TRAP-TYPE
                ENTERPRISE   cdx6500
                VARIABLES    { cdx6500SNMPLastTrap }
                DESCRIPTION
                             "%s - SUSPICIOUS CONFIGURATION - ZERO VOICE BANDWIDTH AND VOICE RELAY CIRCUITS PRESENT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 88010

        fripPort-boot-Stn-novoice  TRAP-TYPE
                ENTERPRISE   cdx6500
                VARIABLES    { cdx6500SNMPLastTrap }
                DESCRIPTION
                       "%s - SUSPICIOUS CONFIGURATION - NON ZERO VOICE BANDWIDTH BUT NO VOICE RELAY CIRCUITS PRESENT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 88011

        fripPort-boot-vbd-noseg  TRAP-TYPE
                ENTERPRISE   cdx6500
                VARIABLES    { cdx6500SNMPLastTrap }
                DESCRIPTION
                             "%s - SUSPICIOUS CONFIGURATION - FRAME SEGMENTER DISABLE AND VOICE BANDWIDTH IS NON-ZERO"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 88012

        frip-Port-boot-seg-novbd  TRAP-TYPE
                ENTERPRISE   cdx6500
                VARIABLES    { cdx6500SNMPLastTrap }
                DESCRIPTION
                             "%s - SUSPICIOUS CONFIGURATION - FRAME SEGMENTER ENABLE AND VOICE BANDWIDTH IS ZERO"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 88013

        fri-suspicious-configuration-fra  TRAP-TYPE
		ENTERPRISE   cdx6500
		VARIABLES    { cdx6500SNMPLastTrap }
		DESCRIPTION
		     "%s - SUSPICIOUS CONFIGURATION - FRAME SEGMENTER ENABLE AND VOICE BANDWIDTH IS ZERO"
		     --#TYPE
		     --#SUMMARY "Trap #$G, specific: $S, arg(1) : $1"
		     --#ARGUMENTS {}
		     --#SEVERITY  MAJOR
		     --#TIMEINDEX
		     --#HELP
		     --#HELPTAG
		     --#STATE
		::= 88014

        fri-rfc1315-ifindexdlcifrcircuit  TRAP-TYPE
		ENTERPRISE   cdx6500
		VARIABLES    { cdx6500SNMPLastTrap }
		DESCRIPTION
		     "RFC1315-ifIndex/Dlci/frCircuitState : %s - VC STATE CHANGED"
		     --#TYPE
		     --#SUMMARY "Trap #$G, specific: $S, arg(1) : $1"
		     --#ARGUMENTS {}
		     --#SEVERITY  CRITICAL
		     --#TIMEINDEX
		     --#HELP
		     --#HELPTAG
		     --#STATE
		::= 88015

        fri-port-update-complete  TRAP-TYPE
		ENTERPRISE   cdx6500
		VARIABLES    { cdx6500SNMPLastTrap }
		DESCRIPTION
		     "%s - PORT UPDATE COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 88016

        fri-out-of-memory  TRAP-TYPE
		ENTERPRISE   cdx6500
		VARIABLES    { cdx6500SNMPLastTrap }
		DESCRIPTION
		     "%s - OUT OF MEMORY - SOME STATIONS NOT CREATED"
		     --#TYPE
		     --#SUMMARY "Trap #$G, specific: $S, arg(1) : $1"
		     --#ARGUMENTS {}
		     --#SEVERITY  MAJOR
		     --#TIMEINDEX
		     --#HELP
		     --#HELPTAG
		     --#STATE
		::= 88017

        dcp-fsm-call-termination  TRAP-TYPE
		ENTERPRISE   cdx6500
		VARIABLES    { cdx6500SNMPLastTrap }
		DESCRIPTION
		             " %s - ABNORMAL CALL TERMINATION - %sPROTOCOL : %d STATES : %d,%d EVENT : %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 90000

        dcp-na-fac-set-fail  TRAP-TYPE
		ENTERPRISE   cdx6500
		VARIABLES    { cdx6500SNMPLastTrap }
		DESCRIPTION
		             " NO ROOM IN FACILITY FOR DCP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 91000

        dcp-na-fac-get-fail  TRAP-TYPE
		ENTERPRISE   cdx6500
		VARIABLES    { cdx6500SNMPLastTrap }
		DESCRIPTION
		             " CAN'T GET FACILITY FOR DCP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 91001

        dcp-na-null-ptr  TRAP-TYPE
		ENTERPRISE   cdx6500
		VARIABLES    { cdx6500SNMPLastTrap }
		DESCRIPTION
		             " RECEIVED NULL POINTER"
                     --#TYPE
                     --#SUMMARY "Trap #$G, specific: $S, arg(1): $1"
                     --#ARGUMENTS {}
                     --#SEVERITY  INFORMATIONAL
                     --#TIMEINDEX
                     --#HELP
                     --#HELPTAG
                     --#STATE
		::= 91002

        dcp-na-invalid-cr  TRAP-TYPE
		ENTERPRISE   cdx6500
		VARIABLES    { cdx6500SNMPLastTrap }
		DESCRIPTION
		             " RECEIVED INVALID CR TPDU"
                     --#TYPE
                     --#SUMMARY "Trap #$G, specific: $S, arg(1): $1"
                     --#ARGUMENTS {}
                     --#SEVERITY  INFORMATIONAL
                     --#TIMEINDEX
                     --#HELP
                     --#HELPTAG
                     --#STATE
		::= 91003

        dcp-na-invalid-cc  TRAP-TYPE
		ENTERPRISE   cdx6500
		VARIABLES    { cdx6500SNMPLastTrap }
		DESCRIPTION
		             " RECEIVED INVALID CC TPDU"
                     --#TYPE
                     --#SUMMARY "Trap #$G, specific: $S, arg(1): $1"
                     --#ARGUMENTS {}
                     --#SEVERITY  INFORMATIONAL
                     --#TIMEINDEX
                     --#HELP
                     --#HELPTAG
                     --#STATE
		::= 91004

        dcp-na-invalid-pkt-type  TRAP-TYPE
		ENTERPRISE   cdx6500
		VARIABLES    { cdx6500SNMPLastTrap }
		DESCRIPTION
		             " RECEIVED UNKNOWN PACKET TYPE INDICATOR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 91005

        dcp-na-invalid-tpdu-len  TRAP-TYPE
		ENTERPRISE   cdx6500
		VARIABLES    { cdx6500SNMPLastTrap }
		DESCRIPTION
		             "RECEIVED INVALID TPDU HEADER LENGTH"
                     --#TYPE
                     --#SUMMARY "Trap #$G, specific: $S, arg(1): $1"
                     --#ARGUMENTS {}
                     --#SEVERITY  INFORMATIONAL
                     --#TIMEINDEX
                     --#HELP
                     --#HELPTAG
                     --#STATE
		::= 91006

        dcp-na-invalid-tpdu-type  TRAP-TYPE
		ENTERPRISE   cdx6500
		VARIABLES    { cdx6500SNMPLastTrap }
		DESCRIPTION
		             "RECEIVED INVALID TPDU TYPE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 91007

        dcp-pa-invalid-pkt-type  TRAP-TYPE
		ENTERPRISE   cdx6500
		VARIABLES    { cdx6500SNMPLastTrap }
		DESCRIPTION
		             " RECEIVED UNKNOWN PACKET TYPE INDICATOR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 92000

        dcp-pa-null-ptr  TRAP-TYPE
		ENTERPRISE   cdx6500
		VARIABLES    { cdx6500SNMPLastTrap }
		DESCRIPTION
		             " RECEIVED NULL POINTER"
                     --#TYPE
                     --#SUMMARY "Trap #$G, specific: $S, arg(1): $1"
                     --#ARGUMENTS {}
                     --#SEVERITY  INFORMATIONAL
                     --#TIMEINDEX
                     --#HELP
                     --#HELPTAG
                     --#STATE
		::= 92001

        dsdPort-boot  TRAP-TYPE
		ENTERPRISE   cdx6500
		VARIABLES    { cdx6500SNMPLastTrap }
		DESCRIPTION
		             "%s - DSD BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 94000

        dsdPort-boot-fail  TRAP-TYPE
		ENTERPRISE   cdx6500
		VARIABLES    { cdx6500SNMPLastTrap }
		DESCRIPTION
		             "%s - DSD BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 94001

        rs366Port-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 97000

        rs366Port-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 97001

        rs366Port-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 97002

        rs366Port-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 97003

        rs366Port-enable-fail  TRAP-TYPE
		ENTERPRISE   cdx6500
		VARIABLES    { cdx6500SNMPLastTrap }
		DESCRIPTION
		             "%s - PORT ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 97004

        rs366Port-disable-fail  TRAP-TYPE
		ENTERPRISE   cdx6500
		VARIABLES    { cdx6500SNMPLastTrap }
		DESCRIPTION
		             "%s - PORT DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 97005

        flash-cannot-read-from-memory-sl  TRAP-TYPE
		ENTERPRISE   cdx6500
		VARIABLES    { cdx6500SNMPLastTrap }
		DESCRIPTION
		     "CANNOT READ FROM FLASH MEMORY, SLOT %d"
		     --#TYPE
		     --#SUMMARY "Trap #$G, specific: $S, arg(1) : $1"
		     --#ARGUMENTS {}
		     --#SEVERITY  CRITICAL
		     --#TIMEINDEX
		     --#HELP
		     --#HELPTAG
		     --#STATE
		::= 104000

        software-copying-to-flash  TRAP-TYPE
		ENTERPRISE   cdx6500
		VARIABLES    { cdx6500SNMPLastTrap }
		DESCRIPTION
		             "COPYING SOFTWARE TO FLASH MEMORY"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105000

        num-bytes-copied-to-flash  TRAP-TYPE
		ENTERPRISE   cdx6500
		VARIABLES    { cdx6500SNMPLastTrap }
		DESCRIPTION
		             "%08d BYTES COPIED TO FLASH MEMORY"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105001

        copy-to-flash-complete  TRAP-TYPE
		ENTERPRISE   cdx6500
		VARIABLES    { cdx6500SNMPLastTrap }
		DESCRIPTION
		             "COPY COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105002

        copy-to-flash-fail  TRAP-TYPE
		ENTERPRISE   cdx6500
		VARIABLES    { cdx6500SNMPLastTrap }
		DESCRIPTION
		             "FAILED TO COPY SOFTWARE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105003

        updating-software  TRAP-TYPE
		ENTERPRISE   cdx6500
		VARIABLES    { cdx6500SNMPLastTrap }
		DESCRIPTION
		             "UPDATING SOFTWARE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105004

        software-update-complete  TRAP-TYPE
		ENTERPRISE   cdx6500
		VARIABLES    { cdx6500SNMPLastTrap }
		DESCRIPTION
		             "SOFTWARE UPDATE COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105005

        software-update-fail  TRAP-TYPE
		ENTERPRISE   cdx6500
		VARIABLES    { cdx6500SNMPLastTrap }
		DESCRIPTION
		             "FAILED TO UPDATE SOFTWARE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105006

        flash-checksum-err  TRAP-TYPE
		ENTERPRISE   cdx6500
		VARIABLES    { cdx6500SNMPLastTrap }
		DESCRIPTION
		             "FLASH CHECKSUM ERROR, %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105007

        flash-erase-fail  TRAP-TYPE
		ENTERPRISE   cdx6500
		VARIABLES    { cdx6500SNMPLastTrap }
		DESCRIPTION
		             "CANNOT ERASE FLASH MEMORY, %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105008

        flash-write-fail  TRAP-TYPE
		ENTERPRISE   cdx6500
		VARIABLES    { cdx6500SNMPLastTrap }
		DESCRIPTION
		             "CANNOT WRITE TO FLASH MEMORY, %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105009

        lfash-copying  TRAP-TYPE
		ENTERPRISE   cdx6500
		VARIABLES    { cdx6500SNMPLastTrap }
		DESCRIPTION
		             "COPYING SOFTWARE FROM LOCAL FLASH TO FLASH"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105010

        lflash-copy  TRAP-TYPE
		ENTERPRISE   cdx6500
		VARIABLES    { cdx6500SNMPLastTrap }
		DESCRIPTION
		             "LOCAL FLASH COPY COMPLETE %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105011

        lflash-copy-fail  TRAP-TYPE
		ENTERPRISE   cdx6500
		VARIABLES    { cdx6500SNMPLastTrap }
		DESCRIPTION
		             "LOCAL FLASH COPY FAILED, %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 105012

        sd-copying-software-from-local-f  TRAP-TYPE
		ENTERPRISE   cdx6500
		VARIABLES    { cdx6500SNMPLastTrap }
		DESCRIPTION
		     "COPYING SOFTWARE FROM LOCAL FLASH TO FLASH"
		     --#TYPE
		     --#SUMMARY "Trap #$G, specific: $S, arg(1) : $1"
		     --#ARGUMENTS {}
		     --#SEVERITY  CRITICAL
		     --#TIMEINDEX
		     --#HELP
		     --#HELPTAG
		     --#STATE
		::= 105013

        sd-local-flash-copy-complete  TRAP-TYPE
		ENTERPRISE   cdx6500
		VARIABLES    { cdx6500SNMPLastTrap }
		DESCRIPTION
		     "LOCAL FLASH COPY COMPLETE %s"
		     --#TYPE
		     --#SUMMARY "Trap #$G, specific: $S, arg(1) : $1"
		     --#ARGUMENTS {}
		     --#SEVERITY  CRITICAL
		     --#TIMEINDEX
		     --#HELP
		     --#HELPTAG
		     --#STATE
		::= 105014

        sd-local-flash-copy-failed  TRAP-TYPE
		ENTERPRISE   cdx6500
		VARIABLES    { cdx6500SNMPLastTrap }
		DESCRIPTION
		     "LOCAL FLASH COPY FAILED, %s"
		     --#TYPE
		     --#SUMMARY "Trap #$G, specific: $S, arg(1) : $1"
		     --#ARGUMENTS {}
		     --#SEVERITY  CRITICAL
		     --#TIMEINDEX
		     --#HELP
		     --#HELPTAG
		     --#STATE
		::= 105015

        cmem-simm-init  TRAP-TYPE
		ENTERPRISE   cdx6500
		VARIABLES    { cdx6500SNMPLastTrap }
		DESCRIPTION
		             "CMEM SIMM REINITIALIZED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 106000

        alt-flash-software-load  TRAP-TYPE
		ENTERPRISE   cdx6500
		VARIABLES    { cdx6500SNMPLastTrap }
		DESCRIPTION
		             "SOFTWARE LOADED FROM ALTERNATE FLASH"
                     --#TYPE
                     --#SUMMARY "Trap #$G, specific: $S, arg(1): $1"
                     --#ARGUMENTS {}
                     --#SEVERITY  INFORMATIONAL
                     --#TIMEINDEX
                     --#HELP
                     --#HELPTAG
                     --#STATE
		::= 106001

        unknown-card-type  TRAP-TYPE
		ENTERPRISE   cdx6500
		VARIABLES    { cdx6500SNMPLastTrap }
		DESCRIPTION
		             "UNKNOWN CARD TYPE - SLOT %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 106002

        mboard-lab-strap-install  TRAP-TYPE
		ENTERPRISE   cdx6500
		VARIABLES    { cdx6500SNMPLastTrap }
		DESCRIPTION
		             "MOTHERBOARD LAB STRAP INSTALLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 106003

        async302-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 107000

        async302-dbits-unsupp  TRAP-TYPE
		ENTERPRISE   cdx6500
		VARIABLES    { cdx6500SNMPLastTrap }
		DESCRIPTION
		             " %s - UNSUPPORTED DATABITS: OPERATING WITH 8 DATABITS, NO PARITY"
                     --#TYPE
                     --#SUMMARY "Trap #$G, specific: $S, arg(1): $1"
                     --#ARGUMENTS {}
                     --#SEVERITY  INFORMATIONAL
                     --#TIMEINDEX
                     --#HELP
                     --#HELPTAG
                     --#STATE
		::= 107001

        async302-baud-unsupp  TRAP-TYPE
		ENTERPRISE   cdx6500
		VARIABLES    { cdx6500SNMPLastTrap }
		DESCRIPTION
		             " %s - UNSUPPORTED BAUDRATE: OPERATING AT 9600 BPS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 107002

        async302-parity-unsupp  TRAP-TYPE
		ENTERPRISE   cdx6500
		VARIABLES    { cdx6500SNMPLastTrap }
		DESCRIPTION
		             " %s - UNSUPPORTED PARITY: OPERATING WITH 8 DATABITS, NO PARITY"
                     --#TYPE
                     --#SUMMARY "Trap #$G, specific: $S, arg(1): $1"
                     --#ARGUMENTS {}
                     --#SEVERITY  INFORMATIONAL
                     --#TIMEINDEX
                     --#HELP
                     --#HELPTAG
                     --#STATE
		::= 107003

        bop302-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 108000

        bop302-unsupp-speed  TRAP-TYPE
		ENTERPRISE   cdx6500
		VARIABLES    { cdx6500SNMPLastTrap }
		DESCRIPTION
		             " %s - UNSUPPORTED SPEED: OPERATING AT %d BITS PER SECOND"
                     --#TYPE
                     --#SUMMARY "Trap #$G, specific: $S, arg(1): $1"
                     --#ARGUMENTS {}
                     --#SEVERITY  INFORMATIONAL
                     --#TIMEINDEX
                     --#HELP
                     --#HELPTAG
                     --#STATE
		::= 108001

        bop302-rx-byte-count-err  TRAP-TYPE
		ENTERPRISE   cdx6500
		VARIABLES    { cdx6500SNMPLastTrap }
		DESCRIPTION
		             " %s - UNSUPPORTED RECEIVE BYTE COUNT: OPERATING WITH %d RX BYTE COUNT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 108002

        bop302-erroneous-bool  TRAP-TYPE
		ENTERPRISE   cdx6500
		VARIABLES    { cdx6500SNMPLastTrap }
		DESCRIPTION
		             " %s - ERRONEOUS BOOLEAN PARAMETER: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 108003

        bop302-clk-override  TRAP-TYPE
		ENTERPRISE   cdx6500
		VARIABLES    { cdx6500SNMPLastTrap }
		DESCRIPTION
		             " %s - CLOCK SOURCE OVERRIDE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 108004

        bop302-tx-sanity-timeout  TRAP-TYPE
                ENTERPRISE   cdx6500
                VARIABLES    { cdx6500SNMPLastTrap }
                DESCRIPTION
                             " %s - TX SANITY TIMEOUT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 108005

	iodrivers108006-corr   TRAP-TYPE
		ENTERPRISE   cdx6500
		VARIABLES    { cdx6500SNMPLastTrap }
		DESCRIPTION
		     "%s - CORRUTPED PCK, NULL POINTER GENERATED"
		     --#TYPE
		     --#SUMMARY "Trap #$G, specific: $S, arg(1) : $1"
		     --#ARGUMENTS {}
		     --#SEVERITY  MAJOR
		     --#TIMEINDEX
		     --#HELP
		     --#HELPTAG
		     --#STATE
		::= 108006

        cop302-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 109000

        bstdPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110000

        bstdPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110001

        bstdPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110002

        bstdPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110003

        bstdPort-enable-fail  TRAP-TYPE
		ENTERPRISE   cdx6500
		VARIABLES    { cdx6500SNMPLastTrap }
		DESCRIPTION
		             "%s - PORT ENABLE FAILED - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110004

        bstdPort-inbound-err  TRAP-TYPE
		ENTERPRISE   cdx6500
		VARIABLES    { cdx6500SNMPLastTrap }
		DESCRIPTION
		             "%s - NON-RECOVERABLE INBOUND ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110005

        bstdPort-outbound-err  TRAP-TYPE
		ENTERPRISE   cdx6500
		VARIABLES    { cdx6500SNMPLastTrap }
		DESCRIPTION
		             "%s - NON-RECOVERABLE OUTBOUND ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110006

        bstdPort-line-down  TRAP-TYPE
		ENTERPRISE   cdx6500
		VARIABLES    { cdx6500SNMPLastTrap }
		DESCRIPTION
		             "%s - LINE DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110007

        bstdPort-line-up  TRAP-TYPE
		ENTERPRISE   cdx6500
		VARIABLES    { cdx6500SNMPLastTrap }
		DESCRIPTION
		             "%s - LINE OPERATIONAL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110008

        bstdPort-stn-down  TRAP-TYPE
		ENTERPRISE   cdx6500
		VARIABLES    { cdx6500SNMPLastTrap }
		DESCRIPTION
		             "%s - STATION DOWN - %02X,%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110009

        bstdPort-stn-up  TRAP-TYPE
		ENTERPRISE   cdx6500
		VARIABLES    { cdx6500SNMPLastTrap }
		DESCRIPTION
		             "%s - STATION OPERATIONAL - %02X,%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110010

        bstdPort-address-conflict  TRAP-TYPE
		ENTERPRISE   cdx6500
		VARIABLES    { cdx6500SNMPLastTrap }
		DESCRIPTION
		             "%s - STATION(%d) INHIBITED - %02X,%02X - ADDRESS CONFLICT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110011

        bstdPort-possible-data-loss  TRAP-TYPE
		ENTERPRISE   cdx6500
		VARIABLES    { cdx6500SNMPLastTrap }
		DESCRIPTION
		             "%s - POSSIBLE DATA LOSS - %02X,%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110012

        bstdPort-cont-tgrp-conflict  TRAP-TYPE
		ENTERPRISE   cdx6500
		VARIABLES    { cdx6500SNMPLastTrap }
		DESCRIPTION
		             " %s - STATION(%d) CONFIGURATION ERROR: CONTENTION MODE OVERRIDES TGRP DEVICE OPTION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110013

        bstdPort-hpad-tgrp-conflict  TRAP-TYPE
		ENTERPRISE   cdx6500
		VARIABLES    { cdx6500SNMPLastTrap }
		DESCRIPTION
		             " %s - STATION(%d) CONFIGURATION ERROR: TGRP DEVICE OPTION IGNORED ON HPAD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 110014

        bstd-station-inhibited-no-dsp-co  TRAP-TYPE
		ENTERPRISE   cdx6500
		VARIABLES    { cdx6500SNMPLastTrap }
		DESCRIPTION
		     "%s - STATION(%d) INHIBITED - %02X,%02X - NO DSP CONNECTION AVAILABLE"
		     --#TYPE
		     --#SUMMARY "Trap #$G, specific: $S, arg(1) : $1"
		     --#ARGUMENTS {}
		     --#SEVERITY  CRITICAL
		     --#TIMEINDEX
		     --#HELP
		     --#HELPTAG
		     --#STATE
		::= 110015

        bstd-initialization-failed-softw  TRAP-TYPE
		ENTERPRISE   cdx6500
		VARIABLES    { cdx6500SNMPLastTrap }
		DESCRIPTION
		     "%s - INITIALIZATION FAILED, SOFTWARE BUG DETECTED in %s at line %d"
		     --#TYPE
		     --#SUMMARY "Trap #$G, specific: $S, arg(1) : $1"
		     --#ARGUMENTS {}
		     --#SEVERITY  CRITICAL
		     --#TIMEINDEX
		     --#HELP
		     --#HELPTAG
		     --#STATE
		::= 110016

        xdlcL2-bad-frame-len  TRAP-TYPE
		ENTERPRISE   cdx6500
		VARIABLES    { cdx6500SNMPLastTrap }
		DESCRIPTION
		             " %s - BAD FRAME LENGTH (%d)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111001

        xdlcL2-bad-frame-type  TRAP-TYPE
		ENTERPRISE   cdx6500
		VARIABLES    { cdx6500SNMPLastTrap }
		DESCRIPTION
		             " %s - BAD FRAME TYPE (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111002

        xdlcL2-bad-n-r  TRAP-TYPE
		ENTERPRISE   cdx6500
		VARIABLES    { cdx6500SNMPLastTrap }
		DESCRIPTION
		             " %s - BAD N(R) (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111003

        xdlcL2-addr-error  TRAP-TYPE
		ENTERPRISE   cdx6500
		VARIABLES    { cdx6500SNMPLastTrap }
		DESCRIPTION
		             " %s - ADDRESS ERROR (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111004

        xdlcL2-norm-seq-frmr  TRAP-TYPE
		ENTERPRISE   cdx6500
		VARIABLES    { cdx6500SNMPLastTrap }
		DESCRIPTION
		             " %s - FRMR (%02X/%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111005

        xdlcL2-stn-disconnect  TRAP-TYPE
		ENTERPRISE   cdx6500
		VARIABLES    { cdx6500SNMPLastTrap }
		DESCRIPTION
		             "%s - STATION REQUESTED DISCONNECT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111006

        xdlcL2-mx25-stn-down  TRAP-TYPE
		ENTERPRISE   cdx6500
		VARIABLES    { cdx6500SNMPLastTrap }
		DESCRIPTION
		             "%s - MX25 STATION DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111007

        xdlcL2-mx25-stn-up  TRAP-TYPE
		ENTERPRISE   cdx6500
		VARIABLES    { cdx6500SNMPLastTrap }
		DESCRIPTION
		             "%s - MX25 STATION UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111008

        xdlcL2-multiple-masters  TRAP-TYPE
		ENTERPRISE   cdx6500
		VARIABLES    { cdx6500SNMPLastTrap }
		DESCRIPTION
		             "%s - TWO MASTERS ON MULTIPOINT LINK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111009

        xdlcL2-stat-overflow  TRAP-TYPE
		ENTERPRISE   cdx6500
		VARIABLES    { cdx6500SNMPLastTrap }
		DESCRIPTION
		             "%s - %s STAT OVERFLOW - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111010

        xdlcL2-tpad-stn-active  TRAP-TYPE
		ENTERPRISE   cdx6500
		VARIABLES    { cdx6500SNMPLastTrap }
		DESCRIPTION
		             " %s - TPAD STATION ACTIVE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111011

        xdlcL2-tpad-stn-inactive  TRAP-TYPE
		ENTERPRISE   cdx6500
		VARIABLES    { cdx6500SNMPLastTrap }
		DESCRIPTION
		             " %s - TPAD STATION INACTIVE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111012

        xdlcL2-ovsize-frame  TRAP-TYPE
		ENTERPRISE   cdx6500
		VARIABLES    { cdx6500SNMPLastTrap }
		DESCRIPTION
		             " %s - OVERSIZE FRAME (%d) FROM REMOTE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 111013

        xdlcPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112000

        xdlcPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112001

        xdlcPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112002

        xdlcPort-disable-fail  TRAP-TYPE
		ENTERPRISE   cdx6500
		VARIABLES    { cdx6500SNMPLastTrap }
		DESCRIPTION
		             "%s - PORT DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112003

        xdlcPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112004

        xdlcPort-enable-fail  TRAP-TYPE
		ENTERPRISE   cdx6500
		VARIABLES    { cdx6500SNMPLastTrap }
		DESCRIPTION
		             "%s - PORT ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112005

        xdlcPort-stn-boot  TRAP-TYPE
		ENTERPRISE   cdx6500
		VARIABLES    { cdx6500SNMPLastTrap }
		DESCRIPTION
		             "%s - STATION BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112006

        xdlcPort-stn-boot-fail  TRAP-TYPE
		ENTERPRISE   cdx6500
		VARIABLES    { cdx6500SNMPLastTrap }
		DESCRIPTION
		             "%s - STATION BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112007

        xdlcPort-stn-disable  TRAP-TYPE
		ENTERPRISE   cdx6500
		VARIABLES    { cdx6500SNMPLastTrap }
		DESCRIPTION
		             "%s - STATION DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112008

        xdlcPort-stn-disable-fail  TRAP-TYPE
		ENTERPRISE   cdx6500
		VARIABLES    { cdx6500SNMPLastTrap }
		DESCRIPTION
		             "%s - STATION DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112009

        xdlcPort-stn-enable  TRAP-TYPE
		ENTERPRISE   cdx6500
		VARIABLES    { cdx6500SNMPLastTrap }
		DESCRIPTION
		             "%s - STATION ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112010

        xdlcPort-stn-enable-fail  TRAP-TYPE
		ENTERPRISE   cdx6500
		VARIABLES    { cdx6500SNMPLastTrap }
		DESCRIPTION
		             "%s - STATION ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112011

        xdlcPort-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112012

        xdlcPort-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112013

        xdlcPort-stn-addr-dupl  TRAP-TYPE
		ENTERPRISE   cdx6500
		VARIABLES    { cdx6500SNMPLastTrap }
		DESCRIPTION
		             "%s - STATION ADDRESS DUPLICATED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112014

        xdlcPort-stat-overflow  TRAP-TYPE
		ENTERPRISE   cdx6500
		VARIABLES    { cdx6500SNMPLastTrap }
		DESCRIPTION
		             "%s - PORT STAT OVERFLOW - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112015

        xdlcPort-stn-stat-overflow  TRAP-TYPE
		ENTERPRISE   cdx6500
		VARIABLES    { cdx6500SNMPLastTrap }
		DESCRIPTION
		             "%s - STATION STAT OVERFLOW - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112016

        xdlcPort-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112017

        xdlcPort-unsupport-frm-size  TRAP-TYPE
		ENTERPRISE   cdx6500
		VARIABLES    { cdx6500SNMPLastTrap }
		DESCRIPTION
		             " %s - UNSUPPORTED FRAME SIZE: OPERATING WITH 1024 BYTES"
                     --#TYPE
                     --#SUMMARY "Trap #$G, specific: $S, arg(1): $1"
                     --#ARGUMENTS {}
                     --#SEVERITY  INFORMATIONAL
                     --#TIMEINDEX
                     --#HELP
                     --#HELPTAG
                     --#STATE
		::= 112018

        xdlc-insufficient-memory-to-prot  TRAP-TYPE
		ENTERPRISE   cdx6500
		VARIABLES    { cdx6500SNMPLastTrap }
		DESCRIPTION
		     "%s - INSUFFICIENT MEMORY TO PROTECT STATION"
		     --#TYPE
		     --#SUMMARY "Trap #$G, specific: $S, arg(1) : $1"
		     --#ARGUMENTS {}
		     --#SEVERITY  CRITICAL
		     --#TIMEINDEX
		     --#HELP
		     --#HELPTAG
		     --#STATE
		::= 112019

	xdlc112020-xdlc-s-dy   TRAP-TYPE
		ENTERPRISE   cdx6500
		VARIABLES    { cdx6500SNMPLastTrap }
		DESCRIPTION
		     "XDLC-%dS%d - DYNAMIC STATION BOOT STARTED"
		     --#TYPE
		     --#SUMMARY "Trap #$G, specific: $S, arg(1) : $1"
		     --#ARGUMENTS {}
		     --#SEVERITY  CRITICAL
		     --#TIMEINDEX
		     --#HELP
		     --#HELPTAG
		     --#STATE
		::= 112020

	xdlc112021-xdlc-s-dy   TRAP-TYPE
		ENTERPRISE   cdx6500
		VARIABLES    { cdx6500SNMPLastTrap }
		DESCRIPTION
		     "XDLC-%dS%d - DYNAMIC STATION BEING CREATED"
		     --#TYPE
		     --#SUMMARY "Trap #$G, specific: $S, arg(1) : $1"
		     --#ARGUMENTS {}
		     --#SEVERITY  MAJOR
		     --#TIMEINDEX
		     --#HELP
		     --#HELPTAG
		     --#STATE
		::= 112021

	xdlc112022-xdlc-s-dy   TRAP-TYPE
		ENTERPRISE   cdx6500
		VARIABLES    { cdx6500SNMPLastTrap }
		DESCRIPTION
		     "XDLC-%dS%d - DYNAMIC STATION BOOT COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 112022

	xdlc112023-insuffici   TRAP-TYPE
		ENTERPRISE   cdx6500
		VARIABLES    { cdx6500SNMPLastTrap }
		DESCRIPTION
		     "%s - INSUFFICIENT MEMORY FOR CONFIGURED STATIONS"
		     --#TYPE
		     --#SUMMARY "Trap #$G, specific: $S, arg(1) : $1"
		     --#ARGUMENTS {}
		     --#SEVERITY  CRITICAL
		     --#TIMEINDEX
		     --#HELP
		     --#HELPTAG
		     --#STATE
		::= 112023

        nccpDpad-unknown-device  TRAP-TYPE
		ENTERPRISE   cdx6500
		VARIABLES    { cdx6500SNMPLastTrap }
		DESCRIPTION
		             "%s DETECTED DEVICE %d (%x hex) %s "
                     --#TYPE
                     --#SUMMARY "Trap #$G, specific: $S, arg(1): $1"
                     --#ARGUMENTS {}
                     --#SEVERITY  INFORMATIONAL
                     --#TIMEINDEX
                     --#HELP
                     --#HELPTAG
                     --#STATE
		::= 115000

        nccpDpad-crc-error  TRAP-TYPE
		ENTERPRISE   cdx6500
		VARIABLES    { cdx6500SNMPLastTrap }
		DESCRIPTION
		             " %s NCCP CRC ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 115001

        nccpDpad-streaming-device  TRAP-TYPE
		ENTERPRISE   cdx6500
		VARIABLES    { cdx6500SNMPLastTrap }
		DESCRIPTION
		             " %s HAS DETECTED A STREAMING DEVICE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 115002

        nccpDpad-stream-device-clear  TRAP-TYPE
		ENTERPRISE   cdx6500
		VARIABLES    { cdx6500SNMPLastTrap }
		DESCRIPTION
		             " %s STREAMING DEVICE CONDITION CLEARED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 115003

        nccpDpad-main-chan-fail  TRAP-TYPE
		ENTERPRISE   cdx6500
		VARIABLES    { cdx6500SNMPLastTrap }
		DESCRIPTION
		             " %s FAILED MAIN CHANNEL CONNECT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 115004

        nccpDpad-main-chan-connect  TRAP-TYPE
		ENTERPRISE   cdx6500
		VARIABLES    { cdx6500SNMPLastTrap }
		DESCRIPTION
		             " %s CONNECTED TO MAIN CHANNEL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 115005

        nccpDpad-main-chan-disconn  TRAP-TYPE
		ENTERPRISE   cdx6500
		VARIABLES    { cdx6500SNMPLastTrap }
		DESCRIPTION
		             " %s LOST MAIN CHANNEL CONNECTION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 115006

        nccpDpad-state-search-abort  TRAP-TYPE
		ENTERPRISE   cdx6500
		VARIABLES    { cdx6500SNMPLastTrap }
		DESCRIPTION
		             " %s STATE SEARCH ABORTED %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 115007

        nccpMpad-not-responding  TRAP-TYPE
		ENTERPRISE   cdx6500
		VARIABLES    { cdx6500SNMPLastTrap }
		DESCRIPTION
		             " %s - DPAD '%s' IS NON RESPONDING"
                     --#TYPE
                     --#SUMMARY "Trap #$G, specific: $S, arg(1): $1"
                     --#ARGUMENTS {}
                     --#SEVERITY  INFORMATIONAL
                     --#TIMEINDEX
                     --#HELP
                     --#HELPTAG
                     --#STATE
		::= 116000

        nccpMpad-device-status  TRAP-TYPE
		ENTERPRISE   cdx6500
		VARIABLES    { cdx6500SNMPLastTrap }
		DESCRIPTION
		             " DEVICE-STATUS %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 116001

        nccpMpad-dupl-device  TRAP-TYPE
		ENTERPRISE   cdx6500
		VARIABLES    { cdx6500SNMPLastTrap }
		DESCRIPTION
		             " %s  DUPLICATE NCCP DEVICE ent #%d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 116002

        nccpMpad-chan-conn-fail  TRAP-TYPE
		ENTERPRISE   cdx6500
		VARIABLES    { cdx6500SNMPLastTrap }
		DESCRIPTION
		             " %s FAILED MAIN CHANNEL CONNECT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 116003

        nccpMpad-chan-conn  TRAP-TYPE
		ENTERPRISE   cdx6500
		VARIABLES    { cdx6500SNMPLastTrap }
		DESCRIPTION
		             " %s CONNECTED TO MAIN CHANNEL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 116004

        nccpMpad-chan-disconn  TRAP-TYPE
		ENTERPRISE   cdx6500
		VARIABLES    { cdx6500SNMPLastTrap }
		DESCRIPTION
		             " %s LOST MAIN CHANNEL CONNECTION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 116005

        nccpMpad-proto-err  TRAP-TYPE
		ENTERPRISE   cdx6500
		VARIABLES    { cdx6500SNMPLastTrap }
		DESCRIPTION
		             " %s NCCP PROTOCOL ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 116006

        ibm2260Port-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125000

        ibm2260Port-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125001

        ibm2260Port-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125002

        ibm2260Port-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125003

        ibm2260Port-enable-fail  TRAP-TYPE
		ENTERPRISE   cdx6500
		VARIABLES    { cdx6500SNMPLastTrap }
		DESCRIPTION
		             "%s - PORT ENABLE FAILED - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125004

        ibm2260Port-inbound-err  TRAP-TYPE
		ENTERPRISE   cdx6500
		VARIABLES    { cdx6500SNMPLastTrap }
		DESCRIPTION
		             "%s - NON-RECOVERABLE INBOUND ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125005

        ibm2260Port-outbound-err  TRAP-TYPE
		ENTERPRISE   cdx6500
		VARIABLES    { cdx6500SNMPLastTrap }
		DESCRIPTION
		             "%s - NON-RECOVERABLE OUTBOUND ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125006

        ibm2260Port-line-down  TRAP-TYPE
		ENTERPRISE   cdx6500
		VARIABLES    { cdx6500SNMPLastTrap }
		DESCRIPTION
		             "%s - LINE DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125007

        ibm2260Port-line-up  TRAP-TYPE
		ENTERPRISE   cdx6500
		VARIABLES    { cdx6500SNMPLastTrap }
		DESCRIPTION
		             "%s - LINE OPERATIONAL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125008

        ibm2260Port-stn-down  TRAP-TYPE
		ENTERPRISE   cdx6500
		VARIABLES    { cdx6500SNMPLastTrap }
		DESCRIPTION
		             "%s - STATION DOWN - %02X,%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125009

        ibm2260Port-stn-up  TRAP-TYPE
		ENTERPRISE   cdx6500
		VARIABLES    { cdx6500SNMPLastTrap }
		DESCRIPTION
		             "%s - STATION OPERATIONAL - %02X,%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125010

        ibm2260Port-addr-conflict  TRAP-TYPE
		ENTERPRISE   cdx6500
		VARIABLES    { cdx6500SNMPLastTrap }
		DESCRIPTION
		             "%s - STATION(%d) INHIBITED - %02X,%02X - ADDRESS CONFLICT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125011

        ibm2260Port-poss-data-loss  TRAP-TYPE
		ENTERPRISE   cdx6500
		VARIABLES    { cdx6500SNMPLastTrap }
		DESCRIPTION
		             "%s - POSSIBLE DATA LOSS - %02X,%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 125012

        tbopPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126000

        tbopPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126001

        tbopPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126002

        tbopPort-disable-fail  TRAP-TYPE
		ENTERPRISE   cdx6500
		VARIABLES    { cdx6500SNMPLastTrap }
		DESCRIPTION
		             "%s - PORT DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126003

        tbopPort-Port-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126004

        tbopPort-enable-fail  TRAP-TYPE
		ENTERPRISE   cdx6500
		VARIABLES    { cdx6500SNMPLastTrap }
		DESCRIPTION
		             "%s - PORT ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126005

        tbopPort-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126006

        tbopPort-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126007

        tbopPort-busyout  TRAP-TYPE
		ENTERPRISE   cdx6500
		VARIABLES    { cdx6500SNMPLastTrap }
		DESCRIPTION
		             "%s - PORT BUSY-OUT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126008

        tbopPort-busyout-fail  TRAP-TYPE
		ENTERPRISE   cdx6500
		VARIABLES    { cdx6500SNMPLastTrap }
		DESCRIPTION
		             "%s - PORT BUSY-OUT-FAIL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 126009

        tbop-port-status-warning  TRAP-TYPE
		ENTERPRISE   cdx6500
		VARIABLES    { cdx6500SNMPLastTrap }
		DESCRIPTION
		     "%s - PORT STATUS WARNING - %s"
		     --#TYPE
		     --#SUMMARY "Trap #$G, specific: $S, arg(1) : $1"
		     --#ARGUMENTS {}
		     --#SEVERITY  MINOR
		     --#TIMEINDEX
		     --#HELP
		     --#HELPTAG
		     --#STATE
		::= 126010

        tbopL2-bad-frame-len  TRAP-TYPE
		ENTERPRISE   cdx6500
		VARIABLES    { cdx6500SNMPLastTrap }
		DESCRIPTION
		             " %s - BAD FRAME LENGTH (%d)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 127001

        tcop-Port-boot  TRAP-TYPE
                ENTERPRISE   cdx6500
                VARIABLES    { cdx6500SNMPLastTrap }
                DESCRIPTION
                             "%s - PORT BOOT COMPLETE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129000

        tcop-Port-boot-fail  TRAP-TYPE
                ENTERPRISE   cdx6500
                VARIABLES    { cdx6500SNMPLastTrap }
                DESCRIPTION
                             "%s - PORT BOOT FAILURE - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129001

        tcop-Port-disable  TRAP-TYPE
                ENTERPRISE   cdx6500
                VARIABLES    { cdx6500SNMPLastTrap }
                DESCRIPTION
                             "%s - PORT DISABLED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129002

        tcop-Port-disable-fail  TRAP-TYPE
                ENTERPRISE   cdx6500
                VARIABLES    { cdx6500SNMPLastTrap }
                DESCRIPTION
                             "%s - PORT DISABLE FAILURE - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129003

        tcop-Port-enable  TRAP-TYPE
                ENTERPRISE   cdx6500
                VARIABLES    { cdx6500SNMPLastTrap }
                DESCRIPTION
                             "%s - PORT ENABLED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129004

        tcop-Port-enable-fail  TRAP-TYPE
                ENTERPRISE   cdx6500
                VARIABLES    { cdx6500SNMPLastTrap }
                DESCRIPTION
                             "%s - PORT ENABLE FAILURE - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129005

        tcop-Port-util-exceeded  TRAP-TYPE
                ENTERPRISE   cdx6500
                VARIABLES    { cdx6500SNMPLastTrap }
                DESCRIPTION
                             "%s - PORT UTILIZATION > THRESHOLD"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129006

        tcop-Port-error-exceeded  TRAP-TYPE
                ENTERPRISE   cdx6500
                VARIABLES    { cdx6500SNMPLastTrap }
                DESCRIPTION
                             "%s - PORT ERROR COUNT > THRESHOLD"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129007

        tcop-Port-busy-out  TRAP-TYPE
                ENTERPRISE   cdx6500
                VARIABLES    { cdx6500SNMPLastTrap }
                DESCRIPTION
                             "%s - PORT BUSY-OUT"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129008

        tcop-Port-busy-out-fail  TRAP-TYPE
                ENTERPRISE   cdx6500
                VARIABLES    { cdx6500SNMPLastTrap }
                DESCRIPTION
                             "%s - PORT BUSY-OUT-FAIL"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129009

        tcop-Port-subtype-notsupported  TRAP-TYPE
                ENTERPRISE   cdx6500
                VARIABLES    { cdx6500SNMPLastTrap }
                DESCRIPTION
                             "%s %d- TCOP SUPPORTED ONLY ON PLUS CARDS"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 129010

        tcop-rx-queue-overflow  TRAP-TYPE
                ENTERPRISE   cdx6500
                VARIABLES    { cdx6500SNMPLastTrap }
                DESCRIPTION
                             "%s - RX MESSAGE QUEUE OVERFLOW"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 130001

        tcop-tx-queue-overflow  TRAP-TYPE
                ENTERPRISE   cdx6500
                VARIABLES    { cdx6500SNMPLastTrap }
                DESCRIPTION
                             "%s - TX MESSAGE QUEUE OVERFLOW"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 130002

        tcop-tx-timeout  TRAP-TYPE
                ENTERPRISE   cdx6500
                VARIABLES    { cdx6500SNMPLastTrap }
                DESCRIPTION
                             "%s - TRANSMITTER INACTIVITY TIMEOUT"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 130003

        tcop-threshold  TRAP-TYPE
                ENTERPRISE   cdx6500
                VARIABLES    { cdx6500SNMPLastTrap }
                DESCRIPTION
                             "%s - PORT UTILIZATION > THRESHOLD"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 130004

        bridge-init-fail  TRAP-TYPE
		ENTERPRISE   cdx6500
		VARIABLES    { cdx6500SNMPLastTrap }
		DESCRIPTION
		             "%s BRIDGE INITIALIZATION FAILURE %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 134000

        bridge-link-boot  TRAP-TYPE
		ENTERPRISE   cdx6500
		VARIABLES    { cdx6500SNMPLastTrap }
		DESCRIPTION
		             "%s BRIDGE LINK BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 134001

        bridge-link-boot-fail  TRAP-TYPE
		ENTERPRISE   cdx6500
		VARIABLES    { cdx6500SNMPLastTrap }
		DESCRIPTION
		             "%s BRIDGE LINK BOOT FAILURE %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 134002

        bridge-link-enabled  TRAP-TYPE
		ENTERPRISE   cdx6500
		VARIABLES    { cdx6500SNMPLastTrap }
		DESCRIPTION
		             "%s BRIDGE LINK ENABLE COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 134003

        bridge-link-disabled  TRAP-TYPE
		ENTERPRISE   cdx6500
		VARIABLES    { cdx6500SNMPLastTrap }
		DESCRIPTION
		             "%s BRIDGE LINK DISABLE COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 134004

        bridge-param-boot  TRAP-TYPE
		ENTERPRISE   cdx6500
		VARIABLES    { cdx6500SNMPLastTrap }
		DESCRIPTION
		             "%s BRIDGE PARAMETERS BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 134005

        bridge-param-boot-fail  TRAP-TYPE
		ENTERPRISE   cdx6500
		VARIABLES    { cdx6500SNMPLastTrap }
		DESCRIPTION
		             "%s BRIDGE PARAMETERS BOOT FAILURE %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 134006

        bridge-link-out-of-range  TRAP-TYPE
		ENTERPRISE   cdx6500
		VARIABLES    { cdx6500SNMPLastTrap }
		DESCRIPTION
		             "%s EXCEEDING MAXIMUM RANGE ALLOWED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 134007

        sr-ring-num-mismatch  TRAP-TYPE
		ENTERPRISE   cdx6500
		VARIABLES    { cdx6500SNMPLastTrap }
		DESCRIPTION
		             "BR-%d RING NUMBER MISMATCH LOCAL=%d REMOTE=%d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 136000

        sr-bridge-id-mismatch  TRAP-TYPE
		ENTERPRISE   cdx6500
		VARIABLES    { cdx6500SNMPLastTrap }
		DESCRIPTION
		             "BR-%d BRIDGE ID MISMATCH"
                     --#TYPE
                     --#SUMMARY "Trap #$G, specific: $S, arg(1): $1"
                     --#ARGUMENTS {}
                     --#SEVERITY  INFORMATIONAL
                     --#TIMEINDEX
                     --#HELP
                     --#HELPTAG
                     --#STATE
		::= 136001

        sr-dupl-rbr-triplet  TRAP-TYPE
		ENTERPRISE   cdx6500
		VARIABLES    { cdx6500SNMPLastTrap }
		DESCRIPTION
		             "BR-%d DUPLICATE RBR TRIPLET"
                     --#TYPE
                     --#SUMMARY "Trap #$G, specific: $S, arg(1): $1"
                     --#ARGUMENTS {}
                     --#SEVERITY  INFORMATIONAL
                     --#TIMEINDEX
                     --#HELP
                     --#HELPTAG
                     --#STATE
		::= 136002

        sr-incompat-link-mode  TRAP-TYPE
		ENTERPRISE   cdx6500
		VARIABLES    { cdx6500SNMPLastTrap }
		DESCRIPTION
		             "BR-%d INCOMPATIBLE LINK MODE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 136003

        include-br-one-trans-link-allowe  TRAP-TYPE
		ENTERPRISE   cdx6500
		VARIABLES    { cdx6500SNMPLastTrap }
		DESCRIPTION
		     "BR-%d ONE TRANS LINK ALLOWED PER NODE"
		     --#TYPE
		     --#SUMMARY "Trap #$G, specific: $S, arg(1) : $1"
		     --#ARGUMENTS {}
		     --#SEVERITY  CRITICAL
		     --#TIMEINDEX
		     --#HELP
		     --#HELPTAG
		     --#STATE
		::= 136004

        sr-duplicate-token-ring  TRAP-TYPE
		ENTERPRISE   cdx6500
		VARIABLES    { cdx6500SNMPLastTrap }
		DESCRIPTION
		     "TR-%d PORT DUPLICATE TOKEN RING NUMBERS"
		     --#TYPE
		     --#SUMMARY "Trap #$G, specific: $S, arg(1) : $1"
		     --#ARGUMENTS {}
		     --#SEVERITY  CRITICAL
		     --#TIMEINDEX
		     --#HELP
		     --#HELPTAG
		     --#STATE
		::= 136005

        stp-unknown-bpdu-type  TRAP-TYPE
		ENTERPRISE   cdx6500
		VARIABLES    { cdx6500SNMPLastTrap }
		DESCRIPTION
		             " link %d - UNKNOWN STP BPDU received"
                     --#TYPE
                     --#SUMMARY "Trap #$G, specific: $S, arg(1): $1"
                     --#ARGUMENTS {}
                     --#SEVERITY  INFORMATIONAL
                     --#TIMEINDEX
                     --#HELP
                     --#HELPTAG
                     --#STATE
		::= 137000

        stp-bridge-is-root  TRAP-TYPE
		ENTERPRISE   cdx6500
		VARIABLES    { cdx6500SNMPLastTrap }
		DESCRIPTION
		             " BRIDGE IS THE ROOT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 137001

        stp-bridge-is-not-root  TRAP-TYPE
		ENTERPRISE   cdx6500
		VARIABLES    { cdx6500SNMPLastTrap }
		DESCRIPTION
		             " BRIDGE IS NOT THE ROOT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 137002

        stp-topo-unstable  TRAP-TYPE
		ENTERPRISE   cdx6500
		VARIABLES    { cdx6500SNMPLastTrap }
		DESCRIPTION
		             " TOPOLOGY UNSTABLE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 137003

        stp-topo-stable  TRAP-TYPE
		ENTERPRISE   cdx6500
		VARIABLES    { cdx6500SNMPLastTrap }
		DESCRIPTION
		             " TOPOLOGY STABLE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 137004

        stp-config-buff-not-avail  TRAP-TYPE
		ENTERPRISE   cdx6500
		VARIABLES    { cdx6500SNMPLastTrap }
		DESCRIPTION
		             "BUFFER NOT AVAILABLE FOR STP CONFIG BPDUs"
                     --#TYPE
                     --#SUMMARY "Trap #$G, specific: $S, arg(1): $1"
                     --#ARGUMENTS {}
                     --#SEVERITY  INFORMATIONAL
                     --#TIMEINDEX
                     --#HELP
                     --#HELPTAG
                     --#STATE
		::= 137005

        stp-tcn-buff-not-avail  TRAP-TYPE
		ENTERPRISE   cdx6500
		VARIABLES    { cdx6500SNMPLastTrap }
		DESCRIPTION
		             "BUFFER NOT AVAILABLE FOR STP TCN BPDUs"
                     --#TYPE
                     --#SUMMARY "Trap #$G, specific: $S, arg(1): $1"
                     --#ARGUMENTS {}
                     --#SEVERITY  INFORMATIONAL
                     --#TIMEINDEX
                     --#HELP
                     --#HELPTAG
                     --#STATE
		::= 137006

        trPort-reset-fail  TRAP-TYPE
		ENTERPRISE   cdx6500
		VARIABLES    { cdx6500SNMPLastTrap }
		DESCRIPTION
		             "TR-%d PORT INITIALIZATION FAILURE TMS380 RESET FAILED %x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138000

        trPort-chip-init-fail  TRAP-TYPE
		ENTERPRISE   cdx6500
		VARIABLES    { cdx6500SNMPLastTrap }
		DESCRIPTION
		             "TR-%d PORT INITIALIZATION FAILURE TMS380 INIT FAILED %x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138001

        trPort-open-fail  TRAP-TYPE
		ENTERPRISE   cdx6500
		VARIABLES    { cdx6500SNMPLastTrap }
		DESCRIPTION
		             "TR-%d PORT INITIALIZATION FAILURE TMS380 OPEN FAILED %x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138002

        trPort-Port-init  TRAP-TYPE
		ENTERPRISE   cdx6500
		VARIABLES    { cdx6500SNMPLastTrap }
		DESCRIPTION
		             "TR-%d PORT INITIALIZATION SUCCESSFUL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138003

        trPort-rx-cmd-timeout  TRAP-TYPE
		ENTERPRISE   cdx6500
		VARIABLES    { cdx6500SNMPLastTrap }
		DESCRIPTION
		             "TR-%d RX COMMAND TIMED OUT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138004

        trPort-tx-cmd-timeout  TRAP-TYPE
		ENTERPRISE   cdx6500
		VARIABLES    { cdx6500SNMPLastTrap }
		DESCRIPTION
		             "TR-%d TX COMMAND TIMED OUT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138005

        trPort-loss-of-signal  TRAP-TYPE
		ENTERPRISE   cdx6500
		VARIABLES    { cdx6500SNMPLastTrap }
		DESCRIPTION
		             " TR-%d LOSS OF SIGNAL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138006

        trPort-loss-of-signal-clear  TRAP-TYPE
		ENTERPRISE   cdx6500
		VARIABLES    { cdx6500SNMPLastTrap }
		DESCRIPTION
		             " TR-%d LOSS OF SIGNAL CLEARED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138007

        trPort-beacon  TRAP-TYPE
		ENTERPRISE   cdx6500
		VARIABLES    { cdx6500SNMPLastTrap }
		DESCRIPTION
		             " TR-%d BEACON CONDITION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138008

        trPort-beacon-clear  TRAP-TYPE
		ENTERPRISE   cdx6500
		VARIABLES    { cdx6500SNMPLastTrap }
		DESCRIPTION
		             " TR-%d BEACON CONDITION CLEARED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138009

        trPort-tx-beacon  TRAP-TYPE
		ENTERPRISE   cdx6500
		VARIABLES    { cdx6500SNMPLastTrap }
		DESCRIPTION
		             " TR-%d TX BEACON CONDITION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138010

        trPort-tx-beacon-clear  TRAP-TYPE
		ENTERPRISE   cdx6500
		VARIABLES    { cdx6500SNMPLastTrap }
		DESCRIPTION
		             " TR-%d TX BEACON CONDITION CLEARED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138011

        trPort-tx-halted  TRAP-TYPE
		ENTERPRISE   cdx6500
		VARIABLES    { cdx6500SNMPLastTrap }
		DESCRIPTION
		             " TR-%d TX HALTED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138012

        trPort-cmd-reject  TRAP-TYPE
		ENTERPRISE   cdx6500
		VARIABLES    { cdx6500SNMPLastTrap }
		DESCRIPTION
		             " TR-%d COMMAND REJECT %x (%x)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138013

        trPort-lobe-error  TRAP-TYPE
		ENTERPRISE   cdx6500
		VARIABLES    { cdx6500SNMPLastTrap }
		DESCRIPTION
		             " TR-%d LOBE WIRE FAULT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138014

        trPort-auto-remove-err  TRAP-TYPE
		ENTERPRISE   cdx6500
		VARIABLES    { cdx6500SNMPLastTrap }
		DESCRIPTION
		             " TR-%d AUTO REMOVE ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138015

        trPort-remove-rcvd  TRAP-TYPE
		ENTERPRISE   cdx6500
		VARIABLES    { cdx6500SNMPLastTrap }
		DESCRIPTION
		             " TR-%d REMOVE RECEIVED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138016

        trPort-not-disabled  TRAP-TYPE
		ENTERPRISE   cdx6500
		VARIABLES    { cdx6500SNMPLastTrap }
		DESCRIPTION
		             " TR-%d PORT NOT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138017

        trPort-cmd-timeout  TRAP-TYPE
		ENTERPRISE   cdx6500
		VARIABLES    { cdx6500SNMPLastTrap }
		DESCRIPTION
		             "TR-%d PORT CMD TIMEOUT %x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138018

        trPort-fatal-err  TRAP-TYPE
		ENTERPRISE   cdx6500
		VARIABLES    { cdx6500SNMPLastTrap }
		DESCRIPTION
		             "TR-%d FATAL ERROR %x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138019

        trPort-single-stn-err  TRAP-TYPE
		ENTERPRISE   cdx6500
		VARIABLES    { cdx6500SNMPLastTrap }
		DESCRIPTION
		             " TR-%d SINGLE STATION ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138020

        trPort-up  TRAP-TYPE
		ENTERPRISE   cdx6500
		VARIABLES    { cdx6500SNMPLastTrap }
		DESCRIPTION
		             "TR-%d PORT UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138021

        trPort-down  TRAP-TYPE
		ENTERPRISE   cdx6500
		VARIABLES    { cdx6500SNMPLastTrap }
		DESCRIPTION
		             "TR-%d PORT DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138022

        trPort-trans-err  TRAP-TYPE
		ENTERPRISE   cdx6500
		VARIABLES    { cdx6500SNMPLastTrap }
		DESCRIPTION
		             "TR-%d TRANSMIT ERROR p0=%x p1=%x p2=%x dp=%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138023

        trPort-unkn-trans-err  TRAP-TYPE
		ENTERPRISE   cdx6500
		VARIABLES    { cdx6500SNMPLastTrap }
		DESCRIPTION
		             "TR-%d TRANSMIT ERROR 2 p0=%x p1=%x p2=%x dp=%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138024

        trPort-diag-check  TRAP-TYPE
		ENTERPRISE   cdx6500
		VARIABLES    { cdx6500SNMPLastTrap }
		DESCRIPTION
		             "TR-%d DIAGNOSTIC CHECK %x cb=%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 138025

        trd-tr-diagnostic-check-cb  TRAP-TYPE
		ENTERPRISE   cdx6500
		VARIABLES    { cdx6500SNMPLastTrap }
		DESCRIPTION
		     "TR-%d DIAGNOSTIC CHECK %x cb=%x"
		     --#TYPE
		     --#SUMMARY "Trap #$G, specific: $S, arg(1) : $1"
		     --#ARGUMENTS {}
		     --#SEVERITY  CRITICAL
		     --#TIMEINDEX
		     --#HELP
		     --#HELPTAG
		     --#STATE
		::= 138026

        trPort-boot  TRAP-TYPE
		ENTERPRISE   cdx6500
		VARIABLES    { cdx6500SNMPLastTrap }
		DESCRIPTION
		             "%s PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 139000

        trPort-boot-fail  TRAP-TYPE
		ENTERPRISE   cdx6500
		VARIABLES    { cdx6500SNMPLastTrap }
		DESCRIPTION
		             "%s PORT BOOT FAILURE %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 139001

        trPort-enable  TRAP-TYPE
		ENTERPRISE   cdx6500
		VARIABLES    { cdx6500SNMPLastTrap }
		DESCRIPTION
		             "%s PORT ENABLED COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 139002

        trPort-disable  TRAP-TYPE
		ENTERPRISE   cdx6500
		VARIABLES    { cdx6500SNMPLastTrap }
		DESCRIPTION
		             "%s PORT DISABLE COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 139003

        trPort-init-fail  TRAP-TYPE
		ENTERPRISE   cdx6500
		VARIABLES    { cdx6500SNMPLastTrap }
		DESCRIPTION
		             "%s PORT INITIALIZATION FAILURE %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 139004

        trPort-ring-num-cfg-err  TRAP-TYPE
		ENTERPRISE   cdx6500
		VARIABLES    { cdx6500SNMPLastTrap }
		DESCRIPTION
		             "%s RING NUMBER CONFIGURATION ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 139005

        hdwareAccel-comm-fail  TRAP-TYPE
		ENTERPRISE   cdx6500
		VARIABLES    { cdx6500SNMPLastTrap }
		DESCRIPTION
		             " Port %s CPU - HA Communications Failure %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 141000

        hdwareAccel-ha-warn  TRAP-TYPE
		ENTERPRISE   cdx6500
		VARIABLES    { cdx6500SNMPLastTrap }
		DESCRIPTION
		             " Port %s HA Warning: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 141001

        hdwareAccel-test  TRAP-TYPE
		ENTERPRISE   cdx6500
		VARIABLES    { cdx6500SNMPLastTrap }
		DESCRIPTION
		             " Test: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 141002

        agent-coldstart  TRAP-TYPE
		ENTERPRISE   cdx6500
		VARIABLES    { cdx6500SNMPLastTrap }
		DESCRIPTION
		             " %s - SNMP Agent Cold Start"
                     --#TYPE
                     --#SUMMARY "Trap #$G, specific: $S, arg(1): $1"
                     --#ARGUMENTS {}
                     --#SEVERITY  INFORMATIONAL
                     --#TIMEINDEX
                     --#HELP
                     --#HELPTAG
                     --#STATE
		::= 151000

        agent-warmstart  TRAP-TYPE
		ENTERPRISE   cdx6500
		VARIABLES    { cdx6500SNMPLastTrap }
		DESCRIPTION
		             " %s - SNMP Agent Warm Start"
                     --#TYPE
                     --#SUMMARY "Trap #$G, specific: $S, arg(1): $1"
                     --#ARGUMENTS {}
                     --#SEVERITY  INFORMATIONAL
                     --#TIMEINDEX
                     --#HELP
                     --#HELPTAG
                     --#STATE
		::= 151001

        agent-chan-conn-up  TRAP-TYPE
		ENTERPRISE   cdx6500
		VARIABLES    { cdx6500SNMPLastTrap }
		DESCRIPTION
		             " %s CONNECTED TO MAIN CHANNEL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 151002

        agent-chan-conn-down  TRAP-TYPE
		ENTERPRISE   cdx6500
		VARIABLES    { cdx6500SNMPLastTrap }
		DESCRIPTION
		             " %s LOST MAIN CHANNEL CONNECTION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 151003

        agent-missing-module  TRAP-TYPE
		ENTERPRISE   cdx6500
		VARIABLES    { cdx6500SNMPLastTrap }
		DESCRIPTION
		             "  %s MISSING MODULE FOR OID %s, PID %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 151004

        agent-missing-aaf  TRAP-TYPE
		ENTERPRISE   cdx6500
		VARIABLES    { cdx6500SNMPLastTrap }
		DESCRIPTION
		             "  %s MISSING AAF FOR OID %s, PID %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 151005

        agent-auth-fail  TRAP-TYPE
		ENTERPRISE   cdx6500
		VARIABLES    { cdx6500SNMPLastTrap }
		DESCRIPTION
		             " %s AUTHENTICATION FAILURE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 151006

        agent-wrong-pointer  TRAP-TYPE
                ENTERPRISE   cdx6500
                VARIABLES    { cdx6500SNMPLastTrap }
                DESCRIPTION
                             " %s WRONG POINTER PASSED IN"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 151007

        snmpmgr-snmp-manager-is-restarti  TRAP-TYPE
		ENTERPRISE   cdx6500
		VARIABLES    { cdx6500SNMPLastTrap }
		DESCRIPTION
		     " %s - SNMP Manager is Restarting"
		     --#TYPE
		     --#SUMMARY "Trap #$G, specific: $S, arg(1) : $1"
		     --#ARGUMENTS {}
		     --#SEVERITY  CRITICAL
		     --#TIMEINDEX
		     --#HELP
		     --#HELPTAG
		     --#STATE
		::= 152000

        snmpmgr-failed-main-channel-conn  TRAP-TYPE
		ENTERPRISE   cdx6500
		VARIABLES    { cdx6500SNMPLastTrap }
		DESCRIPTION
		     " %s FAILED MAIN CHANNEL CONNECT"
		     --#TYPE
		     --#SUMMARY "Trap #$G, specific: $S, arg(1) : $1"
		     --#ARGUMENTS {}
		     --#SEVERITY  CRITICAL
		     --#TIMEINDEX
		     --#HELP
		     --#HELPTAG
		     --#STATE
		::= 152001

        snmpmgr-connected-to-main-channe  TRAP-TYPE
		ENTERPRISE   cdx6500
		VARIABLES    { cdx6500SNMPLastTrap }
		DESCRIPTION
		     " %s CONNECTED TO MAIN CHANNEL"
		     --#TYPE
		     --#SUMMARY "Trap #$G, specific: $S, arg(1) : $1"
		     --#ARGUMENTS {}
		     --#SEVERITY  CRITICAL
		     --#TIMEINDEX
		     --#HELP
		     --#HELPTAG
		     --#STATE
		::= 152002

        snmpmgr-lost-main-channel-connec  TRAP-TYPE
		ENTERPRISE   cdx6500
		VARIABLES    { cdx6500SNMPLastTrap }
		DESCRIPTION
		     " %s LOST MAIN CHANNEL CONNECTION"
		     --#TYPE
		     --#SUMMARY "Trap #$G, specific: $S, arg(1) : $1"
		     --#ARGUMENTS {}
		     --#SEVERITY  CRITICAL
		     --#TIMEINDEX
		     --#HELP
		     --#HELPTAG
		     --#STATE
		::= 152003

        snmpmgr-connected-to-pms-channel  TRAP-TYPE
		ENTERPRISE   cdx6500
		VARIABLES    { cdx6500SNMPLastTrap }
		DESCRIPTION
		     " %s CONNECTED TO PMS CHANNEL"
		     --#TYPE
		     --#SUMMARY "Trap #$G, specific: $S, arg(1) : $1"
		     --#ARGUMENTS {}
		     --#SEVERITY  CRITICAL
		     --#TIMEINDEX
		     --#HELP
		     --#HELPTAG
		     --#STATE
		::= 152004

        snmpmgr-lost-pms-channel-connect  TRAP-TYPE
		ENTERPRISE   cdx6500
		VARIABLES    { cdx6500SNMPLastTrap }
		DESCRIPTION
		     " %s LOST PMS CHANNEL CONNECTION"
		     --#TYPE
		     --#SUMMARY "Trap #$G, specific: $S, arg(1) : $1"
		     --#ARGUMENTS {}
		     --#SEVERITY  CRITICAL
		     --#TIMEINDEX
		     --#HELP
		     --#HELPTAG
		     --#STATE
		::= 152005

        snmpconn-snmp-connection-is-rest  TRAP-TYPE
		ENTERPRISE   cdx6500
		VARIABLES    { cdx6500SNMPLastTrap }
		DESCRIPTION
		     " SNMP CONNection is Restarting"
		     --#TYPE
		     --#SUMMARY "Trap #$G, specific: $S, arg(1) : $1"
		     --#ARGUMENTS {}
		     --#SEVERITY  CRITICAL
		     --#TIMEINDEX
		     --#HELP
		     --#HELPTAG
		     --#STATE
		::= 153000

        snmpconn-cannot-get-memory  TRAP-TYPE
		ENTERPRISE   cdx6500
		VARIABLES    { cdx6500SNMPLastTrap }
		DESCRIPTION
		     " SNMP CONNection FLOW CONTROL (cannot get memory)"
		     --#TYPE
		     --#SUMMARY "Trap #$G, specific: $S, arg(1) : $1"
		     --#ARGUMENTS {}
		     --#SEVERITY  CRITICAL
		     --#TIMEINDEX
		     --#HELP
		     --#HELPTAG
		     --#STATE
		::= 153001

        snmpconn-cannot-get-iorb  TRAP-TYPE
		ENTERPRISE   cdx6500
		VARIABLES    { cdx6500SNMPLastTrap }
		DESCRIPTION
		     " SNMP CONNection FLOW CONTROL (cannot get IORB)"
		     --#TYPE
		     --#SUMMARY "Trap #$G, specific: $S, arg(1) : $1"
		     --#ARGUMENTS {}
		     --#SEVERITY  CRITICAL
		     --#TIMEINDEX
		     --#HELP
		     --#HELPTAG
		     --#STATE
		::= 153002

        snmpconn-cannot-get-dbuffer  TRAP-TYPE
		ENTERPRISE   cdx6500
		VARIABLES    { cdx6500SNMPLastTrap }
		DESCRIPTION
		     " SNMP CONNection FLOW CONTROL (cannot get DBUFFER)"
		     --#TYPE
		     --#SUMMARY "Trap #$G, specific: $S, arg(1) : $1"
		     --#ARGUMENTS {}
		     --#SEVERITY  CRITICAL
		     --#TIMEINDEX
		     --#HELP
		     --#HELPTAG
		     --#STATE
		::= 153003

        ret-high-priority-traps  TRAP-TYPE
		ENTERPRISE   cdx6500
		VARIABLES    { cdx6500SNMPLastTrap }
		DESCRIPTION
		             "ROUTER,ETH PORT,TKR PORT subsystems high priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 154000

        ret-med-priority-traps  TRAP-TYPE
		ENTERPRISE   cdx6500
		VARIABLES    { cdx6500SNMPLastTrap }
		DESCRIPTION
		             " ROUTER,ETH PORT,TKR PORT subsystems medium priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 154001

        ret-low-priority-traps  TRAP-TYPE
		ENTERPRISE   cdx6500
		VARIABLES    { cdx6500SNMPLastTrap }
		DESCRIPTION
		             " ROUTER,ETH PORT,TKR PORT subsystems low priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 154002

        lclTermi-invalid-frame  TRAP-TYPE
		ENTERPRISE   cdx6500
		VARIABLES    { cdx6500SNMPLastTrap }
		DESCRIPTION
		             " LLC LT: INVALID FRAME (%s) RCVD FROM %sLOC MAC/SAP %s/%02X, REM MAC/SAP %s/%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 155000

        lclTermi-ssn-not-started  TRAP-TYPE
		ENTERPRISE   cdx6500
		VARIABLES    { cdx6500SNMPLastTrap }
		DESCRIPTION
		             " LLC LT: SESSION NOT STARTED %03u LOC MAC/SAP %s/%02X, REM MAC/SAP %s/%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 155001

        lclTermi-ssn-started  TRAP-TYPE
		ENTERPRISE   cdx6500
		VARIABLES    { cdx6500SNMPLastTrap }
		DESCRIPTION
		             " LLC LT: SESSION %02u STARTED - BL %u LOC MAC/SAP %s/%02X, REM MAC/SAP %s/%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 155002

        lclTermi-ssn-terminated  TRAP-TYPE
		ENTERPRISE   cdx6500
		VARIABLES    { cdx6500SNMPLastTrap }
		DESCRIPTION
		             " LLC LT: SESSION %02u TERMINATED %03u - BL %u LOC MAC/SAP %s/%02X, REM MAC/SAP %s/%02X"
                     --#TYPE
                     --#SUMMARY "Trap #$G, specific: $S, arg(1): $1"
                     --#ARGUMENTS {}
                     --#SEVERITY  INFORMATIONAL
                     --#TIMEINDEX
                     --#HELP
                     --#HELPTAG
                     --#STATE
		::= 155003

        lcon-config-err  TRAP-TYPE
		ENTERPRISE   cdx6500
		VARIABLES    { cdx6500SNMPLastTrap }
		DESCRIPTION
		             "%s - CONFIG ERROR - %s %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156000

        lcon-disabled  TRAP-TYPE
		ENTERPRISE   cdx6500
		VARIABLES    { cdx6500SNMPLastTrap }
		DESCRIPTION
		             "%s - LAN CONNECTION DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156001

        lcon-enabled  TRAP-TYPE
		ENTERPRISE   cdx6500
		VARIABLES    { cdx6500SNMPLastTrap }
		DESCRIPTION
		             "%s - LAN CONNECTION ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156002

        lcon-disable-fail  TRAP-TYPE
		ENTERPRISE   cdx6500
		VARIABLES    { cdx6500SNMPLastTrap }
		DESCRIPTION
		             "%s - LAN CONNECTION DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156003

        lcon-enable-fail  TRAP-TYPE
		ENTERPRISE   cdx6500
		VARIABLES    { cdx6500SNMPLastTrap }
		DESCRIPTION
		             "%s - LAN CONNECTION ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156004

        lcon-booted  TRAP-TYPE
		ENTERPRISE   cdx6500
		VARIABLES    { cdx6500SNMPLastTrap }
		DESCRIPTION
		             "%s - LAN CONNECTION BOOTED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156005

        lcon-boot-fail  TRAP-TYPE
		ENTERPRISE   cdx6500
		VARIABLES    { cdx6500SNMPLastTrap }
		DESCRIPTION
		             "%s - LAN CONNECTION BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156006

        lcon-create-fail  TRAP-TYPE
		ENTERPRISE   cdx6500
		VARIABLES    { cdx6500SNMPLastTrap }
		DESCRIPTION
                             "%s - LAN CONNECTION CREATION FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 156007

        lcon-group-config-error  TRAP-TYPE
                ENTERPRISE   cdx6500
                VARIABLES    { cdx6500SNMPLastTrap }
                DESCRIPTION
		             "%s - CONFIG ERROR - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156008

        lcon-nexthop-config-err  TRAP-TYPE
		ENTERPRISE   cdx6500
		VARIABLES    { cdx6500SNMPLastTrap }
		DESCRIPTION
		             "%s - CONFIG ERROR - %s %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156009

        lcon-out-of-range  TRAP-TYPE
		ENTERPRISE   cdx6500
		VARIABLES    { cdx6500SNMPLastTrap }
		DESCRIPTION
		             "%s - EXCEEDING MAXIMUM RANGE ALLOWED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 156010

        wa-protocol-priority-profile-ent  TRAP-TYPE
		ENTERPRISE   cdx6500
		VARIABLES    { cdx6500SNMPLastTrap }
		DESCRIPTION
		     "Protocol Priority Profile Entry %d in LCON-%d not found"
		     --#TYPE
		     --#SUMMARY "Trap #$G, specific: $S, arg(1) : $1"
		     --#ARGUMENTS {}
		     --#SEVERITY  CRITICAL
		     --#TIMEINDEX
		     --#HELP
		     --#HELPTAG
		     --#STATE
		::= 156011

        wa-precedence-array-assignments  TRAP-TYPE
		ENTERPRISE   cdx6500
		VARIABLES    { cdx6500SNMPLastTrap }
		DESCRIPTION
		     "Precedence Array Assignments = %d  %d  %d  %d"
		     --#TYPE
		     --#SUMMARY "Trap #$G, specific: $S, arg(1) : $1"
		     --#ARGUMENTS {}
		     --#SEVERITY  CRITICAL
		     --#TIMEINDEX
		     --#HELP
		     --#HELPTAG
		     --#STATE
		::= 156012

        wsl-Port-boot  TRAP-TYPE
                ENTERPRISE   cdx6500
                VARIABLES    { cdx6500SNMPLastTrap }
                DESCRIPTION
                             "%s - WSL BOOT COMPLETE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 157000

        lcon-creation-fail  TRAP-TYPE
		ENTERPRISE   cdx6500
		VARIABLES    { cdx6500SNMPLastTrap }
		DESCRIPTION
		             "%s - LAN CONNECTION CREATION FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 157001

        wsl-not-monitored  TRAP-TYPE
                ENTERPRISE   cdx6500
                VARIABLES    { cdx6500SNMPLastTrap }
                DESCRIPTION
                             "%s IS NOT MONITORED BY BOD, NO PARALLEL LCON CREATED"
                     --#TYPE
	             --#SUMMARY "Trap #$G, specific: $S, arg(1): $1"
	             --#ARGUMENTS {}
	             --#SEVERITY  INFORMATIONAL
	             --#TIMEINDEX
	             --#HELP
	             --#HELPTAG
	             --#STATE
               ::= 157002

        lcon-bad-hello-thresh  TRAP-TYPE
		ENTERPRISE   cdx6500
		VARIABLES    { cdx6500SNMPLastTrap }
		DESCRIPTION
		             "%s - STPE BAD HELLO THRESHOLD EXCEEDED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 159000

        lcon-invalid-id  TRAP-TYPE
		ENTERPRISE   cdx6500
		VARIABLES    { cdx6500SNMPLastTrap }
		DESCRIPTION
		             "%s - RECEIVED INVALID FORWARDER ID FROM THE WAN LINK %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 159001

        sram-high-prior-traps  TRAP-TYPE
		ENTERPRISE   cdx6500
		VARIABLES    { cdx6500SNMPLastTrap }
		DESCRIPTION
		             "ROUTER,ETH PORT,TKR PORT subsystems SRAM related high priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 162000

        sram-med-prior-traps  TRAP-TYPE
		ENTERPRISE   cdx6500
		VARIABLES    { cdx6500SNMPLastTrap }
		DESCRIPTION
		             " ROUTER,ETH PORT,TKR PORT subsystems SRAM related medium priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 162001

        sram-low-prior-traps  TRAP-TYPE
		ENTERPRISE   cdx6500
		VARIABLES    { cdx6500SNMPLastTrap }
		DESCRIPTION
		             " ROUTER,ETH PORT,TKR PORT subsystems SRAM related low priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 162002

        node-record-boot-fail  TRAP-TYPE
		ENTERPRISE   cdx6500
		VARIABLES    { cdx6500SNMPLastTrap }
		DESCRIPTION
		             "NODE RECORD BOOT FAILED,CAUSE:%s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 173000

        ethPort-no-throttle-timers  TRAP-TYPE
		ENTERPRISE   cdx6500
		VARIABLES    { cdx6500SNMPLastTrap }
		DESCRIPTION
		             " Enet%d - Bus Throttle Timers wouldn't load."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174000

        ethPort-no-initialization  TRAP-TYPE
                ENTERPRISE   cdx6500
                VARIABLES    { cdx6500SNMPLastTrap }
                DESCRIPTION
                             " Enet%d - The initialization didn't complete. "
                     --#TYPE
                     --#SUMMARY "Trap #$G, specific: $S, arg(1): $1"
                     --#ARGUMENTS {}
                     --#SEVERITY  INFORMATIONAL
                     --#TIMEINDEX
                     --#HELP
                     --#HELPTAG
                     --#STATE
                ::= 174001

        ethPort-config-fail  TRAP-TYPE
		ENTERPRISE   cdx6500
		VARIABLES    { cdx6500SNMPLastTrap }
		DESCRIPTION
		             " Enet%d - The Configuration command failed."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174002

        ethPort-ia-fail  TRAP-TYPE
		ENTERPRISE   cdx6500
		VARIABLES    { cdx6500SNMPLastTrap }
		DESCRIPTION
		             " Enet%d - The individual address command failed."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174003

        ethPort-configuration-timeout  TRAP-TYPE
                ENTERPRISE   cdx6500
                VARIABLES    { cdx6500SNMPLastTrap }
                DESCRIPTION
                             " Enet%d - The Configuration command timed out. "
                     --#TYPE
                     --#SUMMARY "Trap #$G, specific: $S, arg(1): $1"
                     --#ARGUMENTS {}
                     --#SEVERITY  INFORMATIONAL
                     --#TIMEINDEX
                     --#HELP
                     --#HELPTAG
                     --#STATE
                ::= 174004

        ethPort-no-suspension  TRAP-TYPE
		ENTERPRISE   cdx6500
		VARIABLES    { cdx6500SNMPLastTrap }
		DESCRIPTION
		             " Enet%d - The 82596 failed to suspend operation."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174005

        ethPort-tx-put-fail  TRAP-TYPE
		ENTERPRISE   cdx6500
		VARIABLES    { cdx6500SNMPLastTrap }
		DESCRIPTION
		             " Enet%d - Adding to the Transmit queue failed."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174006

        ethPort-excess-tx-err  TRAP-TYPE
		ENTERPRISE   cdx6500
		VARIABLES    { cdx6500SNMPLastTrap }
		DESCRIPTION
		             " Enet%d - Excessive TX Error Condition SET."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174007

        ethPort-loc  TRAP-TYPE
		ENTERPRISE   cdx6500
		VARIABLES    { cdx6500SNMPLastTrap }
		DESCRIPTION
		             " Enet%d - Loss of Carrier Condition SET."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174008

        ethPort-excess-rx-err  TRAP-TYPE
		ENTERPRISE   cdx6500
		VARIABLES    { cdx6500SNMPLastTrap }
		DESCRIPTION
		             " Enet%d - Excessive RX Error Condition SET."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174009

        ethPort-excess-tx-clear  TRAP-TYPE
		ENTERPRISE   cdx6500
		VARIABLES    { cdx6500SNMPLastTrap }
		DESCRIPTION
		             " Enet%d - Excessive TX Error Condition CLR."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174010

        ethPort-loc-clear  TRAP-TYPE
		ENTERPRISE   cdx6500
		VARIABLES    { cdx6500SNMPLastTrap }
		DESCRIPTION
		             " Enet%d - Loss of Carrier Condition CLR."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174011

        ethPort-excessive-rx-clear  TRAP-TYPE
		ENTERPRISE   cdx6500
		VARIABLES    { cdx6500SNMPLastTrap }
		DESCRIPTION
		             " Enet%d - Excessive RX Error Condition CLR."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174012

        ethPort-invalid-state-enabled  TRAP-TYPE
                ENTERPRISE   cdx6500
                VARIABLES    { cdx6500SNMPLastTrap }
                DESCRIPTION
                             " Enet%d - Invalid driver state, should be enabled, function not performed. "
                     --#TYPE
                     --#SUMMARY "Trap #$G, specific: $S, arg(1): $1"
                     --#ARGUMENTS {}
                     --#SEVERITY  INFORMATIONAL
                     --#TIMEINDEX
                     --#HELP
                     --#HELPTAG
                     --#STATE
                ::= 174013

        ethPort-inval-state-disable  TRAP-TYPE
		ENTERPRISE   cdx6500
		VARIABLES    { cdx6500SNMPLastTrap }
		DESCRIPTION
		             " Enet%d - Invalid driver state, should be disabled, function not performed."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174014

        ethPort-loopback-fail  TRAP-TYPE
		ENTERPRISE   cdx6500
		VARIABLES    { cdx6500SNMPLastTrap }
		DESCRIPTION
		             " Enet%d - The loopback Configuration command failed."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174015

        ethPort-tdr-fail  TRAP-TYPE
		ENTERPRISE   cdx6500
		VARIABLES    { cdx6500SNMPLastTrap }
		DESCRIPTION
		             " Enet%d - The Time Domain Reflectometry command failed."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174016

        ethPort-ca-fail  TRAP-TYPE
		ENTERPRISE   cdx6500
		VARIABLES    { cdx6500SNMPLastTrap }
		DESCRIPTION
		             " Enet%d - 82596 Hardware Failure %d."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174017

        ethPort-rx-list-err  TRAP-TYPE
		ENTERPRISE   cdx6500
		VARIABLES    { cdx6500SNMPLastTrap }
		DESCRIPTION
		             " Enet%d - RX List Error %d."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174018

        ethPort-tx-list-err  TRAP-TYPE
		ENTERPRISE   cdx6500
		VARIABLES    { cdx6500SNMPLastTrap }
		DESCRIPTION
		             " Enet%d - TX List Error %d."
                     --#TYPE
                     --#SUMMARY "Trap #$G, specific: $S, arg(1): $1"
                     --#ARGUMENTS {}
                     --#SEVERITY  INFORMATIONAL
                     --#TIMEINDEX
                     --#HELP
                     --#HELPTAG
                     --#STATE
		::= 174019

        ethPort-lockup-err  TRAP-TYPE
		ENTERPRISE   cdx6500
		VARIABLES    { cdx6500SNMPLastTrap }
		DESCRIPTION
		             " Enet%d - Diag Check p1=%x p2=%x dp=%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 174020

        alcPort-boot  TRAP-TYPE
                ENTERPRISE   cdx6500
                VARIABLES    { cdx6500SNMPLastTrap }
                DESCRIPTION
                             "%s - BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 176000

        alcPort-boot-fail  TRAP-TYPE
                ENTERPRISE   cdx6500
                VARIABLES    { cdx6500SNMPLastTrap }
                DESCRIPTION
                             "%s - BOOT FAILURE (%s)"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 176001

        alcPort-disable  TRAP-TYPE
                ENTERPRISE   cdx6500
                VARIABLES    { cdx6500SNMPLastTrap }
                DESCRIPTION
                             "%s - DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 176002

        alcPort-disable-fail  TRAP-TYPE
                ENTERPRISE   cdx6500
                VARIABLES    { cdx6500SNMPLastTrap }
                DESCRIPTION
                             "%s - DISABLE FAILURE (%s)"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 176003

        alcPort-enable  TRAP-TYPE
                ENTERPRISE   cdx6500
                VARIABLES    { cdx6500SNMPLastTrap }
                DESCRIPTION
                             "%s - ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 176004

        alcPort-enable-fail  TRAP-TYPE
                ENTERPRISE   cdx6500
                VARIABLES    { cdx6500SNMPLastTrap }
                DESCRIPTION
                             "%s - ENABLE FAILURE (%s)"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 176005

        alcPort-nomodule  TRAP-TYPE
                ENTERPRISE   cdx6500
                VARIABLES    { cdx6500SNMPLastTrap }
                DESCRIPTION
                             "%s - REQUIRED MODULE %s (%d) NOT FOUND"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 176006

        alch-al-line-down  TRAP-TYPE
                ENTERPRISE   cdx6500
                VARIABLES    { cdx6500SNMPLastTrap }
                DESCRIPTION
                             "%s - LINE DOWN"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177000

        alch-al-line-up  TRAP-TYPE
                ENTERPRISE   cdx6500
                VARIABLES    { cdx6500SNMPLastTrap }
                DESCRIPTION
                             "%s - LINE UP"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177001

        alch-al-flow-ctl-imp  TRAP-TYPE
                ENTERPRISE   cdx6500
                VARIABLES    { cdx6500SNMPLastTrap }
                DESCRIPTION
                             "%s - FLOW CONTROL IMPOSED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177002

        alch-al-flow-ctl-rel  TRAP-TYPE
                ENTERPRISE   cdx6500
                VARIABLES    { cdx6500SNMPLastTrap }
                DESCRIPTION
                             "%s - FLOW CONTROL RELEASED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177003

        alch-al-ia-fast-poll  TRAP-TYPE
                ENTERPRISE   cdx6500
                VARIABLES    { cdx6500SNMPLastTrap }
                DESCRIPTION
                             "%s - IA ENTERING FAST POLL"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177004

        alch-al-ia-slow-poll  TRAP-TYPE
                ENTERPRISE   cdx6500
                VARIABLES    { cdx6500SNMPLastTrap }
                DESCRIPTION
                             "%s - IA ENTERING SLOW POLL"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177005

        alch-al-ia-stop-poll  TRAP-TYPE
                ENTERPRISE   cdx6500
                VARIABLES    { cdx6500SNMPLastTrap }
                DESCRIPTION
                             "%s - STOPPED POLLING IA"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177006

        alch-al-reset-disc  TRAP-TYPE
                ENTERPRISE   cdx6500
                VARIABLES    { cdx6500SNMPLastTrap }
                DESCRIPTION
                             "%s - RESET DISCARDED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177007

        alch-al-T1-timeout  TRAP-TYPE
                ENTERPRISE   cdx6500
                VARIABLES    { cdx6500SNMPLastTrap }
                DESCRIPTION
                             "%s - T1 TIMEOUT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177008

        alch-al-T2-timeout  TRAP-TYPE
                ENTERPRISE   cdx6500
                VARIABLES    { cdx6500SNMPLastTrap }
                DESCRIPTION
                             "%s - T2 TIMEOUT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177009

        alch-al-bad-ccc-rec  TRAP-TYPE
                ENTERPRISE   cdx6500
                VARIABLES    { cdx6500SNMPLastTrap }
                DESCRIPTION
                             "%s - BAD CCC RECEIVED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177010

        alch-al-host-timeout  TRAP-TYPE
                ENTERPRISE   cdx6500
                VARIABLES    { cdx6500SNMPLastTrap }
                DESCRIPTION
                             "%s - HOST TIMEOUT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177011

        alch-al-host-start-poll  TRAP-TYPE
                ENTERPRISE   cdx6500
                VARIABLES    { cdx6500SNMPLastTrap }
                DESCRIPTION
                             "%s - HOST HAS STARTED POLLING"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177012

        alch-al-msg-dis-no-conn  TRAP-TYPE
                ENTERPRISE   cdx6500
                VARIABLES    { cdx6500SNMPLastTrap }
                DESCRIPTION
                             "%s - MESSAGE DISCARDED, NO CONNECTION AVAILABLE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 177013

        alp-al-buff-disc  TRAP-TYPE
                ENTERPRISE   cdx6500
                VARIABLES    { cdx6500SNMPLastTrap }
                DESCRIPTION
                             "%s - BUFFER DISCARDED (%s)"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 178000

        apl-al-call-fail  TRAP-TYPE
                ENTERPRISE   cdx6500
                VARIABLES    { cdx6500SNMPLastTrap }
                DESCRIPTION
                             "%s - X.25 CALL FAILED %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 178001

        alp-al-lost-msgs  TRAP-TYPE
                ENTERPRISE   cdx6500
                VARIABLES    { cdx6500SNMPLastTrap }
                DESCRIPTION
                             "%s - LOST %d MESSAGES IN 60 SECONDS"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 178002

        alp-al-SIP-error  TRAP-TYPE
                ENTERPRISE   cdx6500
                VARIABLES    { cdx6500SNMPLastTrap }
                DESCRIPTION
                             "%s - SIP ERROR: %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 178003

        alp-al-SIP-nexist  TRAP-TYPE
                ENTERPRISE   cdx6500
                VARIABLES    { cdx6500SNMPLastTrap }
                DESCRIPTION
                             "%s - SIP MODULE DOES NOT EXIST"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 178004

        alp-al-src-IP-rqd  TRAP-TYPE
                ENTERPRISE   cdx6500
                VARIABLES    { cdx6500SNMPLastTrap }
                DESCRIPTION
                             "%s - SOURCE IP ADDRESS REQUIRED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 178005

        fraPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186000

        fraPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186001

        fraPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186002

        fraPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186003

        fraPort-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186004

        fraPort-stn-disable  TRAP-TYPE
		ENTERPRISE   cdx6500
		VARIABLES    { cdx6500SNMPLastTrap }
		DESCRIPTION
		             "%s - STATION DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186005

        fraPort-stn-enable  TRAP-TYPE
		ENTERPRISE   cdx6500
		VARIABLES    { cdx6500SNMPLastTrap }
		DESCRIPTION
		             "%s - STATION ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186006

        fraPort-stn-boot  TRAP-TYPE
		ENTERPRISE   cdx6500
		VARIABLES    { cdx6500SNMPLastTrap }
		DESCRIPTION
		             "%s - STATION BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186007

        fraPort-stn-boot-fail  TRAP-TYPE
		ENTERPRISE   cdx6500
		VARIABLES    { cdx6500SNMPLastTrap }
		DESCRIPTION
		             "%s - STATION BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186008

        fraPort-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 186009

        fra-port-update-complete  TRAP-TYPE
		ENTERPRISE   cdx6500
		VARIABLES    { cdx6500SNMPLastTrap }
		DESCRIPTION
		     "%s - PORT UPDATE COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 186010

        fra-out-of-memory-some-stations  TRAP-TYPE
		ENTERPRISE   cdx6500
		VARIABLES    { cdx6500SNMPLastTrap }
		DESCRIPTION
		     "%s - OUT OF MEMORY - SOME STATIONS NOT CREATED"
		     --#TYPE
		     --#SUMMARY "Trap #$G, specific: $S, arg(1) : $1"
		     --#ARGUMENTS {}
		     --#SEVERITY  MAJOR
		     --#TIMEINDEX
		     --#HELP
		     --#HELPTAG
		     --#STATE
		::= 186011

        fraL2-unconfig-dlci  TRAP-TYPE
		ENTERPRISE   cdx6500
		VARIABLES    { cdx6500SNMPLastTrap }
		DESCRIPTION
		             " %s - FRAME RECEIVED FROM UNKNOWN DLCI: %04d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187000

        fraL2-dsbl-stn-pack  TRAP-TYPE
		ENTERPRISE   cdx6500
		VARIABLES    { cdx6500SNMPLastTrap }
		DESCRIPTION
		             " %s - FRAME RECEIVED FOR DISABLED STATION: DLCI %04d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187001

        fraL2-bad-frame-len  TRAP-TYPE
		ENTERPRISE   cdx6500
		VARIABLES    { cdx6500SNMPLastTrap }
		DESCRIPTION
		             " %s - FRAME RECEIVED WITH BAD LENGTH: DLCI %04d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187002

        fraL2-annexd-err  TRAP-TYPE
		ENTERPRISE   cdx6500
		VARIABLES    { cdx6500SNMPLastTrap }
		DESCRIPTION
		             " %s - ANNEX D PROTOCOL ERROR THRESHOLD REACHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187003

        fraL2-lmi-err  TRAP-TYPE
		ENTERPRISE   cdx6500
		VARIABLES    { cdx6500SNMPLastTrap }
		DESCRIPTION
		             " %s - LMI PROTOCOL ERROR THRESHOLD REACHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187004

        fraL2-fsm-err  TRAP-TYPE
		ENTERPRISE   cdx6500
		VARIABLES    { cdx6500SNMPLastTrap }
		DESCRIPTION
		             "%s - FRA FSM ERROR State %04d Event %04d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187005

        fraL2-invalid-addr  TRAP-TYPE
		ENTERPRISE   cdx6500
		VARIABLES    { cdx6500SNMPLastTrap }
		DESCRIPTION
		             " %s - FRAME RECEIVED INVALID ADDRESS: %04d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187006

        fraL2-net-congested  TRAP-TYPE
		ENTERPRISE   cdx6500
		VARIABLES    { cdx6500SNMPLastTrap }
		DESCRIPTION
		             " %s - FLOW CONTROL THRESHOLD REACHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187007

        fraL2-link-up  TRAP-TYPE
		ENTERPRISE   cdx6500
		VARIABLES    { cdx6500SNMPLastTrap }
		DESCRIPTION
		             "%s - LINK UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187008

        fraL2-link-down  TRAP-TYPE
		ENTERPRISE   cdx6500
		VARIABLES    { cdx6500SNMPLastTrap }
		DESCRIPTION
		             "%s - LINK DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187009

        fraL2-annexa-err  TRAP-TYPE
		ENTERPRISE   cdx6500
		VARIABLES    { cdx6500SNMPLastTrap }
		DESCRIPTION
		             " %s - ANNEX A PROTOCOL ERROR THRESHOLD REACHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 187010

        fra-station-up  TRAP-TYPE
		ENTERPRISE   cdx6500
		VARIABLES    { cdx6500SNMPLastTrap }
		DESCRIPTION
		     "%s - STATION UP"
		     --#TYPE
		     --#SUMMARY "Trap #$G, specific: $S, arg(1) : $1"
		     --#ARGUMENTS {}
		     --#SEVERITY  MAJOR
		     --#TIMEINDEX
		     --#HELP
		     --#HELPTAG
		     --#STATE
		::= 187011

        fra-station-down  TRAP-TYPE
		ENTERPRISE   cdx6500
		VARIABLES    { cdx6500SNMPLastTrap }
		DESCRIPTION
		     "%s - STATION DOWN"
		     --#TYPE
		     --#SUMMARY "Trap #$G, specific: $S, arg(1) : $1"
		     --#ARGUMENTS {}
		     --#SEVERITY  MAJOR
		     --#TIMEINDEX
		     --#HELP
		     --#HELPTAG
		     --#STATE
		::= 187012

        lcon-invalid-proto-id  TRAP-TYPE
		ENTERPRISE   cdx6500
		VARIABLES    { cdx6500SNMPLastTrap }
		DESCRIPTION
		             "%ld - RECEIVED INVALID PROTOCOL ID FROM THE ROUTER %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 188000

        lcon-invalid-forward-id  TRAP-TYPE
		ENTERPRISE   cdx6500
		VARIABLES    { cdx6500SNMPLastTrap }
		DESCRIPTION
		             "%s - RECEIVED INVALID FORWARDER ID FROM THE WAN LINK %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 188001

        lcon-rx-no-route-discard  TRAP-TYPE
		ENTERPRISE   cdx6500
		VARIABLES    { cdx6500SNMPLastTrap }
		DESCRIPTION
		             "LCON RX DISCARD - NO ROUTE TO %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 188002

        lcon-rx-no-hop-discard  TRAP-TYPE
		ENTERPRISE   cdx6500
		VARIABLES    { cdx6500SNMPLastTrap }
		DESCRIPTION
		             "LCON RX DISCARD - NO NEXT HOP TO %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 188003

        lcon-tx-bad-hop-discard  TRAP-TYPE
		ENTERPRISE   cdx6500
		VARIABLES    { cdx6500SNMPLastTrap }
		DESCRIPTION
		             "LCON TX DISCARD - UNKNOWN NEXT HOP %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 188004

        lcon-svc-creation-fail  TRAP-TYPE
		ENTERPRISE   cdx6500
		VARIABLES    { cdx6500SNMPLastTrap }
		DESCRIPTION
		             "%s - LAN CONNECTION CREATION FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 189000

        lcon-1294-invalid-encap  TRAP-TYPE
		ENTERPRISE   cdx6500
		VARIABLES    { cdx6500SNMPLastTrap }
		DESCRIPTION
		             "%s - PACKET RECEIVED WITH INVALID RFC1294 ENCAPSULATION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 191000

        tb-forwarding-table-full  TRAP-TYPE
		ENTERPRISE   cdx6500
		VARIABLES    { cdx6500SNMPLastTrap }
		DESCRIPTION
		             " CHAIN portion of the TRANSPARENT BRIDGE FORWARDING TABLE is full. "
                     --#TYPE
                     --#SUMMARY "Trap #$G, specific: $S, arg(1): $1"
                     --#ARGUMENTS {}
                     --#SEVERITY  INFORMATIONAL
                     --#TIMEINDEX
                     --#HELP
                     --#HELPTAG
                     --#STATE
		::= 192000

        ethPort-boot  TRAP-TYPE
		ENTERPRISE   cdx6500
		VARIABLES    { cdx6500SNMPLastTrap }
		DESCRIPTION
		             "%s PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 193000

        ethPort-boot-fail  TRAP-TYPE
		ENTERPRISE   cdx6500
		VARIABLES    { cdx6500SNMPLastTrap }
		DESCRIPTION
		             "%s PORT BOOT FAILURE %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 193001

        ethPort-enable  TRAP-TYPE
		ENTERPRISE   cdx6500
		VARIABLES    { cdx6500SNMPLastTrap }
		DESCRIPTION
		             "%s PORT ENABLED COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 193002

        ethPort-disable  TRAP-TYPE
		ENTERPRISE   cdx6500
		VARIABLES    { cdx6500SNMPLastTrap }
		DESCRIPTION
		             "%s PORT DISABLE COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 193003

        ethPort-init-fail  TRAP-TYPE
		ENTERPRISE   cdx6500
		VARIABLES    { cdx6500SNMPLastTrap }
		DESCRIPTION
		             "%s PORT INITIALIZATION FAILURE %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 193004

        shdlc-link-down  TRAP-TYPE
		ENTERPRISE   cdx6500
		VARIABLES    { cdx6500SNMPLastTrap }
		DESCRIPTION
		             "%s - LINK DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195000

        shdlc-disc-recv  TRAP-TYPE
		ENTERPRISE   cdx6500
		VARIABLES    { cdx6500SNMPLastTrap }
		DESCRIPTION
		             "%s - DISC RECEIVED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195001

        shdlc-bad-frame-type  TRAP-TYPE
		ENTERPRISE   cdx6500
		VARIABLES    { cdx6500SNMPLastTrap }
		DESCRIPTION
		             " %s - BAD FRAME TYPE (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195002

        shdlc-address-err  TRAP-TYPE
		ENTERPRISE   cdx6500
		VARIABLES    { cdx6500SNMPLastTrap }
		DESCRIPTION
		             " %s - ADDRESS ERROR (%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195003

        shdlc-bad-frame-len  TRAP-TYPE
		ENTERPRISE   cdx6500
		VARIABLES    { cdx6500SNMPLastTrap }
		DESCRIPTION
		             " %s - BAD FRAME LENGTH (%d)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195004

        shdlc-extend-seq-frmr  TRAP-TYPE
		ENTERPRISE   cdx6500
		VARIABLES    { cdx6500SNMPLastTrap }
		DESCRIPTION
		             " %s - FRMR (%02X%02X/%02X%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195005

        shdlc-norm-seq-frmr  TRAP-TYPE
		ENTERPRISE   cdx6500
		VARIABLES    { cdx6500SNMPLastTrap }
		DESCRIPTION
		             " %s - FRMR (%02X/%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195006

        shdlc-link-up  TRAP-TYPE
		ENTERPRISE   cdx6500
		VARIABLES    { cdx6500SNMPLastTrap }
		DESCRIPTION
		             "%s - LINK UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195007

        shdlc-link-blocked  TRAP-TYPE
		ENTERPRISE   cdx6500
		VARIABLES    { cdx6500SNMPLastTrap }
		DESCRIPTION
		             " %s - LINK BLOCKED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195008

        shdlc-bad-n-r  TRAP-TYPE
		ENTERPRISE   cdx6500
		VARIABLES    { cdx6500SNMPLastTrap }
		DESCRIPTION
		             " %s - BAD N(R) (%02X/%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195009

        shdlc-backup-activated  TRAP-TYPE
		ENTERPRISE   cdx6500
		VARIABLES    { cdx6500SNMPLastTrap }
		DESCRIPTION
		             "%s - BACKUP LINK ACTIVATED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195010

        shdlc-extend-bad-frame-type  TRAP-TYPE
		ENTERPRISE   cdx6500
		VARIABLES    { cdx6500SNMPLastTrap }
		DESCRIPTION
		             " %s - BAD FRAME TYPE (%02X%02X)"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195011

        shdlc-access-link-down  TRAP-TYPE
		ENTERPRISE   cdx6500
		VARIABLES    { cdx6500SNMPLastTrap }
		DESCRIPTION
		             " %s - ACCESS PORT DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195012

        shdlc-access-link-up  TRAP-TYPE
		ENTERPRISE   cdx6500
		VARIABLES    { cdx6500SNMPLastTrap }
		DESCRIPTION
		             " %s - ACCESS PORT UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195013

        shdlc-ovsize-frame  TRAP-TYPE
		ENTERPRISE   cdx6500
		VARIABLES    { cdx6500SNMPLastTrap }
		DESCRIPTION
		             " %s - OVERSIZE FRAME (%d) FROM REMOTE LINK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 195014

        shdlc-port-boot-complete  TRAP-TYPE
		ENTERPRISE   cdx6500
		VARIABLES    { cdx6500SNMPLastTrap }
		DESCRIPTION
		     "%s - PORT BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 196000

        shdlc-port-boot-failure  TRAP-TYPE
		ENTERPRISE   cdx6500
		VARIABLES    { cdx6500SNMPLastTrap }
		DESCRIPTION
		     "%s - PORT BOOT FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 196001

        shdlc-port-disabled  TRAP-TYPE
		ENTERPRISE   cdx6500
		VARIABLES    { cdx6500SNMPLastTrap }
		DESCRIPTION
		     "%s - PORT DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 196002

        shdlc-port-enabled  TRAP-TYPE
		ENTERPRISE   cdx6500
		VARIABLES    { cdx6500SNMPLastTrap }
		DESCRIPTION
		     "%s - PORT ENABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 196003

        shdlc-port-utilization-threshold  TRAP-TYPE
		ENTERPRISE   cdx6500
		VARIABLES    { cdx6500SNMPLastTrap }
		DESCRIPTION
		     "%s - PORT UTILIZATION > THRESHOLD"
		     --#TYPE
		     --#SUMMARY "Trap #$G, specific: $S, arg(1) : $1"
		     --#ARGUMENTS {}
		     --#SEVERITY  MAJOR
		     --#TIMEINDEX
		     --#HELP
		     --#HELPTAG
		     --#STATE
		::= 196004

        shdlc-port-status-warning  TRAP-TYPE
		ENTERPRISE   cdx6500
		VARIABLES    { cdx6500SNMPLastTrap }
		DESCRIPTION
		     "%s - PORT STATUS WARNING - %s"
		     --#TYPE
		     --#SUMMARY "Trap #$G, specific: $S, arg(1) : $1"
		     --#ARGUMENTS {}
		     --#SEVERITY  MINOR
		     --#TIMEINDEX
		     --#HELP
		     --#HELPTAG
		     --#STATE
		::= 196005

        shdlc-unsupported-frame-size-ope  TRAP-TYPE
		ENTERPRISE   cdx6500
		VARIABLES    { cdx6500SNMPLastTrap }
		DESCRIPTION
		     "%s - UNSUPPORTED FRAME SIZE: OPERATING WITH %d BYTES"
		     --#TYPE
		     --#SUMMARY "Trap #$G, specific: $S, arg(1) : $1"
		     --#ARGUMENTS {}
		     --#SEVERITY  MAJOR
		     --#TIMEINDEX
		     --#HELP
		     --#HELPTAG
		     --#STATE
		::= 196006

        tftp-op-success  TRAP-TYPE
		ENTERPRISE   cdx6500
		VARIABLES    { cdx6500SNMPLastTrap }
		DESCRIPTION
		             "TFTP: Operation successful %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198000

        tftp-cmem-fail  TRAP-TYPE
		ENTERPRISE   cdx6500
		VARIABLES    { cdx6500SNMPLastTrap }
		DESCRIPTION
		             "TFTP: CMEM access failure %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198001

        tftp-local-transfer-fail  TRAP-TYPE
		ENTERPRISE   cdx6500
		VARIABLES    { cdx6500SNMPLastTrap }
		DESCRIPTION
		             "TFTP: Local transfer failure %s, Error text = %s, Error code = %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198002

        tftp-remote-transfer-fail  TRAP-TYPE
		ENTERPRISE   cdx6500
		VARIABLES    { cdx6500SNMPLastTrap }
		DESCRIPTION
		             "TFTP: Remote transfer failure %s Error text = %s Error code = %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198003

        tftp-system-fail  TRAP-TYPE
		ENTERPRISE   cdx6500
		VARIABLES    { cdx6500SNMPLastTrap }
		DESCRIPTION
		             "TFTP: System failure %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198004

        tftp-udp-reg-fail  TRAP-TYPE
		ENTERPRISE   cdx6500
		VARIABLES    { cdx6500SNMPLastTrap }
		DESCRIPTION
		             "TFTP: UDP registration failure %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198005

        tftp-dl-in-progress  TRAP-TYPE
		ENTERPRISE   cdx6500
		VARIABLES    { cdx6500SNMPLastTrap }
		DESCRIPTION
		             "TFTP: Software download already in progress %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198006

        tftp-sw-image-err  TRAP-TYPE
		ENTERPRISE   cdx6500
		VARIABLES    { cdx6500SNMPLastTrap }
		DESCRIPTION
		             "TFTP: Error in software image file %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198007

        tftp-flash-erase-fail  TRAP-TYPE
		ENTERPRISE   cdx6500
		VARIABLES    { cdx6500SNMPLastTrap }
		DESCRIPTION
		             "TFTP: Flash erasure failure %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198008

        tftp-flash-write-fail  TRAP-TYPE
		ENTERPRISE   cdx6500
		VARIABLES    { cdx6500SNMPLastTrap }
		DESCRIPTION
		             "TFTP: Flash write failure %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 198009

        tftp-tftp  TRAP-TYPE
		ENTERPRISE   cdx6500
		VARIABLES    { cdx6500SNMPLastTrap }
		DESCRIPTION
		     "TFTP: %s"
		     --#TYPE
		     --#SUMMARY "Trap #$G, specific: $S, arg(1) : $1"
		     --#ARGUMENTS {}
		     --#SEVERITY  CRITICAL
		     --#TIMEINDEX
		     --#HELP
		     --#HELPTAG
		     --#STATE
		::= 198010

        tftp-partial-success  TRAP-TYPE
		ENTERPRISE   cdx6500
		VARIABLES    { cdx6500SNMPLastTrap }
		DESCRIPTION
		     "TFTP: partial success\r\n%s"
		     --#TYPE
		     --#SUMMARY "Trap #$G, specific: $S, arg(1) : $1"
		     --#ARGUMENTS {}
		     --#SEVERITY  CRITICAL
		     --#TIMEINDEX
		     --#HELP
		     --#HELPTAG
		     --#STATE
		::= 198011

        tftp-failure  TRAP-TYPE
		ENTERPRISE   cdx6500
		VARIABLES    { cdx6500SNMPLastTrap }
		DESCRIPTION
		     "TFTP: failure\r\n%s"
		     --#TYPE
		     --#SUMMARY "Trap #$G, specific: $S, arg(1) : $1"
		     --#ARGUMENTS {}
		     --#SEVERITY  CRITICAL
		     --#TIMEINDEX
		     --#HELP
		     --#HELPTAG
		     --#STATE
		::= 198012

        ipx-multiple-paths  TRAP-TYPE
		ENTERPRISE   cdx6500
		VARIABLES    { cdx6500SNMPLastTrap }
		DESCRIPTION
		             "Duplicate static path to %s - in entry %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 202000

        ipx-net-unreachable  TRAP-TYPE
		ENTERPRISE   cdx6500
		VARIABLES    { cdx6500SNMPLastTrap }
		DESCRIPTION
		             "Unreachable network %d - in entry %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 202001

        router-ipx-disabled-memory-alloc  TRAP-TYPE
		ENTERPRISE   cdx6500
		VARIABLES    { cdx6500SNMPLastTrap }
		DESCRIPTION
		     "IPX Disabled - memory allocation failure during init"
		     --#TYPE
		     --#SUMMARY "Trap #$G, specific: $S, arg(1) : $1"
		     --#ARGUMENTS {}
		     --#SEVERITY  CRITICAL
		     --#TIMEINDEX
		     --#HELP
		     --#HELPTAG
		     --#STATE
		::= 202002

        router-no-memory-for-table  TRAP-TYPE
		ENTERPRISE   cdx6500
		VARIABLES    { cdx6500SNMPLastTrap }
		DESCRIPTION
		     "No memory for %s table"
		     --#TYPE
		     --#SUMMARY "Trap #$G, specific: $S, arg(1) : $1"
		     --#ARGUMENTS {}
		     --#SEVERITY  CRITICAL
		     --#TIMEINDEX
		     --#HELP
		     --#HELPTAG
		     --#STATE
		::= 202006

        router-no-memory-for-record  TRAP-TYPE
		ENTERPRISE   cdx6500
		VARIABLES    { cdx6500SNMPLastTrap }
		DESCRIPTION
		     "No memory for %s record"
		     --#TYPE
		     --#SUMMARY "Trap #$G, specific: $S, arg(1) : $1"
		     --#ARGUMENTS {}
		     --#SEVERITY  MAJOR
		     --#TIMEINDEX
		     --#HELP
		     --#HELPTAG
		     --#STATE
		::= 202007

        router-record-attempt-to-add-dup  TRAP-TYPE
		ENTERPRISE   cdx6500
		VARIABLES    { cdx6500SNMPLastTrap }
		DESCRIPTION
		     "%s record %d : Attempt to add duplicate record"
		     --#TYPE
		     --#SUMMARY "Trap #$G, specific: $S, arg(1) : $1"
		     --#ARGUMENTS {}
		     --#SEVERITY  MINOR
		     --#TIMEINDEX
		     --#HELP
		     --#HELPTAG
		     --#STATE
		::= 202008

        dscope-user-message-lost  TRAP-TYPE
                ENTERPRISE   cdx6500
                VARIABLES    { cdx6500SNMPLastTrap }
                DESCRIPTION
                             "%s - USER MESSAGE LOST"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 206000

        dscope-subaddress-incorrect-leng  TRAP-TYPE
		ENTERPRISE   cdx6500
		VARIABLES    { cdx6500SNMPLastTrap }
		DESCRIPTION
		     "%s - SUBADDRESS %s INCORRECT, LENGTH - %s"
		     --#TYPE
		     --#SUMMARY "Trap #$G, specific: $S, arg(1) : $1"
		     --#ARGUMENTS {}
		     --#SEVERITY  MAJOR
		     --#TIMEINDEX
		     --#HELP
		     --#HELPTAG
		     --#STATE
		::= 206001

        ipx-high-priority-traps  TRAP-TYPE
		ENTERPRISE   cdx6500
		VARIABLES    { cdx6500SNMPLastTrap }
		DESCRIPTION
		             "IPX protocol subsystem high priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 210000

        ipx-med-priority-traps  TRAP-TYPE
		ENTERPRISE   cdx6500
		VARIABLES    { cdx6500SNMPLastTrap }
		DESCRIPTION
		             " IPX protocol subsystem medium priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 210001

        ipx-low-priority-traps  TRAP-TYPE
		ENTERPRISE   cdx6500
		VARIABLES    { cdx6500SNMPLastTrap }
		DESCRIPTION
		             " IPX protocol subsystem low priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 210002

        ipx-max-interf-exceeded  TRAP-TYPE
		ENTERPRISE   cdx6500
		VARIABLES    { cdx6500SNMPLastTrap }
		DESCRIPTION
		             " %s - EXCEEDING THE MAXIMUM NUMBER OF INTERFACES ALLOWED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 210003

        router-record-attempt-to-add-dup2  TRAP-TYPE
		ENTERPRISE   cdx6500
		VARIABLES    { cdx6500SNMPLastTrap }
		DESCRIPTION
		     "%s record %d : Attempt to add duplicate record"
		     --#TYPE
		     --#SUMMARY "Trap #$G, specific: $S, arg(1) : $1"
		     --#ARGUMENTS {}
		     --#SEVERITY  MINOR
		     --#TIMEINDEX
		     --#HELP
		     --#HELPTAG
		     --#STATE
		::= 210004

        code-bytes-loaded-from-extended  TRAP-TYPE
		ENTERPRISE   cdx6500
		VARIABLES    { cdx6500SNMPLastTrap }
		DESCRIPTION
		     "%d BYTES LOADED FROM EXTENDED FLASH MEMORY (%d)"
		     --#TYPE
		     --#SUMMARY "Trap #$G, specific: $S, arg(1) : $1"
		     --#ARGUMENTS {}
		     --#SEVERITY  CRITICAL
		     --#TIMEINDEX
		     --#HELP
		     --#HELPTAG
		     --#STATE
		::= 211000

        cougar-code-loaded-from-extended  TRAP-TYPE
		ENTERPRISE   cdx6500
		VARIABLES    { cdx6500SNMPLastTrap }
		DESCRIPTION
		     "%d BYTES LOADED FROM EXTENDED FLASH MEMORY"
		     --#TYPE
		     --#SUMMARY "Trap #$G, specific: $S, arg(1) : $1"
		     --#ARGUMENTS {}
		     --#SEVERITY  CRITICAL
		     --#TIMEINDEX
		     --#HELP
		     --#HELPTAG
		     --#STATE
		::= 211001

        code-extended-software-load-fail  TRAP-TYPE
		ENTERPRISE   cdx6500
		VARIABLES    { cdx6500SNMPLastTrap }
		DESCRIPTION
		     "EXTENDED SOFTWARE LOAD FAILS IN SLOT %d"
		     --#TYPE
		     --#SUMMARY "Trap #$G, specific: $S, arg(1) : $1"
		     --#ARGUMENTS {}
		     --#SEVERITY  MAJOR
		     --#TIMEINDEX
		     --#HELP
		     --#HELPTAG
		     --#STATE
		::= 211002

        code-master-failed-to-copy-exten  TRAP-TYPE
		ENTERPRISE   cdx6500
		VARIABLES    { cdx6500SNMPLastTrap }
		DESCRIPTION
		     "MASTER FAILED TO COPY EXTENDED S/W"
		     --#TYPE
		     --#SUMMARY "Trap #$G, specific: $S, arg(1) : $1"
		     --#ARGUMENTS {}
		     --#SEVERITY  MAJOR
		     --#TIMEINDEX
		     --#HELP
		     --#HELPTAG
		     --#STATE
		::= 211003

        code-extended-checksum-error-slo  TRAP-TYPE
		ENTERPRISE   cdx6500
		VARIABLES    { cdx6500SNMPLastTrap }
		DESCRIPTION
		     "EXTENDED CHECKSUM ERROR: SLOT %d DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 211004

        asyncModem-speed-unsupp  TRAP-TYPE
		ENTERPRISE   cdx6500
		VARIABLES    { cdx6500SNMPLastTrap }
		DESCRIPTION
		             " %s - UNSUPPORTED SPEED: OPERATING AT %d BITS PER SECOND"
                     --#TYPE
                     --#SUMMARY "Trap #$G, specific: $S, arg(1): $1"
                     --#ARGUMENTS {}
                     --#SEVERITY  INFORMATIONAL
                     --#TIMEINDEX
                     --#HELP
                     --#HELPTAG
                     --#STATE
		::= 212000

        asyncModem-databits-unsupp  TRAP-TYPE
		ENTERPRISE   cdx6500
		VARIABLES    { cdx6500SNMPLastTrap }
		DESCRIPTION
		             " %s - UNSUPPORTED DATABITS: OPERATING WITH 8 DATABITS, NO PARITY"
                     --#TYPE
                     --#SUMMARY "Trap #$G, specific: $S, arg(1): $1"
                     --#ARGUMENTS {}
                     --#SEVERITY  INFORMATIONAL
                     --#TIMEINDEX
                     --#HELP
                     --#HELPTAG
                     --#STATE
		::= 212001

        asyncModem-connection  TRAP-TYPE
		ENTERPRISE   cdx6500
		VARIABLES    { cdx6500SNMPLastTrap }
		DESCRIPTION
		             "SERVICE MODEM: CONNECTION %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 212002

        t3pos-fat-timer-expired-line-dis  TRAP-TYPE
		ENTERPRISE   cdx6500
		VARIABLES    { cdx6500SNMPLastTrap }
		DESCRIPTION
		     "%s - FAT TIMER EXPIRED, LINE DISCONNECTING"
		     --#TYPE
		     --#SUMMARY "Trap #$G, specific: $S, arg(1) : $1"
		     --#ARGUMENTS {}
		     --#SEVERITY  CRITICAL
		     --#TIMEINDEX
		     --#HELP
		     --#HELPTAG
		     --#STATE
		::= 215000

        t3pos-connection-towards-host-in  TRAP-TYPE
		ENTERPRISE   cdx6500
		VARIABLES    { cdx6500SNMPLastTrap }
		DESCRIPTION
		     "%s - CONNECTION TOWARDS HOST IN PROGRESS"
		     --#TYPE
		     --#SUMMARY "Trap #$G, specific: $S, arg(1) : $1"
		     --#ARGUMENTS {}
		     --#SEVERITY  MINOR
		     --#TIMEINDEX
		     --#HELP
		     --#HELPTAG
		     --#STATE
		::= 215001

        t3pos-dleeot-received-call-clear  TRAP-TYPE
		ENTERPRISE   cdx6500
		VARIABLES    { cdx6500SNMPLastTrap }
		DESCRIPTION
		     "%s - DLE,EOT RECEIVED, CALL CLEARED"
		     --#TYPE
		     --#SUMMARY "Trap #$G, specific: $S, arg(1) : $1"
		     --#ARGUMENTS {}
		     --#SEVERITY  MAJOR
		     --#TIMEINDEX
		     --#HELP
		     --#HELPTAG
		     --#STATE
		::= 215002

        t3pos-invalid-frame-from-pos-cal  TRAP-TYPE
		ENTERPRISE   cdx6500
		VARIABLES    { cdx6500SNMPLastTrap }
		DESCRIPTION
		     "%s - INVALID FRAME FROM POS, CALL CLEARED"
		     --#TYPE
		     --#SUMMARY "Trap #$G, specific: $S, arg(1) : $1"
		     --#ARGUMENTS {}
		     --#SEVERITY  MAJOR
		     --#TIMEINDEX
		     --#HELP
		     --#HELPTAG
		     --#STATE
		::= 215003

        t3pos-dle-eot-timeout-call-clear  TRAP-TYPE
		ENTERPRISE   cdx6500
		VARIABLES    { cdx6500SNMPLastTrap }
		DESCRIPTION
		     "%s - DLE-EOT TIMEOUT, CALL CLEARED"
		     --#TYPE
		     --#SUMMARY "Trap #$G, specific: $S, arg(1) : $1"
		     --#ARGUMENTS {}
		     --#SEVERITY  CRITICAL
		     --#TIMEINDEX
		     --#HELP
		     --#HELPTAG
		     --#STATE
		::= 215004

        t3pos-line-failure-line-disconne  TRAP-TYPE
		ENTERPRISE   cdx6500
		VARIABLES    { cdx6500SNMPLastTrap }
		DESCRIPTION
		     "%s - LINE FAILURE, LINE DISCONNECTED"
		     --#TYPE
		     --#SUMMARY "Trap #$G, specific: $S, arg(1) : $1"
		     --#ARGUMENTS {}
		     --#SEVERITY  CRITICAL
		     --#TIMEINDEX
		     --#HELP
		     --#HELPTAG
		     --#STATE
		::= 215005

        t3pos-output-queue-overrun  TRAP-TYPE
		ENTERPRISE   cdx6500
		VARIABLES    { cdx6500SNMPLastTrap }
		DESCRIPTION
		     "%s - OUTPUT QUEUE OVERRUN"
		     --#TYPE
		     --#SUMMARY "Trap #$G, specific: $S, arg(1) : $1"
		     --#ARGUMENTS {}
		     --#SEVERITY  MAJOR
		     --#TIMEINDEX
		     --#HELP
		     --#HELPTAG
		     --#STATE
		::= 215006

        t3pos-input-queue-overrun  TRAP-TYPE
		ENTERPRISE   cdx6500
		VARIABLES    { cdx6500SNMPLastTrap }
		DESCRIPTION
		     "%s - INPUT QUEUE OVERRUN"
		     --#TYPE
		     --#SUMMARY "Trap #$G, specific: $S, arg(1) : $1"
		     --#ARGUMENTS {}
		     --#SEVERITY  MAJOR
		     --#TIMEINDEX
		     --#HELP
		     --#HELPTAG
		     --#STATE
		::= 215007

        t3pos-call-cleared-by-host  TRAP-TYPE
		ENTERPRISE   cdx6500
		VARIABLES    { cdx6500SNMPLastTrap }
		DESCRIPTION
		     "%s - CALL CLEARED BY HOST-%d"
		     --#TYPE
		     --#SUMMARY "Trap #$G, specific: $S, arg(1) : $1"
		     --#ARGUMENTS {}
		     --#SEVERITY  MAJOR
		     --#TIMEINDEX
		     --#HELP
		     --#HELPTAG
		     --#STATE
		::= 215008

        t3pos-call-rejected-by-level3  TRAP-TYPE
		ENTERPRISE   cdx6500
		VARIABLES    { cdx6500SNMPLastTrap }
		DESCRIPTION
		     "%s - CALL REJECTED BY LEVEL3 -%d"
		     --#TYPE
		     --#SUMMARY "Trap #$G, specific: $S, arg(1) : $1"
		     --#ARGUMENTS {}
		     --#SEVERITY  MAJOR
		     --#TIMEINDEX
		     --#HELP
		     --#HELPTAG
		     --#STATE
		::= 215009

        t3pos-invalid-mss-from-pos-call  TRAP-TYPE
		ENTERPRISE   cdx6500
		VARIABLES    { cdx6500SNMPLastTrap }
		DESCRIPTION
		     "%s - INVALID MSS FROM POS, CALL REJECTED"
		     --#TYPE
		     --#SUMMARY "Trap #$G, specific: $S, arg(1) : $1"
		     --#ARGUMENTS {}
		     --#SEVERITY  MAJOR
		     --#TIMEINDEX
		     --#HELP
		     --#HELPTAG
		     --#STATE
		::= 215010

        t3pos-invalid-mss-from-host-call  TRAP-TYPE
		ENTERPRISE   cdx6500
		VARIABLES    { cdx6500SNMPLastTrap }
		DESCRIPTION
		     "%s - INVALID MSS FROM HOST, CALL CLEARED"
		     --#TYPE
		     --#SUMMARY "Trap #$G, specific: $S, arg(1) : $1"
		     --#ARGUMENTS {}
		     --#SEVERITY  MAJOR
		     --#TIMEINDEX
		     --#HELP
		     --#HELPTAG
		     --#STATE
		::= 215011

        t3pos-dial-out-not-supported-cal  TRAP-TYPE
		ENTERPRISE   cdx6500
		VARIABLES    { cdx6500SNMPLastTrap }
		DESCRIPTION
		     "%s - DIAL OUT NOT SUPPORTED, CALL REJECTED"
		     --#TYPE
		     --#SUMMARY "Trap #$G, specific: $S, arg(1) : $1"
		     --#ARGUMENTS {}
		     --#SEVERITY  MAJOR
		     --#TIMEINDEX
		     --#HELP
		     --#HELPTAG
		     --#STATE
		::= 215012

        t3pos-host-frame-size-exceeded-c  TRAP-TYPE
		ENTERPRISE   cdx6500
		VARIABLES    { cdx6500SNMPLastTrap }
		DESCRIPTION
		     "%s - HOST FRAME SIZE EXCEEDED, CALL CLEARED"
		     --#TYPE
		     --#SUMMARY "Trap #$G, specific: $S, arg(1) : $1"
		     --#ARGUMENTS {}
		     --#SEVERITY  MAJOR
		     --#TIMEINDEX
		     --#HELP
		     --#HELPTAG
		     --#STATE
		::= 215013

        t3pos-control-frame-from-host-ca  TRAP-TYPE
		ENTERPRISE   cdx6500
		VARIABLES    { cdx6500SNMPLastTrap }
		DESCRIPTION
		     "%s - CONTROL FRAME FROM HOST, CALL CLEARED"
		     --#TYPE
		     --#SUMMARY "Trap #$G, specific: $S, arg(1) : $1"
		     --#ARGUMENTS {}
		     --#SEVERITY  MAJOR
		     --#TIMEINDEX
		     --#HELP
		     --#HELPTAG
		     --#STATE
		::= 215014

        t3pos-retry-exceeded-line-discon  TRAP-TYPE
		ENTERPRISE   cdx6500
		VARIABLES    { cdx6500SNMPLastTrap }
		DESCRIPTION
		     "%s - RETRY EXCEEDED, LINE DISCONNECTED"
		     --#TYPE
		     --#SUMMARY "Trap #$G, specific: $S, arg(1) : $1"
		     --#ARGUMENTS {}
		     --#SEVERITY  MAJOR
		     --#TIMEINDEX
		     --#HELP
		     --#HELPTAG
		     --#STATE
		::= 215015

        t3pos-retry-exceeded-call-cleare  TRAP-TYPE
		ENTERPRISE   cdx6500
		VARIABLES    { cdx6500SNMPLastTrap }
		DESCRIPTION
		     "%s - RETRY EXCEEDED, CALL CLEARED"
		     --#TYPE
		     --#SUMMARY "Trap #$G, specific: $S, arg(1) : $1"
		     --#ARGUMENTS {}
		     --#SEVERITY  MAJOR
		     --#TIMEINDEX
		     --#HELP
		     --#HELPTAG
		     --#STATE
		::= 215016

        t3pos-virtual-retry-exceeded-cal  TRAP-TYPE
		ENTERPRISE   cdx6500
		VARIABLES    { cdx6500SNMPLastTrap }
		DESCRIPTION
		     "%s - VIRTUAL RETRY EXCEEDED, CALL CLEARED"
		     --#TYPE
		     --#SUMMARY "Trap #$G, specific: $S, arg(1) : $1"
		     --#ARGUMENTS {}
		     --#SEVERITY  MAJOR
		     --#TIMEINDEX
		     --#HELP
		     --#HELPTAG
		     --#STATE
		::= 215017

        t3pos-virtual-call-retry-exceede  TRAP-TYPE
		ENTERPRISE   cdx6500
		VARIABLES    { cdx6500SNMPLastTrap }
		DESCRIPTION
		     "%s - VIRTUAL CALL RETRY EXCEEDED, LINE DISCONNECTED"
		     --#TYPE
		     --#SUMMARY "Trap #$G, specific: $S, arg(1) : $1"
		     --#ARGUMENTS {}
		     --#SEVERITY  MAJOR
		     --#TIMEINDEX
		     --#HELP
		     --#HELPTAG
		     --#STATE
		::= 215018

        t3pos-invitation-to-clear-from-h  TRAP-TYPE
		ENTERPRISE   cdx6500
		VARIABLES    { cdx6500SNMPLastTrap }
		DESCRIPTION
		     "%s - INVITATION TO CLEAR FROM HOST, CALL CLEARED"
		     --#TYPE
		     --#SUMMARY "Trap #$G, specific: $S, arg(1) : $1"
		     --#ARGUMENTS {}
		     --#SEVERITY  MAJOR
		     --#TIMEINDEX
		     --#HELP
		     --#HELPTAG
		     --#STATE
		::= 215019

        t3pos-invalid-control-field-call  TRAP-TYPE
		ENTERPRISE   cdx6500
		VARIABLES    { cdx6500SNMPLastTrap }
		DESCRIPTION
		     "%s - INVALID CONTROL FIELD, CALL REJECTED -%d"
		     --#TYPE
		     --#SUMMARY "Trap #$G, specific: $S, arg(1) : $1"
		     --#ARGUMENTS {}
		     --#SEVERITY  MAJOR
		     --#TIMEINDEX
		     --#HELP
		     --#HELPTAG
		     --#STATE
		::= 215020

        t3pos-port-stat-overflow  TRAP-TYPE
		ENTERPRISE   cdx6500
		VARIABLES    { cdx6500SNMPLastTrap }
		DESCRIPTION
		     "%s - PORT STAT OVERFLOW -%d"
		     --#TYPE
		     --#SUMMARY "Trap #$G, specific: $S, arg(1) : $1"
		     --#ARGUMENTS {}
		     --#SEVERITY  MAJOR
		     --#TIMEINDEX
		     --#HELP
		     --#HELPTAG
		     --#STATE
		::= 215021

        t3pos-connected-to-host  TRAP-TYPE
		ENTERPRISE   cdx6500
		VARIABLES    { cdx6500SNMPLastTrap }
		DESCRIPTION
		     "%s - CONNECTED TO HOST"
		     --#TYPE
		     --#SUMMARY "Trap #$G, specific: $S, arg(1) : $1"
		     --#ARGUMENTS {}
		     --#SEVERITY  MINOR
		     --#TIMEINDEX
		     --#HELP
		     --#HELPTAG
		     --#STATE
		::= 215022

        t3pos-control-field-empty-call-r  TRAP-TYPE
		ENTERPRISE   cdx6500
		VARIABLES    { cdx6500SNMPLastTrap }
		DESCRIPTION
		     "%s - CONTROL FIELD EMPTY , CALL REJECTED"
		     --#TYPE
		     --#SUMMARY "Trap #$G, specific: $S, arg(1) : $1"
		     --#ARGUMENTS {}
		     --#SEVERITY  MINOR
		     --#TIMEINDEX
		     --#HELP
		     --#HELPTAG
		     --#STATE
		::= 215023

        t3pos-port-boot-complete  TRAP-TYPE
		ENTERPRISE   cdx6500
		VARIABLES    { cdx6500SNMPLastTrap }
		DESCRIPTION
		     "%s - PORT BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 216000

        t3pos-portbootfailure  TRAP-TYPE
		ENTERPRISE   cdx6500
		VARIABLES    { cdx6500SNMPLastTrap }
		DESCRIPTION
		     "%s - PORT-BOOT-FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 216001

        t3pos-port-disabled  TRAP-TYPE
		ENTERPRISE   cdx6500
		VARIABLES    { cdx6500SNMPLastTrap }
		DESCRIPTION
		     "%s - PORT DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 216002

        t3pos-port-disable-failure  TRAP-TYPE
		ENTERPRISE   cdx6500
		VARIABLES    { cdx6500SNMPLastTrap }
		DESCRIPTION
		     "%s - PORT DISABLE FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 216003

        t3pos-port-enabled  TRAP-TYPE
		ENTERPRISE   cdx6500
		VARIABLES    { cdx6500SNMPLastTrap }
		DESCRIPTION
		     "%s - PORT ENABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 216004

        t3pos-port-enable-failure  TRAP-TYPE
		ENTERPRISE   cdx6500
		VARIABLES    { cdx6500SNMPLastTrap }
		DESCRIPTION
		     "%s - PORT ENABLE FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 216005

        t3pos-port-connection-cleared  TRAP-TYPE
		ENTERPRISE   cdx6500
		VARIABLES    { cdx6500SNMPLastTrap }
		DESCRIPTION
		     "%s - PORT CONNECTION CLEARED - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 216006

        t3pos-port-utilization-threshold  TRAP-TYPE
		ENTERPRISE   cdx6500
		VARIABLES    { cdx6500SNMPLastTrap }
		DESCRIPTION
		     "%s - %s PORT UTILIZATION > THRESHOLD"
		     --#TYPE
		     --#SUMMARY "Trap #$G, specific: $S, arg(1) : $1"
		     --#ARGUMENTS {}
		     --#SEVERITY  CRITICAL
		     --#TIMEINDEX
		     --#HELP
		     --#HELPTAG
		     --#STATE
		::= 216007

        atpad-data-loss  TRAP-TYPE
                ENTERPRISE   cdx6500
                VARIABLES    { cdx6500SNMPLastTrap }
                DESCRIPTION
                             "%s - DATA LOST FROM DATA QUEUE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 218000

        atpad-data-loss-cmd  TRAP-TYPE
                ENTERPRISE   cdx6500
                VARIABLES    { cdx6500SNMPLastTrap }
                DESCRIPTION
                             "%s - DATA LOST FROM COMMAND QUEUE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 218001

        atpadPort-boot  TRAP-TYPE
	            ENTERPRISE   cdx6500
	            VARIABLES    { cdx6500SNMPLastTrap }
	            DESCRIPTION
		                 "%s - PORT BOOT COMPLETE"
                     --#TYPE
		             --#SUMMARY "Trap #$G, specific: $S, arg(1): $1"
                     --#ARGUMENTS {}
                     --#SEVERITY  INFORMATIONAL
                     --#TIMEINDEX
                     --#HELP
                     --#HELPTAG
                     --#STATE
                ::= 219000

        atpadPort-boot-fail  TRAP-TYPE
                ENTERPRISE   cdx6500
                VARIABLES    { cdx6500SNMPLastTrap }
                DESCRIPTION
                             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
               ::= 219001

        atpadPort-disable  TRAP-TYPE
               ENTERPRISE   cdx6500
               VARIABLES    { cdx6500SNMPLastTrap }
               DESCRIPTION
                            "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
               ::= 219002

        atpadPort-enable  TRAP-TYPE
               ENTERPRISE   cdx6500
               VARIABLES    { cdx6500SNMPLastTrap }
               DESCRIPTION
	                    "%s - PORT ENABLED"
                    --#TYPE
                    --#SUMMARY "Trap #$G, specific: $S, arg(1): $1"
                    --#ARGUMENTS {}
                    --#SEVERITY  INFORMATIONAL
                    --#TIMEINDEX
                    --#HELP
                    --#HELPTAG
                    --#STATE
               ::= 219003

        atpadPort-util-exceeded  TRAP-TYPE
	           ENTERPRISE   cdx6500
	           VARIABLES    { cdx6500SNMPLastTrap }
	           DESCRIPTION
		                "%s - PORT UTILIZATION > THRESHOLD"
                    --#TYPE
                    --#SUMMARY "Trap #$G, specific: $S, arg(1): $1"
                    --#ARGUMENTS {}
                    --#SEVERITY  INFORMATIONAL
                    --#TIMEINDEX
                    --#HELP
                    --#HELPTAG
                    --#STATE
               ::= 219004

        atpadPort-warn-status  TRAP-TYPE
               ENTERPRISE   cdx6500
               VARIABLES    { cdx6500SNMPLastTrap }
               DESCRIPTION
                            "%s - PORT STATUS WARNING - %s"
                    --#TYPE
                    --#SUMMARY "Trap #$G, specific: $S, arg(1): $1"
                    --#ARGUMENTS {}
                    --#SEVERITY  INFORMATIONAL
                    --#TIMEINDEX
                    --#HELP
                    --#HELPTAG
                    --#STATE
               ::= 219005

        atpadPort-errcnt-exceeded  TRAP-TYPE
               ENTERPRISE   cdx6500
               VARIABLES    { cdx6500SNMPLastTrap }
               DESCRIPTION
                            "%s - PORT ERROR COUNT > THRESHOLD"
                    --#TYPE
                    --#SUMMARY "Trap #$G, specific: $S, arg(1): $1"
                    --#ARGUMENTS {}
                    --#SEVERITY  INFORMATIONAL
                    --#TIMEINDEX
                    --#HELP
                    --#HELPTAG
                    --#STATE
               ::= 219006

        lclTerm-stn-up  TRAP-TYPE
		ENTERPRISE   cdx6500
		VARIABLES    { cdx6500SNMPLastTrap }
		DESCRIPTION
		             " %s - STATION UP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 222000

        lclTerm-stn-down  TRAP-TYPE
		ENTERPRISE   cdx6500
		VARIABLES    { cdx6500SNMPLastTrap }
		DESCRIPTION
		             " %s - STATION DOWN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 222001

        lclTerm-stn-timed-out  TRAP-TYPE
		ENTERPRISE   cdx6500
		VARIABLES    { cdx6500SNMPLastTrap }
		DESCRIPTION
		             "%s - STATION TIMED OUT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 222002

        lclTerm-remote-disconn  TRAP-TYPE
		ENTERPRISE   cdx6500
		VARIABLES    { cdx6500SNMPLastTrap }
		DESCRIPTION
		             "%s - STATION RECEIVED A REMOTE DISCONNECT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 222003

        lclTerm-remote-conn-estab  TRAP-TYPE
		ENTERPRISE   cdx6500
		VARIABLES    { cdx6500SNMPLastTrap }
		DESCRIPTION
		             "%s - REMOTE CONNECTION ESTABLISHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 222004

        lclTerm-remote-call-up  TRAP-TYPE
		ENTERPRISE   cdx6500
		VARIABLES    { cdx6500SNMPLastTrap }
		DESCRIPTION
		             "%s - REMOTE CALL ESTABLISHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 222005

        ethltm-station-frame-type-does-n  TRAP-TYPE
		ENTERPRISE   cdx6500
		VARIABLES    { cdx6500SNMPLastTrap }
		DESCRIPTION
		     "%s - STATION FRAME TYPE DOES NOT MATCH RXD FRAME"
		     --#TYPE
		     --#SUMMARY "Trap #$G, specific: $S, arg(1) : $1"
		     --#ARGUMENTS {}
		     --#SEVERITY  MAJOR
		     --#TIMEINDEX
		     --#HELP
		     --#HELPTAG
		     --#STATE
		::= 224000

        ethltm-remote-call-established  TRAP-TYPE
		ENTERPRISE   cdx6500
		VARIABLES    { cdx6500SNMPLastTrap }
		DESCRIPTION
		     "%s - REMOTE CALL ESTABLISHED"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 224001

        frltm-fri-dlci-disconn  TRAP-TYPE
		ENTERPRISE   cdx6500
		VARIABLES    { cdx6500SNMPLastTrap }
		DESCRIPTION
		             " %s - DLCI CHANNEL DISCONNECTED BY FRI."
                     --#TYPE
                     --#SUMMARY "Trap #$G, specific: $S, arg(1): $1"
                     --#ARGUMENTS {}
                     --#SEVERITY  INFORMATIONAL
                     --#TIMEINDEX
                     --#HELP
                     --#HELPTAG
                     --#STATE
		::= 225001

        lctTerm-stn-boot  TRAP-TYPE
		ENTERPRISE   cdx6500
		VARIABLES    { cdx6500SNMPLastTrap }
		DESCRIPTION
		             "%s - STATION BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 226000

        lctTerm-stn-boot-fail  TRAP-TYPE
		ENTERPRISE   cdx6500
		VARIABLES    { cdx6500SNMPLastTrap }
		DESCRIPTION
		             "%s - STATION BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 226001

        lctTerm-stn-disable  TRAP-TYPE
		ENTERPRISE   cdx6500
		VARIABLES    { cdx6500SNMPLastTrap }
		DESCRIPTION
		             "%s - STATION DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 226002

        lctTerm-stn-disable-fail  TRAP-TYPE
		ENTERPRISE   cdx6500
		VARIABLES    { cdx6500SNMPLastTrap }
		DESCRIPTION
		             "%s - STATION DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 226003

        lctTerm-stn-enable  TRAP-TYPE
		ENTERPRISE   cdx6500
		VARIABLES    { cdx6500SNMPLastTrap }
		DESCRIPTION
		             "%s - STATION ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 226004

        lctTerm-stn-enable-fail  TRAP-TYPE
		ENTERPRISE   cdx6500
		VARIABLES    { cdx6500SNMPLastTrap }
		DESCRIPTION
		             "%s - STATION ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 226005

        lctTerm-port-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 226006

        slaccm-insufficient-memory-to-pr  TRAP-TYPE
		ENTERPRISE   cdx6500
		VARIABLES    { cdx6500SNMPLastTrap }
		DESCRIPTION
		     "%s- INSUFFICIENT MEMORY TO PROTECT STATION"
		     --#TYPE
		     --#SUMMARY "Trap #$G, specific: $S, arg(1) : $1"
		     --#ARGUMENTS {}
		     --#SEVERITY  CRITICAL
		     --#TIMEINDEX
		     --#HELP
		     --#HELPTAG
		     --#STATE
		::= 226007

        slaccm-insufficient-memory  TRAP-TYPE
		ENTERPRISE   cdx6500
		VARIABLES    { cdx6500SNMPLastTrap }
		DESCRIPTION
		     "INSUFFICIENT MEMORY TO SUPPORT LLC/SDLC CONFIGURATION"
		     --#TYPE
		     --#SUMMARY "Trap #$G, specific: $S, arg(1) : $1"
		     --#ARGUMENTS {}
		     --#SEVERITY  CRITICAL
		     --#TIMEINDEX
		     --#HELP
		     --#HELPTAG
		     --#STATE
		::= 226008

	slaccm226009-dynamic   TRAP-TYPE
		ENTERPRISE   cdx6500
		VARIABLES    { cdx6500SNMPLastTrap }
		DESCRIPTION
		     "%s - DYNAMIC ALL STATIONS BOOT STARTED"
		     --#TYPE
		     --#SUMMARY "Trap #$G, specific: $S, arg(1) : $1"
		     --#ARGUMENTS {}
		     --#SEVERITY  CRITICAL
		     --#TIMEINDEX
		     --#HELP
		     --#HELPTAG
		     --#STATE
		::= 226009

	slaccm226010-dynamic   TRAP-TYPE
		ENTERPRISE   cdx6500
		VARIABLES    { cdx6500SNMPLastTrap }
		DESCRIPTION
		     "%s - DYNAMIC ALL STATIONS BEING CREATED"
		     --#TYPE
		     --#SUMMARY "Trap #$G, specific: $S, arg(1) : $1"
		     --#ARGUMENTS {}
		     --#SEVERITY  MAJOR
		     --#TIMEINDEX
		     --#HELP
		     --#HELPTAG
		     --#STATE
		::= 226010

	slaccm226011-dynamic   TRAP-TYPE
		ENTERPRISE   cdx6500
		VARIABLES    { cdx6500SNMPLastTrap }
		DESCRIPTION
		     "%s - DYNAMIC ALL STATIONS BOOT COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 226011

	slaccm226012-dynamic   TRAP-TYPE
		ENTERPRISE   cdx6500
		VARIABLES    { cdx6500SNMPLastTrap }
		DESCRIPTION
		     "%s - DYNAMIC STATION BOOT STARTED"
		     --#TYPE
		     --#SUMMARY "Trap #$G, specific: $S, arg(1) : $1"
		     --#ARGUMENTS {}
		     --#SEVERITY  CRITICAL
		     --#TIMEINDEX
		     --#HELP
		     --#HELPTAG
		     --#STATE
		::= 226012

	slaccm226013-dynamic   TRAP-TYPE
		ENTERPRISE   cdx6500
		VARIABLES    { cdx6500SNMPLastTrap }
		DESCRIPTION
		     "%s - DYNAMIC STATION BEING CREATED"
		     --#TYPE
		     --#SUMMARY "Trap #$G, specific: $S, arg(1) : $1"
		     --#ARGUMENTS {}
		     --#SEVERITY  MAJOR
		     --#TIMEINDEX
		     --#HELP
		     --#HELPTAG
		     --#STATE
		::= 226013

	slaccm226014-dynamic   TRAP-TYPE
		ENTERPRISE   cdx6500
		VARIABLES    { cdx6500SNMPLastTrap }
		DESCRIPTION
		     "%s - DYNAMIC STATION BOOT COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 226014

	slaccm226015-insuffi   TRAP-TYPE
		ENTERPRISE   cdx6500
		VARIABLES    { cdx6500SNMPLastTrap }
		DESCRIPTION
		     "INSUFFICIENT DYNAMIC MEMORY TO SUPPORT %s CONFIGURATION"
		     --#TYPE
		     --#SUMMARY "Trap #$G, specific: $S, arg(1) : $1"
		     --#ARGUMENTS {}
		     --#SEVERITY  CRITICAL
		     --#TIMEINDEX
		     --#HELP
		     --#HELPTAG
		     --#STATE
		::= 226015

	slaccm226016-no-stat   TRAP-TYPE
		ENTERPRISE   cdx6500
		VARIABLES    { cdx6500SNMPLastTrap }
		DESCRIPTION
		     "%s - NO STATION CREATED"
		     --#TYPE
		     --#SUMMARY "Trap #$G, specific: $S, arg(1) : $1"
		     --#ARGUMENTS {}
		     --#SEVERITY  CRITICAL
		     --#TIMEINDEX
		     --#HELP
		     --#HELPTAG
		     --#STATE
		::= 226016

	slaccm226017-all-sta   TRAP-TYPE
		ENTERPRISE   cdx6500
		VARIABLES    { cdx6500SNMPLastTrap }
		DESCRIPTION
		     "%s - ALL STATIONS BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 226017

	slaccm226018-will-re   TRAP-TYPE
		ENTERPRISE   cdx6500
		VARIABLES    { cdx6500SNMPLastTrap }
		DESCRIPTION
		     "*** %s WILL REQUIRE FRI BOOT OF PORT %d or\r\n"
		     --#TYPE
		     --#SUMMARY "Trap #$G, specific: $S, arg(1) : $1"
		     --#ARGUMENTS {}
		     --#SEVERITY  CRITICAL
		     --#TIMEINDEX
		     --#HELP
		     --#HELPTAG
		     --#STATE
		::= 226018

	slaccm226019-err-sla   TRAP-TYPE
		ENTERPRISE   cdx6500
		VARIABLES    { cdx6500SNMPLastTrap }
		DESCRIPTION
		     "%s ERR: SLAC DYNAMIC BOOT IN PROGRESS, TRY AGAIN WHEN COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 226019

        tnpplp-link-down  TRAP-TYPE
                ENTERPRISE   cdx6500
                VARIABLES    { cdx6500SNMPLastTrap }
                DESCRIPTION
                             "%s, LINK DOWN - %s, %d DATA FRAMES LOST"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227000      

        tnpplp-link-up  TRAP-TYPE
                ENTERPRISE   cdx6500
                VARIABLES    { cdx6500SNMPLastTrap }
                DESCRIPTION
                             "%s, LINK UP"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227001 

        tnpplp-protocol-errors  TRAP-TYPE
                ENTERPRISE   cdx6500
                VARIABLES    { cdx6500SNMPLastTrap }
                DESCRIPTION
                             "%s, PROTOCOL ERROR"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227002

        tnpplp-frame-discarded  TRAP-TYPE
                ENTERPRISE   cdx6500
                VARIABLES    { cdx6500SNMPLastTrap }
                DESCRIPTION
                             "%s, FRAME DISCARDED - %s, %s - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227003

        tnpplp-rempad-connprogress  TRAP-TYPE
                ENTERPRISE   cdx6500
                VARIABLES    { cdx6500SNMPLastTrap }
                DESCRIPTION
                             "%s - CONNECTION TOWARDS REMOTE TNPP PAD IN PROGRESS"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227004

        tnpplp-autocalltry-exhaust  TRAP-TYPE
                ENTERPRISE   cdx6500
                VARIABLES    { cdx6500SNMPLastTrap }
                DESCRIPTION
                             "%s - AUTOCALL RETRIES EXHAUSTED, REBOOT THE PORT"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227005                 

        tnpplp-remdevice-down  TRAP-TYPE
                ENTERPRISE   cdx6500
                VARIABLES    { cdx6500SNMPLastTrap }
                DESCRIPTION
                             "%s - REMOTE DEVICE IS DOWN"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227006

        tnpplp-rempad-callclear  TRAP-TYPE
                ENTERPRISE   cdx6500
                VARIABLES    { cdx6500SNMPLastTrap }
                DESCRIPTION 
                             "%s - CALL CLEARED BY REMOTE TNPP PAD -%d"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227007

        tnpplp-level3-callreject  TRAP-TYPE
                ENTERPRISE   cdx6500
                VARIABLES    { cdx6500SNMPLastTrap }
                DESCRIPTION
                             "%s - CALL REJECTED BY LEVEL3 -%d"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227008

        tnpplp-mnemonic-error  TRAP-TYPE
                ENTERPRISE   cdx6500
                VARIABLES    { cdx6500SNMPLastTrap }
                DESCRIPTION
                             "%s - MNEMONIC IS EITHER BLANK OR NOT CONFIGURED - %d"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227009

        tnpplp-remdevice-up  TRAP-TYPE
                ENTERPRISE   cdx6500
                VARIABLES    { cdx6500SNMPLastTrap }
                DESCRIPTION
                             "%s - REMOTE DEVICE IS UP"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227010

        tnpplp-x25call-reject  TRAP-TYPE
                ENTERPRISE   cdx6500
                VARIABLES    { cdx6500SNMPLastTrap }
                DESCRIPTION
                             "%s - REJECTING X25 CALL, ALREADY CONNECTED"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227011

        tnpplp-network-callclear  TRAP-TYPE
                ENTERPRISE   cdx6500
                VARIABLES    { cdx6500SNMPLastTrap }
                DESCRIPTION
                             "%s - CALL CLEARED BY NETWORK, CAUSE CODE-%d"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227012 

        tnpplp-rempad-mismatch  TRAP-TYPE
                ENTERPRISE   cdx6500
                VARIABLES    { cdx6500SNMPLastTrap }
                DESCRIPTION
                             "%s - REMOTE PAD IS NOT TNPP PAD, CLEARING CALL "
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227013

        tnpplp-x25-up  TRAP-TYPE
                ENTERPRISE   cdx6500
                VARIABLES    { cdx6500SNMPLastTrap }
                DESCRIPTION
                             "%s - X25 CONNECTION IS UP"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  227014

        tnppPort-boot  TRAP-TYPE
                ENTERPRISE   cdx6500  
                VARIABLES    { cdx6500SNMPLastTrap }
                DESCRIPTION
                             "%s - PORT BOOT COMPLETE "
                     --#TYPE
                     --#SUMMARY "Trap #$G, specific: $S, arg(1): $1"
                     --#ARGUMENTS {}
                     --#SEVERITY  INFORMATIONAL
                     --#TIMEINDEX
                     --#HELP
                     --#HELPTAG
                     --#STATE
                ::=  228000    

        tnppPort-boot-fail  TRAP-TYPE
                ENTERPRISE   cdx6500
                VARIABLES    { cdx6500SNMPLastTrap }
                DESCRIPTION
                            "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE                           
                ::=  228001   

        tnppPort-disable  TRAP-TYPE
                ENTERPRISE   cdx6500
                VARIABLES    { cdx6500SNMPLastTrap }
                DESCRIPTION                                         
                           "%s - PORT DISABLED"           
                     --#TYPE
                     --#SUMMARY "Trap #$G, specific: $S, arg(1): $1"
                     --#ARGUMENTS {}
                     --#SEVERITY  INFORMATIONAL
                     --#TIMEINDEX
                     --#HELP
                     --#HELPTAG
                     --#STATE 
                ::=  228002

        tnppPort-disable-fail  TRAP-TYPE
                ENTERPRISE   cdx6500
                VARIABLES    { cdx6500SNMPLastTrap }
                DESCRIPTION
                             "%s - PORT DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  228003    

        tnppPort-enable  TRAP-TYPE
                ENTERPRISE   cdx6500
                VARIABLES    { cdx6500SNMPLastTrap }
                DESCRIPTION 
                           "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  228004

        tnppPort-enable-fail  TRAP-TYPE
                ENTERPRISE   cdx6500
                VARIABLES    { cdx6500SNMPLastTrap }
                DESCRIPTION
                           "%s - PORT ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  228005                               

        tnppPort-connection-cleared  TRAP-TYPE
                ENTERPRISE   cdx6500
                VARIABLES    { cdx6500SNMPLastTrap }
                DESCRIPTION
                           "%s - PORT CONNECTION CLEARED - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  228006   

        tnppPort-util-exceeded  TRAP-TYPE
                ENTERPRISE   cdx6500
                VARIABLES    { cdx6500SNMPLastTrap }
                DESCRIPTION
                           "%s - %s PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  228007 

        tnppPort-status-warning  TRAP-TYPE
                ENTERPRISE   cdx6500
                VARIABLES    { cdx6500SNMPLastTrap }
                DESCRIPTION
                           "%s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  228008  

        netSvcs-param-err  TRAP-TYPE
		ENTERPRISE   cdx6500
		VARIABLES    { cdx6500SNMPLastTrap }
		DESCRIPTION
		             "NS RUN-TIME PARAMETER ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 229000

        netSvcs-no-features  TRAP-TYPE
		ENTERPRISE   cdx6500
		VARIABLES    { cdx6500SNMPLastTrap }
		DESCRIPTION
		             "NS RUN-TIME ERROR - NO FEATURES"
                     --#TYPE
                     --#SUMMARY "Trap #$G, specific: $S, arg(1): $1"
                     --#ARGUMENTS {}
                     --#SEVERITY  INFORMATIONAL
                     --#TIMEINDEX
                     --#HELP
                     --#HELPTAG
                     --#STATE
		::= 229001

        netSvcs-data-struct-err  TRAP-TYPE
		ENTERPRISE   cdx6500
		VARIABLES    { cdx6500SNMPLastTrap }
		DESCRIPTION
		             "NS RUN-TIME ERROR - DATA STRUCTURE IN ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 229002

        netSvcs-unav-chans  TRAP-TYPE
		ENTERPRISE   cdx6500
		VARIABLES    { cdx6500SNMPLastTrap }
		DESCRIPTION
		             "NS RUN-TIME ERROR -  NO AVAILABLE NS CHANNELS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 229003

        netSvcs-rereg  TRAP-TYPE
		ENTERPRISE   cdx6500
		VARIABLES    { cdx6500SNMPLastTrap }
		DESCRIPTION
		             "NS RUN-TIME ERROR -  CHANNEL OR FEATURE REGISTERED TWICE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 229004

        netSvcs-invalid-config  TRAP-TYPE
		ENTERPRISE   cdx6500
		VARIABLES    { cdx6500SNMPLastTrap }
		DESCRIPTION
		             "%s - NS INVALID CONFIGURATION "
                     --#TYPE
                     --#SUMMARY "Trap #$G, specific: $S, arg(1): $1"
                     --#ARGUMENTS {}
                     --#SEVERITY  INFORMATIONAL
                     --#TIMEINDEX
                     --#HELP
                     --#HELPTAG
                     --#STATE
		::= 229005

        bod-I-lead-up  TRAP-TYPE
                ENTERPRISE   cdx6500
                VARIABLES    { cdx6500SNMPLastTrap }
                DESCRIPTION
                             "%s:UTILIZATION UP:SWITCHED TO HIGH BANDWIDTH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230000

        bod-I-lead-down  TRAP-TYPE
                ENTERPRISE   cdx6500
                VARIABLES    { cdx6500SNMPLastTrap }
                DESCRIPTION
                             "%s:UTILIZATION DOWN:SWITCHED TO LOW BANDWIDTH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230001

        bod-I-leased-line-down  TRAP-TYPE
                ENTERPRISE   cdx6500
                VARIABLES    { cdx6500SNMPLastTrap }
                DESCRIPTION
                             "%s:LEASED LINE DOWN:SWITCHED TO HIGH BANDWIDTH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230002

        bod-I-leased-line-up  TRAP-TYPE
                ENTERPRISE   cdx6500
                VARIABLES    { cdx6500SNMPLastTrap }
                DESCRIPTION
                             "%s:LEASED LINE DOWN:SWITCHED TO HIGH BANDWIDTH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230003

        bod-tow-switch  TRAP-TYPE
                ENTERPRISE   cdx6500
                VARIABLES    { cdx6500SNMPLastTrap }
                DESCRIPTION
                             "%s:TIME OF WEEK DISABLING:SWITCHED TO LOW BANDWIDTH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230004

        bod-tow-disabling  TRAP-TYPE
                ENTERPRISE   cdx6500
                VARIABLES    { cdx6500SNMPLastTrap }
                DESCRIPTION
                             "%s:BOD FEATURE DISABLED BY TIME OF WEEK"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230005

        bod-tow-enabling  TRAP-TYPE
                ENTERPRISE   cdx6500
                VARIABLES    { cdx6500SNMPLastTrap }
                DESCRIPTION
                             "%s:BOD FEATURE ENABLED BY TIME OF WEEK"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230006

        bod-isdn-down  TRAP-TYPE
                ENTERPRISE   cdx6500
                VARIABLES    { cdx6500SNMPLastTrap }
                DESCRIPTION
                             "%s:ISDN LINE DOWN:SWITCHED TO LOW BANDWIDTH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230007

        bod-user-disable  TRAP-TYPE
                ENTERPRISE   cdx6500
                VARIABLES    { cdx6500SNMPLastTrap }
                DESCRIPTION
                             "%s:USER-DISABLE:SWITCHED TO LOW BANDWIDTH"
                     --#TYPE
                     --#SUMMARY "Trap #$G, specific: $S, arg(1): $1"
                     --#ARGUMENTS {}
                     --#SEVERITY  INFORMATIONAL
                     --#TIMEINDEX
                     --#HELP
                     --#HELPTAG
                     --#STATE
               ::= 230008

        bod-Port-disable  TRAP-TYPE
                ENTERPRISE   cdx6500
                VARIABLES    { cdx6500SNMPLastTrap }
                DESCRIPTION
                             "%s:PORT-DISABLE:SWITCHED TO LOW BANDWIDTH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230009

        bod-Port-boot  TRAP-TYPE
                ENTERPRISE   cdx6500
                VARIABLES    { cdx6500SNMPLastTrap }
                DESCRIPTION
                             "%s:PORT-BOOT:SWITCHED TO LOW BANDWIDTH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 230010

        slipPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 231000

        slipPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 231001

        slipPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 231002

        slipPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 231003

        slipPort-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 231004

        slipPort-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 231005

        slipPort-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 231006

        slipProto-inb-data-loss  TRAP-TYPE
		ENTERPRISE   cdx6500
		VARIABLES    { cdx6500SNMPLastTrap }
		DESCRIPTION
		             "%s - DATA LOST FROM DATA QUEUE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 232000

        slipProto-outb-data-loss  TRAP-TYPE
		ENTERPRISE   cdx6500
		VARIABLES    { cdx6500SNMPLastTrap }
		DESCRIPTION
		             "%s - DATA LOST FROM DATA QUEUE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 233000

        slipProto-invalid-encaps  TRAP-TYPE
		ENTERPRISE   cdx6500
		VARIABLES    { cdx6500SNMPLastTrap }
		DESCRIPTION
		             " %s - INVALID ENCAPSULATION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 233001

        lcon-877-unsup-proto-rcvd  TRAP-TYPE
		ENTERPRISE   cdx6500
		VARIABLES    { cdx6500SNMPLastTrap }
		DESCRIPTION
		             " %s - PACKET TYPE NOT SUPPORTED FOR ENCAPSULATION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 234000

        appleTalk-bad-param  TRAP-TYPE
		ENTERPRISE   cdx6500
		VARIABLES    { cdx6500SNMPLastTrap }
		DESCRIPTION
		             "Bad Param in %s: %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236000

        appleTalk-no-mem  TRAP-TYPE
		ENTERPRISE   cdx6500
		VARIABLES    { cdx6500SNMPLastTrap }
		DESCRIPTION
		             "Out of Memory: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236001

        appleTalk-low-prior-traps  TRAP-TYPE
		ENTERPRISE   cdx6500
		VARIABLES    { cdx6500SNMPLastTrap }
		DESCRIPTION
		             " Apple talk protocol subsystem low priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236002

        appleTalk-med-prior-traps  TRAP-TYPE
		ENTERPRISE   cdx6500
		VARIABLES    { cdx6500SNMPLastTrap }
		DESCRIPTION
		             " Apple talk protocol subsystem medium priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236003

        appleTalk-high-prior-traps  TRAP-TYPE
		ENTERPRISE   cdx6500
		VARIABLES    { cdx6500SNMPLastTrap }
		DESCRIPTION
		             "Apple talk protocol subsystem high priority traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236004

        appleTalk-verbose  TRAP-TYPE
		ENTERPRISE   cdx6500
		VARIABLES    { cdx6500SNMPLastTrap }
		DESCRIPTION
		             " Appletalk Port #%d, MsgNum %d: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236005

        appleTalk-warning  TRAP-TYPE
		ENTERPRISE   cdx6500
		VARIABLES    { cdx6500SNMPLastTrap }
		DESCRIPTION
		             " Appletalk Port #%d, ErrorNum %d: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236006

        appleTalk-err  TRAP-TYPE
		ENTERPRISE   cdx6500
		VARIABLES    { cdx6500SNMPLastTrap }
		DESCRIPTION
		             " Appletalk Port #%d, ErrorNum %d: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236007

        appleTalk-fatal-err  TRAP-TYPE
		ENTERPRISE   cdx6500
		VARIABLES    { cdx6500SNMPLastTrap }
		DESCRIPTION
		             "Appletalk Port #%d, ErrorNum %d: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236008

        appleTalk-unknown-err  TRAP-TYPE
		ENTERPRISE   cdx6500
		VARIABLES    { cdx6500SNMPLastTrap }
		DESCRIPTION
		             "Appletalk Port #%d, ErrorNum %d: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236009

        appleTalk-failure  TRAP-TYPE
		ENTERPRISE   cdx6500
		VARIABLES    { cdx6500SNMPLastTrap }
		DESCRIPTION
		             " %s %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 236010

        sip-restart  TRAP-TYPE
                ENTERPRISE   cdx6500
                VARIABLES    { cdx6500SNMPLastTrap }
                DESCRIPTION
                             "SIP is Restarting"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 237000

        sip-lan-restart  TRAP-TYPE
                ENTERPRISE   cdx6500
                VARIABLES    { cdx6500SNMPLastTrap }
                DESCRIPTION
                             "SIP-LAN is Restarting"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 238000

        sip-lan-connect-client  TRAP-TYPE
                ENTERPRISE   cdx6500
                VARIABLES    { cdx6500SNMPLastTrap }
                DESCRIPTION
                             "SIP-LAN Connecting Client #%d, port #%d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 238001

        sip-lan-disconnect-client  TRAP-TYPE
                ENTERPRISE   cdx6500
                VARIABLES    { cdx6500SNMPLastTrap }
                DESCRIPTION
                             "SIP-LAN Disconnecting Client #%d, port #%d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 238002

        sip-wan-restart  TRAP-TYPE
                ENTERPRISE   cdx6500
                VARIABLES    { cdx6500SNMPLastTrap }
                DESCRIPTION
                       "SIP-WAN is Restarting"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 239000

        sip-wan-lan-disconnect  TRAP-TYPE
                ENTERPRISE   cdx6500
                VARIABLES    { cdx6500SNMPLastTrap }
                DESCRIPTION
                             "SIP-WAN is Disconnecting LAN connection"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 239001

        sip-wan-lan-restart  TRAP-TYPE
                ENTERPRISE   cdx6500
                VARIABLES    { cdx6500SNMPLastTrap }
                DESCRIPTION
                             "SIP-WAN is Restarting LAN connection"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 239002

        sip-wan-lan-connect  TRAP-TYPE
                ENTERPRISE   cdx6500
                VARIABLES    { cdx6500SNMPLastTrap }
                DESCRIPTION
                             "SIP-WAN Connected to LAN"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 239003

        sip-wan-lan-disc  TRAP-TYPE
                ENTERPRISE   cdx6500
                VARIABLES    { cdx6500SNMPLastTrap }
                DESCRIPTION
                             "SIP-WAN lost LAN Connection"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 239004

        sip-wan-wan-connect  TRAP-TYPE
                ENTERPRISE   cdx6500
                VARIABLES    { cdx6500SNMPLastTrap }
                DESCRIPTION
                             "SIP-WAN Connected to WAN"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 239005

        sip-wan-wan-disconnect  TRAP-TYPE
                ENTERPRISE   cdx6500
                VARIABLES    { cdx6500SNMPLastTrap }
                DESCRIPTION
                             "SIP-WAN lost WAN Connection"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 239006

        sip-wan-wan-interrupted  TRAP-TYPE
                ENTERPRISE   cdx6500
                VARIABLES    { cdx6500SNMPLastTrap }
                DESCRIPTION
                             "SIP-WAN Connection to WAN Interrupted"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 239007

        bop-bri-no-report  TRAP-TYPE
		ENTERPRISE   cdx6500
		VARIABLES    { cdx6500SNMPLastTrap }
		DESCRIPTION
                       " "
                     --#TYPE
                     --#SUMMARY "Trap #$G, specific: $S, arg(1): $1"
                     --#ARGUMENTS {}
                     --#SEVERITY  INFORMATIONAL
                     --#TIMEINDEX
                     --#HELP
                     --#HELPTAG
                     --#STATE
                ::= 241000

        briPort-call-up  TRAP-TYPE
		ENTERPRISE   cdx6500
		VARIABLES    { cdx6500SNMPLastTrap }
		DESCRIPTION
		             " BRI-%dC%d - CALL %s %s CONNECTED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241001

        briPort-call-down  TRAP-TYPE
		ENTERPRISE   cdx6500
		VARIABLES    { cdx6500SNMPLastTrap }
		DESCRIPTION
		             " BRI-%dC%d - CALL %s %s DISCONNECTED. REASON CODE = %d,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241002

        briPort-tx-setup-fail  TRAP-TYPE
		ENTERPRISE   cdx6500
		VARIABLES    { cdx6500SNMPLastTrap }
		DESCRIPTION
		             "BRI-%dC%d - CALL SETUP TO %s FAILED. REASON CODE =  %d,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241003

        briPort-rx-setup-fail  TRAP-TYPE
		ENTERPRISE   cdx6500
		VARIABLES    { cdx6500SNMPLastTrap }
		DESCRIPTION
		             "BRI-%dC%d - CALL SETUP FROM %s FAILED. REASON CODE =  %d,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241004

        briPort-disconn-fail  TRAP-TYPE
		ENTERPRISE   cdx6500
		VARIABLES    { cdx6500SNMPLastTrap }
		DESCRIPTION
		             "BRI-%dC%d - CALL %s %s DISCONNECT FAILED. REASON CODE = %d,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241005

        briPort-tx-call-fail  TRAP-TYPE
		ENTERPRISE   cdx6500
		VARIABLES    { cdx6500SNMPLastTrap }
		DESCRIPTION
		             " BRI-%dC%d - CALL SETUP TO %s DISCONNECTED BEFORE CONNECTION COMPLETED. REASON CODE = %d,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241006

        briPort-rx-call-fail  TRAP-TYPE
		ENTERPRISE   cdx6500
		VARIABLES    { cdx6500SNMPLastTrap }
		DESCRIPTION
		             " BRI-%dC%d - CALL SETUP FROM %s REJECTED. REASON CODE = %d,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241007

        briPort-init-fail  TRAP-TYPE
		ENTERPRISE   cdx6500
		VARIABLES    { cdx6500SNMPLastTrap }
		DESCRIPTION
		             "BRI-%d - INITIALIZATION INCOMPLETE. REASON CODE = %x,%x,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241008

        briPort-boot-fail  TRAP-TYPE
		ENTERPRISE   cdx6500
		VARIABLES    { cdx6500SNMPLastTrap }
		DESCRIPTION
		             "BRI-%d - PORT BOOT FAILED. REASON CODE = %x,%x,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241009

        briPort-boot  TRAP-TYPE
		ENTERPRISE   cdx6500
		VARIABLES    { cdx6500SNMPLastTrap }
		DESCRIPTION
		             "BRI-%d - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241010

        briPort-buff-congested  TRAP-TYPE
		ENTERPRISE   cdx6500
		VARIABLES    { cdx6500SNMPLastTrap }
		DESCRIPTION
		             " BRI-%dC%d - BRI TX BUFFERS CONGESTED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241011

        briPort-dchan-err  TRAP-TYPE
		ENTERPRISE   cdx6500
		VARIABLES    { cdx6500SNMPLastTrap }
		DESCRIPTION
		             "BRI-%dC%d - X.25 OVER D CHANNEL ERROR: %x,%d%,%x,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241012

        briPort-card-fail  TRAP-TYPE
		ENTERPRISE   cdx6500
		VARIABLES    { cdx6500SNMPLastTrap }
		DESCRIPTION
		             "BRI CARD FAILURE: %x,%x,%x,%x"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241013

        briPort-dchan-link-down  TRAP-TYPE
		ENTERPRISE   cdx6500
		VARIABLES    { cdx6500SNMPLastTrap }
		DESCRIPTION
		             "BRI-%dC%d - LINK DOWN, CAUSE = %d, DIAG = %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 241014

        bopbri-bri-internal-error  TRAP-TYPE
		ENTERPRISE   cdx6500
		VARIABLES    { cdx6500SNMPLastTrap }
		DESCRIPTION
		     "BRI INTERNAL ERROR: %d,%x,%x,%x"
		     --#TYPE
		     --#SUMMARY "Trap #$G, specific: $S, arg(1) : $1"
		     --#ARGUMENTS {}
		     --#SEVERITY  CRITICAL
		     --#TIMEINDEX
		     --#HELP
		     --#HELPTAG
		     --#STATE
		::= 241015

	bopbri241062-channel   TRAP-TYPE
		ENTERPRISE   cdx6500
		VARIABLES    { cdx6500SNMPLastTrap }
		DESCRIPTION
		     " Channel %d state variable is at location 0x%x"
		     --#TYPE
		     --#SUMMARY "Trap #$G, specific: $S, arg(1) : $1"
		     --#ARGUMENTS {}
		     --#SEVERITY  MINOR
		     --#TIMEINDEX
		     --#HELP
		     --#HELPTAG
		     --#STATE
		::= 241062

        swServ-link-activated  TRAP-TYPE
		ENTERPRISE   cdx6500
		VARIABLES    { cdx6500SNMPLastTrap }
		DESCRIPTION
		             "BACKUP/SWSERVICE PORT %s ACTIVATED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 242000

        swServ-link-deactivated  TRAP-TYPE
		ENTERPRISE   cdx6500
		VARIABLES    { cdx6500SNMPLastTrap }
		DESCRIPTION
		             "LINK %s DEACTIVATED -- REASON: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 242001

        swServ-invalid-entry  TRAP-TYPE
		ENTERPRISE   cdx6500
		VARIABLES    { cdx6500SNMPLastTrap }
		DESCRIPTION
		             "SS: ENTRY %s IS INVALID."
                     --#TYPE
                     --#SUMMARY "Trap #$G, specific: $S, arg(1): $1"
                     --#ARGUMENTS {}
                     --#SEVERITY  INFORMATIONAL
                     --#TIMEINDEX
                     --#HELP
                     --#HELPTAG
                     --#STATE
		::= 242002

        swServ-serving-multi-ports  TRAP-TYPE
		ENTERPRISE   cdx6500
		VARIABLES    { cdx6500SNMPLastTrap }
		DESCRIPTION
		             "LBU port %s is now servicing multiple ports."
                     --#TYPE
                     --#SUMMARY "Trap #$G, specific: $S, arg(1): $1"
                     --#ARGUMENTS {}
                     --#SEVERITY  INFORMATIONAL
                     --#TIMEINDEX
                     --#HELP
                     --#HELPTAG
                     --#STATE
		::= 242003

        swServ-param-error  TRAP-TYPE
		ENTERPRISE   cdx6500
		VARIABLES    { cdx6500SNMPLastTrap }
		DESCRIPTION
		             "SS RUN-TIME PARAMETER ERROR"
                     --#TYPE
                     --#SUMMARY "Trap #$G, specific: $S, arg(1): $1"
                     --#ARGUMENTS {}
                     --#SEVERITY  INFORMATIONAL
                     --#TIMEINDEX
                     --#HELP
                     --#HELPTAG
                     --#STATE
		::= 242004

        swServ-already-active  TRAP-TYPE
		ENTERPRISE   cdx6500
		VARIABLES    { cdx6500SNMPLastTrap }
		DESCRIPTION
		             "SS incoming call on already active link"
                     --#TYPE
                     --#SUMMARY "Trap #$G, specific: $S, arg(1): $1"
                     --#ARGUMENTS {}
                     --#SEVERITY  INFORMATIONAL
                     --#TIMEINDEX
                     --#HELP
                     --#HELPTAG
                     --#STATE
		::= 242005

        swServ-num-entries-changed  TRAP-TYPE
		ENTERPRISE   cdx6500
		VARIABLES    { cdx6500SNMPLastTrap }
		DESCRIPTION
		             "THE NUMBER OF SWITCHED SERVICE ENTRIES HAS BEEN CHANGED. A NODE BOOT IS REQUIRED."
                     --#TYPE
                     --#SUMMARY "Trap #$G, specific: $S, arg(1): $1"
                     --#ARGUMENTS {}
                     --#SEVERITY  INFORMATIONAL
                     --#TIMEINDEX
                     --#HELP
                     --#HELPTAG
                     --#STATE
		::= 242006

        swServ-dest-changed  TRAP-TYPE
		ENTERPRISE   cdx6500
		VARIABLES    { cdx6500SNMPLastTrap }
		DESCRIPTION
		             "DESTINATION NAME IN SWITCHED SERVICE ENTRY #%d HAS BEEN CHANGED. A NODE BOOT IS REQUIRED."
                     --#TYPE
                     --#SUMMARY "Trap #$G, specific: $S, arg(1): $1"
                     --#ARGUMENTS {}
                     --#SEVERITY  INFORMATIONAL
                     --#TIMEINDEX
                     --#HELP
                     --#HELPTAG
                     --#STATE
		::= 242007

        swServ-monitored-changed  TRAP-TYPE
		ENTERPRISE   cdx6500
		VARIABLES    { cdx6500SNMPLastTrap }
		DESCRIPTION
		             "MONITORED NAME IN SWITCHED SERVICE ENTRY #%d HAS BEEN CHANGED. A NODE BOOT IS REQUIRED."
                     --#TYPE
                     --#SUMMARY "Trap #$G, specific: $S, arg(1): $1"
                     --#ARGUMENTS {}
                     --#SEVERITY  INFORMATIONAL
                     --#TIMEINDEX
                     --#HELP
                     --#HELPTAG
                     --#STATE
		::= 242008

        swServ-backup-changed  TRAP-TYPE
		ENTERPRISE   cdx6500
		VARIABLES    { cdx6500SNMPLastTrap }
		DESCRIPTION
		             "BACKUP NAME IN SWITCHED SERVICE ENTRY #%d HAS BEEN CHANGED. A NODE BOOT IS REQUIRED."
                     --#TYPE
                     --#SUMMARY "Trap #$G, specific: $S, arg(1): $1"
                     --#ARGUMENTS {}
                     --#SEVERITY  INFORMATIONAL
                     --#TIMEINDEX
                     --#HELP
                     --#HELPTAG
                     --#STATE
		::= 242009

        ss-number-of-max-entries-in-node  TRAP-TYPE
		ENTERPRISE   cdx6500
		VARIABLES    { cdx6500SNMPLastTrap }
		DESCRIPTION
		     "NUMBER OF MAX SS ENTRIES IN NODE RECORD \r\n"
		     --#TYPE
		     --#SUMMARY "Trap #$G, specific: $S, arg(1) : $1"
		     --#ARGUMENTS {}
		     --#SEVERITY  CRITICAL
		     --#TIMEINDEX
		     --#HELP
		     --#HELPTAG
		     --#STATE
		::= 242010

	ss242011-process-msg   TRAP-TYPE
		ENTERPRISE   cdx6500
		VARIABLES    { cdx6500SNMPLastTrap }
		DESCRIPTION
		     "PROCESS-MSG: LINK %s : STATUS: %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 242011

	ss242012-ss-dynamic-rte   TRAP-TYPE
		ENTERPRISE   cdx6500
		VARIABLES    { cdx6500SNMPLastTrap }
		DESCRIPTION
		     "SS-DYNAMIC-RTE: %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 242012

	ss242013-select-dest   TRAP-TYPE
		ENTERPRISE   cdx6500
		VARIABLES    { cdx6500SNMPLastTrap }
		DESCRIPTION
		     "Select Destination: %s  %s  %s  %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 242013

	ss242014-select-cond   TRAP-TYPE
		ENTERPRISE   cdx6500
		VARIABLES    { cdx6500SNMPLastTrap }
		DESCRIPTION
		     "Select Condition: Chain: %d  PID: %s TbleAddr: %d SETUP: %d Tel: %d igST: %d Status:%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 242014

	ss242015-process-msg   TRAP-TYPE
		ENTERPRISE   cdx6500
		VARIABLES    { cdx6500SNMPLastTrap }
		DESCRIPTION
		     "Process Msg: PID: %s Event: %s x25cause: %d x25diag: %d State:%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 242015

	ss242016-cmem-compre   TRAP-TYPE
		ENTERPRISE   cdx6500
		VARIABLES    { cdx6500SNMPLastTrap }
		DESCRIPTION
		     "CMEM Compression: Parameter Value: %s\t\t Param Size: %d Current Size: %d Rec. Size: %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 242016

	ss242017-cmem-decomp   TRAP-TYPE
		ENTERPRISE   cdx6500
		VARIABLES    { cdx6500SNMPLastTrap }
		DESCRIPTION
		     "CMEM Decompression: Parameter Value: %s\t\t Param Size: %d Current Size: %d Comp Size: %d Rec. Size: %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 242017

        ss242018-ss-max-retries   TRAP-TYPE
                ENTERPRISE   cdx6500
                VARIABLES    { cdx6500SNMPLastTrap }
                DESCRIPTION
                     "DIAL OUT FAILURE - CALL RETRIES EXCEEDED"
                     --#TYPE
                     --#SUMMARY "Trap #$G, specific: $S, arg(1) : $1"
                     --#ARGUMENTS {}
                     --#SEVERITY  INFORMATIONAL
                     --#TIMEINDEX
                     --#HELP
                     --#HELPTAG
                     --#STATE
                ::= 242018

	ss242019-max-callid   TRAP-TYPE
		ENTERPRISE   cdx6500
		VARIABLES    { cdx6500SNMPLastTrap }
		DESCRIPTION
		     "MAX CALLID TABLE SIZE IN NODE RECORD \r\n"
		     --#TYPE
		     --#SUMMARY "Trap #$G, specific: $S, arg(1) : $1"
		     --#ARGUMENTS {}
		     --#SEVERITY  CRITICAL
		     --#TIMEINDEX
		     --#HELP
		     --#HELPTAG
		     --#STATE
		::= 242019

	ss242020-possible-ra   TRAP-TYPE
		ENTERPRISE   cdx6500
		VARIABLES    { cdx6500SNMPLastTrap }
		DESCRIPTION
		     "POSSIBLE RACE CONDITION IN SWITCH SERVICES - LINK ACTIVATE TIMER EXPIRED for %s"
		     --#TYPE
		     --#SUMMARY "Trap #$G, specific: $S, arg(1) : $1"
		     --#ARGUMENTS {}
		     --#SEVERITY  CRITICAL
		     --#TIMEINDEX
		     --#HELP
		     --#HELPTAG
		     --#STATE
		::= 242020

        hubPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 243000

        hubPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 243001

        hubPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 243002

        hubPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 243003

        hubPort-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 243004

        briPort-chan-boot  TRAP-TYPE
		ENTERPRISE   cdx6500
		VARIABLES    { cdx6500SNMPLastTrap }
		DESCRIPTION
		             "%s - CHANNEL BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245000

        briPort-chan-boot-fail  TRAP-TYPE
		ENTERPRISE   cdx6500
		VARIABLES    { cdx6500SNMPLastTrap }
		DESCRIPTION
		             "%s - CHANNEL BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245001

        bri-Port-boot  TRAP-TYPE
                ENTERPRISE   cdx6500
                VARIABLES    { cdx6500SNMPLastTrap }
                DESCRIPTION
                             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 245002

        briPort-invalid-boot  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245003

        briPort-chan-disable  TRAP-TYPE
		ENTERPRISE   cdx6500
		VARIABLES    { cdx6500SNMPLastTrap }
		DESCRIPTION
		             "%s - CHANNEL DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245004

        briPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245005

        briPort-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245006

        briPort-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245007

        briPort-chan-warn-status  TRAP-TYPE
		ENTERPRISE   cdx6500
		VARIABLES    { cdx6500SNMPLastTrap }
		DESCRIPTION
		             " %s - CHANNEL STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245008

        briPort-chan-enable  TRAP-TYPE
		ENTERPRISE   cdx6500
		VARIABLES    { cdx6500SNMPLastTrap }
		DESCRIPTION
		             "%s - CHANNEL ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245009

        briPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245010

        briPort-chan-util-exceeded  TRAP-TYPE
		ENTERPRISE   cdx6500
		VARIABLES    { cdx6500SNMPLastTrap }
		DESCRIPTION
		             " %s - CHANNEL UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245011

        briPort-no-chans  TRAP-TYPE
		ENTERPRISE   cdx6500
		VARIABLES    { cdx6500SNMPLastTrap }
		DESCRIPTION
		             "%s - NO CHANNELS CONFIGURED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 245012

        briPort-protocol-mismatch  TRAP-TYPE
                ENTERPRISE   cdx6500
                VARIABLES    { cdx6500SNMPLastTrap }
                DESCRIPTION
                             "%s - INIT FAILED - PROTOCOL TYPE MISMATCH"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 245013

	bri245014-card-failu   TRAP-TYPE
		ENTERPRISE   cdx6500
		VARIABLES    { cdx6500SNMPLastTrap }
		DESCRIPTION
		     "%s - CARD FAILURE DETECTED - AUTO-RECOVERY INITIATED"
		     --#TYPE
		     --#SUMMARY "Trap #$G, specific: $S, arg(1) : $1"
		     --#ARGUMENTS {}
		     --#SEVERITY  CRITICAL
		     --#TIMEINDEX
		     --#HELP
		     --#HELPTAG
		     --#STATE
		::= 245014

	bri245015-port-boot   TRAP-TYPE
		ENTERPRISE   cdx6500
		VARIABLES    { cdx6500SNMPLastTrap }
		DESCRIPTION
		     "%s - PORT BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 245015

	bri245016-auto-recov   TRAP-TYPE
		ENTERPRISE   cdx6500
		VARIABLES    { cdx6500SNMPLastTrap }
		DESCRIPTION
		     "%s - AUTO RECOVERY COMPLETE - PARAMETERS NOT CHANGED"
		     --#TYPE
		     --#SUMMARY "Trap #$G, specific: $S, arg(1) : $1"
		     --#ARGUMENTS {}
		     --#SEVERITY  CRITICAL
		     --#TIMEINDEX
		     --#HELP
		     --#HELPTAG
		     --#STATE
		::= 245016

        briPort-pkt-lvl-restart  TRAP-TYPE
		ENTERPRISE   cdx6500
		VARIABLES    { cdx6500SNMPLastTrap }
		DESCRIPTION
		             " %s - PACKET LEVEL RESTART"
                     --#TYPE
                     --#SUMMARY "Trap #$G, specific: $S, arg(1): $1"
                     --#ARGUMENTS {}
                     --#SEVERITY  INFORMATIONAL
                     --#TIMEINDEX
                     --#HELP
                     --#HELPTAG
                     --#STATE
		::= 246000

        dc-dsp-disabled  TRAP-TYPE
		ENTERPRISE   cdx6500
		VARIABLES    { cdx6500SNMPLastTrap }
		DESCRIPTION
		             "DC - DATA COMPRESSION DISABLED, POWER-UP DIAGNOSTICS FAILURE "
                     --#TYPE
                     --#SUMMARY "Trap #$G, specific: $S, arg(1): $1"
                     --#ARGUMENTS {}
                     --#SEVERITY  INFORMATIONAL
                     --#TIMEINDEX
                     --#HELP
                     --#HELPTAG
                     --#STATE
		::= 248000

        dc-dsp-fail  TRAP-TYPE
		ENTERPRISE   cdx6500
		VARIABLES    { cdx6500SNMPLastTrap }
		DESCRIPTION
		             "DC - DATA COMPRESSION DISABLED, DC HARDWARE FAILURE "
                     --#TYPE
                     --#SUMMARY "Trap #$G, specific: $S, arg(1): $1"
                     --#ARGUMENTS {}
                     --#SEVERITY  INFORMATIONAL
                     --#TIMEINDEX
                     --#HELP
                     --#HELPTAG
                     --#STATE
		::= 248001

        dc-no-ram  TRAP-TYPE
		ENTERPRISE   cdx6500
		VARIABLES    { cdx6500SNMPLastTrap }
		DESCRIPTION
		             "DC - DATA COMPRESSION DISABLED, DSP RAM NOT FOUND"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248002

        dc-insuff-ram  TRAP-TYPE
		ENTERPRISE   cdx6500
		VARIABLES    { cdx6500SNMPLastTrap }
		DESCRIPTION
		             "DC - INSUFFICIENT RAM FOR DATA COMPRESSION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248003

        dc-no-channels  TRAP-TYPE
		ENTERPRISE   cdx6500
		VARIABLES    { cdx6500SNMPLastTrap }
		DESCRIPTION
		             "DC - CHANNEL UNAVAILABLE, CALL REJECTED FOR %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248004

        dc-rcvd-neg  TRAP-TYPE
		ENTERPRISE   cdx6500
		VARIABLES    { cdx6500SNMPLastTrap }
		DESCRIPTION
		             "DC - %s RECEIVED NEGOTIATE FACILITY IN CALL REQUEST AND IS CONFIGURED AS FORCE ON"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248005

        dc-mis-configure  TRAP-TYPE
		ENTERPRISE   cdx6500
		VARIABLES    { cdx6500SNMPLastTrap }
		DESCRIPTION
		             "DC - PVC MISCONFIGURED, %s IS AN AP CONNECTING TO ANOTHER AP"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248006

        dc-abnorm-clr-flush  TRAP-TYPE
		ENTERPRISE   cdx6500
		VARIABLES    { cdx6500SNMPLastTrap }
		DESCRIPTION
		             "DC - ABNORMAL CLEAR FLUSH FROM NS: Event=%d, State=%d, Chan-ID=%d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248007

        dc-lost-clr  TRAP-TYPE
		ENTERPRISE   cdx6500
		VARIABLES    { cdx6500SNMPLastTrap }
		DESCRIPTION
		             "DC - LOST/PENDING CALL CLEAR IN EP Q: Event=%d, State=%d, Chan-ID=%d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248008

        dc-ap-to-ap  TRAP-TYPE
		ENTERPRISE   cdx6500
		VARIABLES    { cdx6500SNMPLastTrap }
		DESCRIPTION
		             "DC - %s IS CONNECTED TO ANOTHER AP, COMPRESSION IS NOT ALLOWED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248009

        dc-no-chan-for-pvc  TRAP-TYPE
		ENTERPRISE   cdx6500
		VARIABLES    { cdx6500SNMPLastTrap }
		DESCRIPTION
		             "DC - CHANNEL UNAVAILABLE, PVC %s DID NOT GET CONNECTED WITH DATA COMPRESSION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248010

        dc-src-config-err  TRAP-TYPE
		ENTERPRISE   cdx6500
		VARIABLES    { cdx6500SNMPLastTrap }
		DESCRIPTION
		             "DC - CALL REQUEST ORIGINATOR IS NOT CONFIGURED FOR DATA COMPRESSION - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248011

        dc-corrupt-control-blk  TRAP-TYPE
		ENTERPRISE   cdx6500
		VARIABLES    { cdx6500SNMPLastTrap }
		DESCRIPTION
		             "DC - %s CLEARED THE CALL DURING SRC NEGOTIATION, SAVED FACILITY WAS %d, CORRUPTED CONTROL BLOCK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248012

        dc-abnorm-cmd  TRAP-TYPE
		ENTERPRISE   cdx6500
		VARIABLES    { cdx6500SNMPLastTrap }
		DESCRIPTION
		             "DC - ABNORMAL COMMAND ID FROM NS: Command-ID = %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248013

        dc-dsp-download-err  TRAP-TYPE
		ENTERPRISE   cdx6500
		VARIABLES    { cdx6500SNMPLastTrap }
		DESCRIPTION
		             "DC - DATA COMPRESSION DISABLED, DSP DOWNLOAD FAILURE, STATUS = %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248014

        dc-incorrect-config  TRAP-TYPE
		ENTERPRISE   cdx6500
		VARIABLES    { cdx6500SNMPLastTrap }
		DESCRIPTION
		             "DC - %s CONFIGURATION IS INCORRECT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248015

        dc-hdr-err  TRAP-TYPE
		ENTERPRISE   cdx6500
		VARIABLES    { cdx6500SNMPLastTrap }
		DESCRIPTION
		             "DC - DATA COMPRESSION HEADER ERROR, AP=%s, NP=%s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 248016

        dc-max-dc-chan  TRAP-TYPE
                ENTERPRISE   cdx6500
                VARIABLES    { cdx6500SNMPLastTrap }
                DESCRIPTION
                             "DC - NODE CONFIGURATION FOR DATA COMPRESSION CHANNELS DIFFERS CMEM. MAX DC CHANNELS=%d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248017

        dc-gen-init-fail  TRAP-TYPE
                ENTERPRISE   cdx6500
                VARIABLES    { cdx6500SNMPLastTrap }
                DESCRIPTION
                             "DC - DC HANDLER GENERAL INIT FAILURE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248018

        dc-dbg-sem-locked  TRAP-TYPE
                ENTERPRISE   cdx6500
                VARIABLES    { cdx6500SNMPLastTrap }
                DESCRIPTION
                             "DC - THE DC CONTEXT WAS ALREADY LOCKED, UNABLE TO ALLOCATE RESOURCES, %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248019

        dc-dbg-ca-no-cr  TRAP-TYPE
                ENTERPRISE   cdx6500
                VARIABLES    { cdx6500SNMPLastTrap }
                DESCRIPTION
                             "DC - DC WAS CALLED TO PROCESS CALL ACCEPT WITHOUT
A SAVED CALL REQUEST FOR %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248020

        dc-dbg-no-config  TRAP-TYPE
                ENTERPRISE   cdx6500
                VARIABLES    { cdx6500SNMPLastTrap }
                DESCRIPTION
                             "DC - dca-get-config-value() WAS CALLED WHEN CONFIG AS DISABLED FOR %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248021

        dc-dbg-dealloc-no-cb  TRAP-TYPE
                ENTERPRISE   cdx6500
                VARIABLES    { cdx6500SNMPLastTrap }
                DESCRIPTION
                             "DC - dca-deallocate-resources() WAS CALLED WITH A NULL DCCB PTR"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248022

        dc-dbg-dch-ch-stat-fail  TRAP-TYPE
                ENTERPRISE   cdx6500
                VARIABLES    { cdx6500SNMPLastTrap }
                DESCRIPTION
                             "DC - DCH RESET STATS FAILED < %s > FOR CHANNEL %d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248023

        dc-dbg-lost-buffs  TRAP-TYPE
                ENTERPRISE   cdx6500
                VARIABLES    { cdx6500SNMPLastTrap }
                DESCRIPTION
                             "DC - M BIT PACKETS LOST FOR CHANNEL %d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248024

        dc-dbg-abnorm-fsm-event  TRAP-TYPE
                ENTERPRISE   cdx6500
                VARIABLES    { cdx6500SNMPLastTrap }
                DESCRIPTION
                             "DC - ABNORMAL FSM EVENT: Event=%d, State=%d, Chan-ID=%d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248025

        dc-dbg-zero-out-desc-cnt  TRAP-TYPE
                ENTERPRISE   cdx6500
                VARIABLES    { cdx6500SNMPLastTrap }
                DESCRIPTION
                             "DC - OUTPUT DESCRIPTOR BUFFER COUNT REACHED ZERO"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248026

        dc-dbg-dch-func-status-fail  TRAP-TYPE
                ENTERPRISE   cdx6500
                VARIABLES    { cdx6500SNMPLastTrap }
                DESCRIPTION
                             "DC - dch-api-status-dcfunct() WAS CALLED CONCURRENTLY"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248027

        dc-dbg-dch-ch-prov-fail  TRAP-TYPE
                ENTERPRISE   cdx6500
                VARIABLES    { cdx6500SNMPLastTrap }
                DESCRIPTION
                             "DC - dca-provide-buffers() DETECTED dch-api-dho-provide-new-buf() WAS CALLED CONCURRENTLY"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248028

        dc-dbg-dch-ch-pop-fail  TRAP-TYPE
                ENTERPRISE   cdx6500
                VARIABLES    { cdx6500SNMPLastTrap }
                DESCRIPTION
                             "DC - dca-pop-output-packet() DETECTED dch-api-dho-pop() WAS CALLED CONCURRENTLY"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248029

        dc-dbg-dch-ch-free-fail  TRAP-TYPE
                ENTERPRISE   cdx6500
                VARIABLES    { cdx6500SNMPLastTrap }
                DESCRIPTION
                             "DC - dca-pop-used-packet() DETECTED dch-api-dhi-free-used-buf() WAS CALLED CONCURRENTLY"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248030

        dc-dbg-bad-compress  TRAP-TYPE
                ENTERPRISE   cdx6500
                VARIABLES    { cdx6500SNMPLastTrap }
                DESCRIPTION
                             "DC - BAD COMPRESSED PACKET"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248031

        dc-dbg-func-type-fail  TRAP-TYPE
                ENTERPRISE   cdx6500
                VARIABLES    { cdx6500SNMPLastTrap }
                DESCRIPTION
                             "DC - DC HANDLER FUNC TYPE FAILURE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248032

        dc-dbg-chan-num-fail  TRAP-TYPE
                ENTERPRISE   cdx6500
                VARIABLES    { cdx6500SNMPLastTrap }
                DESCRIPTION
                             "DC - DC HANDLER CHANNEL NUMBER FAILURE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 248033

        dc-dbg-chan-stat-fail  TRAP-TYPE
                ENTERPRISE   cdx6500
                VARIABLES    { cdx6500SNMPLastTrap }
                DESCRIPTION
                             "DC - DC HANDLER CHANNEL STATISTICS FAILURE, STATUS = %d"
               --#TYPE
	       --#SUMMARY "Trap #$G, specific: $S, arg(1): $1"
	       --#ARGUMENTS {}
	       --#SEVERITY  INFORMATIONAL
	       --#TIMEINDEX
	       --#HELP
	       --#HELPTAG
	       --#STATE
                ::= 248034

        dc-dbg-chan-reset-fail  TRAP-TYPE
                ENTERPRISE   cdx6500
                VARIABLES    { cdx6500SNMPLastTrap }
                DESCRIPTION
                             "DC - DC HANDLER VOCABULARY RESET FAILURE"
               --#TYPE
	       --#SUMMARY "Trap #$G, specific: $S, arg(1): $1"
	       --#ARGUMENTS {}
	       --#SEVERITY  INFORMATIONAL
	       --#TIMEINDEX
	       --#HELP
	       --#HELPTAG
	       --#STATE
                ::= 248035

        dc-dbg-frm-error  TRAP-TYPE
                ENTERPRISE   cdx6500
                VARIABLES    { cdx6500SNMPLastTrap }
                DESCRIPTION
                             "DC - DATA COMPRESSION FRAME ERROR, AP=%s, NP=%s"
               --#TYPE
	       --#SUMMARY "Trap #$G, specific: $S, arg(1): $1"
	       --#ARGUMENTS {}
	       --#SEVERITY  INFORMATIONAL
	       --#TIMEINDEX
	       --#HELP
	       --#HELPTAG
	       --#STATE
                ::= 248036

        dc-dbg-qpck-cnt-error  TRAP-TYPE
                ENTERPRISE   cdx6500
                VARIABLES    { cdx6500SNMPLastTrap }
                DESCRIPTION
                             "DC - dca-channel-flush(): PACKET COUNT ON THE QUEUE IS NON-ZERO"
               --#TYPE
	       --#SUMMARY "Trap #$G, specific: $S, arg(1): $1"
	       --#ARGUMENTS {}
	       --#SEVERITY  INFORMATIONAL
	       --#TIMEINDEX
	       --#HELP
	       --#HELPTAG
	       --#STATE
                ::= 248037

        dc-dbg-dch-ch-nb-fail  TRAP-TYPE
                ENTERPRISE   cdx6500
                VARIABLES    { cdx6500SNMPLastTrap }
                DESCRIPTION
                             "DC - dch-api-dho-provide-new-buf() RETURNED DCH FAILURE"
               --#TYPE
	       --#SUMMARY "Trap #$G, specific: $S, arg(1): $1"
	       --#ARGUMENTS {}
	       --#SEVERITY  INFORMATIONAL
	       --#TIMEINDEX
	       --#HELP
	       --#HELPTAG
	       --#STATE
                ::= 248038

        dc-dbg-reset-stat-fail  TRAP-TYPE
                ENTERPRISE   cdx6500
                VARIABLES    { cdx6500SNMPLastTrap }
                DESCRIPTION
                             "DC - DC HANDLER CHANNEL STATS RESET FAILURE, STATUS = %d"
               --#TYPE
	       --#SUMMARY "Trap #$G, specific: $S, arg(1): $1"
	       --#ARGUMENTS {}
	       --#SEVERITY  INFORMATIONAL
	       --#TIMEINDEX
	       --#HELP
	       --#HELPTAG
	       --#STATE
                ::= 248039

        dc-dbg-chan-status-fail  TRAP-TYPE
                ENTERPRISE   cdx6500
                VARIABLES    { cdx6500SNMPLastTrap }
                DESCRIPTION
                             "DC - DC HANDLER CHANNEL STATUS FAILURE, STATUS = %d"
               --#TYPE
	       --#SUMMARY "Trap #$G, specific: $S, arg(1): $1"
	       --#ARGUMENTS {}
	       --#SEVERITY  INFORMATIONAL
	       --#TIMEINDEX
	       --#HELP
	       --#HELPTAG
	       --#STATE
                ::= 248040

        dc-dbg-param-error  TRAP-TYPE
                ENTERPRISE   cdx6500
                VARIABLES    { cdx6500SNMPLastTrap }
                DESCRIPTION
                             "DC - RUN-TIME PARAMETER ERROR"
               --#TYPE
	       --#SUMMARY "Trap #$G, specific: $S, arg(1): $1"
	       --#ARGUMENTS {}
	       --#SEVERITY  INFORMATIONAL
	       --#TIMEINDEX
	       --#HELP
	       --#HELPTAG
	       --#STATE
                ::= 248041

        dc-dbg-hw-missing  TRAP-TYPE
                ENTERPRISE   cdx6500
                VARIABLES    { cdx6500SNMPLastTrap }
                DESCRIPTION
                             "DC - DATA COMPRESSION DISABLED, DC SIMM MISSING "
               --#TYPE
	       --#SUMMARY "Trap #$G, specific: $S, arg(1): $1"
	       --#ARGUMENTS {}
	       --#SEVERITY  INFORMATIONAL
	       --#TIMEINDEX
	       --#HELP
	       --#HELPTAG
	       --#STATE
                ::= 248042

        x32Port-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250000

        x32Port-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250001

        x32Port-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250002

        x32Port-disable-fail  TRAP-TYPE
		ENTERPRISE   cdx6500
		VARIABLES    { cdx6500SNMPLastTrap }
		DESCRIPTION
		             "%s - PORT DISABLE FAILURE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250003

        x32Port-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250004

        x32Port-enable-fail  TRAP-TYPE
		ENTERPRISE   cdx6500
		VARIABLES    { cdx6500SNMPLastTrap }
		DESCRIPTION
		             "%s - PORT ENABLE FAILURE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250005

        x32Port-conn-clear  TRAP-TYPE
		ENTERPRISE   cdx6500
		VARIABLES    { cdx6500SNMPLastTrap }
		DESCRIPTION
		             " %s - PORT CONNECTION CLEARED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250006

        x32Port-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250007

        x32Port-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250008

        x32Port-call-thresh-exceed  TRAP-TYPE
		ENTERPRISE   cdx6500
		VARIABLES    { cdx6500SNMPLastTrap }
		DESCRIPTION
		             "%s - CALL THRESHOLD EXCEEDED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250009

        x32Port-unsucc-call-exceed  TRAP-TYPE
		ENTERPRISE   cdx6500
		VARIABLES    { cdx6500SNMPLastTrap }
		DESCRIPTION
		             "%s - UNSUCCESSFUL CALL THRESHOLD EXCEEDED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250010

        x32Port-t14-timer-expiry  TRAP-TYPE
		ENTERPRISE   cdx6500
		VARIABLES    { cdx6500SNMPLastTrap }
		DESCRIPTION
		             "%s - T14 TIMER EXPIRED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 250011

        cnui-port-disconn  TRAP-TYPE
		ENTERPRISE   cdx6500
		VARIABLES    { cdx6500SNMPLastTrap }
		DESCRIPTION
		             " NCI - %s, %d VIOLATIONS, PORT DISCONNECTED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 251000

        cnui-port-locked  TRAP-TYPE
		ENTERPRISE   cdx6500
		VARIABLES    { cdx6500SNMPLastTrap }
		DESCRIPTION
		             " NCI - %s, %d VIOLATIONS, PORT LOCKED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 251001

        cnui-port-degraded  TRAP-TYPE
		ENTERPRISE   cdx6500
		VARIABLES    { cdx6500SNMPLastTrap }
		DESCRIPTION
		             " NCI - %s, %d VIOLATIONS, PORT DEGRADED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 251002

        cnui-no-action  TRAP-TYPE
		ENTERPRISE   cdx6500
		VARIABLES    { cdx6500SNMPLastTrap }
		DESCRIPTION
		             " NCI - %s, %d VIOLATIONS, NO ACTION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 251003

        dor-agt-tbl-overflow  TRAP-TYPE
		ENTERPRISE   cdx6500
		VARIABLES    { cdx6500SNMPLastTrap }
		DESCRIPTION
		             " DORA - TABLE OVERFLOW"
                     --#TYPE
                     --#SUMMARY "Trap #$G, specific: $S, arg(1): $1"
                     --#ARGUMENTS {}
                     --#SEVERITY  INFORMATIONAL
                     --#TIMEINDEX
                     --#HELP
                     --#HELPTAG
                     --#STATE
		::= 252000

        dor-agt-config-err  TRAP-TYPE
		ENTERPRISE   cdx6500
		VARIABLES    { cdx6500SNMPLastTrap }
		DESCRIPTION
		             " DORA - CONFIGURATION ERROR - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 252001

        dor-unknown-call  TRAP-TYPE
		ENTERPRISE   cdx6500
		VARIABLES    { cdx6500SNMPLastTrap }
		DESCRIPTION
		             " DORA - UNKNOWN CALLER - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 252002

        dor-comm-error  TRAP-TYPE
		ENTERPRISE   cdx6500
		VARIABLES    { cdx6500SNMPLastTrap }
		DESCRIPTION
		             " DORA - DORM (%s) COMMUNICATION ERROR - X25 Cause : %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 252003

        dor-agt-req-abandoned  TRAP-TYPE
		ENTERPRISE   cdx6500
		VARIABLES    { cdx6500SNMPLastTrap }
		DESCRIPTION
		             " DORA - DIAL-OUT REQ (%s) ABANDONED - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 252004

        dor-stat-overflow  TRAP-TYPE
		ENTERPRISE   cdx6500
		VARIABLES    { cdx6500SNMPLastTrap }
		DESCRIPTION
		             " DORA - STAT OVERFLOW -  %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 252005

        dor-mgr-config-err  TRAP-TYPE
		ENTERPRISE   cdx6500
		VARIABLES    { cdx6500SNMPLastTrap }
		DESCRIPTION
		             " DORM CONFIGURATION - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 253000

        dor-link-fail  TRAP-TYPE
		ENTERPRISE   cdx6500
		VARIABLES    { cdx6500SNMPLastTrap }
		DESCRIPTION
		             " DORM - DORM LINK FAILURE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 253001

        dor-link-up  TRAP-TYPE
		ENTERPRISE   cdx6500
		VARIABLES    { cdx6500SNMPLastTrap }
		DESCRIPTION
		             " DORM - DORM COMMUNICATION ESTABLISHED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 253002

        dor-mgr-req-abandoned  TRAP-TYPE
		ENTERPRISE   cdx6500
		VARIABLES    { cdx6500SNMPLastTrap }
		DESCRIPTION
		             " DORM - DIAL-OUT REQ %s ABANDONED - DOR FAILURE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 253003

        dor-agent-fail  TRAP-TYPE
		ENTERPRISE   cdx6500
		VARIABLES    { cdx6500SNMPLastTrap }
		DESCRIPTION
		             " DORM - %s DORA FAILURE - REMOVED FROM DORM TABLE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 253004

        dor-mgr-tbl-overflow  TRAP-TYPE
		ENTERPRISE   cdx6500
		VARIABLES    { cdx6500SNMPLastTrap }
		DESCRIPTION
		             " DORM - TABLE OVERFLOW"
                     --#TYPE
                     --#SUMMARY "Trap #$G, specific: $S, arg(1): $1"
                     --#ARGUMENTS {}
                     --#SEVERITY  INFORMATIONAL
                     --#TIMEINDEX
                     --#HELP
                     --#HELPTAG
                     --#STATE
		::= 253005

        cnui-rrt-boot  TRAP-TYPE
		ENTERPRISE   cdx6500
		VARIABLES    { cdx6500SNMPLastTrap }
		DESCRIPTION
		             "%s - BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 255000

        cnui-rrt-boot-fail  TRAP-TYPE
		ENTERPRISE   cdx6500
		VARIABLES    { cdx6500SNMPLastTrap }
		DESCRIPTION
		             "%s - BOOT FAILED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 255001

        cnui-rrt-util-thres-exceed  TRAP-TYPE
		ENTERPRISE   cdx6500
		VARIABLES    { cdx6500SNMPLastTrap }
		DESCRIPTION
		             " %s - NCI CHANNEL UTILIZATION > 100%%"
                     --#TYPE
                     --#SUMMARY "Trap #$G, specific: $S, arg(1): $1"
                     --#ARGUMENTS {}
                     --#SEVERITY  INFORMATIONAL
                     --#TIMEINDEX
                     --#HELP
                     --#HELPTAG
                     --#STATE
		::= 255002

        tcp-checksum-error  TRAP-TYPE
		ENTERPRISE   cdx6500
		VARIABLES    { cdx6500SNMPLastTrap }
		DESCRIPTION
		             " TCP: pkt cksum fld pkt = %d calc = %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256000

        tcp-pkt-for-invalid-conn  TRAP-TYPE
		ENTERPRISE   cdx6500
		VARIABLES    { cdx6500SNMPLastTrap }
		DESCRIPTION
		             " TCP: rcvd pkt %s -> %s dst prt %d no cnn "
                     --#TYPE
                     --#SUMMARY "Trap #$G, specific: $S, arg(1): $1"
                     --#ARGUMENTS {}
                     --#SEVERITY  INFORMATIONAL
                     --#TIMEINDEX
                     --#HELP
                     --#HELPTAG
                     --#STATE
		::= 256001

        tcp-active-open-sccful  TRAP-TYPE
		ENTERPRISE   cdx6500
		VARIABLES    { cdx6500SNMPLastTrap }
		DESCRIPTION
		             "TCP: Act opn sccfl dst prt %d "
                     --#TYPE
                     --#SUMMARY "Trap #$G, specific: $S, arg(1): $1"
                     --#ARGUMENTS {}
                     --#SEVERITY  INFORMATIONAL
                     --#TIMEINDEX
                     --#HELP
                     --#HELPTAG
                     --#STATE
		::= 256002

        tcp-rcvd-invld-syn  TRAP-TYPE
		ENTERPRISE   cdx6500
		VARIABLES    { cdx6500SNMPLastTrap }
		DESCRIPTION
		             "TCP: rcvd invld SYN in wndw %s -> %s dst prt %d kill cnn "
                     --#TYPE
                     --#SUMMARY "Trap #$G, specific: $S, arg(1): $1"
                     --#ARGUMENTS {}
                     --#SEVERITY  INFORMATIONAL
                     --#TIMEINDEX
                     --#HELP
                     --#HELPTAG
                     --#STATE
		::= 256003

        tcp-rcvd-old-syn  TRAP-TYPE
		ENTERPRISE   cdx6500
		VARIABLES    { cdx6500SNMPLastTrap }
		DESCRIPTION
		             " TCP: rcvd old SYN %s -> %s dst prt %d snd ACK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256004

        tcp-rcvd-out-of-wdow-seg  TRAP-TYPE
		ENTERPRISE   cdx6500
		VARIABLES    { cdx6500SNMPLastTrap }
		DESCRIPTION
		             " TCP: rcvd out of wndow seg %s -> %s dst prt %d snd ACK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256005

        tcp-dropping-seg  TRAP-TYPE
		ENTERPRISE   cdx6500
		VARIABLES    { cdx6500SNMPLastTrap }
		DESCRIPTION
		             " TCP: drp seg %s -> %s dst prt %d rsn %d snd ACK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256006

        tcp-rcvd-old-seg  TRAP-TYPE
		ENTERPRISE   cdx6500
		VARIABLES    { cdx6500SNMPLastTrap }
		DESCRIPTION
		             " TCP: rcvd old seg dst prt %d seq num %d snd ACK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256007

        tcp-rcvd-rst-in-listen  TRAP-TYPE
		ENTERPRISE   cdx6500
		VARIABLES    { cdx6500SNMPLastTrap }
		DESCRIPTION
		             " TCP: LISTEN: rcvd RST dst prt %d seq num %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256008

        tcp-rcvd-rst-in-synrcvd  TRAP-TYPE
		ENTERPRISE   cdx6500
		VARIABLES    { cdx6500SNMPLastTrap }
		DESCRIPTION
		             " TCP: SYN-RCVD|SYN-SNT: rcvd RST dst %d seq %d, rtrn->LISTEN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256009

        tcp-rcvd-rst-so-aborting  TRAP-TYPE
		ENTERPRISE   cdx6500
		VARIABLES    { cdx6500SNMPLastTrap }
		DESCRIPTION
		             "TCP: rcvd RST dst prt %d seq num %d, abort"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256010

        tcp-no-ack-so-dropping  TRAP-TYPE
		ENTERPRISE   cdx6500
		VARIABLES    { cdx6500SNMPLastTrap }
		DESCRIPTION
		             " TCP: drop seg dst prt %d seq num %d no ACK present"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256011

        tcp-invld-ack-dropping  TRAP-TYPE
		ENTERPRISE   cdx6500
		VARIABLES    { cdx6500SNMPLastTrap }
		DESCRIPTION
		             " TCP: drop seg dst prt %d seq num %d ack num %d rcv invld ACK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256012

        tcp-rcvd-fin-in-estab  TRAP-TYPE
		ENTERPRISE   cdx6500
		VARIABLES    { cdx6500SNMPLastTrap }
		DESCRIPTION
		             " TCP: ESTAB: rcvd FIN dst prt %d seq num %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256013

        tcp-rcvd-push  TRAP-TYPE
		ENTERPRISE   cdx6500
		VARIABLES    { cdx6500SNMPLastTrap }
		DESCRIPTION
		             " TCP: rcvd PSH dst prt %d seq num %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256014

        tcp-entering-estab  TRAP-TYPE
		ENTERPRISE   cdx6500
		VARIABLES    { cdx6500SNMPLastTrap }
		DESCRIPTION
		             " TCP: SYNRCVD: rcvd vld seg dst prt %d seq num %d, enter ESTAB"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256015

        tcp-rcvd-fin-in-listen  TRAP-TYPE
		ENTERPRISE   cdx6500
		VARIABLES    { cdx6500SNMPLastTrap }
		DESCRIPTION
		             " TCP: rcvd FIN while in LISTEN dst prt %d seq num %d, snd RST"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256016

        tcp-add-hole-at-end  TRAP-TYPE
		ENTERPRISE   cdx6500
		VARIABLES    { cdx6500SNMPLastTrap }
		DESCRIPTION
		             " TCP: rcvd out of order seg dst prt %d seq num %d, add hole at end %dto %d"

                     --#TYPE
                     --#SUMMARY "Trap #$G, specific: $S, arg(1): $1"
                     --#ARGUMENTS {}
                     --#SEVERITY  INFORMATIONAL
                     --#TIMEINDEX
                     --#HELP
                     --#HELPTAG
                     --#STATE
		::= 256017

        tcp-add-hole-at-beg  TRAP-TYPE
		ENTERPRISE   cdx6500
		VARIABLES    { cdx6500SNMPLastTrap }
		DESCRIPTION
		             " TCP: rcvd out of order seg dst prt %d seq num %d, add hole at end %dto %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256018

        tcp-fill-beg-hole  TRAP-TYPE
		ENTERPRISE   cdx6500
		VARIABLES    { cdx6500SNMPLastTrap }
		DESCRIPTION
		             " TCP: rcvd seg dst prt %d seq num %d, fill beg hole %d to %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256019

        tcp-fill-end-hole  TRAP-TYPE
		ENTERPRISE   cdx6500
		VARIABLES    { cdx6500SNMPLastTrap }
		DESCRIPTION
		             " TCP: rcvd seg dst prt %d seq num %d, fill end hole %d to %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256020

        tcp-remove-hole  TRAP-TYPE
		ENTERPRISE   cdx6500
		VARIABLES    { cdx6500SNMPLastTrap }
		DESCRIPTION
		             " TCP: rcvd seg dst prt %d seq num %d, rmv hole %d to %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256021

        tcp-too-big-for-rcv-buff  TRAP-TYPE
		ENTERPRISE   cdx6500
		VARIABLES    { cdx6500SNMPLastTrap }
		DESCRIPTION
		             " TCP: drp seg dst prt %d seq num %d, too big for rcv buff"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256022

        tcp-fin-in-invld-state  TRAP-TYPE
		ENTERPRISE   cdx6500
		VARIABLES    { cdx6500SNMPLastTrap }
		DESCRIPTION
		             " TCP: prcss FIN in invld state"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256023

        tcp-fin-in-valid-state  TRAP-TYPE
		ENTERPRISE   cdx6500
		VARIABLES    { cdx6500SNMPLastTrap }
		DESCRIPTION
		             " TCP: prcss FIN in ESTAB|SYNRCVD state frgn hst %s lcl hst %s dprt %dsprt %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256024

        tcp-appln-rcv-timeout  TRAP-TYPE
		ENTERPRISE   cdx6500
		VARIABLES    { cdx6500SNMPLastTrap }
		DESCRIPTION
		             " TCP: app rcv tmout"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256025

        tcp-illgl-clos-frgn-wndw  TRAP-TYPE
		ENTERPRISE   cdx6500
		VARIABLES    { cdx6500SNMPLastTrap }
		DESCRIPTION
		             " TCP: frgn prt illgl close of wndw frgn hst %s lcl hst %s dprt %d sprt %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256026

        tcp-state-to-synrcvd  TRAP-TYPE
		ENTERPRISE   cdx6500
		VARIABLES    { cdx6500SNMPLastTrap }
		DESCRIPTION
		             " TCP: state trnstn to SYNRCVD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256027

        tcp-state-to-estab  TRAP-TYPE
		ENTERPRISE   cdx6500
		VARIABLES    { cdx6500SNMPLastTrap }
		DESCRIPTION
		             " TCP: state trnstn to ESTAB"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256028

        tcp-rcvd-tcp-pkt  TRAP-TYPE
		ENTERPRISE   cdx6500
		VARIABLES    { cdx6500SNMPLastTrap }
		DESCRIPTION
		             " TCP: rcvd TCP pkt %s -> %s dst prt %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256029

        tcp-data-given-to-appln  TRAP-TYPE
		ENTERPRISE   cdx6500
		VARIABLES    { cdx6500SNMPLastTrap }
		DESCRIPTION
		             " TCP: seq num %d to %d given to app."
                     --#TYPE
                     --#SUMMARY "Trap #$G, specific: $S, arg(1): $1"
                     --#ARGUMENTS {}
                     --#SEVERITY  INFORMATIONAL
                     --#TIMEINDEX
                     --#HELP
                     --#HELPTAG
                     --#STATE
		::= 256030

        tcp-excessive-retries  TRAP-TYPE
		ENTERPRISE   cdx6500
		VARIABLES    { cdx6500SNMPLastTrap }
		DESCRIPTION
		             " TCP: excssv num rtries "
                     --#TYPE
                     --#SUMMARY "Trap #$G, specific: $S, arg(1): $1"
                     --#ARGUMENTS {}
                     --#SEVERITY  INFORMATIONAL
                     --#TIMEINDEX
                     --#HELP
                     --#HELPTAG
                     --#STATE
		::= 256031

        tcp-sending-control-seg  TRAP-TYPE
		ENTERPRISE   cdx6500
		VARIABLES    { cdx6500SNMPLastTrap }
		DESCRIPTION
		             " TCP: snd ctrl seg seq num %d ack num %d wndw %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256032

        tcp-retransmitting  TRAP-TYPE
		ENTERPRISE   cdx6500
		VARIABLES    { cdx6500SNMPLastTrap }
		DESCRIPTION
		             " TCP: rxmt seq num %d to %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256033

        tcp-transmitting  TRAP-TYPE
		ENTERPRISE   cdx6500
		VARIABLES    { cdx6500SNMPLastTrap }
		DESCRIPTION
		             " TCP: xmt seq num %d to %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256034

        tcp-illgl-optn-in-syn  TRAP-TYPE
		ENTERPRISE   cdx6500
		VARIABLES    { cdx6500SNMPLastTrap }
		DESCRIPTION
		             " TCP: illgl optn rcvd in SYN seg "
                     --#TYPE
                     --#SUMMARY "Trap #$G, specific: $S, arg(1): $1"
                     --#ARGUMENTS {}
                     --#SEVERITY  INFORMATIONAL
                     --#TIMEINDEX
                     --#HELP
                     --#HELPTAG
                     --#STATE
		::= 256035

        tcp-zero-wndw-probe  TRAP-TYPE
		ENTERPRISE   cdx6500
		VARIABLES    { cdx6500SNMPLastTrap }
		DESCRIPTION
		             " TCP: zero wndw probe seq num %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256036

        tcp-bad-ack-in-synrcvd  TRAP-TYPE
		ENTERPRISE   cdx6500
		VARIABLES    { cdx6500SNMPLastTrap }
		DESCRIPTION
		             " TCP: rjct seg dst prt %d seq num %d bad ACK in SYNRCVD, snd RST"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256037

        tcp-rcvd-ack-in-listen  TRAP-TYPE
		ENTERPRISE   cdx6500
		VARIABLES    { cdx6500SNMPLastTrap }
		DESCRIPTION
		             " TCP: rcvd ACK seg with dst prt %d seq num %d in LISTEN, snd RST"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256038

        tcp-sending-rst  TRAP-TYPE
		ENTERPRISE   cdx6500
		VARIABLES    { cdx6500SNMPLastTrap }
		DESCRIPTION
		             " TCP: TCP snd rst to hst %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256039

        tcp-connection-closed  TRAP-TYPE
		ENTERPRISE   cdx6500
		VARIABLES    { cdx6500SNMPLastTrap }
		DESCRIPTION
		             " TCP: TCP cnn clsd frgn hst %s lcl hst %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256040

        tcp-firing-tcb-1  TRAP-TYPE
		ENTERPRISE   cdx6500
		VARIABLES    { cdx6500SNMPLastTrap }
		DESCRIPTION
		             " TCP: Frng TCB for frgn hst %s lcl hst %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256041

        tcp-firing-tcb-2  TRAP-TYPE
		ENTERPRISE   cdx6500
		VARIABLES    { cdx6500SNMPLastTrap }
		DESCRIPTION
		             " TCP: Frng TCB for frgn hst %s lcl hst %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256042

        tcp-idle-tmr-fires  TRAP-TYPE
		ENTERPRISE   cdx6500
		VARIABLES    { cdx6500SNMPLastTrap }
		DESCRIPTION
		             " TCP: Idle tmr fires frgn hst %s lcl hst %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256043

        tcp-retransmit-tmr-fires  TRAP-TYPE
		ENTERPRISE   cdx6500
		VARIABLES    { cdx6500SNMPLastTrap }
		DESCRIPTION
		             " TCP: Rxmt tmr fires frgn hst %s lcl hst %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256044

        tcp-estab-to-finwait  TRAP-TYPE
		ENTERPRISE   cdx6500
		VARIABLES    { cdx6500SNMPLastTrap }
		DESCRIPTION
		             " TCP: State trnstn frm ESTAB to FINWAIT %s -> %s dst prt %d src prt %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256045

        tcp-state-to-closed  TRAP-TYPE
		ENTERPRISE   cdx6500
		VARIABLES    { cdx6500SNMPLastTrap }
		DESCRIPTION
        	             "TCP: State trnstn to CLOSED %s -> %s dst prt %d src prt %d"
	             --#TYPE
                     --#SUMMARY "Trap #$G, specific: $S, arg(1): $1"
                     --#ARGUMENTS {}
                     --#SEVERITY  INFORMATIONAL
                     --#TIMEINDEX
                     --#HELP
                     --#HELPTAG
                     --#STATE
			::= 256046

        tcp-rcvd-data-aftr-close  TRAP-TYPE
		ENTERPRISE   cdx6500
		VARIABLES    { cdx6500SNMPLastTrap }
		DESCRIPTION
		             " TCP: Rcvd data after close, snd RST %s -> %s dst prt %d src prt %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256047

        tcp-received-nack  TRAP-TYPE
		ENTERPRISE   cdx6500
		VARIABLES    { cdx6500SNMPLastTrap }
		DESCRIPTION
		             " TCP: Rcvd NACK "
                     --#TYPE
                     --#SUMMARY "Trap #$G, specific: $S, arg(1): $1"
                     --#ARGUMENTS {}
                     --#SEVERITY  INFORMATIONAL
                     --#TIMEINDEX
                     --#HELP
                     --#HELPTAG
                     --#STATE
		::= 256048

        tcp-rcvd-ack-keepalive  TRAP-TYPE
		ENTERPRISE   cdx6500
		VARIABLES    { cdx6500SNMPLastTrap }
		DESCRIPTION
		             " TCP: Rcvd ACK for Keep Alive"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256049

        tcp-local-wndw-zero  TRAP-TYPE
		ENTERPRISE   cdx6500
		VARIABLES    { cdx6500SNMPLastTrap }
		DESCRIPTION
		             " TCP: Lcl wndw zero"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256050

        tcp-sending-fin  TRAP-TYPE
		ENTERPRISE   cdx6500
		VARIABLES    { cdx6500SNMPLastTrap }
		DESCRIPTION
		             " TCP: snd FIN seq %d, ack %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256051

        tcp-no-buf-to-send-pkt  TRAP-TYPE
		ENTERPRISE   cdx6500
		VARIABLES    { cdx6500SNMPLastTrap }
		DESCRIPTION
		             "TCP: get buf fld - cannot snd pkt"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256052

        tcp-transmit-buf-clipped  TRAP-TYPE
		ENTERPRISE   cdx6500
		VARIABLES    { cdx6500SNMPLastTrap }
		DESCRIPTION
		             " TCP: xmit buf too large (%), clipped to %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256053

        tcp-recv-buf-clipped  TRAP-TYPE
		ENTERPRISE   cdx6500
		VARIABLES    { cdx6500SNMPLastTrap }
		DESCRIPTION
		             " TCP: recv buf too large (%), clipped to %d"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256054

        tcp-restarting  TRAP-TYPE
		ENTERPRISE   cdx6500
		VARIABLES    { cdx6500SNMPLastTrap }
		DESCRIPTION
		             " TCP: TCP is Restarting"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256055

        tcp-mot-high-prty-trap  TRAP-TYPE
		ENTERPRISE   cdx6500
		VARIABLES    { cdx6500SNMPLastTrap }
		DESCRIPTION
		             "Motorola specific high priority TCP traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256056

        tcp-mot-med-prty-trap  TRAP-TYPE
		ENTERPRISE   cdx6500
		VARIABLES    { cdx6500SNMPLastTrap }
		DESCRIPTION
		             " Motorola specific medium priority TCP traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256057

        tcp-mot-low-prty-trap  TRAP-TYPE
		ENTERPRISE   cdx6500
		VARIABLES    { cdx6500SNMPLastTrap }
		DESCRIPTION
		             " Motorola specific low priority TCP traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 256058

        telnet-internal-err  TRAP-TYPE
		ENTERPRISE   cdx6500
		VARIABLES    { cdx6500SNMPLastTrap }
		DESCRIPTION
		             "Telnet-Internal Error: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 257000

        telnet-err  TRAP-TYPE
		ENTERPRISE   cdx6500
		VARIABLES    { cdx6500SNMPLastTrap }
		DESCRIPTION
		             "Telnet-Error: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 257001

        async360-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 259000

        async360-dbits-unsupp  TRAP-TYPE
		ENTERPRISE   cdx6500
		VARIABLES    { cdx6500SNMPLastTrap }
		DESCRIPTION
		             " %s - UNSUPPORTED DATABITS: OPERATING WITH 8 DATABITS, NO PARITY"
                     --#TYPE
                     --#SUMMARY "Trap #$G, specific: $S, arg(1): $1"
                     --#ARGUMENTS {}
                     --#SEVERITY  INFORMATIONAL
                     --#TIMEINDEX
                     --#HELP
                     --#HELPTAG
                     --#STATE
		::= 259001

        async360-baud-unsupp  TRAP-TYPE
		ENTERPRISE   cdx6500
		VARIABLES    { cdx6500SNMPLastTrap }
		DESCRIPTION
		             " %s - UNSUPPORTED BAUDRATE: OPERATING AT 9600 BPS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 259002

        async360-parity-unsupp  TRAP-TYPE
		ENTERPRISE   cdx6500
		VARIABLES    { cdx6500SNMPLastTrap }
		DESCRIPTION
		             " %s - UNSUPPORTED PARITY: OPERATING WITH 8 DATABITS, NO PARITY"
                     --#TYPE
                     --#SUMMARY "Trap #$G, specific: $S, arg(1): $1"
                     --#ARGUMENTS {}
                     --#SEVERITY  INFORMATIONAL
                     --#TIMEINDEX
                     --#HELP
                     --#HELPTAG
                     --#STATE
		::= 259003

        bop360-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 260000

        bop360-unsupp-speed  TRAP-TYPE
		ENTERPRISE   cdx6500
		VARIABLES    { cdx6500SNMPLastTrap }
		DESCRIPTION
		             " %s - UNSUPPORTED SPEED: OPERATING AT %d BITS PER SECOND"
                     --#TYPE
                     --#SUMMARY "Trap #$G, specific: $S, arg(1): $1"
                     --#ARGUMENTS {}
                     --#SEVERITY  INFORMATIONAL
                     --#TIMEINDEX
                     --#HELP
                     --#HELPTAG
                     --#STATE
		::= 260001

        bop360-rx-byte-count-err  TRAP-TYPE
		ENTERPRISE   cdx6500
		VARIABLES    { cdx6500SNMPLastTrap }
		DESCRIPTION
		             " %s - UNSUPPORTED RECEIVE BYTE COUNT: OPERATING WITH %d RX BYTE COUNT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 260002

        bop360-erroneous-bool  TRAP-TYPE
		ENTERPRISE   cdx6500
		VARIABLES    { cdx6500SNMPLastTrap }
		DESCRIPTION
		             " %s - ERRONEOUS BOOLEAN PARAMETER: %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 260003

        bop360-clk-override  TRAP-TYPE
		ENTERPRISE   cdx6500
		VARIABLES    { cdx6500SNMPLastTrap }
		DESCRIPTION
		             " %s - CLOCK SOURCE OVERRIDE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 260004

        bop360-tx-sanity-timeout  TRAP-TYPE
                ENTERPRISE   cdx6500
                VARIABLES    { cdx6500SNMPLastTrap }
                DESCRIPTION
                             " %s - TX SANITY TIMEOUT"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 260005

	iodrivers260006-corr   TRAP-TYPE
		ENTERPRISE   cdx6500
		VARIABLES    { cdx6500SNMPLastTrap }
		DESCRIPTION
		     "%s - CORRUTPED PCK, NULL POINTER GENERATED"
		     --#TYPE
		     --#SUMMARY "Trap #$G, specific: $S, arg(1) : $1"
		     --#ARGUMENTS {}
		     --#SEVERITY  MAJOR
		     --#TIMEINDEX
		     --#HELP
		     --#HELPTAG
		     --#STATE
		::= 260006

        cop360-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 261000

        mc68302drvr-trap  TRAP-TYPE
		ENTERPRISE   cdx6500
		VARIABLES    { cdx6500SNMPLastTrap }
		DESCRIPTION
		             " MC68302 driver traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 262000

        mc68360drvr-traps  TRAP-TYPE
		ENTERPRISE   cdx6500
		VARIABLES    { cdx6500SNMPLastTrap }
		DESCRIPTION
		             " MC68360 driver traps"
                     --#TYPE
                     --#SUMMARY "Trap #$G, specific: $S, arg(1): $1"
                     --#ARGUMENTS {}
                     --#SEVERITY  INFORMATIONAL
                     --#TIMEINDEX
                     --#HELP
                     --#HELPTAG
                     --#STATE
		::= 264000

        iodrivers-sgnothrottletimer  TRAP-TYPE
		ENTERPRISE   cdx6500
		VARIABLES    { cdx6500SNMPLastTrap }
		DESCRIPTION
		     "SG-NO-THROTTLE-TIMER"
		     --#TYPE
		     --#SUMMARY "Trap #$G, specific: $S, arg(1) : $1"
		     --#ARGUMENTS {}
		     --#SEVERITY  MAJOR
		     --#TIMEINDEX
		     --#HELP
		     --#HELPTAG
		     --#STATE
		::= 265000

        iodrivers-sgnoinitializatio  TRAP-TYPE
		ENTERPRISE   cdx6500
		VARIABLES    { cdx6500SNMPLastTrap }
		DESCRIPTION
		     "SG-NO-INITIALIZATIO"
		     --#TYPE
		     --#SUMMARY "Trap #$G, specific: $S, arg(1) : $1"
		     --#ARGUMENTS {}
		     --#SEVERITY  MAJOR
		     --#TIMEINDEX
		     --#HELP
		     --#HELPTAG
		     --#STATE
		::= 265001

        iodrivers-sgconfigurationfaile  TRAP-TYPE
		ENTERPRISE   cdx6500
		VARIABLES    { cdx6500SNMPLastTrap }
		DESCRIPTION
		     "SG-CONFIGURATION-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 265002

        iodrivers-sgiafaile  TRAP-TYPE
		ENTERPRISE   cdx6500
		VARIABLES    { cdx6500SNMPLastTrap }
		DESCRIPTION
		     "SG-IA-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 265003

        iodrivers-sgconfigurationtimedout  TRAP-TYPE
		ENTERPRISE   cdx6500
		VARIABLES    { cdx6500SNMPLastTrap }
		DESCRIPTION
		     "SG-CONFIGURATION-TIMEDOU"
		     --#TYPE
		     --#SUMMARY "Trap #$G, specific: $S, arg(1) : $1"
		     --#ARGUMENTS {}
		     --#SEVERITY  MAJOR
		     --#TIMEINDEX
		     --#HELP
		     --#HELPTAG
		     --#STATE
		::= 265004

        iodrivers-sgnosuspensio  TRAP-TYPE
		ENTERPRISE   cdx6500
		VARIABLES    { cdx6500SNMPLastTrap }
		DESCRIPTION
		     "SG-NO-SUSPENSIO"
		     --#TYPE
		     --#SUMMARY "Trap #$G, specific: $S, arg(1) : $1"
		     --#ARGUMENTS {}
		     --#SEVERITY  MAJOR
		     --#TIMEINDEX
		     --#HELP
		     --#HELPTAG
		     --#STATE
		::= 265005

        iodrivers-sgtxlistputfaile  TRAP-TYPE
		ENTERPRISE   cdx6500
		VARIABLES    { cdx6500SNMPLastTrap }
		DESCRIPTION
		     "SG-TX-LIST-PUT-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 265006

        iodrivers-sgexcessivetxerror  TRAP-TYPE
		ENTERPRISE   cdx6500
		VARIABLES    { cdx6500SNMPLastTrap }
		DESCRIPTION
		     "SG-EXCESSIVE-TX-ERROR"
		     --#TYPE
		     --#SUMMARY "Trap #$G, specific: $S, arg(1) : $1"
		     --#ARGUMENTS {}
		     --#SEVERITY  MAJOR
		     --#TIMEINDEX
		     --#HELP
		     --#HELPTAG
		     --#STATE
		::= 265007

        iodrivers-sglossofcarrie  TRAP-TYPE
		ENTERPRISE   cdx6500
		VARIABLES    { cdx6500SNMPLastTrap }
		DESCRIPTION
		     "SG-LOSS-OF-CARRIE"
		     --#TYPE
		     --#SUMMARY "Trap #$G, specific: $S, arg(1) : $1"
		     --#ARGUMENTS {}
		     --#SEVERITY  MAJOR
		     --#TIMEINDEX
		     --#HELP
		     --#HELPTAG
		     --#STATE
		::= 265008

        iodrivers-sgexcessiverxerror  TRAP-TYPE
		ENTERPRISE   cdx6500
		VARIABLES    { cdx6500SNMPLastTrap }
		DESCRIPTION
		     "SG-EXCESSIVE-RX-ERROR"
		     --#TYPE
		     --#SUMMARY "Trap #$G, specific: $S, arg(1) : $1"
		     --#ARGUMENTS {}
		     --#SEVERITY  MAJOR
		     --#TIMEINDEX
		     --#HELP
		     --#HELPTAG
		     --#STATE
		::= 265009

        iodrivers-sgexcessivetxclea  TRAP-TYPE
		ENTERPRISE   cdx6500
		VARIABLES    { cdx6500SNMPLastTrap }
		DESCRIPTION
		     "SG-EXCESSIVE-TX-CLEA"
		     --#TYPE
		     --#SUMMARY "Trap #$G, specific: $S, arg(1) : $1"
		     --#ARGUMENTS {}
		     --#SEVERITY  MAJOR
		     --#TIMEINDEX
		     --#HELP
		     --#HELPTAG
		     --#STATE
		::= 265010

        iodrivers-sglossofcarrierclea  TRAP-TYPE
		ENTERPRISE   cdx6500
		VARIABLES    { cdx6500SNMPLastTrap }
		DESCRIPTION
		     "SG-LOSS-OF-CARRIER-CLEA"
		     --#TYPE
		     --#SUMMARY "Trap #$G, specific: $S, arg(1) : $1"
		     --#ARGUMENTS {}
		     --#SEVERITY  MAJOR
		     --#TIMEINDEX
		     --#HELP
		     --#HELPTAG
		     --#STATE
		::= 265011

        iodrivers-sgexcessiverxclea  TRAP-TYPE
		ENTERPRISE   cdx6500
		VARIABLES    { cdx6500SNMPLastTrap }
		DESCRIPTION
		     "SG-EXCESSIVE-RX-CLEA"
		     --#TYPE
		     --#SUMMARY "Trap #$G, specific: $S, arg(1) : $1"
		     --#ARGUMENTS {}
		     --#SEVERITY  MAJOR
		     --#TIMEINDEX
		     --#HELP
		     --#HELPTAG
		     --#STATE
		::= 265012

        iodrivers-sginvalidstateenable  TRAP-TYPE
		ENTERPRISE   cdx6500
		VARIABLES    { cdx6500SNMPLastTrap }
		DESCRIPTION
		     "SG-INVALID-STATE-ENABLE"
		     --#TYPE
		     --#SUMMARY "Trap #$G, specific: $S, arg(1) : $1"
		     --#ARGUMENTS {}
		     --#SEVERITY  MAJOR
		     --#TIMEINDEX
		     --#HELP
		     --#HELPTAG
		     --#STATE
		::= 265013

        iodrivers-sginvalidstatedisable  TRAP-TYPE
		ENTERPRISE   cdx6500
		VARIABLES    { cdx6500SNMPLastTrap }
		DESCRIPTION
		     "SG-INVALID-STATE-DISABLE"
		     --#TYPE
		     --#SUMMARY "Trap #$G, specific: $S, arg(1) : $1"
		     --#ARGUMENTS {}
		     --#SEVERITY  MAJOR
		     --#TIMEINDEX
		     --#HELP
		     --#HELPTAG
		     --#STATE
		::= 265014

        iodrivers-sgloopbackfaile  TRAP-TYPE
		ENTERPRISE   cdx6500
		VARIABLES    { cdx6500SNMPLastTrap }
		DESCRIPTION
		     "SG-LOOPBACK-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 265015

        iodrivers-sgtdrfaile  TRAP-TYPE
		ENTERPRISE   cdx6500
		VARIABLES    { cdx6500SNMPLastTrap }
		DESCRIPTION
		     "SG-TDR-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 265016

        pppPort-boot  TRAP-TYPE
		ENTERPRISE   cdx6500
		VARIABLES    { cdx6500SNMPLastTrap }
		DESCRIPTION
		             "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 268000

        pppPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 268001

        pppPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 268002

        pppPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 268003

        pppPort-util-exceeded  TRAP-TYPE
		ENTERPRISE   cdx6500
		VARIABLES    { cdx6500SNMPLastTrap }
		DESCRIPTION
		             " %s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 268004

        pppPort-warn-status  TRAP-TYPE
		ENTERPRISE   cdx6500
		VARIABLES    { cdx6500SNMPLastTrap }
		DESCRIPTION
		             " %s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 268005

        pppPort-err-count-exceeded  TRAP-TYPE
		ENTERPRISE   cdx6500
		VARIABLES    { cdx6500SNMPLastTrap }
		DESCRIPTION
		             " %s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 268006

        ppp-allocated-bytes-for-tracing  TRAP-TYPE
		ENTERPRISE   cdx6500
		VARIABLES    { cdx6500SNMPLastTrap }
		DESCRIPTION
		     "%s - ALLOCATED %d BYTES FOR PPP TRACING"
		     --#TYPE
		     --#SUMMARY "Trap #$G, specific: $S, arg(1) : $1"
		     --#ARGUMENTS {}
		     --#SEVERITY  CRITICAL
		     --#TIMEINDEX
		     --#HELP
		     --#HELPTAG
		     --#STATE
		::= 268007

        ppp-port-initialization-failed  TRAP-TYPE
		ENTERPRISE   cdx6500
		VARIABLES    { cdx6500SNMPLastTrap }
		DESCRIPTION
		     "%s - PORT INITIALIZATION FAILED - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 268008

        pppL2-out-data-loss  TRAP-TYPE
		ENTERPRISE   cdx6500
		VARIABLES    { cdx6500SNMPLastTrap }
		DESCRIPTION
		             "%s - DATA LOST FROM OUTBOUND QUEUE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 269000

        pppL2-frame-reject  TRAP-TYPE
		ENTERPRISE   cdx6500
		VARIABLES    { cdx6500SNMPLastTrap }
		DESCRIPTION
		             " %s - REJECTED THE PACKET WITH COMPRESSED HEADER"
                     --#TYPE
                     --#SUMMARY "Trap #$G, specific: $S, arg(1): $1"
                     --#ARGUMENTS {}
                     --#SEVERITY  INFORMATIONAL
                     --#TIMEINDEX
                     --#HELP
                     --#HELPTAG
                     --#STATE
		::= 269001

        pppL2-unsupp-proto  TRAP-TYPE
		ENTERPRISE   cdx6500
		VARIABLES    { cdx6500SNMPLastTrap }
		DESCRIPTION
		             " %s - RECEIVED OUTBOUND PACKET OF UNSUPPORTED PROTOCOL"
                     --#TYPE
                     --#SUMMARY "Trap #$G, specific: $S, arg(1): $1"
                     --#ARGUMENTS {}
                     --#SEVERITY  INFORMATIONAL
                     --#TIMEINDEX
                     --#HELP
                     --#HELPTAG
                     --#STATE
		::= 270000

        pppL2-vj-comp-fail  TRAP-TYPE
		ENTERPRISE   cdx6500
		VARIABLES    { cdx6500SNMPLastTrap }
		DESCRIPTION
		             " %s - VAN JACOBSON COMPRESSION FAILED ON INBOUND PACKET"
                     --#TYPE
                     --#SUMMARY "Trap #$G, specific: $S, arg(1): $1"
                     --#ARGUMENTS {}
                     --#SEVERITY  INFORMATIONAL
                     --#TIMEINDEX
                     --#HELP
                     --#HELPTAG
                     --#STATE
		::= 270001

        pppL2-login-fail  TRAP-TYPE
		ENTERPRISE   cdx6500
		VARIABLES    { cdx6500SNMPLastTrap }
		DESCRIPTION
		             " %s - INCORRECT LOGIN"
                     --#TYPE
                     --#SUMMARY "Trap #$G, specific: $S, arg(1): $1"
                     --#ARGUMENTS {}
                     --#SEVERITY  INFORMATIONAL
                     --#TIMEINDEX
                     --#HELP
                     --#HELPTAG
                     --#STATE
		::= 270002

        pppL2-login-ok  TRAP-TYPE
		ENTERPRISE   cdx6500
		VARIABLES    { cdx6500SNMPLastTrap }
		DESCRIPTION
		             " %s - LOGIN OK"
                     --#TYPE
                     --#SUMMARY "Trap #$G, specific: $S, arg(1): $1"
                     --#ARGUMENTS {}
                     --#SEVERITY  INFORMATIONAL
                     --#TIMEINDEX
                     --#HELP
                     --#HELPTAG
                     --#STATE
		::= 270003

        ppp-proto-compneg-failed  TRAP-TYPE
                ENTERPRISE   cdx6500
                VARIABLES    { cdx6500SNMPLastTrap }
                DESCRIPTION
                             "%s - COMPRESSION NEGOTIATION FAILED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 270004

        ppp-proto-data-loss  TRAP-TYPE
                ENTERPRISE   cdx6500
                VARIABLES    { cdx6500SNMPLastTrap }
                DESCRIPTION
                             "%s - DATA LOST FROM OUTBOUND %s QUEUE"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 270005

        ppp-dedicated-link-not-configure  TRAP-TYPE
		ENTERPRISE   cdx6500
		VARIABLES    { cdx6500SNMPLastTrap }
		DESCRIPTION
		     "%s - DEDICATED LINK %s NOT CONFIGURED"
		     --#TYPE
		     --#SUMMARY "Trap #$G, specific: $S, arg(1) : $1"
		     --#ARGUMENTS {}
		     --#SEVERITY  CRITICAL
		     --#TIMEINDEX
		     --#HELP
		     --#HELPTAG
		     --#STATE
		::= 270006

        ppp-dedicated-link-already-alloc  TRAP-TYPE
		ENTERPRISE   cdx6500
		VARIABLES    { cdx6500SNMPLastTrap }
		DESCRIPTION
		     "%s - DEDICATED LINK %s ALREADY ALLOCATED"
		     --#TYPE
		     --#SUMMARY "Trap #$G, specific: $S, arg(1) : $1"
		     --#ARGUMENTS {}
		     --#SEVERITY  CRITICAL
		     --#TIMEINDEX
		     --#HELP
		     --#HELPTAG
		     --#STATE
		::= 270007

        ppp-discarding-frames  TRAP-TYPE
		ENTERPRISE   cdx6500
		VARIABLES    { cdx6500SNMPLastTrap }
		DESCRIPTION
		     "%s - DISCARDING %d FRAMES"
		     --#TYPE
		     --#SUMMARY "Trap #$G, specific: $S, arg(1) : $1"
		     --#ARGUMENTS {}
		     --#SEVERITY  MINOR
		     --#TIMEINDEX
		     --#HELP
		     --#HELPTAG
		     --#STATE
		::= 270008

        ppp-received-multilink-frame-wit  TRAP-TYPE
		ENTERPRISE   cdx6500
		VARIABLES    { cdx6500SNMPLastTrap }
		DESCRIPTION
		     "%s - RECEIVED MULTILINK FRAME WITH INVALID FORMAT"
		     --#TYPE
		     --#SUMMARY "Trap #$G, specific: $S, arg(1) : $1"
		     --#ARGUMENTS {}
		     --#SEVERITY  CRITICAL
		     --#TIMEINDEX
		     --#HELP
		     --#HELPTAG
		     --#STATE
		::= 270009

        ppp-remote-is-silent  TRAP-TYPE
		ENTERPRISE   cdx6500
		VARIABLES    { cdx6500SNMPLastTrap }
		DESCRIPTION
		     "%s - REMOTE PPP IS SILENT"
		     --#TYPE
		     --#SUMMARY "Trap #$G, specific: $S, arg(1) : $1"
		     --#ARGUMENTS {}
		     --#SEVERITY  MAJOR
		     --#TIMEINDEX
		     --#HELP
		     --#HELPTAG
		     --#STATE
		::= 270010

        ppp-no-profile-available-for-s  TRAP-TYPE
		ENTERPRISE   cdx6500
		VARIABLES    { cdx6500SNMPLastTrap }
		DESCRIPTION
		     "%s - NO PROFILE AVAILABLE FOR <%.*s>"
		     --#TYPE
		     --#SUMMARY "Trap #$G, specific: $S, arg(1) : $1"
		     --#ARGUMENTS {}
		     --#SEVERITY  MAJOR
		     --#TIMEINDEX
		     --#HELP
		     --#HELPTAG
		     --#STATE
		::= 270011

        ppp-inconsistent-link-negotiatio  TRAP-TYPE
		ENTERPRISE   cdx6500
		VARIABLES    { cdx6500SNMPLastTrap }
		DESCRIPTION
		     "%s - INCONSISTENT LINK NEGOTIATION"
		     --#TYPE
		     --#SUMMARY "Trap #$G, specific: $S, arg(1) : $1"
		     --#ARGUMENTS {}
		     --#SEVERITY  MAJOR
		     --#TIMEINDEX
		     --#HELP
		     --#HELPTAG
		     --#STATE
		::= 270012

        ppp-no-bundles-available  TRAP-TYPE
		ENTERPRISE   cdx6500
		VARIABLES    { cdx6500SNMPLastTrap }
		DESCRIPTION
		     "%s - NO BUNDLES AVAILABLE"
		     --#TYPE
		     --#SUMMARY "Trap #$G, specific: $S, arg(1) : $1"
		     --#ARGUMENTS {}
		     --#SEVERITY  MAJOR
		     --#TIMEINDEX
		     --#HELP
		     --#HELPTAG
		     --#STATE
		::= 270013

        ppp-the-peers-name-exceeds-16-ch  TRAP-TYPE
		ENTERPRISE   cdx6500
		VARIABLES    { cdx6500SNMPLastTrap }
		DESCRIPTION
		     "%s - THE PEER'S NAME EXCEEDS 16 CHARACTERS"
		     --#TYPE
		     --#SUMMARY "Trap #$G, specific: $S, arg(1) : $1"
		     --#ARGUMENTS {}
		     --#SEVERITY  MAJOR
		     --#TIMEINDEX
		     --#HELP
		     --#HELPTAG
		     --#STATE
		::= 270014

        ppp-authentication-was-rejected  TRAP-TYPE
		ENTERPRISE   cdx6500
		VARIABLES    { cdx6500SNMPLastTrap }
		DESCRIPTION
		     "%s - %s AUTHENTICATION WAS REJECTED BY PEER"
		     --#TYPE
		     --#SUMMARY "Trap #$G, specific: $S, arg(1) : $1"
		     --#ARGUMENTS {}
		     --#SEVERITY  MAJOR
		     --#TIMEINDEX
		     --#HELP
		     --#HELPTAG
		     --#STATE
		::= 270015

        ppp-link-is-looped-back  TRAP-TYPE
		ENTERPRISE   cdx6500
		VARIABLES    { cdx6500SNMPLastTrap }
		DESCRIPTION
		     "%s - LINK IS LOOPED BACK"
		     --#TYPE
		     --#SUMMARY "Trap #$G, specific: $S, arg(1) : $1"
		     --#ARGUMENTS {}
		     --#SEVERITY  CRITICAL
		     --#TIMEINDEX
		     --#HELP
		     --#HELPTAG
		     --#STATE
		::= 270016

        ppp-exceeds-maximum-number-of-li  TRAP-TYPE
		ENTERPRISE   cdx6500
		VARIABLES    { cdx6500SNMPLastTrap }
		DESCRIPTION
		     "%s - EXCEEDS MAXIMUM NUMBER OF LINKS FOR THIS BUNDLE"
		     --#TYPE
		     --#SUMMARY "Trap #$G, specific: $S, arg(1) : $1"
		     --#ARGUMENTS {}
		     --#SEVERITY  MAJOR
		     --#TIMEINDEX
		     --#HELP
		     --#HELPTAG
		     --#STATE
		::= 270017

        ppp-permanent-links-must-configu  TRAP-TYPE
		ENTERPRISE   cdx6500
		VARIABLES    { cdx6500SNMPLastTrap }
		DESCRIPTION
		     "%s - PERMANENT LINKS MUST CONFIGURED AS A DEDICATED LINK IN A PROFILE"
		     --#TYPE
		     --#SUMMARY "Trap #$G, specific: $S, arg(1) : $1"
		     --#ARGUMENTS {}
		     --#SEVERITY  CRITICAL
		     --#TIMEINDEX
		     --#HELP
		     --#HELPTAG
		     --#STATE
		::= 270018

        pppL2-in-data-loss  TRAP-TYPE
		ENTERPRISE   cdx6500
		VARIABLES    { cdx6500SNMPLastTrap }
		DESCRIPTION
		             "%s - DATA LOST FROM INBOUND QUEUE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 271000

        pppL2-invalid-encaps  TRAP-TYPE
		ENTERPRISE   cdx6500
		VARIABLES    { cdx6500SNMPLastTrap }
		DESCRIPTION
		             " %s - INVALID ENCAPSULATION"
                     --#TYPE
                     --#SUMMARY "Trap #$G, specific: $S, arg(1): $1"
                     --#ARGUMENTS {}
                     --#SEVERITY  INFORMATIONAL
                     --#TIMEINDEX
                     --#HELP
                     --#HELPTAG
                     --#STATE
		::= 271001

        isdn-lapd-fseq-override  TRAP-TYPE
                ENTERPRISE   cdx6500
                VARIABLES    { cdx6500SNMPLastTrap }
                DESCRIPTION
                             "%s - FRAME SEQUENCING OVERRIDE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 275000

        isdn-line-active  TRAP-TYPE
                ENTERPRISE   cdx6500
                VARIABLES    { cdx6500SNMPLastTrap }
                DESCRIPTION
                             "ISDN LINE %d IS ACTIVE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278000

        isdn-line-inactive  TRAP-TYPE
                ENTERPRISE   cdx6500
                VARIABLES    { cdx6500SNMPLastTrap }
                DESCRIPTION
                             "ISDN LINE %d IS INACTIVE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278001

        isdn-loop-test  TRAP-TYPE
                ENTERPRISE   cdx6500
                VARIABLES    { cdx6500SNMPLastTrap }
                DESCRIPTION
                             "ISDN LOOP TEST %s %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278002

        isdn-incompatible-detect  TRAP-TYPE
                ENTERPRISE   cdx6500
                VARIABLES    { cdx6500SNMPLastTrap }
                DESCRIPTION
                             "INCOMPATIBLE %s DETECTED FOR ISDN"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278003

        isdn-terminal-init-fail  TRAP-TYPE
                ENTERPRISE   cdx6500
                VARIABLES    { cdx6500SNMPLastTrap }
                DESCRIPTION
                             "TERMINAL (%d) INITIALIZATION FAILED: %d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278004

        isdn-Port-boot  TRAP-TYPE
                ENTERPRISE   cdx6500
                VARIABLES    { cdx6500SNMPLastTrap }
                DESCRIPTION
                             "ISDN BOOT COMPLETED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278005

        isdn-debug-info  TRAP-TYPE
                ENTERPRISE   cdx6500
                VARIABLES    { cdx6500SNMPLastTrap }
                DESCRIPTION
                             "DEBUG INFO - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278006

        isdn-illegal-port-type  TRAP-TYPE
                ENTERPRISE   cdx6500
                VARIABLES    { cdx6500SNMPLastTrap }
                DESCRIPTION
                             "ILLEGAL PORT TYPE CONFIGURED FOR D-CHANNEL ON PORT 1"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278007

        isdn-Port-connected  TRAP-TYPE
                ENTERPRISE   cdx6500
                VARIABLES    { cdx6500SNMPLastTrap }
                DESCRIPTION
                             "ISDN %s CONNECTED TO PORT %d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278008

        isdn-Port-disconnected  TRAP-TYPE
                ENTERPRISE   cdx6500
                VARIABLES    { cdx6500SNMPLastTrap }
                DESCRIPTION
                             "ISDN %s DISCONNECTED FROM PORT %d, CAUSE: %d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278009

        isdn-switch-override  TRAP-TYPE
                ENTERPRISE   cdx6500
                VARIABLES    { cdx6500SNMPLastTrap }
                DESCRIPTION
                             "ISDN SWITCH CONFIGURED OVERRIDE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278010

        isdn-terminal-init  TRAP-TYPE
                ENTERPRISE   cdx6500
                VARIABLES    { cdx6500SNMPLastTrap }
                DESCRIPTION
                             "TERMINAL (%d) INITIALIZATION COMPLETED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 278011

        isdn-dialing-to-on-bri-int-chann  TRAP-TYPE
		ENTERPRISE   cdx6500
		VARIABLES    { cdx6500SNMPLastTrap }
		DESCRIPTION
		     "%s DIALING TO %s ON BRI INT. %d %s CHANNEL"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 278012

        isdn-incoming-call-on-bri-int-chan  TRAP-TYPE
		ENTERPRISE   cdx6500
		VARIABLES    { cdx6500SNMPLastTrap }
		DESCRIPTION
		     "INCOMING CALL %s ON BRI INT. %d B%1d CHANNEL"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 278013

        isdn-bri-int-boot-completed  TRAP-TYPE
		ENTERPRISE   cdx6500
		VARIABLES    { cdx6500SNMPLastTrap }
		DESCRIPTION
		     "ISDN BRI INT. %d BOOT COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 278014

        isdn-duplicate-fix-tei-detected  TRAP-TYPE
		ENTERPRISE   cdx6500
		VARIABLES    { cdx6500SNMPLastTrap }
		DESCRIPTION
		     "DUPLICATE FIX TEI %d DETECTED FOR PKT D ON BRI INTERFACE %d"
		     --#TYPE
		     --#SUMMARY "Trap #$G, specific: $S, arg(1) : $1"
		     --#ARGUMENTS {}
		     --#SEVERITY  CRITICAL
		     --#TIMEINDEX
		     --#HELP
		     --#HELPTAG
		     --#STATE
		::= 278015

        isdn-dial-number-contention  TRAP-TYPE
		ENTERPRISE   cdx6500
		VARIABLES    { cdx6500SNMPLastTrap }
		DESCRIPTION
		     "ISDN BRI INT. %d DIAL NUM. CONTENTION WITH PPP OR SW"
		     --#TYPE
		     --#SUMMARY "Trap #$G, specific: $S, arg(1) : $1"
		     --#ARGUMENTS {}
		     --#SEVERITY  CRITICAL
		     --#TIMEINDEX
		     --#HELP
		     --#HELPTAG
		     --#STATE
		::= 278016

	isdn278017-disconnec   TRAP-TYPE
		ENTERPRISE   cdx6500
		VARIABLES    { cdx6500SNMPLastTrap }
		DESCRIPTION
		     "%s DISCONNECTING FROM BRI INT. %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 278017

	isdn278018-false-dis   TRAP-TYPE
		ENTERPRISE   cdx6500
		VARIABLES    { cdx6500SNMPLastTrap }
		DESCRIPTION
		     "%s FALSE DISCONNECT ATTEMPT"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 278018

	isdn278019-isdn-pri   TRAP-TYPE
		ENTERPRISE   cdx6500
		VARIABLES    { cdx6500SNMPLastTrap }
		DESCRIPTION
		     "ISDN PRI INTERFACE %d IS ACTIVE"
		     --#TYPE
		     --#SUMMARY "Trap #$G, specific: $S, arg(1) : $1"
		     --#ARGUMENTS {}
		     --#SEVERITY  CRITICAL
		     --#TIMEINDEX
		     --#HELP
		     --#HELPTAG
		     --#STATE
		::= 278019

	isdn278020-isdn-pri   TRAP-TYPE
		ENTERPRISE   cdx6500
		VARIABLES    { cdx6500SNMPLastTrap }
		DESCRIPTION
		     "ISDN PRI INTERFACE %d IS INACTIVE"
		     --#TYPE
		     --#SUMMARY "Trap #$G, specific: $S, arg(1) : $1"
		     --#ARGUMENTS {}
		     --#SEVERITY  CRITICAL
		     --#TIMEINDEX
		     --#HELP
		     --#HELPTAG
		     --#STATE
		::= 278020

	isdn278023-isdn-bri   TRAP-TYPE
		ENTERPRISE   cdx6500
		VARIABLES    { cdx6500SNMPLastTrap }
		DESCRIPTION
		     "ISDN BRI INT. UNSUPPORTED MSG RCV'ed FROM CC, MSG-ID = 0x%x"
		     --#TYPE
		     --#SUMMARY "Trap #$G, specific: $S, arg(1) : $1"
		     --#ARGUMENTS {}
		     --#SEVERITY  CRITICAL
		     --#TIMEINDEX
		     --#HELP
		     --#HELPTAG
		     --#STATE
		::= 278023

	isdn278025-qsig-erro   TRAP-TYPE
		ENTERPRISE   cdx6500
		VARIABLES    { cdx6500SNMPLastTrap }
		DESCRIPTION
		     "QSIG ERROR: me-ccs-voice.c Line # %d"
		     --#TYPE
		     --#SUMMARY "Trap #$G, specific: $S, arg(1) : $1"
		     --#ARGUMENTS {}
		     --#SEVERITY  CRITICAL
		     --#TIMEINDEX
		     --#HELP
		     --#HELPTAG
		     --#STATE
		::= 278025

	isdn278026-invalid-q   TRAP-TYPE
		ENTERPRISE   cdx6500
		VARIABLES    { cdx6500SNMPLastTrap }
		DESCRIPTION
		     "INVALID QSIG SIGNALLING : PORT = %d : SIG. STATE = %d, STIMULUS = %d"
		     --#TYPE
		     --#SUMMARY "Trap #$G, specific: $S, arg(1) : $1"
		     --#ARGUMENTS {}
		     --#SEVERITY  CRITICAL
		     --#TIMEINDEX
		     --#HELP
		     --#HELPTAG
		     --#STATE
		::= 278026

	isdn278027-isdn-bri   TRAP-TYPE
		ENTERPRISE   cdx6500
		VARIABLES    { cdx6500SNMPLastTrap }
		DESCRIPTION
		     "ISDN BRI INT. %d CALL TO %s FROM %s FAILED ON PORT %d, %s"
		     --#TYPE
		     --#SUMMARY "Trap #$G, specific: $S, arg(1) : $1"
		     --#ARGUMENTS {}
		     --#SEVERITY  CRITICAL
		     --#TIMEINDEX
		     --#HELP
		     --#HELPTAG
		     --#STATE
		::= 278027

	isdn278030-isdn-bri   TRAP-TYPE
		ENTERPRISE   cdx6500
		VARIABLES    { cdx6500SNMPLastTrap }
		DESCRIPTION
		     "ISDN BRI INTERFACE %d IS ACTIVE"
		     --#TYPE
		     --#SUMMARY "Trap #$G, specific: $S, arg(1) : $1"
		     --#ARGUMENTS {}
		     --#SEVERITY  MINOR
		     --#TIMEINDEX
		     --#HELP
		     --#HELPTAG
		     --#STATE
		::= 278030

	isdn278031-isdn-bri   TRAP-TYPE
		ENTERPRISE   cdx6500
		VARIABLES    { cdx6500SNMPLastTrap }
		DESCRIPTION
		     "ISDN BRI INTERFACE %d IS INACTIVE"
		     --#TYPE
		     --#SUMMARY "Trap #$G, specific: $S, arg(1) : $1"
		     --#ARGUMENTS {}
		     --#SEVERITY  MINOR
		     --#TIMEINDEX
		     --#HELP
		     --#HELPTAG
		     --#STATE
		::= 278031

        isdn-lif-packet  TRAP-TYPE
                ENTERPRISE   cdx6500
                VARIABLES    { cdx6500SNMPLastTrap }
                DESCRIPTION
                             "DBG- %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 279000

        voice-hw-board-fail  TRAP-TYPE
                ENTERPRISE   cdx6500
                VARIABLES    { cdx6500SNMPLastTrap }
                DESCRIPTION
                             "%s - HW BOARD FAILURE - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280000

        voice-Port-fail  TRAP-TYPE
                ENTERPRISE   cdx6500
                VARIABLES    { cdx6500SNMPLastTrap }
                DESCRIPTION
                             "%s - PORT FAILURE - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280001

        voice-Port-init-fail  TRAP-TYPE
                ENTERPRISE   cdx6500
                VARIABLES    { cdx6500SNMPLastTrap }
                DESCRIPTION
                             "%s - PORT INIT FAILURE - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280002

        voice-Port-not-started  TRAP-TYPE
                ENTERPRISE   cdx6500
                VARIABLES    { cdx6500SNMPLastTrap }
                DESCRIPTION
                             "%s - PORT NOT STARTED - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280003

        voice-Port-boot-fail  TRAP-TYPE
                ENTERPRISE   cdx6500
                VARIABLES    { cdx6500SNMPLastTrap }
                DESCRIPTION
                             "%s - PORT BOOT FAILURE - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280004

        voice-Port-boot  TRAP-TYPE
                ENTERPRISE   cdx6500
                VARIABLES    { cdx6500SNMPLastTrap }
                DESCRIPTION
                             "%s - PORT BOOT COMPLETE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280005

        voice-Port-disable  TRAP-TYPE
                ENTERPRISE   cdx6500
                VARIABLES    { cdx6500SNMPLastTrap }
                DESCRIPTION
                             "%s - PORT DISABLED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280006

        voice-Port-busyout  TRAP-TYPE
                ENTERPRISE   cdx6500
                VARIABLES    { cdx6500SNMPLastTrap }
                DESCRIPTION
                             "%s - PORT BUSY OUT"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280007

        voice-Port-disable-fail  TRAP-TYPE
                ENTERPRISE   cdx6500
                VARIABLES    { cdx6500SNMPLastTrap }
                DESCRIPTION
                             "%s - CAN NOT DISABLE PORT - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280008

        voice-Port-enable  TRAP-TYPE
                ENTERPRISE   cdx6500
                VARIABLES    { cdx6500SNMPLastTrap }
                DESCRIPTION
                             "%s - PORT ENABLED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280009

        voice-Port-enable-fail  TRAP-TYPE
                ENTERPRISE   cdx6500
                VARIABLES    { cdx6500SNMPLastTrap }
                DESCRIPTION
                             "%s - CAN NOT ENABLE PORT - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280010

        voice-Port-busyout-fail  TRAP-TYPE
                ENTERPRISE   cdx6500
                VARIABLES    { cdx6500SNMPLastTrap }
                DESCRIPTION
                             "%s - CAN NOT BUSYOUT PORT - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 280011

        vport-virtual-mapping-error-caus  TRAP-TYPE
		ENTERPRISE   cdx6500
		VARIABLES    { cdx6500SNMPLastTrap }
		DESCRIPTION
		     "VIRTUAL MAPPING ERROR, CAUSE: %s"
		     --#TYPE
		     --#SUMMARY "Trap #$G, specific: $S, arg(1) : $1"
		     --#ARGUMENTS {}
		     --#SEVERITY  MINOR
		     --#TIMEINDEX
		     --#HELP
		     --#HELPTAG
		     --#STATE
		::= 280012

        vport-virtual-mapping-error-caus2  TRAP-TYPE
		ENTERPRISE   cdx6500
		VARIABLES    { cdx6500SNMPLastTrap }
		DESCRIPTION
		     "VIRTUAL MAPPING ERROR, CAUSE: %s"
		     --#TYPE
		     --#SUMMARY "Trap #$G, specific: $S, arg(1) : $1"
		     --#ARGUMENTS {}
		     --#SEVERITY  MINOR
		     --#TIMEINDEX
		     --#HELP
		     --#HELPTAG
		     --#STATE
		::= 280013

        vport-voice-record-conversion-co  TRAP-TYPE
		ENTERPRISE   cdx6500
		VARIABLES    { cdx6500SNMPLastTrap }
		DESCRIPTION
		     "VOICE RECORD CONVERSION COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 280014

        vport-voice-record-conversion-fa  TRAP-TYPE
		ENTERPRISE   cdx6500
		VARIABLES    { cdx6500SNMPLastTrap }
		DESCRIPTION
		     "VOICE RECORD CONVERSION FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 280015

        vport-voice-record-conversion-vs  TRAP-TYPE
		ENTERPRISE   cdx6500
		VARIABLES    { cdx6500SNMPLastTrap }
		DESCRIPTION
		     "VOICE RECORD CONVERSION %d vs. %d"
		     --#TYPE
		     --#SUMMARY "Trap #$G, specific: $S, arg(1) : $1"
		     --#ARGUMENTS {}
		     --#SEVERITY  CRITICAL
		     --#TIMEINDEX
		     --#HELP
		     --#HELPTAG
		     --#STATE
		::= 280016

        vdcdm-hw-board-failure-cause-bac  TRAP-TYPE
		ENTERPRISE   cdx6500
		VARIABLES    { cdx6500SNMPLastTrap }
		DESCRIPTION
		     "%s HW BOARD FAILURE, CAUSE: BACKGROUND DIAGNOSTIC"
		     --#TYPE
		     --#SUMMARY "Trap #$G, specific: $S, arg(1) : $1"
		     --#ARGUMENTS {}
		     --#SEVERITY  CRITICAL
		     --#TIMEINDEX
		     --#HELP
		     --#HELPTAG
		     --#STATE
		::= 281000

        vdcdm-board-boot-cause-watchdog  TRAP-TYPE
		ENTERPRISE   cdx6500
		VARIABLES    { cdx6500SNMPLastTrap }
		DESCRIPTION
		     "%s BOARD BOOT, CAUSE: WATCHDOG TIMER EXPIRED"
		     --#TYPE
		     --#SUMMARY "Trap #$G, specific: $S, arg(1) : $1"
		     --#ARGUMENTS {}
		     --#SEVERITY  CRITICAL
		     --#TIMEINDEX
		     --#HELP
		     --#HELPTAG
		     --#STATE
		::= 281001

        vdcdm-port-failure-cause-missing  TRAP-TYPE
		ENTERPRISE   cdx6500
		VARIABLES    { cdx6500SNMPLastTrap }
		DESCRIPTION
		     "%s PORT FAILURE, CAUSE: MISSING BATTERY"
		     --#TYPE
		     --#SUMMARY "Trap #$G, specific: $S, arg(1) : $1"
		     --#ARGUMENTS {}
		     --#SEVERITY  CRITICAL
		     --#TIMEINDEX
		     --#HELP
		     --#HELPTAG
		     --#STATE
		::= 281002

        vdcdm-port-failure-cause-missing2  TRAP-TYPE
		ENTERPRISE   cdx6500
		VARIABLES    { cdx6500SNMPLastTrap }
		DESCRIPTION
		     "%s PORT FAILURE, CAUSE: MISSING RINGER SUPPLY"
		     --#TYPE
		     --#SUMMARY "Trap #$G, specific: $S, arg(1) : $1"
		     --#ARGUMENTS {}
		     --#SEVERITY  CRITICAL
		     --#TIMEINDEX
		     --#HELP
		     --#HELPTAG
		     --#STATE
		::= 281003

        vdcdm-dspm-software-download-com  TRAP-TYPE
		ENTERPRISE   cdx6500
		VARIABLES    { cdx6500SNMPLastTrap }
		DESCRIPTION
		     "%s DSPM SOFTWARE DOWNLOAD COMPLETED"
		     --#TYPE
		     --#SUMMARY "Trap #$G, specific: $S, arg(1) : $1"
		     --#ARGUMENTS {}
		     --#SEVERITY  MINOR
		     --#TIMEINDEX
		     --#HELP
		     --#HELPTAG
		     --#STATE
		::= 281004

        vdcdm-dspm-software-download-fai  TRAP-TYPE
		ENTERPRISE   cdx6500
		VARIABLES    { cdx6500SNMPLastTrap }
		DESCRIPTION
		     "%s DSPM SOFTWARE DOWNLOAD FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 281005

        vdcdm-voice-signaling-trace  TRAP-TYPE
		ENTERPRISE   cdx6500
		VARIABLES    { cdx6500SNMPLastTrap }
		DESCRIPTION
		     "VOICE-%d SIGNALING TRACE: %s"
		     --#TYPE
		     --#SUMMARY "Trap #$G, specific: $S, arg(1) : $1"
		     --#ARGUMENTS {}
		     --#SEVERITY  MAJOR
		     --#TIMEINDEX
		     --#HELP
		     --#HELPTAG
		     --#STATE
		::= 281006

        vdcdm-error-on-channel-cause  TRAP-TYPE
		ENTERPRISE   cdx6500
		VARIABLES    { cdx6500SNMPLastTrap }
		DESCRIPTION
		     "%s ERROR ON CHANNEL-%d, CAUSE:%s"
		     --#TYPE
		     --#SUMMARY "Trap #$G, specific: $S, arg(1) : $1"
		     --#ARGUMENTS {}
		     --#SEVERITY  CRITICAL
		     --#TIMEINDEX
		     --#HELP
		     --#HELPTAG
		     --#STATE
		::= 281007

        vdcdm-dspm-crash-reason-pc-add  TRAP-TYPE
		ENTERPRISE   cdx6500
		VARIABLES    { cdx6500SNMPLastTrap }
		DESCRIPTION
		     "DSPM CRASH REASON - %s  PC=%x  ADD=%x"
		     --#TYPE
		     --#SUMMARY "Trap #$G, specific: $S, arg(1) : $1"
		     --#ARGUMENTS {}
		     --#SEVERITY  CRITICAL
		     --#TIMEINDEX
		     --#HELP
		     --#HELPTAG
		     --#STATE
		::= 281008

        vdcdm-dspm-first-recovery-succes  TRAP-TYPE
		ENTERPRISE   cdx6500
		VARIABLES    { cdx6500SNMPLastTrap }
		DESCRIPTION
		     "DSPM FIRST RECOVERY SUCCESSFULL"
		     --#TYPE
		     --#SUMMARY "Trap #$G, specific: $S, arg(1) : $1"
		     --#ARGUMENTS {}
		     --#SEVERITY  CRITICAL
		     --#TIMEINDEX
		     --#HELP
		     --#HELPTAG
		     --#STATE
		::= 281009

        vdcdm-dspm-second-recovery-succe  TRAP-TYPE
		ENTERPRISE   cdx6500
		VARIABLES    { cdx6500SNMPLastTrap }
		DESCRIPTION
		     "DSPM SECOND RECOVERY SUCCESSFULL"
		     --#TYPE
		     --#SUMMARY "Trap #$G, specific: $S, arg(1) : $1"
		     --#ARGUMENTS {}
		     --#SEVERITY  CRITICAL
		     --#TIMEINDEX
		     --#HELP
		     --#HELPTAG
		     --#STATE
		::= 281010

        vdcdm-dspm-protocol-initializati  TRAP-TYPE
		ENTERPRISE   cdx6500
		VARIABLES    { cdx6500SNMPLastTrap }
		DESCRIPTION
		     "DSPM PROTOCOL INITIALIZATION FAILED - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 281011

        vdcdm-voice-call-calling-called  TRAP-TYPE
		ENTERPRISE   cdx6500
		VARIABLES    { cdx6500SNMPLastTrap }
		DESCRIPTION
		     "VOICE CALL: CALLING %10s, CALLED %10s, SRC %10s, DEST %10s, CLR %3d, TIME %4d sec"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 281012

        vdcdm-voice-vsm-command-eid-3d-o  TRAP-TYPE
		ENTERPRISE   cdx6500
		VARIABLES    { cdx6500SNMPLastTrap }
		DESCRIPTION
		     "VOICE-%d VSM COMMAND:  EID %-3d, OPCODE %-2x, PAYLOAD %-2x %-2x %-2x %-2x %-2x %-2x %-2x %-2x %-2x %-2x"
		     --#TYPE
		     --#SUMMARY "Trap #$G, specific: $S, arg(1) : $1"
		     --#ARGUMENTS {}
		     --#SEVERITY  MAJOR
		     --#TIMEINDEX
		     --#HELP
		     --#HELPTAG
		     --#STATE
		::= 281013

        vdcdm-voice-vsm-response-eid-3d  TRAP-TYPE
		ENTERPRISE   cdx6500
		VARIABLES    { cdx6500SNMPLastTrap }
		DESCRIPTION
		     "VOICE-%d VSM RESPONSE: EID %-3d, OPCODE %-2x, PAYLOAD %-2x %-2x %-2x %-2x %-2x %-2x %-2x %-2x %-2x %-2x"
		     --#TYPE
		     --#SUMMARY "Trap #$G, specific: $S, arg(1) : $1"
		     --#ARGUMENTS {}
		     --#SEVERITY  MAJOR
		     --#TIMEINDEX
		     --#HELP
		     --#HELPTAG
		     --#STATE
		::= 281014

	vdcdm281015-voice-trace   TRAP-TYPE
		ENTERPRISE   cdx6500
		VARIABLES    { cdx6500SNMPLastTrap }
		DESCRIPTION
		     "VOICE-%d TRACE: Voice Roundtrip Delay (msec): Max Delay %d, Min Delay %d, Mean Delay %d, Samples %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 281015

	vdcdm281016-voice-ca   TRAP-TYPE
		ENTERPRISE   cdx6500
		VARIABLES    { cdx6500SNMPLastTrap }
		DESCRIPTION
		     "VOICE CALL-%3d S/T%4d/2 SRC %-16s DEST %-16s CLR %-2d TIME %-6d SEC"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 281016

	vdcdm281017-voice   TRAP-TYPE
		ENTERPRISE   cdx6500
		VARIABLES    { cdx6500SNMPLastTrap }
		DESCRIPTION
		     "VOICE-%d %s"
		     --#TYPE
		     --#SUMMARY "Trap #$G, specific: $S, arg(1) : $1"
		     --#ARGUMENTS {}
		     --#SEVERITY  MAJOR
		     --#TIMEINDEX
		     --#HELP
		     --#HELPTAG
		     --#STATE
		::= 281017

	vdcdm281018-dsp-last   TRAP-TYPE
		ENTERPRISE   cdx6500
		VARIABLES    { cdx6500SNMPLastTrap }
		DESCRIPTION
		     "%s DSP #%d LAST VSM RESPONSE: %02X %02X %02X %02X %02X %02X %02X %02X %02X %02X %02X %02X %02X %02X %02X %02X %02X %02X %02X %02X"
		     --#TYPE
		     --#SUMMARY "Trap #$G, specific: $S, arg(1) : $1"
		     --#ARGUMENTS {}
		     --#SEVERITY  CRITICAL
		     --#TIMEINDEX
		     --#HELP
		     --#HELPTAG
		     --#STATE
		::= 281018

	vdcdm281019-voice   TRAP-TYPE
		ENTERPRISE   cdx6500
		VARIABLES    { cdx6500SNMPLastTrap }
		DESCRIPTION
		     "VOICE-%d %s"
		     --#TYPE
		     --#SUMMARY "Trap #$G, specific: $S, arg(1) : $1"
		     --#ARGUMENTS {}
		     --#SEVERITY  MAJOR
		     --#TIMEINDEX
		     --#HELP
		     --#HELPTAG
		     --#STATE
		::= 281019

        t1e1-Port-boot  TRAP-TYPE
                ENTERPRISE   cdx6500
                VARIABLES    { cdx6500SNMPLastTrap }
                DESCRIPTION
                             "%s - PORT BOOT COMPLETED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 282000

        t1e1-Port-boot-fail  TRAP-TYPE
                ENTERPRISE   cdx6500
                VARIABLES    { cdx6500SNMPLastTrap }
                DESCRIPTION
                             "%s - PORT BOOT FAILED, CAUSE: %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 282001

        t1e1-Port-disable  TRAP-TYPE
                ENTERPRISE   cdx6500
                VARIABLES    { cdx6500SNMPLastTrap }
                DESCRIPTION
                             "%s - PORT DISABLED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 282002

        t1e1-Port-enable  TRAP-TYPE
                ENTERPRISE   cdx6500
                VARIABLES    { cdx6500SNMPLastTrap }
                DESCRIPTION
                             "%s - PORT ENABLED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 282003

        t1e1-Port-not-init  TRAP-TYPE
                ENTERPRISE   cdx6500
                VARIABLES    { cdx6500SNMPLastTrap }
                DESCRIPTION
                             "%s - PORT INIT FAILURE, CAUSE: %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 282004

        t1e1-Port-vmt-error  TRAP-TYPE
                ENTERPRISE   cdx6500
                VARIABLES    { cdx6500SNMPLastTrap }
                DESCRIPTION
                             "VIRTUAL MAPPING ERROR, CAUSE: %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 282005

        t1e1-putmsg-failed  TRAP-TYPE
                ENTERPRISE   cdx6500
                VARIABLES    { cdx6500SNMPLastTrap }
                DESCRIPTION
                             "T1E1DRV-<%d:%d>: CARD IS NOT ACTIVE <%s>, CAUSE : %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283000

        t1e1-comm-error  TRAP-TYPE
                ENTERPRISE   cdx6500
                VARIABLES    { cdx6500SNMPLastTrap }
                DESCRIPTION
                             "T1E1DRV-<%d>: L3L4mERROR FROM T1/E1 CARD, Cause : %d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283001

        t1e1-fatal-error  TRAP-TYPE
                ENTERPRISE   cdx6500
                VARIABLES    { cdx6500SNMPLastTrap }
                DESCRIPTION
                             "T1E1DRV-<%d>: ERROR: CAUSE-%s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283002

        t1e1-dload-failed  TRAP-TYPE
                ENTERPRISE   cdx6500
                VARIABLES    { cdx6500SNMPLastTrap }
                DESCRIPTION
                             "<%s>-<%d>: BOARD BOOT: CAUSE SOFTWARE DOWNLOAD FAILED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283003

        t1e1-threshold-exceeded  TRAP-TYPE
                ENTERPRISE   cdx6500
                VARIABLES    { cdx6500SNMPLastTrap }
                DESCRIPTION
                             "%s-<%d> %s THRESHOLD EXCEEDED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283004

        t1e1-t1-alarm  TRAP-TYPE
                ENTERPRISE   cdx6500
                VARIABLES    { cdx6500SNMPLastTrap }
                DESCRIPTION
                             "T1-<%d> - %s ALARM %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283005

        t1e1-e1-alarm  TRAP-TYPE
                ENTERPRISE   cdx6500
                VARIABLES    { cdx6500SNMPLastTrap }
                DESCRIPTION
                             "E1-<%d> - <%s> - %s"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283006

        t1e1-background-diag  TRAP-TYPE
                ENTERPRISE   cdx6500
                VARIABLES    { cdx6500SNMPLastTrap }
                DESCRIPTION
                             "%s-<%d> - HW BOARD FAILURE, CAUSE: BACKGROUND DIGNOSTIC"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283007

        t1e1-watchdog-expired  TRAP-TYPE
                ENTERPRISE   cdx6500
                VARIABLES    { cdx6500SNMPLastTrap }
                DESCRIPTION
                             "%s-<%d> - BOARD BOOT: CAUSE WATCHDOG TIMER EXPIRED"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283008

        t1e1-illegal-clocking  TRAP-TYPE
                ENTERPRISE   cdx6500
                VARIABLES    { cdx6500SNMPLastTrap }
                DESCRIPTION
                             "%s-<%d> - Warning - Illegal T1/E1 clock mode - Both ports configured for 'REC' timing"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283009

        t1e1-invalid-message  TRAP-TYPE
                ENTERPRISE   cdx6500
                VARIABLES    { cdx6500SNMPLastTrap }
                DESCRIPTION
                             "T1E1DRV-<%d>: %s -  %d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 283010

        t1e1-pri-b-incoming-call-to-from  TRAP-TYPE
		ENTERPRISE   cdx6500
		VARIABLES    { cdx6500SNMPLastTrap }
		DESCRIPTION
		     "PRI-%dB%d - INCOMING CALL TO %s FROM %s CONNECTED ON PORT %d"
		     --#TYPE
		     --#SUMMARY "Trap #$G, specific: $S, arg(1) : $1"
		     --#ARGUMENTS {}
		     --#SEVERITY  MAJOR
		     --#TIMEINDEX
		     --#HELP
		     --#HELPTAG
		     --#STATE
		::= 283011

        t1e1-pri-b-outgoing-call-to-conn  TRAP-TYPE
		ENTERPRISE   cdx6500
		VARIABLES    { cdx6500SNMPLastTrap }
		DESCRIPTION
		     "PRI-%dB%d - OUTGOING CALL TO %s CONNECTED ON PORT %d"
		     --#TYPE
		     --#SUMMARY "Trap #$G, specific: $S, arg(1) : $1"
		     --#ARGUMENTS {}
		     --#SEVERITY  MAJOR
		     --#TIMEINDEX
		     --#HELP
		     --#HELPTAG
		     --#STATE
		::= 283012

        t1e1-pri-call-on-port-disconnect  TRAP-TYPE
		ENTERPRISE   cdx6500
		VARIABLES    { cdx6500SNMPLastTrap }
		DESCRIPTION
		     "PRI-%d - %s CALL %s %s ON PORT %d DISCONNECTED BY 65xx"
		     --#TYPE
		     --#SUMMARY "Trap #$G, specific: $S, arg(1) : $1"
		     --#ARGUMENTS {}
		     --#SEVERITY  MAJOR
		     --#TIMEINDEX
		     --#HELP
		     --#HELPTAG
		     --#STATE
		::= 283013

        t1e1-pri-call-on-port-disconnect2  TRAP-TYPE
		ENTERPRISE   cdx6500
		VARIABLES    { cdx6500SNMPLastTrap }
		DESCRIPTION
		     "PRI-%d - %s CALL %s %s ON PORT %d DISCONNECTED BY NETWORK"
		     --#TYPE
		     --#SUMMARY "Trap #$G, specific: $S, arg(1) : $1"
		     --#ARGUMENTS {}
		     --#SEVERITY  MAJOR
		     --#TIMEINDEX
		     --#HELP
		     --#HELPTAG
		     --#STATE
		::= 283014

        t1e1-pri-incoming-call-to-from-f  TRAP-TYPE
		ENTERPRISE   cdx6500
		VARIABLES    { cdx6500SNMPLastTrap }
		DESCRIPTION
		     "PRI-%d - INCOMING CALL TO %s FROM %s FAILED ON PORT %d, %s"
		     --#TYPE
		     --#SUMMARY "Trap #$G, specific: $S, arg(1) : $1"
		     --#ARGUMENTS {}
		     --#SEVERITY  MAJOR
		     --#TIMEINDEX
		     --#HELP
		     --#HELPTAG
		     --#STATE
		::= 283015

        t1e1-pri-outgoing-call-to-from-f  TRAP-TYPE
		ENTERPRISE   cdx6500
		VARIABLES    { cdx6500SNMPLastTrap }
		DESCRIPTION
		     "PRI-%d - OUTGOING CALL TO %s FROM %s FAILED ON PORT %d, %s"
		     --#TYPE
		     --#SUMMARY "Trap #$G, specific: $S, arg(1) : $1"
		     --#ARGUMENTS {}
		     --#SEVERITY  MAJOR
		     --#TIMEINDEX
		     --#HELP
		     --#HELPTAG
		     --#STATE
		::= 283016

        t1e1-pri-incoming-call-to-from-f2  TRAP-TYPE
		ENTERPRISE   cdx6500
		VARIABLES    { cdx6500SNMPLastTrap }
		DESCRIPTION
		     "PRI-%d - INCOMING CALL TO %s FROM %s FAILED ON PORT %d, %s"
		     --#TYPE
		     --#SUMMARY "Trap #$G, specific: $S, arg(1) : $1"
		     --#ARGUMENTS {}
		     --#SEVERITY  MAJOR
		     --#TIMEINDEX
		     --#HELP
		     --#HELPTAG
		     --#STATE
		::= 283017

        t1e1-pri-d-channel-up  TRAP-TYPE
		ENTERPRISE   cdx6500
		VARIABLES    { cdx6500SNMPLastTrap }
		DESCRIPTION
		     "PRI-%d - D CHANNEL UP"
		     --#TYPE
		     --#SUMMARY "Trap #$G, specific: $S, arg(1) : $1"
		     --#ARGUMENTS {}
		     --#SEVERITY  CRITICAL
		     --#TIMEINDEX
		     --#HELP
		     --#HELPTAG
		     --#STATE
		::= 283018

        t1e1-pri-d-channel-down  TRAP-TYPE
		ENTERPRISE   cdx6500
		VARIABLES    { cdx6500SNMPLastTrap }
		DESCRIPTION
		     "PRI-%d - D CHANNEL DOWN"
		     --#TYPE
		     --#SUMMARY "Trap #$G, specific: $S, arg(1) : $1"
		     --#ARGUMENTS {}
		     --#SEVERITY  CRITICAL
		     --#TIMEINDEX
		     --#HELP
		     --#HELPTAG
		     --#STATE
		::= 283019

        t1e1-pri-b-b-channel-up  TRAP-TYPE
		ENTERPRISE   cdx6500
		VARIABLES    { cdx6500SNMPLastTrap }
		DESCRIPTION
		     "PRI-%dB%d - B CHANNEL UP"
		     --#TYPE
		     --#SUMMARY "Trap #$G, specific: $S, arg(1) : $1"
		     --#ARGUMENTS {}
		     --#SEVERITY  CRITICAL
		     --#TIMEINDEX
		     --#HELP
		     --#HELPTAG
		     --#STATE
		::= 283020

        t1e1-pri-b-b-channel-down  TRAP-TYPE
		ENTERPRISE   cdx6500
		VARIABLES    { cdx6500SNMPLastTrap }
		DESCRIPTION
		     "PRI-%dB%d - B CHANNEL DOWN"
		     --#TYPE
		     --#SUMMARY "Trap #$G, specific: $S, arg(1) : $1"
		     --#ARGUMENTS {}
		     --#SEVERITY  CRITICAL
		     --#TIMEINDEX
		     --#HELP
		     --#HELPTAG
		     --#STATE
		::= 283021

        t1e1-virtual-port-config-does-no  TRAP-TYPE
		ENTERPRISE   cdx6500
		VARIABLES    { cdx6500SNMPLastTrap }
		DESCRIPTION
		     "VIRTUAL PORT %d CONFIG DOES NOT MATCH T1E1 PORT %d CONFIG"
		     --#TYPE
		     --#SUMMARY "Trap #$G, specific: $S, arg(1) : $1"
		     --#ARGUMENTS {}
		     --#SEVERITY  CRITICAL
		     --#TIMEINDEX
		     --#HELP
		     --#HELPTAG
		     --#STATE
		::= 283022

        t1e1-isdn-signaling-message-rece  TRAP-TYPE
		ENTERPRISE   cdx6500
		VARIABLES    { cdx6500SNMPLastTrap }
		DESCRIPTION
		     "ISDN SIGNALING MESSAGE RECEIVED FOR CHANNEL %d"
		     --#TYPE
		     --#SUMMARY "Trap #$G, specific: $S, arg(1) : $1"
		     --#ARGUMENTS {}
		     --#SEVERITY  CRITICAL
		     --#TIMEINDEX
		     --#HELP
		     --#HELPTAG
		     --#STATE
		::= 283023

        t1e1-pri-d-channel-establishing  TRAP-TYPE
		ENTERPRISE   cdx6500
		VARIABLES    { cdx6500SNMPLastTrap }
		DESCRIPTION
		     "PRI-%d - D CHANNEL ESTABLISHING"
		     --#TYPE
		     --#SUMMARY "Trap #$G, specific: $S, arg(1) : $1"
		     --#ARGUMENTS {}
		     --#SEVERITY  CRITICAL
		     --#TIMEINDEX
		     --#HELP
		     --#HELPTAG
		     --#STATE
		::= 283024

        t1e1-pri-b-incoming-call-to-from2  TRAP-TYPE
		ENTERPRISE   cdx6500
		VARIABLES    { cdx6500SNMPLastTrap }
		DESCRIPTION
		     "PRI-%dB%d - INCOMING CALL TO  %s FROM %s FAILED, %s"
		     --#TYPE
		     --#SUMMARY "Trap #$G, specific: $S, arg(1) : $1"
		     --#ARGUMENTS {}
		     --#SEVERITY  MAJOR
		     --#TIMEINDEX
		     --#HELP
		     --#HELPTAG
		     --#STATE
		::= 283025

        t1e1-function-name-sigstate  TRAP-TYPE
		ENTERPRISE   cdx6500
		VARIABLES    { cdx6500SNMPLastTrap }
		DESCRIPTION
		     "FUNCTION NAME: %s, SIG-STATE: %d"
		     --#TYPE
		     --#SUMMARY "Trap #$G, specific: $S, arg(1) : $1"
		     --#ARGUMENTS {}
		     --#SEVERITY  CRITICAL
		     --#TIMEINDEX
		     --#HELP
		     --#HELPTAG
		     --#STATE
		::= 283026

        t1e1-t1e1drv-invalid-execution-l  TRAP-TYPE
		ENTERPRISE   cdx6500
		VARIABLES    { cdx6500SNMPLastTrap }
		DESCRIPTION
		     "T1E1DRV: INVALID EXECUTION. Line # %d"
		     --#TYPE
		     --#SUMMARY "Trap #$G, specific: $S, arg(1) : $1"
		     --#ARGUMENTS {}
		     --#SEVERITY  MAJOR
		     --#TIMEINDEX
		     --#HELP
		     --#HELPTAG
		     --#STATE
		::= 283027

        t1e1-pri-d-channel-restarted-all  TRAP-TYPE
		ENTERPRISE   cdx6500
		VARIABLES    { cdx6500SNMPLastTrap }
		DESCRIPTION
		     "PRI-%d - D CHANNEL RESTARTED,  ALL CALLS DROPPED"
		     --#TYPE
		     --#SUMMARY "Trap #$G, specific: $S, arg(1) : $1"
		     --#ARGUMENTS {}
		     --#SEVERITY  CRITICAL
		     --#TIMEINDEX
		     --#HELP
		     --#HELPTAG
		     --#STATE
		::= 283028

        t1e1-invalid-pri-signalling-port  TRAP-TYPE
		ENTERPRISE   cdx6500
		VARIABLES    { cdx6500SNMPLastTrap }
		DESCRIPTION
		     "INVALID PRI SIGNALLING : PORT = %d : STATE = %d , SIG. STATE = %d, STIMULOUS = %d"
		     --#TYPE
		     --#SUMMARY "Trap #$G, specific: $S, arg(1) : $1"
		     --#ARGUMENTS {}
		     --#SEVERITY  MAJOR
		     --#TIMEINDEX
		     --#HELP
		     --#HELPTAG
		     --#STATE
		::= 283029

        t1e1-virtual-port-t1e1-card-does  TRAP-TYPE
		ENTERPRISE   cdx6500
		VARIABLES    { cdx6500SNMPLastTrap }
		DESCRIPTION
		     "T1/E1-%d VIRTUAL PORT %d - T1/E1 CARD DOES NOT SUPPORT DATA or SWITCHED DATA PORTS"
		     --#TYPE
		     --#SUMMARY "Trap #$G, specific: $S, arg(1) : $1"
		     --#ARGUMENTS {}
		     --#SEVERITY  CRITICAL
		     --#TIMEINDEX
		     --#HELP
		     --#HELPTAG
		     --#STATE
		::= 283030

        t1e1-virtual-port-no-hdlc-channe  TRAP-TYPE
		ENTERPRISE   cdx6500
		VARIABLES    { cdx6500SNMPLastTrap }
		DESCRIPTION
		     "T1/E1-%d VIRTUAL PORT %d - No HDLC channel available"
		     --#TYPE
		     --#SUMMARY "Trap #$G, specific: $S, arg(1) : $1"
		     --#ARGUMENTS {}
		     --#SEVERITY  MAJOR
		     --#TIMEINDEX
		     --#HELP
		     --#HELPTAG
		     --#STATE
		::= 283031

        t1e1-virtual-port-no-t1e1-memory  TRAP-TYPE
		ENTERPRISE   cdx6500
		VARIABLES    { cdx6500SNMPLastTrap }
		DESCRIPTION
		     "T1/E1-%d VIRTUAL PORT %d - No T1/E1 memory available"
		     --#TYPE
		     --#SUMMARY "Trap #$G, specific: $S, arg(1) : $1"
		     --#ARGUMENTS {}
		     --#SEVERITY  MAJOR
		     --#TIMEINDEX
		     --#HELP
		     --#HELPTAG
		     --#STATE
		::= 283032

        t1e1-pri-call-on-port-disconnect22  TRAP-TYPE
		ENTERPRISE   cdx6500
		VARIABLES    { cdx6500SNMPLastTrap }
		DESCRIPTION
		     "PRI-%d - %s CALL %s %s ON PORT %d DISCONNECTED BY NETWORK  CAUSE:%d"
		     --#TYPE
		     --#SUMMARY "Trap #$G, specific: $S, arg(1) : $1"
		     --#ARGUMENTS {}
		     --#SEVERITY  MAJOR
		     --#TIMEINDEX
		     --#HELP
		     --#HELPTAG
		     --#STATE
		::= 283033

        spfm-pvc-connection-failed-on  TRAP-TYPE
		ENTERPRISE   cdx6500
		VARIABLES    { cdx6500SNMPLastTrap }
		DESCRIPTION
		     "SPFM #%d - PVC CONNECTION FAILED ON %s"
		     --#TYPE
		     --#SUMMARY "Trap #$G, specific: $S, arg(1) : $1"
		     --#ARGUMENTS {}
		     --#SEVERITY  MINOR
		     --#TIMEINDEX
		     --#HELP
		     --#HELPTAG
		     --#STATE
		::= 285001

        spfm-pvc-connected  TRAP-TYPE
		ENTERPRISE   cdx6500
		VARIABLES    { cdx6500SNMPLastTrap }
		DESCRIPTION
		     "SPFM #%d - PVC CONNECTED %s -> %s"
		     --#TYPE
		     --#SUMMARY "Trap #$G, specific: $S, arg(1) : $1"
		     --#ARGUMENTS {}
		     --#SEVERITY  MINOR
		     --#TIMEINDEX
		     --#HELP
		     --#HELPTAG
		     --#STATE
		::= 285002

        spfm-disabled-duplicate-slot-on  TRAP-TYPE
		ENTERPRISE   cdx6500
		VARIABLES    { cdx6500SNMPLastTrap }
		DESCRIPTION
		     "SPFM #%d - DISABLED, DUPLICATE SLOT ON SPFM #%d"
		     --#TYPE
		     --#SUMMARY "Trap #$G, specific: $S, arg(1) : $1"
		     --#ARGUMENTS {}
		     --#SEVERITY  MINOR
		     --#TIMEINDEX
		     --#HELP
		     --#HELPTAG
		     --#STATE
		::= 285003

        spfm-disabled-misconfigured-opti  TRAP-TYPE
		ENTERPRISE   cdx6500
		VARIABLES    { cdx6500SNMPLastTrap }
		DESCRIPTION
		     "SPFM #%d - DISABLED, MISCONFIGURED OPTION"
		     --#TYPE
		     --#SUMMARY "Trap #$G, specific: $S, arg(1) : $1"
		     --#ARGUMENTS {}
		     --#SEVERITY  MINOR
		     --#TIMEINDEX
		     --#HELP
		     --#HELPTAG
		     --#STATE
		::= 285004

        spfm-connection-active  TRAP-TYPE
		ENTERPRISE   cdx6500
		VARIABLES    { cdx6500SNMPLastTrap }
		DESCRIPTION
		     "SPFM #%d - CONNECTION ACTIVE %s -> %s"
		     --#TYPE
		     --#SUMMARY "Trap #$G, specific: $S, arg(1) : $1"
		     --#ARGUMENTS {}
		     --#SEVERITY  MINOR
		     --#TIMEINDEX
		     --#HELP
		     --#HELPTAG
		     --#STATE
		::= 285005

        spfm-connection-inactive  TRAP-TYPE
		ENTERPRISE   cdx6500
		VARIABLES    { cdx6500SNMPLastTrap }
		DESCRIPTION
		     "SPFM #%d - CONNECTION INACTIVE %s -> %s"
		     --#TYPE
		     --#SUMMARY "Trap #$G, specific: $S, arg(1) : $1"
		     --#ARGUMENTS {}
		     --#SEVERITY  MINOR
		     --#TIMEINDEX
		     --#HELP
		     --#HELPTAG
		     --#STATE
		::= 285006

        spfm-rx-data-on-unknown-dlci-slo  TRAP-TYPE
		ENTERPRISE   cdx6500
		VARIABLES    { cdx6500SNMPLastTrap }
		DESCRIPTION
		     "SPFM - RX DATA ON UNKNOWN DLCI SLOT %s(%d)"
		     --#TYPE
		     --#SUMMARY "Trap #$G, specific: $S, arg(1) : $1"
		     --#ARGUMENTS {}
		     --#SEVERITY  MINOR
		     --#TIMEINDEX
		     --#HELP
		     --#HELPTAG
		     --#STATE
		::= 285007

        spfm-header-format-error  TRAP-TYPE
		ENTERPRISE   cdx6500
		VARIABLES    { cdx6500SNMPLastTrap }
		DESCRIPTION
		     "SPFM #%d - SPFM HEADER FORMAT ERROR"
		     --#TYPE
		     --#SUMMARY "Trap #$G, specific: $S, arg(1) : $1"
		     --#ARGUMENTS {}
		     --#SEVERITY  MINOR
		     --#TIMEINDEX
		     --#HELP
		     --#HELPTAG
		     --#STATE
		::= 285008

        spfm-configuration-mismatch-on-r  TRAP-TYPE
		ENTERPRISE   cdx6500
		VARIABLES    { cdx6500SNMPLastTrap }
		DESCRIPTION
		     "SPFM #%d - CONFIGURATION MISMATCH ON REMOTE SPFM"
		     --#TYPE
		     --#SUMMARY "Trap #$G, specific: $S, arg(1) : $1"
		     --#ARGUMENTS {}
		     --#SEVERITY  MINOR
		     --#TIMEINDEX
		     --#HELP
		     --#HELPTAG
		     --#STATE
		::= 285009

        spfm-entry-boot-complete  TRAP-TYPE
		ENTERPRISE   cdx6500
		VARIABLES    { cdx6500SNMPLastTrap }
		DESCRIPTION
		     "SPFM #%d ENTRY BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 286001

        spfm-entry-boot-failed  TRAP-TYPE
		ENTERPRISE   cdx6500
		VARIABLES    { cdx6500SNMPLastTrap }
		DESCRIPTION
		     "SPFM #%d ENTRY BOOT FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 286002

        smds-stn-data-loss  TRAP-TYPE
                ENTERPRISE   cdx6500
                VARIABLES    { cdx6500SNMPLastTrap }
                DESCRIPTION
                             "%s - DATA LOST FROM DATA QUEUE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 289000

        smds-stn-invalid-encap  TRAP-TYPE
                ENTERPRISE   cdx6500
                VARIABLES    { cdx6500SNMPLastTrap }
                DESCRIPTION
                             "%s - INVALID ENCAPSULATION"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 289001

        smds-stn-masked  TRAP-TYPE
                ENTERPRISE   cdx6500
                VARIABLES    { cdx6500SNMPLastTrap }
                DESCRIPTION
                             "%s - CANNOT BE ACTIVATED. <SRC, DST, ENCAPSULATION> CONFLICTS WITH STN %d"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 289002

        smds-sni-data-loss  TRAP-TYPE
                ENTERPRISE   cdx6500
                VARIABLES    { cdx6500SNMPLastTrap }
                DESCRIPTION
                             "%s - DATA LOST FROM DATA QUEUE"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 290000

        smds-sni-invalid-encap  TRAP-TYPE
                ENTERPRISE   cdx6500
                VARIABLES    { cdx6500SNMPLastTrap }
                DESCRIPTION
                             "%s - INVALID ENCAPSULATION"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 290001

        smds-sni-no-station  TRAP-TYPE
                ENTERPRISE   cdx6500
                VARIABLES    { cdx6500SNMPLastTrap }
                DESCRIPTION
                             "%s - NO STATION FOR SMDS DESTINATION - %08X%08X"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 290002

        dxi-port-boot-complete  TRAP-TYPE
		ENTERPRISE   cdx6500
		VARIABLES    { cdx6500SNMPLastTrap }
		DESCRIPTION
		     "%s - PORT BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 291000

        dxi-port-boot-failure  TRAP-TYPE
		ENTERPRISE   cdx6500
		VARIABLES    { cdx6500SNMPLastTrap }
		DESCRIPTION
		     "%s - PORT BOOT FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 291001

        dxi-port-disabled  TRAP-TYPE
		ENTERPRISE   cdx6500
		VARIABLES    { cdx6500SNMPLastTrap }
		DESCRIPTION
		     "%s - PORT DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 291002

        dxi-port-enabled  TRAP-TYPE
		ENTERPRISE   cdx6500
		VARIABLES    { cdx6500SNMPLastTrap }
		DESCRIPTION
		     "%s - PORT ENABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 291003

        dxi-port-utilization-threshold  TRAP-TYPE
		ENTERPRISE   cdx6500
		VARIABLES    { cdx6500SNMPLastTrap }
		DESCRIPTION
		     "%s - PORT UTILIZATION > THRESHOLD"
		     --#TYPE
		     --#SUMMARY "Trap #$G, specific: $S, arg(1) : $1"
		     --#ARGUMENTS {}
		     --#SEVERITY  MAJOR
		     --#TIMEINDEX
		     --#HELP
		     --#HELPTAG
		     --#STATE
		::= 291004

        dxi-port-status-warning  TRAP-TYPE
		ENTERPRISE   cdx6500
		VARIABLES    { cdx6500SNMPLastTrap }
		DESCRIPTION
		     "%s - PORT STATUS WARNING - %s"
		     --#TYPE
		     --#SUMMARY "Trap #$G, specific: $S, arg(1) : $1"
		     --#ARGUMENTS {}
		     --#SEVERITY  MINOR
		     --#TIMEINDEX
		     --#HELP
		     --#HELPTAG
		     --#STATE
		::= 291005

        dxi-data-lost-from-rx-data-queue  TRAP-TYPE
		ENTERPRISE   cdx6500
		VARIABLES    { cdx6500SNMPLastTrap }
		DESCRIPTION
		     "%s - DATA LOST FROM Rx DATA QUEUE"
		     --#TYPE
		     --#SUMMARY "Trap #$G, specific: $S, arg(1) : $1"
		     --#ARGUMENTS {}
		     --#SEVERITY  CRITICAL
		     --#TIMEINDEX
		     --#HELP
		     --#HELPTAG
		     --#STATE
		::= 292000

        dxi-data-lost-from-tx-data-queue  TRAP-TYPE
		ENTERPRISE   cdx6500
		VARIABLES    { cdx6500SNMPLastTrap }
		DESCRIPTION
		     "%s - DATA LOST FROM Tx DATA QUEUE"
		     --#TYPE
		     --#SUMMARY "Trap #$G, specific: $S, arg(1) : $1"
		     --#ARGUMENTS {}
		     --#SEVERITY  CRITICAL
		     --#TIMEINDEX
		     --#HELP
		     --#HELPTAG
		     --#STATE
		::= 292001

        dxi-no-heartbeat  TRAP-TYPE
		ENTERPRISE   cdx6500
		VARIABLES    { cdx6500SNMPLastTrap }
		DESCRIPTION
		     "%s - NO HEARTBEAT"
		     --#TYPE
		     --#SUMMARY "Trap #$G, specific: $S, arg(1) : $1"
		     --#ARGUMENTS {}
		     --#SEVERITY  CRITICAL
		     --#TIMEINDEX
		     --#HELP
		     --#HELPTAG
		     --#STATE
		::= 292002

        ipxwan-null-rfcm-cb  TRAP-TYPE
                ENTERPRISE   cdx6500
                VARIABLES    { cdx6500SNMPLastTrap }
                DESCRIPTION
                             "IPXWAN.1  ipxwan-init called with NULL rfcm Context Block\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293000

        ipxwan-not-enough-ram  TRAP-TYPE
                ENTERPRISE   cdx6500
                VARIABLES    { cdx6500SNMPLastTrap }
                DESCRIPTION
                             "IPXWAN.2  IPXWAN Module Aborted; not enough RAM\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293001

        ipxwan-alloc-failed  TRAP-TYPE
                ENTERPRISE   cdx6500
                VARIABLES    { cdx6500SNMPLastTrap }
                DESCRIPTION
                             "IPXWAN.3  Memory allocation for %s failed\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293002

        ipxwan-module-not-active  TRAP-TYPE
                ENTERPRISE   cdx6500
                VARIABLES    { cdx6500SNMPLastTrap }
                DESCRIPTION
                             "IPXWAN.4  IPXWAN is not active in %s\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293003

        ipxwan-ipx-not-active  TRAP-TYPE
                ENTERPRISE   cdx6500
                VARIABLES    { cdx6500SNMPLastTrap }
                DESCRIPTION
                             "IPXWAN.5  IPX not active in %s\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293004

        ipxwan-called-for-lan  TRAP-TYPE
                ENTERPRISE   cdx6500
                VARIABLES    { cdx6500SNMPLastTrap }
                DESCRIPTION
                             "IPXWAN.6  %s called for a LAN interface\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293005

        ipxwan-nul-ipxwancb  TRAP-TYPE
                ENTERPRISE   cdx6500
                VARIABLES    { cdx6500SNMPLastTrap }
                DESCRIPTION
                             "IPXWAN.7  %s called with a NULL IPXWANCB\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293006

        ipxwan-dropping-packet  TRAP-TYPE
                ENTERPRISE   cdx6500
                VARIABLES    { cdx6500SNMPLastTrap }
                DESCRIPTION
                             "IPXWAN.8  IPX not up in lcon %d - dropping the packet\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293007

        ipxwan-bad-format  TRAP-TYPE
                ENTERPRISE   cdx6500
                VARIABLES    { cdx6500SNMPLastTrap }
                DESCRIPTION
                             "IPXWAN.9  Bad format packet received, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293008

        ipxwan-rcvd-tmr-req-opt-len  TRAP-TYPE
                ENTERPRISE   cdx6500
                VARIABLES    { cdx6500SNMPLastTrap }
                DESCRIPTION
                             "IPXWAN.10  Rcvd Tmr Req - option len not 1 for routing type option, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293009

        ipxwan-rcvd-tmr-req-wnode-id  TRAP-TYPE
                ENTERPRISE   cdx6500
                VARIABLES    { cdx6500SNMPLastTrap }
                DESCRIPTION
                             "IPXWAN.11  Rcvd Tmr Req - wnode id non-zero with extended node id option set, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293010

        ipxwan-rcvd-tmr-req-ext-node  TRAP-TYPE
                ENTERPRISE   cdx6500
                VARIABLES    { cdx6500SNMPLastTrap }
                DESCRIPTION
                             "IPXWAN.12  Rcvd Tmr Req - option len not 4 for extended node id, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293011

        ipxwan-tmr-req-cfg-error  TRAP-TYPE
                ENTERPRISE   cdx6500
                VARIABLES    { cdx6500SNMPLastTrap }
                DESCRIPTION
                             "IPXWAN.13  Rcvd Tmr Req - configuration error, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293012

        ipxwan-rcvd-tmr-req-no-common-routing  TRAP-TYPE
                ENTERPRISE   cdx6500
                VARIABLES    { cdx6500SNMPLastTrap }
                DESCRIPTION
                             "IPXWAN.14  Rcvd Tmr Req - no common routing type, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293013

        ipxwan-rcvd-tmr-resp-wnode-id  TRAP-TYPE
                ENTERPRISE   cdx6500
                VARIABLES    { cdx6500SNMPLastTrap }
                DESCRIPTION
                             "IPXWAN.15  Rcvd Tmr Resp - wnode id zero, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293014

        ipxwan-rcvd-tmr-resp-multiple-routing  TRAP-TYPE
                ENTERPRISE   cdx6500
                VARIABLES    { cdx6500SNMPLastTrap }
                DESCRIPTION
                             "IPXWAN.16  Rcvd Tmr Resp - multiple routing types marked yes, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293015

        ipxwan-rcvd-tmr-resp-routing-type  TRAP-TYPE
                ENTERPRISE   cdx6500
                VARIABLES    { cdx6500SNMPLastTrap }
                DESCRIPTION
                             "IPXWAN.17  Rcvd Tmr Resp - could not set the routing type, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293016

        ipxwan-rcvd-tmr-resp-not-supported  TRAP-TYPE
                ENTERPRISE   cdx6500
                VARIABLES    { cdx6500SNMPLastTrap }
                DESCRIPTION
                             "IPXWAN.18  Rcvd Tmr Resp - routing type not supported, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293017

        ipxwan-rcvd-tmr-resp-opt-len  TRAP-TYPE
                ENTERPRISE   cdx6500
                VARIABLES    { cdx6500SNMPLastTrap }
                DESCRIPTION
                             "IPXWAN.19  Rcvd Tmr Resp - option len not 1 for routing type option, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293018

        ipxwan-rcvd-tmr-resp-header-comp  TRAP-TYPE
                ENTERPRISE   cdx6500
                VARIABLES    { cdx6500SNMPLastTrap }
                DESCRIPTION
                             "IPXWAN.20  Rcvd Tmr Resp - header compression not supported, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293019

        ipxwan-rcvd-tmr-resp-no-routing  TRAP-TYPE
                ENTERPRISE   cdx6500
                VARIABLES    { cdx6500SNMPLastTrap }
                DESCRIPTION
                             "IPXWAN.21  Rcvd Tmr Resp - no routing type option with yes, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293020

        ipxwan-rcvd-info-req-wnode-id  TRAP-TYPE
                ENTERPRISE   cdx6500
                VARIABLES    { cdx6500SNMPLastTrap }
                DESCRIPTION
                             "IPXWAN.22  Rcvd Info Req - rcvd wnode id zero, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293021

        ipxwan-rcvd-info-info-exchg  TRAP-TYPE
                ENTERPRISE   cdx6500
                VARIABLES    { cdx6500SNMPLastTrap }
                DESCRIPTION
                             "IPXWAN.23  %s - bad info exchange option, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293022

        ipxwan-rcvd-info-no-info-exchg  TRAP-TYPE
                ENTERPRISE   cdx6500
                VARIABLES    { cdx6500SNMPLastTrap }
                DESCRIPTION
                             "IPXWAN.24  %s - no info exchange option, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293023

        ipxwan-rcvd-info-netno-zero  TRAP-TYPE
                ENTERPRISE   cdx6500
                VARIABLES    { cdx6500SNMPLastTrap }
                DESCRIPTION
                             "IPXWAN.25  %s - zero netno proposed for numbered RIP/SAP, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293024

        ipxwan-rcvd-info-netno-nonzero  TRAP-TYPE
                ENTERPRISE   cdx6500
                VARIABLES    { cdx6500SNMPLastTrap }
                DESCRIPTION
                             "IPXWAN.26  %s - non-zero netno proposed for an unnumbered protocol, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293025

        ipxwan-rcvd-info-conflict  TRAP-TYPE
                ENTERPRISE   cdx6500
                VARIABLES    { cdx6500SNMPLastTrap }
                DESCRIPTION
                             "IPXWAN.27  %s - the proposed netno is not equal to active netno, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293026

        ipxwan-rcvd-info-resp-wnode-id  TRAP-TYPE
                ENTERPRISE   cdx6500
                VARIABLES    { cdx6500SNMPLastTrap }
                DESCRIPTION
                             "IPXWAN.28  Rcvd Info Resp - rcvd wnode id is incorrect, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293027

        ipxwan-rcvd-info-resp-active  TRAP-TYPE
                ENTERPRISE   cdx6500
                VARIABLES    { cdx6500SNMPLastTrap }
                DESCRIPTION
                             "IPXWAN.29  Rcvd Info Resp - the proposed netno is already active, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293028

        ipxwan-rcvd-info-resp-setting  TRAP-TYPE
                ENTERPRISE   cdx6500
                VARIABLES    { cdx6500SNMPLastTrap }
                DESCRIPTION
                             "IPXWAN.30  Rcvd Info Resp - could not set the active netno, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293029

        ipxwan-getbuf-failed  TRAP-TYPE
                ENTERPRISE   cdx6500
                VARIABLES    { cdx6500SNMPLastTrap }
                DESCRIPTION
                             "IPXWAN.31  getbuf failed in %s\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293030

        ipxwan-unsupported-event  TRAP-TYPE
                ENTERPRISE   cdx6500
                VARIABLES    { cdx6500SNMPLastTrap }
                DESCRIPTION
                             "IPXWAN.32  Event %d ignored in state %d, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293031

        ipxwan-state-machine  TRAP-TYPE
                ENTERPRISE   cdx6500
                VARIABLES    { cdx6500SNMPLastTrap }
                DESCRIPTION
                             "IPXWAN.33  Old State:%d, Event:%d,
New State:%d, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293032

        ipxwan-internal-buffer-overflow  TRAP-TYPE
                ENTERPRISE   cdx6500
                VARIABLES    { cdx6500SNMPLastTrap }
                DESCRIPTION
                             "IPXWAN.34  Too many routing types from
remote end, lcon %d\r\n"
                     --#TYPE
	             --#SUMMARY "Trap #$G, specific: $S, arg(1): $1"
	             --#ARGUMENTS {}
	             --#SEVERITY  INFORMATIONAL
	             --#TIMEINDEX
	             --#HELP
	             --#HELPTAG
	             --#STATE
                ::= 293033

        tow-report-no-memory  TRAP-TYPE
                ENTERPRISE   cdx6500
                VARIABLES    { cdx6500SNMPLastTrap }
                DESCRIPTION
                             "ToW:%s:NOT ENOUGH MEMORY"
                     --#TYPE
                 --#SUMMARY "Trap #$G, specific: $S, arg(1): $1"
                 --#ARGUMENTS {}
                 --#SEVERITY  INFORMATIONAL
                 --#TIMEINDEX
                 --#HELP
                 --#HELPTAG
                 --#STATE
                ::= 294000

        tow-report-not-active  TRAP-TYPE
                ENTERPRISE   cdx6500
                VARIABLES    { cdx6500SNMPLastTrap }
                DESCRIPTION
                             "ToW:%s:NOT ACTIVE, ENTRY NOT FOUND IN CMEM"
                     --#TYPE
                 --#SUMMARY "Trap #$G, specific: $S, arg(1): $1"
                 --#ARGUMENTS {}
                 --#SEVERITY  INFORMATIONAL
                 --#TIMEINDEX
                 --#HELP
                 --#HELPTAG
                 --#STATE
                ::= 294001

        tow-report-default-entry  TRAP-TYPE
                ENTERPRISE   cdx6500
                VARIABLES    { cdx6500SNMPLastTrap }
                DESCRIPTION
                             "ToW:%s:NOT ACTIVE, INITIALIZED TO DEFAULT"
                     --#TYPE
                 --#SUMMARY "Trap #$G, specific: $S, arg(1): $1"
                 --#ARGUMENTS {}
                 --#SEVERITY  INFORMATIONAL
                 --#TIMEINDEX
                 --#HELP
                 --#HELPTAG
                 --#STATE
                ::= 294002

        tow-report-active  TRAP-TYPE
                ENTERPRISE   cdx6500
                VARIABLES    { cdx6500SNMPLastTrap }
                DESCRIPTION
                             "ToW:%s:ACTIVE"
                     --#TYPE
                 --#SUMMARY "Trap #$G, specific: $S, arg(1): $1"
                 --#ARGUMENTS {}
                 --#SEVERITY  INFORMATIONAL
                 --#TIMEINDEX
                 --#HELP
                 --#HELPTAG
                 --#STATE
                ::= 294003

        vx-stn-boot-complete  TRAP-TYPE
		ENTERPRISE   cdx6500
		VARIABLES    { cdx6500SNMPLastTrap }
		DESCRIPTION
		     "%s - STN BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 295000

        vx-stn-boot-failure  TRAP-TYPE
		ENTERPRISE   cdx6500
		VARIABLES    { cdx6500SNMPLastTrap }
		DESCRIPTION
		     "%s - STN BOOT FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 295001

        vx-stn-disabled  TRAP-TYPE
		ENTERPRISE   cdx6500
		VARIABLES    { cdx6500SNMPLastTrap }
		DESCRIPTION
		     "%s - STN DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 295002

        vx-stn-enabled  TRAP-TYPE
		ENTERPRISE   cdx6500
		VARIABLES    { cdx6500SNMPLastTrap }
		DESCRIPTION
		     "%s - STN ENABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 295003

        vx-no-config-for-stn  TRAP-TYPE
		ENTERPRISE   cdx6500
		VARIABLES    { cdx6500SNMPLastTrap }
		DESCRIPTION
		     "NO CONFIG FOR STN"
		     --#TYPE
		     --#SUMMARY "Trap #$G, specific: $S, arg(1) : $1"
		     --#ARGUMENTS {}
		     --#SEVERITY  CRITICAL
		     --#TIMEINDEX
		     --#HELP
		     --#HELPTAG
		     --#STATE
		::= 295004

        pnef-tfr-insufficient-memory  TRAP-TYPE
		ENTERPRISE   cdx6500
		VARIABLES    { cdx6500SNMPLastTrap }
		DESCRIPTION
		     "TFR - INSUFFICIENT MEMORY - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 298000

        pnef-tfr-boot-failure  TRAP-TYPE
		ENTERPRISE   cdx6500
		VARIABLES    { cdx6500SNMPLastTrap }
		DESCRIPTION
		     "TFR BOOT FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 298001

        pnef-tfr-connection-established  TRAP-TYPE
		ENTERPRISE   cdx6500
		VARIABLES    { cdx6500SNMPLastTrap }
		DESCRIPTION
		     "TFR - CONNECTION ESTABLISHED WITH OTHER TFR"
		     --#TYPE
		     --#SUMMARY "Trap #$G, specific: $S, arg(1) : $1"
		     --#ARGUMENTS {}
		     --#SEVERITY  MINOR
		     --#TIMEINDEX
		     --#HELP
		     --#HELPTAG
		     --#STATE
		::= 298002

        pnef-tfr-connection-failure-with  TRAP-TYPE
		ENTERPRISE   cdx6500
		VARIABLES    { cdx6500SNMPLastTrap }
		DESCRIPTION
		     "TFR - CONNECTION FAILURE WITH OTHER TFR - %s"
		     --#TYPE
		     --#SUMMARY "Trap #$G, specific: $S, arg(1) : $1"
		     --#ARGUMENTS {}
		     --#SEVERITY  MAJOR
		     --#TIMEINDEX
		     --#HELP
		     --#HELPTAG
		     --#STATE
		::= 298003

        pnef-tfr-unknown-caller  TRAP-TYPE
		ENTERPRISE   cdx6500
		VARIABLES    { cdx6500SNMPLastTrap }
		DESCRIPTION
		     "TFR - UNKNOWN CALLER %s"
		     --#TYPE
		     --#SUMMARY "Trap #$G, specific: $S, arg(1) : $1"
		     --#ARGUMENTS {}
		     --#SEVERITY  MAJOR
		     --#TIMEINDEX
		     --#HELP
		     --#HELPTAG
		     --#STATE
		::= 298004

        pnef-tfr-frame-discarded  TRAP-TYPE
		ENTERPRISE   cdx6500
		VARIABLES    { cdx6500SNMPLastTrap }
		DESCRIPTION
		     "TFR - FRAME DISCARDED %s - %s"
		     --#TYPE
		     --#SUMMARY "Trap #$G, specific: $S, arg(1) : $1"
		     --#ARGUMENTS {}
		     --#SEVERITY  MINOR
		     --#TIMEINDEX
		     --#HELP
		     --#HELPTAG
		     --#STATE
		::= 298005

        pnef-tfr-queue-overflow  TRAP-TYPE
		ENTERPRISE   cdx6500
		VARIABLES    { cdx6500SNMPLastTrap }
		DESCRIPTION
		     "TFR - QUEUE OVERFLOW"
		     --#TYPE
		     --#SUMMARY "Trap #$G, specific: $S, arg(1) : $1"
		     --#ARGUMENTS {}
		     --#SEVERITY  MINOR
		     --#TIMEINDEX
		     --#HELP
		     --#HELPTAG
		     --#STATE
		::= 298006

        pnef-tfr-received-incomplete-fra  TRAP-TYPE
		ENTERPRISE   cdx6500
		VARIABLES    { cdx6500SNMPLastTrap }
		DESCRIPTION
		     "TFR - RECEIVED INCOMPLETE FRAME"
		     --#TYPE
		     --#SUMMARY "Trap #$G, specific: $S, arg(1) : $1"
		     --#ARGUMENTS {}
		     --#SEVERITY  MINOR
		     --#TIMEINDEX
		     --#HELP
		     --#HELPTAG
		     --#STATE
		::= 298007

        pnef-tfri-insufficient-memory-in  TRAP-TYPE
		ENTERPRISE   cdx6500
		VARIABLES    { cdx6500SNMPLastTrap }
		DESCRIPTION
		     "TFRI - INSUFFICIENT MEMORY - INITIALIZATION FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 299000

        pnef-tfri-insufficient-memory-in2  TRAP-TYPE
		ENTERPRISE   cdx6500
		VARIABLES    { cdx6500SNMPLastTrap }
		DESCRIPTION
		     "TFRI - INSUFFICIENT MEMORY - INITIALIZED WITHOUT DCP"
		     --#TYPE
		     --#SUMMARY "Trap #$G, specific: $S, arg(1) : $1"
		     --#ARGUMENTS {}
		     --#SEVERITY  CRITICAL
		     --#TIMEINDEX
		     --#HELP
		     --#HELPTAG
		     --#STATE
		::= 299001

        pnef-tfri-boot-failure  TRAP-TYPE
		ENTERPRISE   cdx6500
		VARIABLES    { cdx6500SNMPLastTrap }
		DESCRIPTION
		     "TFRI BOOT FAILURE -  %s"
		     --#TYPE
		     --#SUMMARY "Trap #$G, specific: $S, arg(1) : $1"
		     --#ARGUMENTS {}
		     --#SEVERITY  CRITICAL
		     --#TIMEINDEX
		     --#HELP
		     --#HELPTAG
		     --#STATE
		::= 299002

        pnef-tfri-connection-established  TRAP-TYPE
		ENTERPRISE   cdx6500
		VARIABLES    { cdx6500SNMPLastTrap }
		DESCRIPTION
		     "TFRI - CONNECTION ESTABLISHED WITH TFR FOR THE PT %d"
		     --#TYPE
		     --#SUMMARY "Trap #$G, specific: $S, arg(1) : $1"
		     --#ARGUMENTS {}
		     --#SEVERITY  MINOR
		     --#TIMEINDEX
		     --#HELP
		     --#HELPTAG
		     --#STATE
		::= 299003

        pnef-tfri-connection-failure-wit  TRAP-TYPE
		ENTERPRISE   cdx6500
		VARIABLES    { cdx6500SNMPLastTrap }
		DESCRIPTION
		     "TFRI - CONNECTION FAILURE WITH TFR FOR PT %d - %s"
		     --#TYPE
		     --#SUMMARY "Trap #$G, specific: $S, arg(1) : $1"
		     --#ARGUMENTS {}
		     --#SEVERITY  MAJOR
		     --#TIMEINDEX
		     --#HELP
		     --#HELPTAG
		     --#STATE
		::= 299004

        pnef-tfri-frame-discarded  TRAP-TYPE
		ENTERPRISE   cdx6500
		VARIABLES    { cdx6500SNMPLastTrap }
		DESCRIPTION
		     "TFRI - FRAME DISCARDED %s - %s"
		     --#TYPE
		     --#SUMMARY "Trap #$G, specific: $S, arg(1) : $1"
		     --#ARGUMENTS {}
		     --#SEVERITY  MINOR
		     --#TIMEINDEX
		     --#HELP
		     --#HELPTAG
		     --#STATE
		::= 299005

        pnef-tfri-socket-registration-fa  TRAP-TYPE
		ENTERPRISE   cdx6500
		VARIABLES    { cdx6500SNMPLastTrap }
		DESCRIPTION
		     "TFRI - SOCKET REGISTRATION FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 299006

        tdlcPort-boot  TRAP-TYPE
                ENTERPRISE   cdx6500
                VARIABLES    { cdx6500SNMPLastTrap }
                DESCRIPTION
                          "%s - PORT BOOT COMPLETE"
                    --#TYPE
                    --#SUMMARY "Trap #$G, specific: $S, arg(1): $1"
                    --#ARGUMENTS {}
                    --#SEVERITY  INFORMATIONAL
                    --#TIMEINDEX
                    --#HELP
                    --#HELPTAG
                    --#STATE
              ::=  300000

        tdlcPort-disable  TRAP-TYPE
                ENTERPRISE   cdx6500
                VARIABLES    { cdx6500SNMPLastTrap }
                DESCRIPTION
                           "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  300001

        tdlcPort-enable  TRAP-TYPE
                ENTERPRISE   cdx6500
                VARIABLES    { cdx6500SNMPLastTrap }
                DESCRIPTION
                          "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  300002           

        tdlcPort-util-exceeded  TRAP-TYPE
                ENTERPRISE   cdx6500
                VARIABLES    { cdx6500SNMPLastTrap }
                DESCRIPTION
                          "%s - %s PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  300003                                                            

        tdlcPort-statuswarn-disabled  TRAP-TYPE
                ENTERPRISE   cdx6500
                VARIABLES    { cdx6500SNMPLastTrap }
                DESCRIPTION
                          "%s - PORT STATUS WARNING, PORT DISABLED "
                     --#TYPE
                     --#SUMMARY "Trap #$G, specific: $S, arg(1): $1"
                     --#ARGUMENTS {}
                     --#SEVERITY  INFORMATIONAL
                     --#TIMEINDEX
                     --#HELP
                     --#HELPTAG
                     --#STATE
                ::=  300004          

        tdlcPort-utilexceed-pagingTerm  TRAP-TYPE
                ENTERPRISE   cdx6500
                VARIABLES    { cdx6500SNMPLastTrap }
                DESCRIPTION
                     "%s - PORT STATUS WARNING, LIMIT EXCEEDED PAGING TERMINAL IS IDENTFIED AS %d"
                     --#TYPE
                     --#SUMMARY "Trap #$G, specific: $S, arg(1): $1"
                     --#ARGUMENTS {}
                     --#SEVERITY  INFORMATIONAL
                     --#TIMEINDEX
                     --#HELP
                     --#HELPTAG
                     --#STATE
                ::=  300005    

        vport-voice-switching-record-fai  TRAP-TYPE
		ENTERPRISE   cdx6500
		VARIABLES    { cdx6500SNMPLastTrap }
		DESCRIPTION
		     "VOICE SWITCHING RECORD FAILED CONVERSION - %s, %d, %s, %d, %d, %s, %s, %d"
		     --#TYPE
		     --#SUMMARY "Trap #$G, specific: $S, arg(1) : $1"
		     --#ARGUMENTS {}
		     --#SEVERITY  CRITICAL
		     --#TIMEINDEX
		     --#HELP
		     --#HELPTAG
		     --#STATE
		::= 304000

        vport-voice-switching-record-con  TRAP-TYPE
		ENTERPRISE   cdx6500
		VARIABLES    { cdx6500SNMPLastTrap }
		DESCRIPTION
		     "VOICE SWITCHING RECORD CONVERSION COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 304001

        iso3201-Port-boot  TRAP-TYPE
                 ENTERPRISE   cdx6500
                 VARIABLES    { cdx6500SNMPLastTrap }
                 DESCRIPTION
                              "%s - PORT BOOT COMPLETE"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306000

        iso3201-Port-boot-fail  TRAP-TYPE
                 ENTERPRISE   cdx6500
                 VARIABLES    { cdx6500SNMPLastTrap }
                 DESCRIPTION
                              "%s - PORT BOOT FAILURE - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306001

        iso3201-Port-disable  TRAP-TYPE
                 ENTERPRISE   cdx6500
                 VARIABLES    { cdx6500SNMPLastTrap }
                 DESCRIPTION
                              "%s - PORT DISABLED"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306002

        iso3201-Port-disable-fail  TRAP-TYPE
                 ENTERPRISE   cdx6500
                 VARIABLES    { cdx6500SNMPLastTrap }
                 DESCRIPTION
                              "%s - PORT DISABLE FAILURE - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306003

        iso3201-Port-enable  TRAP-TYPE
                 ENTERPRISE   cdx6500
                 VARIABLES    { cdx6500SNMPLastTrap }
                 DESCRIPTION
                              "%s - PORT ENABLED"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306004

        iso3201-Port-enable-fail  TRAP-TYPE
                 ENTERPRISE   cdx6500
                 VARIABLES    { cdx6500SNMPLastTrap }
                 DESCRIPTION
                              "%s - PORT ENABLE FAILURE - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306005

        iso3201-Port-warn-status  TRAP-TYPE
                 ENTERPRISE   cdx6500
                 VARIABLES    { cdx6500SNMPLastTrap }
                 DESCRIPTION
                              "%s - PORT STATUS WARNING - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306006

        iso3201-Stn-boot  TRAP-TYPE
                 ENTERPRISE   cdx6500
                 VARIABLES    { cdx6500SNMPLastTrap }
                 DESCRIPTION
                              "%s - STATION BOOT COMPLETE"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306007

        iso3201-Stn-boot-fail  TRAP-TYPE
                 ENTERPRISE   cdx6500
                 VARIABLES    { cdx6500SNMPLastTrap }
                 DESCRIPTION
                              "%s - STATION BOOT FAILURE - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306008

        iso3201-Stn-disable  TRAP-TYPE
                 ENTERPRISE   cdx6500
                 VARIABLES    { cdx6500SNMPLastTrap }
                 DESCRIPTION
                              "%s - STATION DISABLED"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306009

        iso3201-Stn-disable-fail  TRAP-TYPE
                 ENTERPRISE   cdx6500
                 VARIABLES    { cdx6500SNMPLastTrap }
                 DESCRIPTION
                              "%s - STATION DISABLE FAILURE - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306010

        iso3201-Stn-enable  TRAP-TYPE
                 ENTERPRISE   cdx6500
                 VARIABLES    { cdx6500SNMPLastTrap }
                 DESCRIPTION
                              "%s - STATION ENABLED"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306011

        iso3201-Stn-enable-fail  TRAP-TYPE
                 ENTERPRISE   cdx6500
                 VARIABLES    { cdx6500SNMPLastTrap }
                 DESCRIPTION
                              "%s - STATION ENABLE FAILURE - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306012

        iso3201-Stn-warn-status  TRAP-TYPE
                 ENTERPRISE   cdx6500
                 VARIABLES    { cdx6500SNMPLastTrap }
                 DESCRIPTION
                              "%s - STATION STATUS WARNING - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306013

        iso3201-Stn-inhibited  TRAP-TYPE
                 ENTERPRISE   cdx6500
                 VARIABLES    { cdx6500SNMPLastTrap }
                 DESCRIPTION
                              "%s - STATION INHIBITED - ADDR CONFLICT"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306014

        iso3201-Stn-poll-suspended  TRAP-TYPE
                 ENTERPRISE   cdx6500
                 VARIABLES    { cdx6500SNMPLastTrap }
                 DESCRIPTION
                              "%s - STATION POLL SUSPENDED - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306015

        iso3201-Stn-poll-resumed  TRAP-TYPE
                 ENTERPRISE   cdx6500
                 VARIABLES    { cdx6500SNMPLastTrap }
                 DESCRIPTION
                              "%s - STATION POLL RESUMED"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306016

        iso3201-Stn-mnem-error  TRAP-TYPE
                 ENTERPRISE   cdx6500
                 VARIABLES    { cdx6500SNMPLastTrap }
                 DESCRIPTION
                              "%s - STATION MNEMONIC ERROR"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306017

        iso3201-Stn-acall-exceed  TRAP-TYPE
                 ENTERPRISE   cdx6500
                 VARIABLES    { cdx6500SNMPLastTrap }
                 DESCRIPTION
                              "%s - AUTOCALL ATTEMPTS EXHAUSTED"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306018

        iso3201-local-commn-error  TRAP-TYPE
                 ENTERPRISE   cdx6500
                 VARIABLES    { cdx6500SNMPLastTrap }
                 DESCRIPTION
                              "%s - LOCAL ERROR - 0x%x  - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306019

        iso3201-line-status  TRAP-TYPE
                 ENTERPRISE   cdx6500
                 VARIABLES    { cdx6500SNMPLastTrap }
                 DESCRIPTION
                              "%s - LINE %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306020

        iso3201-dq-error  TRAP-TYPE
                 ENTERPRISE   cdx6500
                 VARIABLES    { cdx6500SNMPLastTrap }
                 DESCRIPTION
                              "%s - DQ ERROR - 0x%x - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306021

        iso3201-data-mesg-error  TRAP-TYPE
                 ENTERPRISE   cdx6500
                 VARIABLES    { cdx6500SNMPLastTrap }
                 DESCRIPTION
                              "%s - DATA ERROR 0x%x - %s"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306022

        iso3201-poll-error-clear  TRAP-TYPE
                 ENTERPRISE   cdx6500
                 VARIABLES    { cdx6500SNMPLastTrap }
                 DESCRIPTION
                              "%s - POLL ERROR CLEARED - 0x%x"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306023

        iso3201-recd-error-mesg  TRAP-TYPE
                 ENTERPRISE   cdx6500
                 VARIABLES    { cdx6500SNMPLastTrap }
                 DESCRIPTION
                              "%s - RECEIVED ERROR MSG - 0x%x"
                      --#TYPE
                      --#SUMMARY "Trap #$G, specific: $S, arg(1): $1"
                      --#ARGUMENTS {}
                      --#SEVERITY  INFORMATIONAL
                      --#TIMEINDEX
                      --#HELP
                      --#HELPTAG
                      --#STATE
                 ::= 306024

        iso3201-station-down  TRAP-TYPE
		ENTERPRISE   cdx6500
		VARIABLES    { cdx6500SNMPLastTrap }
		DESCRIPTION
		     "%s - STATION DOWN"
		     --#TYPE
		     --#SUMMARY "Trap #$G, specific: $S, arg(1) : $1"
		     --#ARGUMENTS {}
		     --#SEVERITY  CRITICAL
		     --#TIMEINDEX
		     --#HELP
		     --#HELPTAG
		     --#STATE
		::= 306025

        gscPort-boot  TRAP-TYPE
		ENTERPRISE   cdx6500
		VARIABLES    { cdx6500SNMPLastTrap }
		DESCRIPTION
		             " %s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308000

        gscPort-boot-fail  TRAP-TYPE
		ENTERPRISE   cdx6500
		VARIABLES    { cdx6500SNMPLastTrap }
		DESCRIPTION
		             "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308001

        gscPort-disable  TRAP-TYPE
		ENTERPRISE   cdx6500
		VARIABLES    { cdx6500SNMPLastTrap }
		DESCRIPTION
		             "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308002

        gscPort-disable-fail  TRAP-TYPE
		ENTERPRISE   cdx6500
		VARIABLES    { cdx6500SNMPLastTrap }
		DESCRIPTION
		             "%s - PORT DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308003

        gscPort-enable  TRAP-TYPE
		ENTERPRISE   cdx6500
		VARIABLES    { cdx6500SNMPLastTrap }
		DESCRIPTION
		             "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308004

        gscPort-enable-fail  TRAP-TYPE
		ENTERPRISE   cdx6500
		VARIABLES    { cdx6500SNMPLastTrap }
		DESCRIPTION
		             "%s - PORT ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308005

        gscStn-boot  TRAP-TYPE
		ENTERPRISE   cdx6500
		VARIABLES    { cdx6500SNMPLastTrap }
		DESCRIPTION
		             "%s - STATION BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308006

        gscStn-boot-fail  TRAP-TYPE
		ENTERPRISE   cdx6500
		VARIABLES    { cdx6500SNMPLastTrap }
		DESCRIPTION
		             "%s - STATION BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308007

        gscStn-disable  TRAP-TYPE
		ENTERPRISE   cdx6500
		VARIABLES    { cdx6500SNMPLastTrap }
		DESCRIPTION
		             "%s - STATION DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308008

        gscStn-disable-fail  TRAP-TYPE
		ENTERPRISE   cdx6500
		VARIABLES    { cdx6500SNMPLastTrap }
		DESCRIPTION
		             "%s - STATION DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308009

        gscStn-enable  TRAP-TYPE
		ENTERPRISE   cdx6500
		VARIABLES    { cdx6500SNMPLastTrap }
		DESCRIPTION
		             "%s - STATION ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308010

        gscStn-enable-fail  TRAP-TYPE
		ENTERPRISE   cdx6500
		VARIABLES    { cdx6500SNMPLastTrap }
		DESCRIPTION
		             "%s - STATION ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308011

        gscPort-util-gt-thres  TRAP-TYPE
		ENTERPRISE   cdx6500
		VARIABLES    { cdx6500SNMPLastTrap }
		DESCRIPTION
		             "%s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308012

        gscPort-error-thres-exceed  TRAP-TYPE
		ENTERPRISE   cdx6500
		VARIABLES    { cdx6500SNMPLastTrap }
		DESCRIPTION
		             "%s - PORT ERROR COUNT > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308013

        gscPort-busyout  TRAP-TYPE
		ENTERPRISE   cdx6500
		VARIABLES    { cdx6500SNMPLastTrap }
		DESCRIPTION
		             "%s - PORT BUSY-OUT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308014

        gscPort-busyout-fail  TRAP-TYPE
		ENTERPRISE   cdx6500
		VARIABLES    { cdx6500SNMPLastTrap }
		DESCRIPTION
		             "%s - PORT BUSY-OUT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308015

        gscStnBusyout  TRAP-TYPE
		ENTERPRISE   cdx6500
		VARIABLES    { cdx6500SNMPLastTrap }
		DESCRIPTION
		             "%s - STATION BUSY-OUT"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308016

        gscStn-busyout-fail  TRAP-TYPE
		ENTERPRISE   cdx6500
		VARIABLES    { cdx6500SNMPLastTrap }
		DESCRIPTION
		             "%s - STATION BUSY-OUT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308017

        gscPort-status-warning  TRAP-TYPE
		ENTERPRISE   cdx6500
		VARIABLES    { cdx6500SNMPLastTrap }
		DESCRIPTION
		             "%s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308018

        gscPort-no-broadcast-stns  TRAP-TYPE
		ENTERPRISE   cdx6500
		VARIABLES    { cdx6500SNMPLastTrap }
		DESCRIPTION
		             "%s - NO BROADCAST STATIONS"
                     --#TYPE
                     --#SUMMARY "Trap #$G, specific: $S, arg(1): $1"
                     --#ARGUMENTS {}
                     --#SEVERITY  INFORMATIONAL
                     --#TIMEINDEX
                     --#HELP
                     --#HELPTAG
                     --#STATE
		::= 308019

        gsc-memory-allocation-failed  TRAP-TYPE
		ENTERPRISE   cdx6500
		VARIABLES    { cdx6500SNMPLastTrap }
		DESCRIPTION
		     "%s - MEMORY ALLOCATION FAILED"
		     --#TYPE
		     --#SUMMARY "Trap #$G, specific: $S, arg(1) : $1"
		     --#ARGUMENTS {}
		     --#SEVERITY  MINOR
		     --#TIMEINDEX
		     --#HELP
		     --#HELPTAG
		     --#STATE
		::= 308020

        gsc-inter-character-timeout  TRAP-TYPE
		ENTERPRISE   cdx6500
		VARIABLES    { cdx6500SNMPLastTrap }
		DESCRIPTION
		     "%s - INTER CHARACTER TIMEOUT"
		     --#TYPE
		     --#SUMMARY "Trap #$G, specific: $S, arg(1) : $1"
		     --#ARGUMENTS {}
		     --#SEVERITY  MINOR
		     --#TIMEINDEX
		     --#HELP
		     --#HELPTAG
		     --#STATE
		::= 308021

        gsc-checksum-error  TRAP-TYPE
		ENTERPRISE   cdx6500
		VARIABLES    { cdx6500SNMPLastTrap }
		DESCRIPTION
		     "%s - CHECKSUM ERROR"
		     --#TYPE
		     --#SUMMARY "Trap #$G, specific: $S, arg(1) : $1"
		     --#ARGUMENTS {}
		     --#SEVERITY  MINOR
		     --#TIMEINDEX
		     --#HELP
		     --#HELPTAG
		     --#STATE
		::= 308022

        gsc-frame-too-long  TRAP-TYPE
		ENTERPRISE   cdx6500
		VARIABLES    { cdx6500SNMPLastTrap }
		DESCRIPTION
		     "%s - FRAME TOO LONG"
		     --#TYPE
		     --#SUMMARY "Trap #$G, specific: $S, arg(1) : $1"
		     --#ARGUMENTS {}
		     --#SEVERITY  MINOR
		     --#TIMEINDEX
		     --#HELP
		     --#HELPTAG
		     --#STATE
		::= 308023

        gsc-unescaped-char-found  TRAP-TYPE
		ENTERPRISE   cdx6500
		VARIABLES    { cdx6500SNMPLastTrap }
		DESCRIPTION
		     "%s - UNESCAPED CHAR FOUND"
		     --#TYPE
		     --#SUMMARY "Trap #$G, specific: $S, arg(1) : $1"
		     --#ARGUMENTS {}
		     --#SEVERITY  MINOR
		     --#TIMEINDEX
		     --#HELP
		     --#HELPTAG
		     --#STATE
		::= 308024

        gsc-unexpected-frame  TRAP-TYPE
		ENTERPRISE   cdx6500
		VARIABLES    { cdx6500SNMPLastTrap }
		DESCRIPTION
		     "%s - UNEXPECTED FRAME"
		     --#TYPE
		     --#SUMMARY "Trap #$G, specific: $S, arg(1) : $1"
		     --#ARGUMENTS {}
		     --#SEVERITY  MINOR
		     --#TIMEINDEX
		     --#HELP
		     --#HELPTAG
		     --#STATE
		::= 308025

        gsc-frame-dropped-after-max-retr  TRAP-TYPE
		ENTERPRISE   cdx6500
		VARIABLES    { cdx6500SNMPLastTrap }
		DESCRIPTION
		     "%s - FRAME DROPPED AFTER MAX RETRY"
		     --#TYPE
		     --#SUMMARY "Trap #$G, specific: $S, arg(1) : $1"
		     --#ARGUMENTS {}
		     --#SEVERITY  MAJOR
		     --#TIMEINDEX
		     --#HELP
		     --#HELPTAG
		     --#STATE
		::= 308031

        gsc-device-not-responding  TRAP-TYPE
		ENTERPRISE   cdx6500
		VARIABLES    { cdx6500SNMPLastTrap }
		DESCRIPTION
		     "%s - DEVICE NOT RESPONDING"
		     --#TYPE
		     --#SUMMARY "Trap #$G, specific: $S, arg(1) : $1"
		     --#ARGUMENTS {}
		     --#SEVERITY  MAJOR
		     --#TIMEINDEX
		     --#HELP
		     --#HELPTAG
		     --#STATE
		::= 308032

        gsc-messages-lost  TRAP-TYPE
		ENTERPRISE   cdx6500
		VARIABLES    { cdx6500SNMPLastTrap }
		DESCRIPTION
		     "%s - MESSAGES LOST"
		     --#TYPE
		     --#SUMMARY "Trap #$G, specific: $S, arg(1) : $1"
		     --#ARGUMENTS {}
		     --#SEVERITY  CRITICAL
		     --#TIMEINDEX
		     --#HELP
		     --#HELPTAG
		     --#STATE
		::= 308033

        gsc-device-active  TRAP-TYPE
		ENTERPRISE   cdx6500
		VARIABLES    { cdx6500SNMPLastTrap }
		DESCRIPTION
		     "%s - DEVICE ACTIVE"
		     --#TYPE
		     --#SUMMARY "Trap #$G, specific: $S, arg(1) : $1"
		     --#ARGUMENTS {}
		     --#SEVERITY  MAJOR
		     --#TIMEINDEX
		     --#HELP
		     --#HELPTAG
		     --#STATE
		::= 308034

        gsc-link-up  TRAP-TYPE
		ENTERPRISE   cdx6500
		VARIABLES    { cdx6500SNMPLastTrap }
		DESCRIPTION
		     "%s - LINK UP"
		     --#TYPE
		     --#SUMMARY "Trap #$G, specific: $S, arg(1) : $1"
		     --#ARGUMENTS {}
		     --#SEVERITY  CRITICAL
		     --#TIMEINDEX
		     --#HELP
		     --#HELPTAG
		     --#STATE
		::= 308035

        gsc-invalid-device-responding  TRAP-TYPE
		ENTERPRISE   cdx6500
		VARIABLES    { cdx6500SNMPLastTrap }
		DESCRIPTION
		     "%s - INVALID DEVICE RESPONDING"
		     --#TYPE
		     --#SUMMARY "Trap #$G, specific: $S, arg(1) : $1"
		     --#ARGUMENTS {}
		     --#SEVERITY  MAJOR
		     --#TIMEINDEX
		     --#HELP
		     --#HELPTAG
		     --#STATE
		::= 308036

        gsc-solicit-abort  TRAP-TYPE
		ENTERPRISE   cdx6500
		VARIABLES    { cdx6500SNMPLastTrap }
		DESCRIPTION
		     "%s - SOLICIT ABORT"
		     --#TYPE
		     --#SUMMARY "Trap #$G, specific: $S, arg(1) : $1"
		     --#ARGUMENTS {}
		     --#SEVERITY  CRITICAL
		     --#TIMEINDEX
		     --#HELP
		     --#HELPTAG
		     --#STATE
		::= 308037

        gsc-fsm-internal-error  TRAP-TYPE
		ENTERPRISE   cdx6500
		VARIABLES    { cdx6500SNMPLastTrap }
		DESCRIPTION
		     "%s - FSM - INTERNAL ERROR"
		     --#TYPE
		     --#SUMMARY "Trap #$G, specific: $S, arg(1) : $1"
		     --#ARGUMENTS {}
		     --#SEVERITY  CRITICAL
		     --#TIMEINDEX
		     --#HELP
		     --#HELPTAG
		     --#STATE
		::= 308038

        gsc-wrong-message-address  TRAP-TYPE
		ENTERPRISE   cdx6500
		VARIABLES    { cdx6500SNMPLastTrap }
		DESCRIPTION
		     "%s - WRONG MESSAGE ADDRESS"
		     --#TYPE
		     --#SUMMARY "Trap #$G, specific: $S, arg(1) : $1"
		     --#ARGUMENTS {}
		     --#SEVERITY  MAJOR
		     --#TIMEINDEX
		     --#HELP
		     --#HELPTAG
		     --#STATE
		::= 308039

        gsc-link-down  TRAP-TYPE
		ENTERPRISE   cdx6500
		VARIABLES    { cdx6500SNMPLastTrap }
		DESCRIPTION
		     "%s - LINK DOWN"
		     --#TYPE
		     --#SUMMARY "Trap #$G, specific: $S, arg(1) : $1"
		     --#ARGUMENTS {}
		     --#SEVERITY  CRITICAL
		     --#TIMEINDEX
		     --#HELP
		     --#HELPTAG
		     --#STATE
		::= 308040

        gsc-autocall-retries-exhausted  TRAP-TYPE
		ENTERPRISE   cdx6500
		VARIABLES    { cdx6500SNMPLastTrap }
		DESCRIPTION
		     "%s - AUTOCALL RETRIES EXHAUSTED"
		     --#TYPE
		     --#SUMMARY "Trap #$G, specific: $S, arg(1) : $1"
		     --#ARGUMENTS {}
		     --#SEVERITY  CRITICAL
		     --#TIMEINDEX
		     --#HELP
		     --#HELPTAG
		     --#STATE
		::= 308041

        gsc-station-not-configured  TRAP-TYPE
		ENTERPRISE   cdx6500
		VARIABLES    { cdx6500SNMPLastTrap }
		DESCRIPTION
		     "%s - %d STATION NOT CONFIGURED"
		     --#TYPE
		     --#SUMMARY "Trap #$G, specific: $S, arg(1) : $1"
		     --#ARGUMENTS {}
		     --#SEVERITY  MINOR
		     --#TIMEINDEX
		     --#HELP
		     --#HELPTAG
		     --#STATE
		::= 308042

        gsc-can-not-forward-station-disa  TRAP-TYPE
		ENTERPRISE   cdx6500
		VARIABLES    { cdx6500SNMPLastTrap }
		DESCRIPTION
		     "%s - CAN NOT FORWARD - STATION DISABLED"
		     --#TYPE
		     --#SUMMARY "Trap #$G, specific: $S, arg(1) : $1"
		     --#ARGUMENTS {}
		     --#SEVERITY  MAJOR
		     --#TIMEINDEX
		     --#HELP
		     --#HELPTAG
		     --#STATE
		::= 308043

        gsc-inactivity-time-out  TRAP-TYPE
		ENTERPRISE   cdx6500
		VARIABLES    { cdx6500SNMPLastTrap }
		DESCRIPTION
		     "%s - INACTIVITY TIME OUT"
		     --#TYPE
		     --#SUMMARY "Trap #$G, specific: $S, arg(1) : $1"
		     --#ARGUMENTS {}
		     --#SEVERITY  MAJOR
		     --#TIMEINDEX
		     --#HELP
		     --#HELPTAG
		     --#STATE
		::= 308044

        gsc-inbound-link-blocked  TRAP-TYPE
		ENTERPRISE   cdx6500
		VARIABLES    { cdx6500SNMPLastTrap }
		DESCRIPTION
		     "%s - INBOUND LINK BLOCKED"
		     --#TYPE
		     --#SUMMARY "Trap #$G, specific: $S, arg(1) : $1"
		     --#ARGUMENTS {}
		     --#SEVERITY  MINOR
		     --#TIMEINDEX
		     --#HELP
		     --#HELPTAG
		     --#STATE
		::= 308045

        gsc-inbound-link-unblocked  TRAP-TYPE
		ENTERPRISE   cdx6500
		VARIABLES    { cdx6500SNMPLastTrap }
		DESCRIPTION
		     "%s - INBOUND LINK UNBLOCKED"
		     --#TYPE
		     --#SUMMARY "Trap #$G, specific: $S, arg(1) : $1"
		     --#ARGUMENTS {}
		     --#SEVERITY  MINOR
		     --#TIMEINDEX
		     --#HELP
		     --#HELPTAG
		     --#STATE
		::= 308046

        gsc-outbound-link-blocked  TRAP-TYPE
		ENTERPRISE   cdx6500
		VARIABLES    { cdx6500SNMPLastTrap }
		DESCRIPTION
		     "%s - OUTBOUND LINK BLOCKED"
		     --#TYPE
		     --#SUMMARY "Trap #$G, specific: $S, arg(1) : $1"
		     --#ARGUMENTS {}
		     --#SEVERITY  MINOR
		     --#TIMEINDEX
		     --#HELP
		     --#HELPTAG
		     --#STATE
		::= 308047

        gsc-outbound-link-unblocked  TRAP-TYPE
		ENTERPRISE   cdx6500
		VARIABLES    { cdx6500SNMPLastTrap }
		DESCRIPTION
		     "%s - OUTBOUND LINK UNBLOCKED"
		     --#TYPE
		     --#SUMMARY "Trap #$G, specific: $S, arg(1) : $1"
		     --#ARGUMENTS {}
		     --#SEVERITY  MINOR
		     --#TIMEINDEX
		     --#HELP
		     --#HELPTAG
		     --#STATE
		::= 308048

        tpa-connection-up  TRAP-TYPE
		ENTERPRISE   cdx6500
		VARIABLES    { cdx6500SNMPLastTrap }
		DESCRIPTION
		     "%s - CONNECTION UP"
		     --#TYPE
		     --#SUMMARY "Trap #$G, specific: $S, arg(1) : $1"
		     --#ARGUMENTS {}
		     --#SEVERITY  CRITICAL
		     --#TIMEINDEX
		     --#HELP
		     --#HELPTAG
		     --#STATE
		::= 315000

        tpa-connection-down  TRAP-TYPE
		ENTERPRISE   cdx6500
		VARIABLES    { cdx6500SNMPLastTrap }
		DESCRIPTION
		     "%s - CONNECTION DOWN (%s)"
		     --#TYPE
		     --#SUMMARY "Trap #$G, specific: $S, arg(1) : $1"
		     --#ARGUMENTS {}
		     --#SEVERITY  CRITICAL
		     --#TIMEINDEX
		     --#HELP
		     --#HELPTAG
		     --#STATE
		::= 315001

        tpa-clearing-call-unexpected-q-b  TRAP-TYPE
		ENTERPRISE   cdx6500
		VARIABLES    { cdx6500SNMPLastTrap }
		DESCRIPTION
		     "%s - CLEARING CALL, UNEXPECTED Q-BIT PACKET(%x)"
		     --#TYPE
		     --#SUMMARY "Trap #$G, specific: $S, arg(1) : $1"
		     --#ARGUMENTS {}
		     --#SEVERITY  CRITICAL
		     --#TIMEINDEX
		     --#HELP
		     --#HELPTAG
		     --#STATE
		::= 315002

        tpa-sdlc-not-enough-memory  TRAP-TYPE
		ENTERPRISE   cdx6500
		VARIABLES    { cdx6500SNMPLastTrap }
		DESCRIPTION
		     "TPA-SDLC, NOT ENOUGH MEMORY"
		     --#TYPE
		     --#SUMMARY "Trap #$G, specific: $S, arg(1) : $1"
		     --#ARGUMENTS {}
		     --#SEVERITY  CRITICAL
		     --#TIMEINDEX
		     --#HELP
		     --#HELPTAG
		     --#STATE
		::= 315003

        tpa-sdlc-idcm-or-tgo-does-not-ex  TRAP-TYPE
		ENTERPRISE   cdx6500
		VARIABLES    { cdx6500SNMPLastTrap }
		DESCRIPTION
		     "TPA-SDLC, IDCM OR TGO DOES NOT EXIST"
		     --#TYPE
		     --#SUMMARY "Trap #$G, specific: $S, arg(1) : $1"
		     --#ARGUMENTS {}
		     --#SEVERITY  CRITICAL
		     --#TIMEINDEX
		     --#HELP
		     --#HELPTAG
		     --#STATE
		::= 315004

        tpa-sdlc-idcm-not-up  TRAP-TYPE
		ENTERPRISE   cdx6500
		VARIABLES    { cdx6500SNMPLastTrap }
		DESCRIPTION
		     "TPA-SDLC, IDCM NOT UP"
		     --#TYPE
		     --#SUMMARY "Trap #$G, specific: $S, arg(1) : $1"
		     --#ARGUMENTS {}
		     --#SEVERITY  CRITICAL
		     --#TIMEINDEX
		     --#HELP
		     --#HELPTAG
		     --#STATE
		::= 315005

        tpa-clearing-call-bad-or-no-resp  TRAP-TYPE
		ENTERPRISE   cdx6500
		VARIABLES    { cdx6500SNMPLastTrap }
		DESCRIPTION
		     "%s - CLEARING CALL, BAD OR NO RESPONSE FOR QSM"
		     --#TYPE
		     --#SUMMARY "Trap #$G, specific: $S, arg(1) : $1"
		     --#ARGUMENTS {}
		     --#SEVERITY  CRITICAL
		     --#TIMEINDEX
		     --#HELP
		     --#HELPTAG
		     --#STATE
		::= 315006

        tpa-received-ve-responsesense-da  TRAP-TYPE
		ENTERPRISE   cdx6500
		VARIABLES    { cdx6500SNMPLastTrap }
		DESCRIPTION
		     "%s : RECEIVED -VE RESPONSE,SENSE DATA- %x,%x,%x,%x"
		     --#TYPE
		     --#SUMMARY "Trap #$G, specific: $S, arg(1) : $1"
		     --#ARGUMENTS {}
		     --#SEVERITY  MINOR
		     --#TIMEINDEX
		     --#HELP
		     --#HELPTAG
		     --#STATE
		::= 315007

        tpa-retry-exceeded-for-sna-messa  TRAP-TYPE
		ENTERPRISE   cdx6500
		VARIABLES    { cdx6500SNMPLastTrap }
		DESCRIPTION
		     "%s : RETRY EXCEEDED, FOR SNA MESSAGE - %x"
		     --#TYPE
		     --#SUMMARY "Trap #$G, specific: $S, arg(1) : $1"
		     --#ARGUMENTS {}
		     --#SEVERITY  MINOR
		     --#TIMEINDEX
		     --#HELP
		     --#HELPTAG
		     --#STATE
		::= 315008

        tpa-lu-lu-session-cleared-cleari  TRAP-TYPE
		ENTERPRISE   cdx6500
		VARIABLES    { cdx6500SNMPLastTrap }
		DESCRIPTION
		     "%s : LU-LU SESSION CLEARED, CLEARING SVC"
		     --#TYPE
		     --#SUMMARY "Trap #$G, specific: $S, arg(1) : $1"
		     --#ARGUMENTS {}
		     --#SEVERITY  MINOR
		     --#TIMEINDEX
		     --#HELP
		     --#HELPTAG
		     --#STATE
		::= 315009

        tpa-pu-session-cleared-clearing  TRAP-TYPE
		ENTERPRISE   cdx6500
		VARIABLES    { cdx6500SNMPLastTrap }
		DESCRIPTION
		     "%s : PU SESSION CLEARED, CLEARING SVC"
		     --#TYPE
		     --#SUMMARY "Trap #$G, specific: $S, arg(1) : $1"
		     --#ARGUMENTS {}
		     --#SEVERITY  MINOR
		     --#TIMEINDEX
		     --#HELP
		     --#HELPTAG
		     --#STATE
		::= 315010

        tpa-pu-session-activated  TRAP-TYPE
		ENTERPRISE   cdx6500
		VARIABLES    { cdx6500SNMPLastTrap }
		DESCRIPTION
		     "%s : PU SESSION ACTIVATED"
		     --#TYPE
		     --#SUMMARY "Trap #$G, specific: $S, arg(1) : $1"
		     --#ARGUMENTS {}
		     --#SEVERITY  MINOR
		     --#TIMEINDEX
		     --#HELP
		     --#HELPTAG
		     --#STATE
		::= 315011

        tpa-lu-session-activated  TRAP-TYPE
		ENTERPRISE   cdx6500
		VARIABLES    { cdx6500SNMPLastTrap }
		DESCRIPTION
		     "%s : LU SESSION ACTIVATED"
		     --#TYPE
		     --#SUMMARY "Trap #$G, specific: $S, arg(1) : $1"
		     --#ARGUMENTS {}
		     --#SEVERITY  MINOR
		     --#TIMEINDEX
		     --#HELP
		     --#HELPTAG
		     --#STATE
		::= 315012

        tpa-invalid-cp-packet-ru-th-rh  TRAP-TYPE
		ENTERPRISE   cdx6500
		VARIABLES    { cdx6500SNMPLastTrap }
		DESCRIPTION
		     "%s : INVALID CP PACKET, RU-%x,TH-%x,%x,%x,%x,RH-%x,%x,%x"
		     --#TYPE
		     --#SUMMARY "Trap #$G, specific: $S, arg(1) : $1"
		     --#ARGUMENTS {}
		     --#SEVERITY  MINOR
		     --#TIMEINDEX
		     --#HELP
		     --#HELPTAG
		     --#STATE
		::= 315013

        tpa-invalid-lu-packet-ru-th-rh  TRAP-TYPE
		ENTERPRISE   cdx6500
		VARIABLES    { cdx6500SNMPLastTrap }
		DESCRIPTION
		     "%s : INVALID LU PACKET, RU-%x,TH-%x,%x,%x,%x,RH-%x,%x,%x"
		     --#TYPE
		     --#SUMMARY "Trap #$G, specific: $S, arg(1) : $1"
		     --#ARGUMENTS {}
		     --#SEVERITY  MINOR
		     --#TIMEINDEX
		     --#HELP
		     --#HELPTAG
		     --#STATE
		::= 315014

        tpa-out-of-sequence-packet-event  TRAP-TYPE
		ENTERPRISE   cdx6500
		VARIABLES    { cdx6500SNMPLastTrap }
		DESCRIPTION
		     "%s : OUT OF SEQUENCE PACKET, Event Code - %x"
		     --#TYPE
		     --#SUMMARY "Trap #$G, specific: $S, arg(1) : $1"
		     --#ARGUMENTS {}
		     --#SEVERITY  MINOR
		     --#TIMEINDEX
		     --#HELP
		     --#HELPTAG
		     --#STATE
		::= 315015

        tpa-retries-over-for-sending-bin  TRAP-TYPE
		ENTERPRISE   cdx6500
		VARIABLES    { cdx6500SNMPLastTrap }
		DESCRIPTION
		     "%s : RETRIES OVER FOR SENDING BIND"
		     --#TYPE
		     --#SUMMARY "Trap #$G, specific: $S, arg(1) : $1"
		     --#ARGUMENTS {}
		     --#SEVERITY  MAJOR
		     --#TIMEINDEX
		     --#HELP
		     --#HELPTAG
		     --#STATE
		::= 315016

        tpa-tpa3270-connected  TRAP-TYPE
		ENTERPRISE   cdx6500
		VARIABLES    { cdx6500SNMPLastTrap }
		DESCRIPTION
		     "%s - TPA3270 CONNECTED"
		     --#TYPE
		     --#SUMMARY "Trap #$G, specific: $S, arg(1) : $1"
		     --#ARGUMENTS {}
		     --#SEVERITY  CRITICAL
		     --#TIMEINDEX
		     --#HELP
		     --#HELPTAG
		     --#STATE
		::= 316000

        tpa-tpa3270-disconnected  TRAP-TYPE
		ENTERPRISE   cdx6500
		VARIABLES    { cdx6500SNMPLastTrap }
		DESCRIPTION
		     "%s - TPA3270 DISCONNECTED"
		     --#TYPE
		     --#SUMMARY "Trap #$G, specific: $S, arg(1) : $1"
		     --#ARGUMENTS {}
		     --#SEVERITY  CRITICAL
		     --#TIMEINDEX
		     --#HELP
		     --#HELPTAG
		     --#STATE
		::= 316001

        tpdu-tpr-boot-complete  TRAP-TYPE
		ENTERPRISE   cdx6500
		VARIABLES    { cdx6500SNMPLastTrap }
		DESCRIPTION
		     "TPR-BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 317000

        tpdu-tpr-slot-boot-complete  TRAP-TYPE
		ENTERPRISE   cdx6500
		VARIABLES    { cdx6500SNMPLastTrap }
		DESCRIPTION
		     "TPR SLOT-%d - BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 317001

        tpdu-tpr-boot-failure-number-of  TRAP-TYPE
		ENTERPRISE   cdx6500
		VARIABLES    { cdx6500SNMPLastTrap }
		DESCRIPTION
		     "TPR-BOOT FAILURE - NUMBER OF SLOTS CHANGED"
		     --#TYPE
		     --#SUMMARY "Trap #$G, specific: $S, arg(1) : $1"
		     --#ARGUMENTS {}
		     --#SEVERITY  CRITICAL
		     --#TIMEINDEX
		     --#HELP
		     --#HELPTAG
		     --#STATE
		::= 317002

        tpdu-tpr-slot-no-boot-failure-sl  TRAP-TYPE
		ENTERPRISE   cdx6500
		VARIABLES    { cdx6500SNMPLastTrap }
		DESCRIPTION
		     "TPR-SLOT (no=%d) BOOT FAILURE - SLOT TYPE CHANGED"
		     --#TYPE
		     --#SUMMARY "Trap #$G, specific: $S, arg(1) : $1"
		     --#ARGUMENTS {}
		     --#SEVERITY  CRITICAL
		     --#TIMEINDEX
		     --#HELP
		     --#HELPTAG
		     --#STATE
		::= 317003

        tpdu-tpr-init-failed  TRAP-TYPE
		ENTERPRISE   cdx6500
		VARIABLES    { cdx6500SNMPLastTrap }
		DESCRIPTION
		     "TPR-INIT FAILED -  %s"
		     --#TYPE
		     --#SUMMARY "Trap #$G, specific: $S, arg(1) : $1"
		     --#ARGUMENTS {}
		     --#SEVERITY  CRITICAL
		     --#TIMEINDEX
		     --#HELP
		     --#HELPTAG
		     --#STATE
		::= 317004

        tpdu-tpr-initslot-tpa-module-doe  TRAP-TYPE
		ENTERPRISE   cdx6500
		VARIABLES    { cdx6500SNMPLastTrap }
		DESCRIPTION
		     "TPR-INIT(slot=%d) TPA module(%d) does not exist"
		     --#TYPE
		     --#SUMMARY "Trap #$G, specific: $S, arg(1) : $1"
		     --#ARGUMENTS {}
		     --#SEVERITY  CRITICAL
		     --#TIMEINDEX
		     --#HELP
		     --#HELPTAG
		     --#STATE
		::= 317005

        tpdu-tpr-initslot-tpa-module-ini  TRAP-TYPE
		ENTERPRISE   cdx6500
		VARIABLES    { cdx6500SNMPLastTrap }
		DESCRIPTION
		     "TPR-INIT(slot=%d) TPA module(%d) init failed"
		     --#TYPE
		     --#SUMMARY "Trap #$G, specific: $S, arg(1) : $1"
		     --#ARGUMENTS {}
		     --#SEVERITY  CRITICAL
		     --#TIMEINDEX
		     --#HELP
		     --#HELPTAG
		     --#STATE
		::= 317006

        tpdu-tpr-slot-enabled  TRAP-TYPE
		ENTERPRISE   cdx6500
		VARIABLES    { cdx6500SNMPLastTrap }
		DESCRIPTION
		     "TPR SLOT-%d ENABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 317007

        tpdu-tpr-slot-disabled  TRAP-TYPE
		ENTERPRISE   cdx6500
		VARIABLES    { cdx6500SNMPLastTrap }
		DESCRIPTION
		     "TPR SLOT-%d DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 317008

        tpdu-tpr-fwd-packet-for-dead-slo  TRAP-TYPE
		ENTERPRISE   cdx6500
		VARIABLES    { cdx6500SNMPLastTrap }
		DESCRIPTION
		     "TPR-FWD Packet for DEAD slot(%d) arrived"
		     --#TYPE
		     --#SUMMARY "Trap #$G, specific: $S, arg(1) : $1"
		     --#ARGUMENTS {}
		     --#SEVERITY  MINOR
		     --#TIMEINDEX
		     --#HELP
		     --#HELPTAG
		     --#STATE
		::= 317009

        tpdu-session-is-in-progress-with  TRAP-TYPE
		ENTERPRISE   cdx6500
		VARIABLES    { cdx6500SNMPLastTrap }
		DESCRIPTION
		     "%s - SESSION IS IN PROGRESS WITH SLOT %s"
		     --#TYPE
		     --#SUMMARY "Trap #$G, specific: $S, arg(1) : $1"
		     --#ARGUMENTS {}
		     --#SEVERITY  MAJOR
		     --#TIMEINDEX
		     --#HELP
		     --#HELPTAG
		     --#STATE
		::= 317010

        tpdu-invalid-session-message-in  TRAP-TYPE
		ENTERPRISE   cdx6500
		VARIABLES    { cdx6500SNMPLastTrap }
		DESCRIPTION
		     "%s - INVALID SESSION MESSAGE IN IDLE STATE FROM SLOT %s"
		     --#TYPE
		     --#SUMMARY "Trap #$G, specific: $S, arg(1) : $1"
		     --#ARGUMENTS {}
		     --#SEVERITY  MAJOR
		     --#TIMEINDEX
		     --#HELP
		     --#HELPTAG
		     --#STATE
		::= 317011

        tpdu-session-aborted-invalid-ses  TRAP-TYPE
		ENTERPRISE   cdx6500
		VARIABLES    { cdx6500SNMPLastTrap }
		DESCRIPTION
		     "%s - SESSION ABORTED(%s) - INVALID SESSION MESSAGE"
		     --#TYPE
		     --#SUMMARY "Trap #$G, specific: $S, arg(1) : $1"
		     --#ARGUMENTS {}
		     --#SEVERITY  MAJOR
		     --#TIMEINDEX
		     --#HELP
		     --#HELPTAG
		     --#STATE
		::= 317012

        tpdu-session-aborted-got-session  TRAP-TYPE
		ENTERPRISE   cdx6500
		VARIABLES    { cdx6500SNMPLastTrap }
		DESCRIPTION
		     "%s - SESSION ABORTED(%s) - GOT SESSION CLOSE"
		     --#TYPE
		     --#SUMMARY "Trap #$G, specific: $S, arg(1) : $1"
		     --#ARGUMENTS {}
		     --#SEVERITY  MAJOR
		     --#TIMEINDEX
		     --#HELP
		     --#HELPTAG
		     --#STATE
		::= 317013

        tpdu-session-aborted-got-invitat  TRAP-TYPE
		ENTERPRISE   cdx6500
		VARIABLES    { cdx6500SNMPLastTrap }
		DESCRIPTION
		     "%s - SESSION ABORTED(%s) - GOT INVITATION TO CLR"
		     --#TYPE
		     --#SUMMARY "Trap #$G, specific: $S, arg(1) : $1"
		     --#ARGUMENTS {}
		     --#SEVERITY  MAJOR
		     --#TIMEINDEX
		     --#HELP
		     --#HELPTAG
		     --#STATE
		::= 317014

        tpdu-session-aborted-got-illegal  TRAP-TYPE
		ENTERPRISE   cdx6500
		VARIABLES    { cdx6500SNMPLastTrap }
		DESCRIPTION
		     "%s - SESSION ABORTED(%s) - GOT ILLEGAL MESSAGE"
		     --#TYPE
		     --#SUMMARY "Trap #$G, specific: $S, arg(1) : $1"
		     --#ARGUMENTS {}
		     --#SEVERITY  MAJOR
		     --#TIMEINDEX
		     --#HELP
		     --#HELPTAG
		     --#STATE
		::= 317015

        tpdu-session-aborted-data-when-o  TRAP-TYPE
		ENTERPRISE   cdx6500
		VARIABLES    { cdx6500SNMPLastTrap }
		DESCRIPTION
		     "%s - SESSION ABORTED(%s) - DATA WHEN OPENING SLOT"
		     --#TYPE
		     --#SUMMARY "Trap #$G, specific: $S, arg(1) : $1"
		     --#ARGUMENTS {}
		     --#SEVERITY  MAJOR
		     --#TIMEINDEX
		     --#HELP
		     --#HELPTAG
		     --#STATE
		::= 317016

        tpdu-session-aborted-got-call-cl  TRAP-TYPE
		ENTERPRISE   cdx6500
		VARIABLES    { cdx6500SNMPLastTrap }
		DESCRIPTION
		     "%s - SESSION ABORTED(%s) - GOT CALL CLEAR"
		     --#TYPE
		     --#SUMMARY "Trap #$G, specific: $S, arg(1) : $1"
		     --#ARGUMENTS {}
		     --#SEVERITY  MAJOR
		     --#TIMEINDEX
		     --#HELP
		     --#HELPTAG
		     --#STATE
		::= 317017

        tpdu-session-aborted-got-call-re  TRAP-TYPE
		ENTERPRISE   cdx6500
		VARIABLES    { cdx6500SNMPLastTrap }
		DESCRIPTION
		     "%s - SESSION ABORTED(%s) - GOT CALL REQUEST"
		     --#TYPE
		     --#SUMMARY "Trap #$G, specific: $S, arg(1) : $1"
		     --#ARGUMENTS {}
		     --#SEVERITY  MAJOR
		     --#TIMEINDEX
		     --#HELP
		     --#HELPTAG
		     --#STATE
		::= 317018

        tpdu-session-aborted-got-call-ac  TRAP-TYPE
		ENTERPRISE   cdx6500
		VARIABLES    { cdx6500SNMPLastTrap }
		DESCRIPTION
		     "%s - SESSION ABORTED(%s) - GOT CALL ACCEPT"
		     --#TYPE
		     --#SUMMARY "Trap #$G, specific: $S, arg(1) : $1"
		     --#ARGUMENTS {}
		     --#SEVERITY  MAJOR
		     --#TIMEINDEX
		     --#HELP
		     --#HELPTAG
		     --#STATE
		::= 317019

        tpdu-session-aborted-got-data-fr  TRAP-TYPE
		ENTERPRISE   cdx6500
		VARIABLES    { cdx6500SNMPLastTrap }
		DESCRIPTION
		     "%s - SESSION ABORTED(%s) - GOT DATA FROM DEVICE WHILE NOT CONNECTED"
		     --#TYPE
		     --#SUMMARY "Trap #$G, specific: $S, arg(1) : $1"
		     --#ARGUMENTS {}
		     --#SEVERITY  MAJOR
		     --#TIMEINDEX
		     --#HELP
		     --#HELPTAG
		     --#STATE
		::= 317020

        tpdu-session-closed  TRAP-TYPE
		ENTERPRISE   cdx6500
		VARIABLES    { cdx6500SNMPLastTrap }
		DESCRIPTION
		     "%s - SESSION CLOSED(%s)"
		     --#TYPE
		     --#SUMMARY "Trap #$G, specific: $S, arg(1) : $1"
		     --#ARGUMENTS {}
		     --#SEVERITY  MAJOR
		     --#TIMEINDEX
		     --#HELP
		     --#HELPTAG
		     --#STATE
		::= 317021

        tpdu-session-established-with-sl  TRAP-TYPE
		ENTERPRISE   cdx6500
		VARIABLES    { cdx6500SNMPLastTrap }
		DESCRIPTION
		     "%s - SESSION ESTABLISHED WITH SLOT %s"
		     --#TYPE
		     --#SUMMARY "Trap #$G, specific: $S, arg(1) : $1"
		     --#ARGUMENTS {}
		     --#SEVERITY  MAJOR
		     --#TIMEINDEX
		     --#HELP
		     --#HELPTAG
		     --#STATE
		::= 317022

        tpdu-data-in-idle-state-from-slo  TRAP-TYPE
		ENTERPRISE   cdx6500
		VARIABLES    { cdx6500SNMPLastTrap }
		DESCRIPTION
		     "%s - DATA IN IDLE STATE FROM SLOT %s"
		     --#TYPE
		     --#SUMMARY "Trap #$G, specific: $S, arg(1) : $1"
		     --#ARGUMENTS {}
		     --#SEVERITY  MAJOR
		     --#TIMEINDEX
		     --#HELP
		     --#HELPTAG
		     --#STATE
		::= 317023

        tpdu-session-closed-got-call-req  TRAP-TYPE
		ENTERPRISE   cdx6500
		VARIABLES    { cdx6500SNMPLastTrap }
		DESCRIPTION
		     "%s - SESSION CLOSED(%s) - GOT CALL REQUEST"
		     --#TYPE
		     --#SUMMARY "Trap #$G, specific: $S, arg(1) : $1"
		     --#ARGUMENTS {}
		     --#SEVERITY  MAJOR
		     --#TIMEINDEX
		     --#HELP
		     --#HELPTAG
		     --#STATE
		::= 317024

        tpdu-session-closed-got-call-acc  TRAP-TYPE
		ENTERPRISE   cdx6500
		VARIABLES    { cdx6500SNMPLastTrap }
		DESCRIPTION
		     "%s - SESSION CLOSED(%s) - GOT CALL ACCEPT"
		     --#TYPE
		     --#SUMMARY "Trap #$G, specific: $S, arg(1) : $1"
		     --#ARGUMENTS {}
		     --#SEVERITY  MAJOR
		     --#TIMEINDEX
		     --#HELP
		     --#HELPTAG
		     --#STATE
		::= 317025

        tpdu-session-closed-got-illegal  TRAP-TYPE
		ENTERPRISE   cdx6500
		VARIABLES    { cdx6500SNMPLastTrap }
		DESCRIPTION
		     "%s - SESSION CLOSED(%s) - GOT ILLEGAL MESSAGE"
		     --#TYPE
		     --#SUMMARY "Trap #$G, specific: $S, arg(1) : $1"
		     --#ARGUMENTS {}
		     --#SEVERITY  MAJOR
		     --#TIMEINDEX
		     --#HELP
		     --#HELPTAG
		     --#STATE
		::= 317026

        tpdu-packet-allocation-failed  TRAP-TYPE
		ENTERPRISE   cdx6500
		VARIABLES    { cdx6500SNMPLastTrap }
		DESCRIPTION
		     "%s - PACKET ALLOCATION FAILED"
		     --#TYPE
		     --#SUMMARY "Trap #$G, specific: $S, arg(1) : $1"
		     --#ARGUMENTS {}
		     --#SEVERITY  MAJOR
		     --#TIMEINDEX
		     --#HELP
		     --#HELPTAG
		     --#STATE
		::= 317027

        tpdu-not-enough-memory  TRAP-TYPE
		ENTERPRISE   cdx6500
		VARIABLES    { cdx6500SNMPLastTrap }
		DESCRIPTION
		     "%s, NOT ENOUGH MEMORY"
		     --#TYPE
		     --#SUMMARY "Trap #$G, specific: $S, arg(1) : $1"
		     --#ARGUMENTS {}
		     --#SEVERITY  MAJOR
		     --#TIMEINDEX
		     --#HELP
		     --#HELPTAG
		     --#STATE
		::= 317028

        tpdu-session-closed-got-invalid  TRAP-TYPE
		ENTERPRISE   cdx6500
		VARIABLES    { cdx6500SNMPLastTrap }
		DESCRIPTION
		     "%s - SESSION CLOSED(%s) - GOT INVALID SESSION MESSAGE"
		     --#TYPE
		     --#SUMMARY "Trap #$G, specific: $S, arg(1) : $1"
		     --#ARGUMENTS {}
		     --#SEVERITY  MAJOR
		     --#TIMEINDEX
		     --#HELP
		     --#HELPTAG
		     --#STATE
		::= 317029

        tpdu-discarded-session-message-f  TRAP-TYPE
		ENTERPRISE   cdx6500
		VARIABLES    { cdx6500SNMPLastTrap }
		DESCRIPTION
		     "%s - DISCARDED - SESSION MESSAGE FROM SLOT %s"
		     --#TYPE
		     --#SUMMARY "Trap #$G, specific: $S, arg(1) : $1"
		     --#ARGUMENTS {}
		     --#SEVERITY  MAJOR
		     --#TIMEINDEX
		     --#HELP
		     --#HELPTAG
		     --#STATE
		::= 317030

        tpdu-session-stataus-message-cou  TRAP-TYPE
		ENTERPRISE   cdx6500
		VARIABLES    { cdx6500SNMPLastTrap }
		DESCRIPTION
		     "%s - SESSION STATAUS MESSAGE COULDN'T SEND TO DEVICE"
		     --#TYPE
		     --#SUMMARY "Trap #$G, specific: $S, arg(1) : $1"
		     --#ARGUMENTS {}
		     --#SEVERITY  MAJOR
		     --#TIMEINDEX
		     --#HELP
		     --#HELPTAG
		     --#STATE
		::= 317031

        sppPort-boot  TRAP-TYPE
                 ENTERPRISE   cdx6500
                 VARIABLES    { cdx6500SNMPLastTrap }
                 DESCRIPTION
                              "%s - PORT BOOT COMPLETE"
                     --#TYPE
                     --#SUMMARY "Trap #$G, specific: $S, arg(1): $1"
                     --#ARGUMENTS {}
                     --#SEVERITY  INFORMATIONAL
                     --#TIMEINDEX
                     --#HELP
                     --#HELPTAG
                     --#STATE
                 ::= 318000

        sppPort-boot-fail  TRAP-TYPE
                 ENTERPRISE   cdx6500
                 VARIABLES    { cdx6500SNMPLastTrap }
                 DESCRIPTION
                              "%s - PORT BOOT FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                 ::= 318001

        sppPort-disable  TRAP-TYPE
                 ENTERPRISE   cdx6500
                 VARIABLES    { cdx6500SNMPLastTrap }
                 DESCRIPTION
                              "%s - PORT DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
                 ::= 318002

        sppPort-disable-fail  TRAP-TYPE
                 ENTERPRISE   cdx6500
                 VARIABLES    { cdx6500SNMPLastTrap }
                 DESCRIPTION
                              "%s - PORT DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                 ::= 318003

        sppPort-enable  TRAP-TYPE
                 ENTERPRISE   cdx6500
                 VARIABLES    { cdx6500SNMPLastTrap }
                 DESCRIPTION
                              "%s - PORT ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
                 ::= 318004

        sppPort-enable-fail  TRAP-TYPE
                 ENTERPRISE   cdx6500
                 VARIABLES    { cdx6500SNMPLastTrap }
                 DESCRIPTION
                              "%s - PORT ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                 ::= 318005

        sppStn-disable  TRAP-TYPE
                 ENTERPRISE   cdx6500
                 VARIABLES    { cdx6500SNMPLastTrap }
                 DESCRIPTION
                              "%s - STATION DISABLED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 318006

        sppStn-disable-fail  TRAP-TYPE
                ENTERPRISE   cdx6500
                VARIABLES    { cdx6500SNMPLastTrap }
                DESCRIPTION
                             "%s - STATION DISABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 318007

        sppStn-enable  TRAP-TYPE
                ENTERPRISE   cdx6500
                VARIABLES    { cdx6500SNMPLastTrap }
                DESCRIPTION
                             "%s - STATION ENABLED"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 318008

        sppStn-enable-fail  TRAP-TYPE
                ENTERPRISE   cdx6500
                VARIABLES    { cdx6500SNMPLastTrap }
                DESCRIPTION
                             "%s - STATION ENABLE FAILURE - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 318009

        sppPort-util-exceeded  TRAP-TYPE
                ENTERPRISE   cdx6500
                VARIABLES    { cdx6500SNMPLastTrap }
                DESCRIPTION
                             "%s - PORT UTILIZATION > THRESHOLD"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 318010

        sppPort-warn-status  TRAP-TYPE
                ENTERPRISE   cdx6500
                VARIABLES    { cdx6500SNMPLastTrap }
                DESCRIPTION
                             "%s - PORT STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 318011

        sppPort-bad-tid  TRAP-TYPE
                ENTERPRISE   cdx6500
                VARIABLES    { cdx6500SNMPLastTrap }
                DESCRIPTION
                             "%s - BAD TID IN CALL FROM %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 318012

        sppPort-bad-pid  TRAP-TYPE
                ENTERPRISE   cdx6500
                VARIABLES    { cdx6500SNMPLastTrap }
                DESCRIPTION
                             "%s - BAD PID IN CALL FROM %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 318013

        spp-stn-warn-status  TRAP-TYPE
                ENTERPRISE   cdx6500
                VARIABLES    { cdx6500SNMPLastTrap }
                DESCRIPTION
                             "%s - STATION STATUS WARNING - %s"
                     --#TYPE
                     --#SUMMARY "Trap #$G, specific: $S, arg(1): $1"
                     --#ARGUMENTS {}
                     --#SEVERITY  INFORMATIONAL
                     --#TIMEINDEX
                     --#HELP
                     --#HELPTAG
                     --#STATE
                ::= 318014

        xlb-insufficient-memory-for-tran  TRAP-TYPE
		ENTERPRISE   cdx6500
		VARIABLES    { cdx6500SNMPLastTrap }
		DESCRIPTION
		     "XLB INSUFFICIENT MEMORY FOR TRANSLATIONAL BRIDGING"
		     --#TYPE
		     --#SUMMARY "Trap #$G, specific: $S, arg(1) : $1"
		     --#ARGUMENTS {}
		     --#SEVERITY  CRITICAL
		     --#TIMEINDEX
		     --#HELP
		     --#HELPTAG
		     --#STATE
		::= 321000

        xlb-module-initialized  TRAP-TYPE
		ENTERPRISE   cdx6500
		VARIABLES    { cdx6500SNMPLastTrap }
		DESCRIPTION
		     "XLB MODULE INITIALIZED 0x%x"
		     --#TYPE
		     --#SUMMARY "Trap #$G, specific: $S, arg(1) : $1"
		     --#ARGUMENTS {}
		     --#SEVERITY  CRITICAL
		     --#TIMEINDEX
		     --#HELP
		     --#HELPTAG
		     --#STATE
		::= 321001

        tpa-x25-not-enough-memory  TRAP-TYPE
		ENTERPRISE   cdx6500
		VARIABLES    { cdx6500SNMPLastTrap }
		DESCRIPTION
		     "TPA-X25, NOT ENOUGH MEMORY"
		     --#TYPE
		     --#SUMMARY "Trap #$G, specific: $S, arg(1) : $1"
		     --#ARGUMENTS {}
		     --#SEVERITY  CRITICAL
		     --#TIMEINDEX
		     --#HELP
		     --#HELPTAG
		     --#STATE
		::= 324000

        tpa-connection-up2  TRAP-TYPE
		ENTERPRISE   cdx6500
		VARIABLES    { cdx6500SNMPLastTrap }
		DESCRIPTION
		     "%s - CONNECTION UP"
		     --#TYPE
		     --#SUMMARY "Trap #$G, specific: $S, arg(1) : $1"
		     --#ARGUMENTS {}
		     --#SEVERITY  CRITICAL
		     --#TIMEINDEX
		     --#HELP
		     --#HELPTAG
		     --#STATE
		::= 324001

        tpa-connection-down2  TRAP-TYPE
		ENTERPRISE   cdx6500
		VARIABLES    { cdx6500SNMPLastTrap }
		DESCRIPTION
		     "%s - CONNECTION DOWN (%s)"
		     --#TYPE
		     --#SUMMARY "Trap #$G, specific: $S, arg(1) : $1"
		     --#ARGUMENTS {}
		     --#SEVERITY  CRITICAL
		     --#TIMEINDEX
		     --#HELP
		     --#HELPTAG
		     --#STATE
		::= 324002

        tpa-connection-is-in-progress  TRAP-TYPE
		ENTERPRISE   cdx6500
		VARIABLES    { cdx6500SNMPLastTrap }
		DESCRIPTION
		     "%s - CONNECTION IS IN PROGRESS"
		     --#TYPE
		     --#SUMMARY "Trap #$G, specific: $S, arg(1) : $1"
		     --#ARGUMENTS {}
		     --#SEVERITY  MINOR
		     --#TIMEINDEX
		     --#HELP
		     --#HELPTAG
		     --#STATE
		::= 324003

        tpa-x25-idcm-or-tgo-does-not-exi  TRAP-TYPE
		ENTERPRISE   cdx6500
		VARIABLES    { cdx6500SNMPLastTrap }
		DESCRIPTION
		     "TPA-X25, IDCM OR TGO DOES NOT EXIST"
		     --#TYPE
		     --#SUMMARY "Trap #$G, specific: $S, arg(1) : $1"
		     --#ARGUMENTS {}
		     --#SEVERITY  CRITICAL
		     --#TIMEINDEX
		     --#HELP
		     --#HELPTAG
		     --#STATE
		::= 324004

        tpa-x25-idcm-not-up  TRAP-TYPE
		ENTERPRISE   cdx6500
		VARIABLES    { cdx6500SNMPLastTrap }
		DESCRIPTION
		     "TPA-X25, IDCM NOT UP"
		     --#TYPE
		     --#SUMMARY "Trap #$G, specific: $S, arg(1) : $1"
		     --#ARGUMENTS {}
		     --#SEVERITY  CRITICAL
		     --#TIMEINDEX
		     --#HELP
		     --#HELPTAG
		     --#STATE
		::= 324005

        tpa-maximum-autocall-attempts-fa  TRAP-TYPE
		ENTERPRISE   cdx6500
		VARIABLES    { cdx6500SNMPLastTrap }
		DESCRIPTION
		     "%s - MAXIMUM AUTOCALL ATTEMPTS FAILURE"
		     --#TYPE
		     --#SUMMARY "Trap #$G, specific: $S, arg(1) : $1"
		     --#ARGUMENTS {}
		     --#SEVERITY  MAJOR
		     --#TIMEINDEX
		     --#HELP
		     --#HELPTAG
		     --#STATE
		::= 324006

   	igmp-1-rfcm  TRAP-TYPE
		ENTERPRISE   cdx6500
		VARIABLES    { cdx6500SNMPLastTrap }
		DESCRIPTION
		     "IGMP.1  RFCM Context Block NULL in  %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327000

   	igmp-2-igmp-module  TRAP-TYPE
		ENTERPRISE   cdx6500
		VARIABLES    { cdx6500SNMPLastTrap }
		DESCRIPTION
		     "IGMP.2  IGMP Module Aborted; not enough RAM\r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327001

   	igmp-3-mem-alloc-failed  TRAP-TYPE
		ENTERPRISE   cdx6500
		VARIABLES    { cdx6500SNMPLastTrap }
		DESCRIPTION
		     "IGMP.3  Memory allocation for %s failed\r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327002

   	igmp-4-module-not-up  TRAP-TYPE
		ENTERPRISE   cdx6500
		VARIABLES    { cdx6500SNMPLastTrap }
		DESCRIPTION
		     "IGMP.4  IGMP Module not up \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327003

   	igmp-5-packet-error  TRAP-TYPE
		ENTERPRISE   cdx6500
		VARIABLES    { cdx6500SNMPLastTrap }
		DESCRIPTION
		     "IGMP.5  Packet %s Error \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327004

   	igmp-6-buffer-failure  TRAP-TYPE
		ENTERPRISE   cdx6500
		VARIABLES    { cdx6500SNMPLastTrap }
		DESCRIPTION
		     "IGMP.6  Getbuff failure  \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327005

   	igmp-7-group-insert-fail  TRAP-TYPE
		ENTERPRISE   cdx6500
		VARIABLES    { cdx6500SNMPLastTrap }
		DESCRIPTION
		     "IGMP.7  Failure to insert a group \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327006

   	igmp-8-debug-trap  TRAP-TYPE
		ENTERPRISE   cdx6500
		VARIABLES    { cdx6500SNMPLastTrap }
		DESCRIPTION
		     "IGMP.8  %s %s %s %s \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327007

   	igmp-9-packet-dropped  TRAP-TYPE
		ENTERPRISE   cdx6500
		VARIABLES    { cdx6500SNMPLastTrap }
		DESCRIPTION
		     "IGMP.9 IGMP Packet dropped for IGMP NOT Active on %d\r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327008

   	igmp-10-multicast-not-enabled  TRAP-TYPE
		ENTERPRISE   cdx6500
		VARIABLES    { cdx6500SNMPLastTrap }
		DESCRIPTION
		     "IGMP.10 Multicast not enabled, IGMP shall not come up\r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327009

   	igmp-11-debug-trap  TRAP-TYPE
		ENTERPRISE   cdx6500
		VARIABLES    { cdx6500SNMPLastTrap }
		DESCRIPTION
		     "IGMP.11 %s\r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327010

   	igmp-12-debug-trap  TRAP-TYPE
		ENTERPRISE   cdx6500
		VARIABLES    { cdx6500SNMPLastTrap }
		DESCRIPTION
		     "IGMP.12 %s %x    %s  %x \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327011

   	igmp-13-null-context-block  TRAP-TYPE
		ENTERPRISE   cdx6500
		VARIABLES    { cdx6500SNMPLastTrap }
		DESCRIPTION
		     "IGMP.13 IP Context Block NULL \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327012

   	igmp-14-packet-received  TRAP-TYPE
		ENTERPRISE   cdx6500
		VARIABLES    { cdx6500SNMPLastTrap }
		DESCRIPTION
		     "IGMP.14 IGMP Packet received on  %d IGMP Circuit \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327013

   	igmp-15-membership-query  TRAP-TYPE
		ENTERPRISE   cdx6500
		VARIABLES    { cdx6500SNMPLastTrap }
		DESCRIPTION
		     "IGMP.15 IGMP Membership Query on %d IGMP Circuit \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327014

   	igmp-16-membership-report  TRAP-TYPE
		ENTERPRISE   cdx6500
		VARIABLES    { cdx6500SNMPLastTrap }
		DESCRIPTION
		     "IGMP.16 IGMP Membership Report(VER-1) on %d IGMP Circuit for %s Multicast Address\r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327015

   	igmp-17-membership-report-ver2  TRAP-TYPE
		ENTERPRISE   cdx6500
		VARIABLES    { cdx6500SNMPLastTrap }
		DESCRIPTION
		     "IGMP.17 IGMP Membership Report(VER-2) on %d IGMP Circuit for %s Multicast Address\r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327016

   	igmp-18-membership-leave-msg  TRAP-TYPE
		ENTERPRISE   cdx6500
		VARIABLES    { cdx6500SNMPLastTrap }
		DESCRIPTION
		     "IGMP.18 IGMP Membership Leave message on %d IGMP Circuit for %s Multicast Address \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327017

   	igmp-19-unknown-group-member  TRAP-TYPE
		ENTERPRISE   cdx6500
		VARIABLES    { cdx6500SNMPLastTrap }
		DESCRIPTION
		     "IGMP.19 IGMP Leave for Unknown grp memeber %s  on ckt %d \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327018

   	igmp-20-unknown-packet  TRAP-TYPE
		ENTERPRISE   cdx6500
		VARIABLES    { cdx6500SNMPLastTrap }
		DESCRIPTION
		     "IGMP.20 IGMP Unknown Packet type %d  on ckt %d \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327019

   	igmp-21-group-membership-timeout  TRAP-TYPE
		ENTERPRISE   cdx6500
		VARIABLES    { cdx6500SNMPLastTrap }
		DESCRIPTION
		     "IGMP.21 IGMP Group Membership Timeout \r\n"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 327020

        router-dvmrp1-dvmrpinit-called-w  TRAP-TYPE
		ENTERPRISE   cdx6500
		VARIABLES    { cdx6500SNMPLastTrap }
		DESCRIPTION
		     "DVMRP.1  dvmrp-init called with NULL rfcm Context Block\r\n"
		     --#TYPE
		     --#SUMMARY "Trap #$G, specific: $S, arg(1) : $1"
		     --#ARGUMENTS {}
		     --#SEVERITY  CRITICAL
		     --#TIMEINDEX
		     --#HELP
		     --#HELPTAG
		     --#STATE
		::= 328000

        router-dvmrp2-dvmrp-module-abort  TRAP-TYPE
		ENTERPRISE   cdx6500
		VARIABLES    { cdx6500SNMPLastTrap }
		DESCRIPTION
		     "DVMRP.2  DVMRP Module Aborted  not enough RAM\r\n"
		     --#TYPE
		     --#SUMMARY "Trap #$G, specific: $S, arg(1) : $1"
		     --#ARGUMENTS {}
		     --#SEVERITY  CRITICAL
		     --#TIMEINDEX
		     --#HELP
		     --#HELPTAG
		     --#STATE
		::= 328001

        tpa-tcp-not-enough-memory  TRAP-TYPE
		ENTERPRISE   cdx6500
		VARIABLES    { cdx6500SNMPLastTrap }
		DESCRIPTION
		     "TPA-TCP, NOT ENOUGH MEMORY"
		     --#TYPE
		     --#SUMMARY "Trap #$G, specific: $S, arg(1) : $1"
		     --#ARGUMENTS {}
		     --#SEVERITY  CRITICAL
		     --#TIMEINDEX
		     --#HELP
		     --#HELPTAG
		     --#STATE
		::= 329000

        tpa-connection-down22  TRAP-TYPE
		ENTERPRISE   cdx6500
		VARIABLES    { cdx6500SNMPLastTrap }
		DESCRIPTION
		     "%s - CONNECTION DOWN (%s)"
		     --#TYPE
		     --#SUMMARY "Trap #$G, specific: $S, arg(1) : $1"
		     --#ARGUMENTS {}
		     --#SEVERITY  CRITICAL
		     --#TIMEINDEX
		     --#HELP
		     --#HELPTAG
		     --#STATE
		::= 329001

        tpa-tcp-tcp-does-not-exist  TRAP-TYPE
		ENTERPRISE   cdx6500
		VARIABLES    { cdx6500SNMPLastTrap }
		DESCRIPTION
		     "TPA-TCP, TCP DOES NOT EXIST"
		     --#TYPE
		     --#SUMMARY "Trap #$G, specific: $S, arg(1) : $1"
		     --#ARGUMENTS {}
		     --#SEVERITY  CRITICAL
		     --#TIMEINDEX
		     --#HELP
		     --#HELPTAG
		     --#STATE
		::= 329002

        tpa-tpatcpqueue-fullpacket-dropp  TRAP-TYPE
		ENTERPRISE   cdx6500
		VARIABLES    { cdx6500SNMPLastTrap }
		DESCRIPTION
		     "TPA-TCP,QUEUE FULL,PACKET DROPPED"
		     --#TYPE
		     --#SUMMARY "Trap #$G, specific: $S, arg(1) : $1"
		     --#ARGUMENTS {}
		     --#SEVERITY  MAJOR
		     --#TIMEINDEX
		     --#HELP
		     --#HELPTAG
		     --#STATE
		::= 329003

        tpa-tpatcptcp-send-failed-connec  TRAP-TYPE
		ENTERPRISE   cdx6500
		VARIABLES    { cdx6500SNMPLastTrap }
		DESCRIPTION
		     "TPA-TCP,TCP-SEND FAILED ,CONNECTION DROPEED"
		     --#TYPE
		     --#SUMMARY "Trap #$G, specific: $S, arg(1) : $1"
		     --#ARGUMENTS {}
		     --#SEVERITY  CRITICAL
		     --#TIMEINDEX
		     --#HELP
		     --#HELPTAG
		     --#STATE
		::= 329004

        tpa-tpatcppacket-allocation-fail  TRAP-TYPE
		ENTERPRISE   cdx6500
		VARIABLES    { cdx6500SNMPLastTrap }
		DESCRIPTION
		     "TPA-TCP,PACKET ALLOCATION FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 329005

        tpa-tpatcpconnection-retries-ove  TRAP-TYPE
		ENTERPRISE   cdx6500
		VARIABLES    { cdx6500SNMPLastTrap }
		DESCRIPTION
		     "TPA-TCP,CONNECTION RETRIES OVER"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 329006

        tpa-tpatcptcp-listen-failed  TRAP-TYPE
		ENTERPRISE   cdx6500
		VARIABLES    { cdx6500SNMPLastTrap }
		DESCRIPTION
		     "TPA-TCP,TCP LISTEN FAILED"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 329007

        tpa-tpatcptcp-active-open-failed  TRAP-TYPE
		ENTERPRISE   cdx6500
		VARIABLES    { cdx6500SNMPLastTrap }
		DESCRIPTION
		     "TPA-TCP,TCP ACTIVE OPEN FAILED"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 329008

        tpa-tpatcppacket-with-m-bit-from  TRAP-TYPE
		ENTERPRISE   cdx6500
		VARIABLES    { cdx6500SNMPLastTrap }
		DESCRIPTION
		     "TPA-TCP,PACKET WITH M BIT FROM TPR RECEIVED"
		     --#TYPE
		     --#SUMMARY "Trap #$G, specific: $S, arg(1) : $1"
		     --#ARGUMENTS {}
		     --#SEVERITY  MAJOR
		     --#TIMEINDEX
		     --#HELP
		     --#HELPTAG
		     --#STATE
		::= 329009

        tpa-connection-up22  TRAP-TYPE
		ENTERPRISE   cdx6500
		VARIABLES    { cdx6500SNMPLastTrap }
		DESCRIPTION
		     "%s - CONNECTION UP"
		     --#TYPE
		     --#SUMMARY "Trap #$G, specific: $S, arg(1) : $1"
		     --#ARGUMENTS {}
		     --#SEVERITY  CRITICAL
		     --#TIMEINDEX
		     --#HELP
		     --#HELPTAG
		     --#STATE
		::= 329010

        tpa-timeout-from-tcp  TRAP-TYPE
		ENTERPRISE   cdx6500
		VARIABLES    { cdx6500SNMPLastTrap }
		DESCRIPTION
		     "%s - TIMEOUT FROM TCP"
		     --#TYPE
		     --#SUMMARY "Trap #$G, specific: $S, arg(1) : $1"
		     --#ARGUMENTS {}
		     --#SEVERITY  MAJOR
		     --#TIMEINDEX
		     --#HELP
		     --#HELPTAG
		     --#STATE
		::= 329011

        tpa-tpatcptcp-timeout-discarding  TRAP-TYPE
		ENTERPRISE   cdx6500
		VARIABLES    { cdx6500SNMPLastTrap }
		DESCRIPTION
		     "TPA-TCP,TCP TIMEOUT, DISCARDING PACKET(S)"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 329012

        tpa-connection-down222  TRAP-TYPE
		ENTERPRISE   cdx6500
		VARIABLES    { cdx6500SNMPLastTrap }
		DESCRIPTION
		     "%s - CONNECTION DOWN (%s)"
		     --#TYPE
		     --#SUMMARY "Trap #$G, specific: $S, arg(1) : $1"
		     --#ARGUMENTS {}
		     --#SEVERITY  CRITICAL
		     --#TIMEINDEX
		     --#HELP
		     --#HELPTAG
		     --#STATE
		::= 330000

        tpa-udp-not-enough-memory  TRAP-TYPE
		ENTERPRISE   cdx6500
		VARIABLES    { cdx6500SNMPLastTrap }
		DESCRIPTION
		     "TPA-UDP, NOT ENOUGH MEMORY"
		     --#TYPE
		     --#SUMMARY "Trap #$G, specific: $S, arg(1) : $1"
		     --#ARGUMENTS {}
		     --#SEVERITY  CRITICAL
		     --#TIMEINDEX
		     --#HELP
		     --#HELPTAG
		     --#STATE
		::= 330001

        tpa-udp-udp-does-not-exist  TRAP-TYPE
		ENTERPRISE   cdx6500
		VARIABLES    { cdx6500SNMPLastTrap }
		DESCRIPTION
		     "TPA-UDP, UDP DOES NOT EXIST"
		     --#TYPE
		     --#SUMMARY "Trap #$G, specific: $S, arg(1) : $1"
		     --#ARGUMENTS {}
		     --#SEVERITY  CRITICAL
		     --#TIMEINDEX
		     --#HELP
		     --#HELPTAG
		     --#STATE
		::= 330002

        tpa-udp-registration-with-udp-fa  TRAP-TYPE
		ENTERPRISE   cdx6500
		VARIABLES    { cdx6500SNMPLastTrap }
		DESCRIPTION
		     "TPA-UDP, REGISTRATION WITH UDP FAILED (%s)"
		     --#TYPE
		     --#SUMMARY "Trap #$G, specific: $S, arg(1) : $1"
		     --#ARGUMENTS {}
		     --#SEVERITY  CRITICAL
		     --#TIMEINDEX
		     --#HELP
		     --#HELPTAG
		     --#STATE
		::= 330003

        tpa-udp-registration-with-sip-fa  TRAP-TYPE
		ENTERPRISE   cdx6500
		VARIABLES    { cdx6500SNMPLastTrap }
		DESCRIPTION
		     "TPA-UDP, REGISTRATION WITH SIP FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 330004

        sotcp-init-failed-insufficient-m  TRAP-TYPE
		ENTERPRISE   cdx6500
		VARIABLES    { cdx6500SNMPLastTrap }
		DESCRIPTION
		     "SOTCP Init failed - Insufficient memory"
		     --#TYPE
		     --#SUMMARY "Trap #$G, specific: $S, arg(1) : $1"
		     --#ARGUMENTS {}
		     --#SEVERITY  CRITICAL
		     --#TIMEINDEX
		     --#HELP
		     --#HELPTAG
		     --#STATE
		::= 331000

        sotcp-init-failed-software-absen  TRAP-TYPE
		ENTERPRISE   cdx6500
		VARIABLES    { cdx6500SNMPLastTrap }
		DESCRIPTION
		     "SOTCP Init failed - Software absent"
		     --#TYPE
		     --#SUMMARY "Trap #$G, specific: $S, arg(1) : $1"
		     --#ARGUMENTS {}
		     --#SEVERITY  CRITICAL
		     --#TIMEINDEX
		     --#HELP
		     --#HELPTAG
		     --#STATE
		::= 331001

        sotcp-no-more-tcp-sessions  TRAP-TYPE
		ENTERPRISE   cdx6500
		VARIABLES    { cdx6500SNMPLastTrap }
		DESCRIPTION
		     "SOTCP - No more TCP sessions"
		     --#TYPE
		     --#SUMMARY "Trap #$G, specific: $S, arg(1) : $1"
		     --#ARGUMENTS {}
		     --#SEVERITY  CRITICAL
		     --#TIMEINDEX
		     --#HELP
		     --#HELPTAG
		     --#STATE
		::= 331002

        sotcp-tcp-listen-failed-trying-a  TRAP-TYPE
		ENTERPRISE   cdx6500
		VARIABLES    { cdx6500SNMPLastTrap }
		DESCRIPTION
		     "SOTCP - TCP Listen failed, trying after a while"
		     --#TYPE
		     --#SUMMARY "Trap #$G, specific: $S, arg(1) : $1"
		     --#ARGUMENTS {}
		     --#SEVERITY  MAJOR
		     --#TIMEINDEX
		     --#HELP
		     --#HELPTAG
		     --#STATE
		::= 331003

        sotcp-tcp-receive-failed-session  TRAP-TYPE
		ENTERPRISE   cdx6500
		VARIABLES    { cdx6500SNMPLastTrap }
		DESCRIPTION
		     "SOTCP-%d - TCP receive failed, session aborted"
		     --#TYPE
		     --#SUMMARY "Trap #$G, specific: $S, arg(1) : $1"
		     --#ARGUMENTS {}
		     --#SEVERITY  CRITICAL
		     --#TIMEINDEX
		     --#HELP
		     --#HELPTAG
		     --#STATE
		::= 331004

        sotcp-invalid-packet  TRAP-TYPE
		ENTERPRISE   cdx6500
		VARIABLES    { cdx6500SNMPLastTrap }
		DESCRIPTION
		     "SOTCP-%d - Invalid packet - %s"
		     --#TYPE
		     --#SUMMARY "Trap #$G, specific: $S, arg(1) : $1"
		     --#ARGUMENTS {}
		     --#SEVERITY  MINOR
		     --#TIMEINDEX
		     --#HELP
		     --#HELPTAG
		     --#STATE
		::= 331005

        sotcp-tcp-active-open-failed-wit  TRAP-TYPE
		ENTERPRISE   cdx6500
		VARIABLES    { cdx6500SNMPLastTrap }
		DESCRIPTION
		     "SOTCP-%d - TCP Active open failed with %s"
		     --#TYPE
		     --#SUMMARY "Trap #$G, specific: $S, arg(1) : $1"
		     --#ARGUMENTS {}
		     --#SEVERITY  CRITICAL
		     --#TIMEINDEX
		     --#HELP
		     --#HELPTAG
		     --#STATE
		::= 331006

        sotcp-tcp-session-established-wi  TRAP-TYPE
		ENTERPRISE   cdx6500
		VARIABLES    { cdx6500SNMPLastTrap }
		DESCRIPTION
		     "SOTCP-%d - TCP session established with destination %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 331007

        sotcp-memory-allocation-failed  TRAP-TYPE
		ENTERPRISE   cdx6500
		VARIABLES    { cdx6500SNMPLastTrap }
		DESCRIPTION
		     "SOTCP-%d - Memory allocation failed"
		     --#TYPE
		     --#SUMMARY "Trap #$G, specific: $S, arg(1) : $1"
		     --#ARGUMENTS {}
		     --#SEVERITY  CRITICAL
		     --#TIMEINDEX
		     --#HELP
		     --#HELPTAG
		     --#STATE
		::= 331008

        sotcp-no-more-connections  TRAP-TYPE
		ENTERPRISE   cdx6500
		VARIABLES    { cdx6500SNMPLastTrap }
		DESCRIPTION
		     "SOTCP-%d - No more connections"
		     --#TYPE
		     --#SUMMARY "Trap #$G, specific: $S, arg(1) : $1"
		     --#ARGUMENTS {}
		     --#SEVERITY  CRITICAL
		     --#TIMEINDEX
		     --#HELP
		     --#HELPTAG
		     --#STATE
		::= 331009

        sotcp-tcp-session-timed-out-with  TRAP-TYPE
		ENTERPRISE   cdx6500
		VARIABLES    { cdx6500SNMPLastTrap }
		DESCRIPTION
		     "SOTCP-%d - TCP session timed out with %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 331010

        sotcp-tcp-session-closed-by-the  TRAP-TYPE
		ENTERPRISE   cdx6500
		VARIABLES    { cdx6500SNMPLastTrap }
		DESCRIPTION
		     "SOTCP-%d - TCP session closed by the remote end"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 331011

        sotcp-session-closed  TRAP-TYPE
		ENTERPRISE   cdx6500
		VARIABLES    { cdx6500SNMPLastTrap }
		DESCRIPTION
		     "SOTCP-%d Session closed"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 331012

        sotcp-new-connection-with-connec  TRAP-TYPE
		ENTERPRISE   cdx6500
		VARIABLES    { cdx6500SNMPLastTrap }
		DESCRIPTION
		     "SOTCP-%d - New connection with connection id %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 331013

        sotcp-c-packet-allocation-failed  TRAP-TYPE
		ENTERPRISE   cdx6500
		VARIABLES    { cdx6500SNMPLastTrap }
		DESCRIPTION
		     "SOTCP-%dC%d - Packet allocation failed"
		     --#TYPE
		     --#SUMMARY "Trap #$G, specific: $S, arg(1) : $1"
		     --#ARGUMENTS {}
		     --#SEVERITY  MINOR
		     --#TIMEINDEX
		     --#HELP
		     --#HELPTAG
		     --#STATE
		::= 331014

        sotcp-c-serial-protocol-blocked  TRAP-TYPE
		ENTERPRISE   cdx6500
		VARIABLES    { cdx6500SNMPLastTrap }
		DESCRIPTION
		     "SOTCP-%dC%d - Serial protocol blocked"
		     --#TYPE
		     --#SUMMARY "Trap #$G, specific: $S, arg(1) : $1"
		     --#ARGUMENTS {}
		     --#SEVERITY  MAJOR
		     --#TIMEINDEX
		     --#HELP
		     --#HELPTAG
		     --#STATE
		::= 331015

        sotcp-no-matching-ip-peer-for  TRAP-TYPE
		ENTERPRISE   cdx6500
		VARIABLES    { cdx6500SNMPLastTrap }
		DESCRIPTION
		     "SOTCP - No matching IP peer for %s"
		     --#TYPE
		     --#SUMMARY "Trap #$G, specific: $S, arg(1) : $1"
		     --#ARGUMENTS {}
		     --#SEVERITY  MAJOR
		     --#TIMEINDEX
		     --#HELP
		     --#HELPTAG
		     --#STATE
		::= 331016

        sotcp-queue-toward-tcp-blocked  TRAP-TYPE
		ENTERPRISE   cdx6500
		VARIABLES    { cdx6500SNMPLastTrap }
		DESCRIPTION
		     "SOTCP-%d : Queue toward TCP blocked"
		     --#TYPE
		     --#SUMMARY "Trap #$G, specific: $S, arg(1) : $1"
		     --#ARGUMENTS {}
		     --#SEVERITY  MAJOR
		     --#TIMEINDEX
		     --#HELP
		     --#HELPTAG
		     --#STATE
		::= 331017

        sotcp-queue-toward-tcp-unblocked  TRAP-TYPE
		ENTERPRISE   cdx6500
		VARIABLES    { cdx6500SNMPLastTrap }
		DESCRIPTION
		     "SOTCP-%d : Queue toward TCP unblocked"
		     --#TYPE
		     --#SUMMARY "Trap #$G, specific: $S, arg(1) : $1"
		     --#ARGUMENTS {}
		     --#SEVERITY  MAJOR
		     --#TIMEINDEX
		     --#HELP
		     --#HELPTAG
		     --#STATE
		::= 331018

        sotcp-c-data-loss-due-to-queue-o  TRAP-TYPE
		ENTERPRISE   cdx6500
		VARIABLES    { cdx6500SNMPLastTrap }
		DESCRIPTION
		     "SOTCP-%dC%d - Data loss due to queue overflow"
		     --#TYPE
		     --#SUMMARY "Trap #$G, specific: $S, arg(1) : $1"
		     --#ARGUMENTS {}
		     --#SEVERITY  MAJOR
		     --#TIMEINDEX
		     --#HELP
		     --#HELPTAG
		     --#STATE
		::= 331019

        sotcp-udp-registration-failure  TRAP-TYPE
		ENTERPRISE   cdx6500
		VARIABLES    { cdx6500SNMPLastTrap }
		DESCRIPTION
		     "SOTCP: UDP registration failure"
		     --#TYPE
		     --#SUMMARY "Trap #$G, specific: $S, arg(1) : $1"
		     --#ARGUMENTS {}
		     --#SEVERITY  CRITICAL
		     --#TIMEINDEX
		     --#HELP
		     --#HELPTAG
		     --#STATE
		::= 331020

        sotcp-c-remote-does-not-support  TRAP-TYPE
		ENTERPRISE   cdx6500
		VARIABLES    { cdx6500SNMPLastTrap }
		DESCRIPTION
		     "SOTCP-%dC%d - Remote does not support pkt type %s"
		     --#TYPE
		     --#SUMMARY "Trap #$G, specific: $S, arg(1) : $1"
		     --#ARGUMENTS {}
		     --#SEVERITY  CRITICAL
		     --#TIMEINDEX
		     --#HELP
		     --#HELPTAG
		     --#STATE
		::= 331021

        sotcp-init-failed-idcm-init-fail  TRAP-TYPE
		ENTERPRISE   cdx6500
		VARIABLES    { cdx6500SNMPLastTrap }
		DESCRIPTION
		     "SOTCP Init failed - IDCM init failed"
		     --#TYPE
		     --#SUMMARY "Trap #$G, specific: $S, arg(1) : $1"
		     --#ARGUMENTS {}
		     --#SEVERITY  CRITICAL
		     --#TIMEINDEX
		     --#HELP
		     --#HELPTAG
		     --#STATE
		::= 331022

        sotcp-udp-module-absent-voice  TRAP-TYPE
		ENTERPRISE   cdx6500
		VARIABLES    { cdx6500SNMPLastTrap }
		DESCRIPTION
		     "UDP module absent : Voice over SOTCP not supported"
		     --#TYPE
		     --#SUMMARY "Trap #$G, specific: $S, arg(1) : $1"
		     --#ARGUMENTS {}
		     --#SEVERITY  CRITICAL
		     --#TIMEINDEX
		     --#HELP
		     --#HELPTAG
		     --#STATE
		::= 331023

	sotcp331024-sotcp-ma   TRAP-TYPE
		ENTERPRISE   cdx6500
		VARIABLES    { cdx6500SNMPLastTrap }
		DESCRIPTION
		     "SOTCP Maximum Sessions Reduced to %d - Insufficient memory"
		     --#TYPE
		     --#SUMMARY "Trap #$G, specific: $S, arg(1) : $1"
		     --#ARGUMENTS {}
		     --#SEVERITY  CRITICAL
		     --#TIMEINDEX
		     --#HELP
		     --#HELPTAG
		     --#STATE
		::= 331024

	sotcp331025-sotcp-c   TRAP-TYPE
		ENTERPRISE   cdx6500
		VARIABLES    { cdx6500SNMPLastTrap }
		DESCRIPTION
		     "SOTCP-%dC%d - Routing loop or maximum hop count exceeded."
		     --#TYPE
		     --#SUMMARY "Trap #$G, specific: $S, arg(1) : $1"
		     --#ARGUMENTS {}
		     --#SEVERITY  INFORMATIONAL
		     --#TIMEINDEX
		     --#HELP
		     --#HELPTAG
		     --#STATE
		::= 331025

	sotcp331026-sotcp-cr   TRAP-TYPE
		ENTERPRISE   cdx6500
		VARIABLES    { cdx6500SNMPLastTrap }
		DESCRIPTION
		     "SOTCP-%sC%s - Routing loop or maximum hop count exceeded."
		     --#TYPE
		     --#SUMMARY "Trap #$G, specific: $S, arg(1) : $1"
		     --#ARGUMENTS {}
		     --#SEVERITY  INFORMATIONAL
		     --#TIMEINDEX
		     --#HELP
		     --#HELPTAG
		     --#STATE
		::= 331026

        flash-multi-config-request  TRAP-TYPE
		ENTERPRISE   cdx6500
		VARIABLES    { cdx6500SNMPLastTrap }
		DESCRIPTION
		     "MULTI-CONFIG: %s request to change to Image #%d, '%s'"
		     --#TYPE
		     --#SUMMARY "Trap #$G, specific: $S, arg(1) : $1"
		     --#ARGUMENTS {}
		     --#SEVERITY  CRITICAL
		     --#TIMEINDEX
		     --#HELP
		     --#HELPTAG
		     --#STATE
		::= 332000

        vconfig-voice-port-failed-to-dow  TRAP-TYPE
		ENTERPRISE   cdx6500
		VARIABLES    { cdx6500SNMPLastTrap }
		DESCRIPTION
		     "VOICE PORT %s FAILED TO DOWNLOAD CONFIGURED VSM IMAGE"
		     --#TYPE
		     --#SUMMARY "Trap #$G, specific: $S, arg(1) : $1"
		     --#ARGUMENTS {}
		     --#SEVERITY  CRITICAL
		     --#TIMEINDEX
		     --#HELP
		     --#HELPTAG
		     --#STATE
		::= 335000

        vconfig-voice-port-boot-complete  TRAP-TYPE
		ENTERPRISE   cdx6500
		VARIABLES    { cdx6500SNMPLastTrap }
		DESCRIPTION
		     "VOICE PORT %s BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 335001

        vr-download-failed-insuf-memory  TRAP-TYPE
		ENTERPRISE   cdx6500
		VARIABLES    { cdx6500SNMPLastTrap }
		DESCRIPTION
		     "DOWNLOAD FAILED: INSUF. MEMORY FOR %s"
		     --#TYPE
		     --#SUMMARY "Trap #$G, specific: $S, arg(1) : $1"
		     --#ARGUMENTS {}
		     --#SEVERITY  CRITICAL
		     --#TIMEINDEX
		     --#HELP
		     --#HELPTAG
		     --#STATE
		::= 339000

        vr-download-failed-vsmio  TRAP-TYPE
		ENTERPRISE   cdx6500
		VARIABLES    { cdx6500SNMPLastTrap }
		DESCRIPTION
		     "DOWNLOAD FAILED: VSMIO OPERATION FAILED"
		     --#TYPE
		     --#SUMMARY "Trap #$G, specific: $S, arg(1) : $1"
		     --#ARGUMENTS {}
		     --#SEVERITY  CRITICAL
		     --#TIMEINDEX
		     --#HELP
		     --#HELPTAG
		     --#STATE
		::= 339001

	vr339002-download-fa   TRAP-TYPE
		ENTERPRISE   cdx6500
		VARIABLES    { cdx6500SNMPLastTrap }
		DESCRIPTION
		     "DOWNLOAD FAILED: VIRTUAL PORT - %d"
		     --#TYPE
		     --#SUMMARY "Trap #$G, specific: $S, arg(1) : $1"
		     --#ARGUMENTS {}
		     --#SEVERITY  CRITICAL
		     --#TIMEINDEX
		     --#HELP
		     --#HELPTAG
		     --#STATE
		::= 339002

	vhardware340000-vhwv   TRAP-TYPE
		ENTERPRISE   cdx6500
		VARIABLES    { cdx6500SNMPLastTrap }
		DESCRIPTION
		     "V-HWVRDC : %s"
		     --#TYPE
		     --#SUMMARY "Trap #$G, specific: $S, arg(1) : $1"
		     --#ARGUMENTS {}
		     --#SEVERITY  CRITICAL
		     --#TIMEINDEX
		     --#HELP
		     --#HELPTAG
		     --#STATE
		::= 340000

        idim-port-i430-dim-installed-on  TRAP-TYPE
		ENTERPRISE   cdx6500
		VARIABLES    { cdx6500SNMPLastTrap }
		DESCRIPTION
		     "PORT-%d - I.430 DIM INSTALLED ON INVALID PORT"
		     --#TYPE
		     --#SUMMARY "Trap #$G, specific: $S, arg(1) : $1"
		     --#ARGUMENTS {}
		     --#SEVERITY  CRITICAL
		     --#TIMEINDEX
		     --#HELP
		     --#HELPTAG
		     --#STATE
		::= 341000

        idim-i430-dim-in-sync  TRAP-TYPE
		ENTERPRISE   cdx6500
		VARIABLES    { cdx6500SNMPLastTrap }
		DESCRIPTION
		     "%s - I.430 DIM IN SYNC"
		     --#TYPE
		     --#SUMMARY "Trap #$G, specific: $S, arg(1) : $1"
		     --#ARGUMENTS {}
		     --#SEVERITY  CRITICAL
		     --#TIMEINDEX
		     --#HELP
		     --#HELPTAG
		     --#STATE
		::= 341001

        idim-i430-dim-out-of-sync  TRAP-TYPE
		ENTERPRISE   cdx6500
		VARIABLES    { cdx6500SNMPLastTrap }
		DESCRIPTION
		     "%s - I.430 DIM OUT OF SYNC"
		     --#TYPE
		     --#SUMMARY "Trap #$G, specific: $S, arg(1) : $1"
		     --#ARGUMENTS {}
		     --#SEVERITY  CRITICAL
		     --#TIMEINDEX
		     --#HELP
		     --#HELPTAG
		     --#STATE
		::= 341002

        h323-internal-error  TRAP-TYPE
		ENTERPRISE   cdx6500
		VARIABLES    { cdx6500SNMPLastTrap }
		DESCRIPTION
		     "H323 Internal Error: %s"
		     --#TYPE
		     --#SUMMARY "Trap #$G, specific: $S, arg(1) : $1"
		     --#ARGUMENTS {}
		     --#SEVERITY  CRITICAL
		     --#TIMEINDEX
		     --#HELP
		     --#HELPTAG
		     --#STATE
		::= 342000

        h323-error  TRAP-TYPE
		ENTERPRISE   cdx6500
		VARIABLES    { cdx6500SNMPLastTrap }
		DESCRIPTION
		     "H323 Error: %s"
		     --#TYPE
		     --#SUMMARY "Trap #$G, specific: $S, arg(1) : $1"
		     --#ARGUMENTS {}
		     --#SEVERITY  CRITICAL
		     --#TIMEINDEX
		     --#HELP
		     --#HELPTAG
		     --#STATE
		::= 342001

        h323-ip-error  TRAP-TYPE
		ENTERPRISE   cdx6500
		VARIABLES    { cdx6500SNMPLastTrap }
		DESCRIPTION
		     "H323 IP Error: %s %s"
		     --#TYPE
		     --#SUMMARY "Trap #$G, specific: $S, arg(1) : $1"
		     --#ARGUMENTS {}
		     --#SEVERITY  CRITICAL
		     --#TIMEINDEX
		     --#HELP
		     --#HELPTAG
		     --#STATE
		::= 342002

        h323-h323  TRAP-TYPE
		ENTERPRISE   cdx6500
		VARIABLES    { cdx6500SNMPLastTrap }
		DESCRIPTION
		     "H323 %s (%s) %s->%s"
		     --#TYPE
		     --#SUMMARY "Trap #$G, specific: $S, arg(1) : $1"
		     --#ARGUMENTS {}
		     --#SEVERITY  MAJOR
		     --#TIMEINDEX
		     --#HELP
		     --#HELPTAG
		     --#STATE
		::= 342003

        h323-not-hdld-in  TRAP-TYPE
		ENTERPRISE   cdx6500
		VARIABLES    { cdx6500SNMPLastTrap }
		DESCRIPTION
		     "H323 %s (%s) not hdld in %s"
		     --#TYPE
		     --#SUMMARY "Trap #$G, specific: $S, arg(1) : $1"
		     --#ARGUMENTS {}
		     --#SEVERITY  MAJOR
		     --#TIMEINDEX
		     --#HELP
		     --#HELPTAG
		     --#STATE
		::= 342004

        h323-qsig-msg-not-handled  TRAP-TYPE
		ENTERPRISE   cdx6500
		VARIABLES    { cdx6500SNMPLastTrap }
		DESCRIPTION
		     "H323 QSIG msg not handled: %d"
		     --#TYPE
		     --#SUMMARY "Trap #$G, specific: $S, arg(1) : $1"
		     --#ARGUMENTS {}
		     --#SEVERITY  MAJOR
		     --#TIMEINDEX
		     --#HELP
		     --#HELPTAG
		     --#STATE
		::= 342005

        h323-tcp  TRAP-TYPE
		ENTERPRISE   cdx6500
		VARIABLES    { cdx6500SNMPLastTrap }
		DESCRIPTION
		     "H323 TCP(%d): %s"
		     --#TYPE
		     --#SUMMARY "Trap #$G, specific: $S, arg(1) : $1"
		     --#ARGUMENTS {}
		     --#SEVERITY  MINOR
		     --#TIMEINDEX
		     --#HELP
		     --#HELPTAG
		     --#STATE
		::= 342006

        h323-msd-error  TRAP-TYPE
		ENTERPRISE   cdx6500
		VARIABLES    { cdx6500SNMPLastTrap }
		DESCRIPTION
		     "H323 MSD error: %s (%d:%d)"
		     --#TYPE
		     --#SUMMARY "Trap #$G, specific: $S, arg(1) : $1"
		     --#ARGUMENTS {}
		     --#SEVERITY  CRITICAL
		     --#TIMEINDEX
		     --#HELP
		     --#HELPTAG
		     --#STATE
		::= 342007

        h323-rtp-discard  TRAP-TYPE
		ENTERPRISE   cdx6500
		VARIABLES    { cdx6500SNMPLastTrap }
		DESCRIPTION
		     "H323 RTP Discard: %s"
		     --#TYPE
		     --#SUMMARY "Trap #$G, specific: $S, arg(1) : $1"
		     --#ARGUMENTS {}
		     --#SEVERITY  CRITICAL
		     --#TIMEINDEX
		     --#HELP
		     --#HELPTAG
		     --#STATE
		::= 342008

        h323-unknown-rtp-payload-type  TRAP-TYPE
		ENTERPRISE   cdx6500
		VARIABLES    { cdx6500SNMPLastTrap }
		DESCRIPTION
		     "H323 Unknown RTP payload type 0x%02X"
		     --#TYPE
		     --#SUMMARY "Trap #$G, specific: $S, arg(1) : $1"
		     --#ARGUMENTS {}
		     --#SEVERITY  CRITICAL
		     --#TIMEINDEX
		     --#HELP
		     --#HELPTAG
		     --#STATE
		::= 342009

        h323-sequence-numbers  TRAP-TYPE
		ENTERPRISE   cdx6500
		VARIABLES    { cdx6500SNMPLastTrap }
		DESCRIPTION
		     "H323 Sequence numbers: %d %d"
		     --#TYPE
		     --#SUMMARY "Trap #$G, specific: $S, arg(1) : $1"
		     --#ARGUMENTS {}
		     --#SEVERITY  CRITICAL
		     --#TIMEINDEX
		     --#HELP
		     --#HELPTAG
		     --#STATE
		::= 342010

        h323-ssrc-mismatch  TRAP-TYPE
		ENTERPRISE   cdx6500
		VARIABLES    { cdx6500SNMPLastTrap }
		DESCRIPTION
		     "H323 SSRC mismatch: 0x%08X 0x%08X"
		     --#TYPE
		     --#SUMMARY "Trap #$G, specific: $S, arg(1) : $1"
		     --#ARGUMENTS {}
		     --#SEVERITY  CRITICAL
		     --#TIMEINDEX
		     --#HELP
		     --#HELPTAG
		     --#STATE
		::= 342011

	h323342012-h323-unhandled-msg   TRAP-TYPE
		ENTERPRISE   cdx6500
		VARIABLES    { cdx6500SNMPLastTrap }
		DESCRIPTION
		     "H323 Unhandled message in %s: %d"
		     --#TYPE
		     --#SUMMARY "Trap #$G, specific: $S, arg(1) : $1"
		     --#ARGUMENTS {}
		     --#SEVERITY  CRITICAL
		     --#TIMEINDEX
		     --#HELP
		     --#HELPTAG
		     --#STATE
		::= 342012

	h323342014-info   TRAP-TYPE
		ENTERPRISE   cdx6500
		VARIABLES    { cdx6500SNMPLastTrap }
		DESCRIPTION
		     "%s Info: %s"
		     --#TYPE
		     --#SUMMARY "Trap #$G, specific: $S, arg(1) : $1"
		     --#ARGUMENTS {}
		     --#SEVERITY  MINOR
		     --#TIMEINDEX
		     --#HELP
		     --#HELPTAG
		     --#STATE
		::= 342014

        tpa-tpa2780-connected  TRAP-TYPE
		ENTERPRISE   cdx6500
		VARIABLES    { cdx6500SNMPLastTrap }
		DESCRIPTION
		     "%s - TPA2780 CONNECTED"
		     --#TYPE
		     --#SUMMARY "Trap #$G, specific: $S, arg(1) : $1"
		     --#ARGUMENTS {}
		     --#SEVERITY  CRITICAL
		     --#TIMEINDEX
		     --#HELP
		     --#HELPTAG
		     --#STATE
		::= 343000

        tpa-tpa2780-disconnected  TRAP-TYPE
		ENTERPRISE   cdx6500
		VARIABLES    { cdx6500SNMPLastTrap }
		DESCRIPTION
		     "%s - TPA2780 DISCONNECTED"
		     --#TYPE
		     --#SUMMARY "Trap #$G, specific: $S, arg(1) : $1"
		     --#ARGUMENTS {}
		     --#SEVERITY  CRITICAL
		     --#TIMEINDEX
		     --#HELP
		     --#HELPTAG
		     --#STATE
		::= 343001

        tpa-connection-up222  TRAP-TYPE
		ENTERPRISE   cdx6500
		VARIABLES    { cdx6500SNMPLastTrap }
		DESCRIPTION
		     "%s - CONNECTION UP"
		     --#TYPE
		     --#SUMMARY "Trap #$G, specific: $S, arg(1) : $1"
		     --#ARGUMENTS {}
		     --#SEVERITY  CRITICAL
		     --#TIMEINDEX
		     --#HELP
		     --#HELPTAG
		     --#STATE
		::= 344000

        tpa-connection-down2222  TRAP-TYPE
		ENTERPRISE   cdx6500
		VARIABLES    { cdx6500SNMPLastTrap }
		DESCRIPTION
		     "%s - CONNECTION DOWN (%s)"
		     --#TYPE
		     --#SUMMARY "Trap #$G, specific: $S, arg(1) : $1"
		     --#ARGUMENTS {}
		     --#SEVERITY  CRITICAL
		     --#TIMEINDEX
		     --#HELP
		     --#HELPTAG
		     --#STATE
		::= 344001

        tpa-connection-is-in-progress2  TRAP-TYPE
		ENTERPRISE   cdx6500
		VARIABLES    { cdx6500SNMPLastTrap }
		DESCRIPTION
		     "%s - CONNECTION IS IN PROGRESS"
		     --#TYPE
		     --#SUMMARY "Trap #$G, specific: $S, arg(1) : $1"
		     --#ARGUMENTS {}
		     --#SEVERITY  MINOR
		     --#TIMEINDEX
		     --#HELP
		     --#HELPTAG
		     --#STATE
		::= 344002

        tpa-clearing-call-remote-station  TRAP-TYPE
		ENTERPRISE   cdx6500
		VARIABLES    { cdx6500SNMPLastTrap }
		DESCRIPTION
		     "%s - CLEARING CALL, REMOTE STATION DOWN RECEIVED(%s)"
		     --#TYPE
		     --#SUMMARY "Trap #$G, specific: $S, arg(1) : $1"
		     --#ARGUMENTS {}
		     --#SEVERITY  CRITICAL
		     --#TIMEINDEX
		     --#HELP
		     --#HELPTAG
		     --#STATE
		::= 344003

        tpa-fra-not-enough-memory  TRAP-TYPE
		ENTERPRISE   cdx6500
		VARIABLES    { cdx6500SNMPLastTrap }
		DESCRIPTION
		     "TPA-FRA, NOT ENOUGH MEMORY"
		     --#TYPE
		     --#SUMMARY "Trap #$G, specific: $S, arg(1) : $1"
		     --#ARGUMENTS {}
		     --#SEVERITY  CRITICAL
		     --#TIMEINDEX
		     --#HELP
		     --#HELPTAG
		     --#STATE
		::= 344004

        tpa-fra-idcm-or-tgo-does-not-exi  TRAP-TYPE
		ENTERPRISE   cdx6500
		VARIABLES    { cdx6500SNMPLastTrap }
		DESCRIPTION
		     "TPA-FRA, IDCM OR TGO DOES NOT EXIST"
		     --#TYPE
		     --#SUMMARY "Trap #$G, specific: $S, arg(1) : $1"
		     --#ARGUMENTS {}
		     --#SEVERITY  CRITICAL
		     --#TIMEINDEX
		     --#HELP
		     --#HELPTAG
		     --#STATE
		::= 344005

        tpa-fra-idcm-not-up  TRAP-TYPE
		ENTERPRISE   cdx6500
		VARIABLES    { cdx6500SNMPLastTrap }
		DESCRIPTION
		     "TPA-FRA, IDCM NOT UP"
		     --#TYPE
		     --#SUMMARY "Trap #$G, specific: $S, arg(1) : $1"
		     --#ARGUMENTS {}
		     --#SEVERITY  CRITICAL
		     --#TIMEINDEX
		     --#HELP
		     --#HELPTAG
		     --#STATE
		::= 344006

        tpa-clearing-call-bad-response  TRAP-TYPE
		ENTERPRISE   cdx6500
		VARIABLES    { cdx6500SNMPLastTrap }
		DESCRIPTION
		     "%s - CLEARING CALL, BAD RESPONSE"
		     --#TYPE
		     --#SUMMARY "Trap #$G, specific: $S, arg(1) : $1"
		     --#ARGUMENTS {}
		     --#SEVERITY  CRITICAL
		     --#TIMEINDEX
		     --#HELP
		     --#HELPTAG
		     --#STATE
		::= 344007

        router-udp-registration-failure  TRAP-TYPE
		ENTERPRISE   cdx6500
		VARIABLES    { cdx6500SNMPLastTrap }
		DESCRIPTION
		     "UDP Registration Failure"
		     --#TYPE
		     --#SUMMARY "Trap #$G, specific: $S, arg(1) : $1"
		     --#ARGUMENTS {}
		     --#SEVERITY  CRITICAL
		     --#TIMEINDEX
		     --#HELP
		     --#HELPTAG
		     --#STATE
		::= 347000

        router-proxy-ignoredip-interface  TRAP-TYPE
		ENTERPRISE   cdx6500
		VARIABLES    { cdx6500SNMPLastTrap }
		DESCRIPTION
		     "Proxy %d Ignored.IP interface not available"
		     --#TYPE
		     --#SUMMARY "Trap #$G, specific: $S, arg(1) : $1"
		     --#ARGUMENTS {}
		     --#SEVERITY  CRITICAL
		     --#TIMEINDEX
		     --#HELP
		     --#HELPTAG
		     --#STATE
		::= 347001

        router-proxy-ignored-has-duplica  TRAP-TYPE
		ENTERPRISE   cdx6500
		VARIABLES    { cdx6500SNMPLastTrap }
		DESCRIPTION
		     "Proxy %d Ignored. Has duplicated IP address or Mac Address"
		     --#TYPE
		     --#SUMMARY "Trap #$G, specific: $S, arg(1) : $1"
		     --#ARGUMENTS {}
		     --#SEVERITY  CRITICAL
		     --#TIMEINDEX
		     --#HELP
		     --#HELPTAG
		     --#STATE
		::= 347002

        router-proxy-specifying-interfac  TRAP-TYPE
		ENTERPRISE   cdx6500
		VARIABLES    { cdx6500SNMPLastTrap }
		DESCRIPTION
		     "Proxy specifying interface %d  Mac Address is deactivated"
		     --#TYPE
		     --#SUMMARY "Trap #$G, specific: $S, arg(1) : $1"
		     --#ARGUMENTS {}
		     --#SEVERITY  CRITICAL
		     --#TIMEINDEX
		     --#HELP
		     --#HELPTAG
		     --#STATE
		::= 347003

        router-proxies-restarted  TRAP-TYPE
		ENTERPRISE   cdx6500
		VARIABLES    { cdx6500SNMPLastTrap }
		DESCRIPTION
		     "Proxies on interface %d are Restarted"
		     --#TYPE
		     --#SUMMARY "Trap #$G, specific: $S, arg(1) : $1"
		     --#ARGUMENTS {}
		     --#SEVERITY  CRITICAL
		     --#TIMEINDEX
		     --#HELP
		     --#HELPTAG
		     --#STATE
		::= 347004

        router-proxy-enabled  TRAP-TYPE
		ENTERPRISE   cdx6500
		VARIABLES    { cdx6500SNMPLastTrap }
		DESCRIPTION
		     "Proxy for %s on interface %d is Enabled"
		     --#TYPE
		     --#SUMMARY "Trap #$G, specific: $S, arg(1) : $1"
		     --#ARGUMENTS {}
		     --#SEVERITY  CRITICAL
		     --#TIMEINDEX
		     --#HELP
		     --#HELPTAG
		     --#STATE
		::= 347005

        router-proxy-disabled  TRAP-TYPE
		ENTERPRISE   cdx6500
		VARIABLES    { cdx6500SNMPLastTrap }
		DESCRIPTION
		     "Proxy for %s on interface %d is Disabled"
		     --#TYPE
		     --#SUMMARY "Trap #$G, specific: $S, arg(1) : $1"
		     --#ARGUMENTS {}
		     --#SEVERITY  CRITICAL
		     --#TIMEINDEX
		     --#HELP
		     --#HELPTAG
		     --#STATE
		::= 347006

        ac100-port-boot-complete  TRAP-TYPE
		ENTERPRISE   cdx6500
		VARIABLES    { cdx6500SNMPLastTrap }
		DESCRIPTION
		     "%s - PORT BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 351000

        ac100-port-boot-failure  TRAP-TYPE
		ENTERPRISE   cdx6500
		VARIABLES    { cdx6500SNMPLastTrap }
		DESCRIPTION
		     "%s - PORT BOOT FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 351001

        ac100-port-disabled  TRAP-TYPE
		ENTERPRISE   cdx6500
		VARIABLES    { cdx6500SNMPLastTrap }
		DESCRIPTION
		     "%s - PORT DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 351002

        ac100-port-disable-failure  TRAP-TYPE
		ENTERPRISE   cdx6500
		VARIABLES    { cdx6500SNMPLastTrap }
		DESCRIPTION
		     "%s - PORT DISABLE FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 351003

        ac100-port-enabled  TRAP-TYPE
		ENTERPRISE   cdx6500
		VARIABLES    { cdx6500SNMPLastTrap }
		DESCRIPTION
		     "%s - PORT ENABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 351004

        ac100-port-enable-failure  TRAP-TYPE
		ENTERPRISE   cdx6500
		VARIABLES    { cdx6500SNMPLastTrap }
		DESCRIPTION
		     "%s - PORT ENABLE FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 351005

        ac100-port-status-warning  TRAP-TYPE
		ENTERPRISE   cdx6500
		VARIABLES    { cdx6500SNMPLastTrap }
		DESCRIPTION
		     "%s - PORT STATUS WARNING - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 351006

        ac100-site-boot-complete  TRAP-TYPE
		ENTERPRISE   cdx6500
		VARIABLES    { cdx6500SNMPLastTrap }
		DESCRIPTION
		     "%s - SITE BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 351007

        ac100-site-boot-failure  TRAP-TYPE
		ENTERPRISE   cdx6500
		VARIABLES    { cdx6500SNMPLastTrap }
		DESCRIPTION
		     "%s - SITE BOOT FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 351008

        ac100-site-disabled  TRAP-TYPE
		ENTERPRISE   cdx6500
		VARIABLES    { cdx6500SNMPLastTrap }
		DESCRIPTION
		     "%s - SITE DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 351009

        ac100-site-disable-failure  TRAP-TYPE
		ENTERPRISE   cdx6500
		VARIABLES    { cdx6500SNMPLastTrap }
		DESCRIPTION
		     "%s - SITE DISABLE FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 351010

        ac100-site-enabled  TRAP-TYPE
		ENTERPRISE   cdx6500
		VARIABLES    { cdx6500SNMPLastTrap }
		DESCRIPTION
		     "%s - SITE ENABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 351011

        ac100-site-enable-failure  TRAP-TYPE
		ENTERPRISE   cdx6500
		VARIABLES    { cdx6500SNMPLastTrap }
		DESCRIPTION
		     "%s - SITE ENABLE FAILURE - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 351012

        ac100-site-alive  TRAP-TYPE
		ENTERPRISE   cdx6500
		VARIABLES    { cdx6500SNMPLastTrap }
		DESCRIPTION
		     "%s - SITE ALIVE"
		     --#TYPE
		     --#SUMMARY "Trap #$G, specific: $S, arg(1) : $1"
		     --#ARGUMENTS {}
		     --#SEVERITY  CRITICAL
		     --#TIMEINDEX
		     --#HELP
		     --#HELPTAG
		     --#STATE
		::= 351013

        ac100-site-dead  TRAP-TYPE
		ENTERPRISE   cdx6500
		VARIABLES    { cdx6500SNMPLastTrap }
		DESCRIPTION
		     "%s - SITE DEAD"
		     --#TYPE
		     --#SUMMARY "Trap #$G, specific: $S, arg(1) : $1"
		     --#ARGUMENTS {}
		     --#SEVERITY  CRITICAL
		     --#TIMEINDEX
		     --#HELP
		     --#HELPTAG
		     --#STATE
		::= 351014

        ac100-data-error  TRAP-TYPE
		ENTERPRISE   cdx6500
		VARIABLES    { cdx6500SNMPLastTrap }
		DESCRIPTION
		     "%s - DATA ERROR - %s"
		     --#TYPE
		     --#SUMMARY "Trap #$G, specific: $S, arg(1) : $1"
		     --#ARGUMENTS {}
		     --#SEVERITY  MAJOR
		     --#TIMEINDEX
		     --#HELP
		     --#HELPTAG
		     --#STATE
		::= 351015

        ac100-errmesg  TRAP-TYPE
		ENTERPRISE   cdx6500
		VARIABLES    { cdx6500SNMPLastTrap }
		DESCRIPTION
		     "%s - ERR-MESG - %s, %x, %x"
		     --#TYPE
		     --#SUMMARY "Trap #$G, specific: $S, arg(1) : $1"
		     --#ARGUMENTS {}
		     --#SEVERITY  MAJOR
		     --#TIMEINDEX
		     --#HELP
		     --#HELPTAG
		     --#STATE
		::= 351016

        ac100-duplicate-site-address  TRAP-TYPE
		ENTERPRISE   cdx6500
		VARIABLES    { cdx6500SNMPLastTrap }
		DESCRIPTION
		     "%s - DUPLICATE SITE ADDRESS - %d"
		     --#TYPE
		     --#SUMMARY "Trap #$G, specific: $S, arg(1) : $1"
		     --#ARGUMENTS {}
		     --#SEVERITY  MAJOR
		     --#TIMEINDEX
		     --#HELP
		     --#HELPTAG
		     --#STATE
		::= 351017

        x25-bcug-table-overflow  TRAP-TYPE
		ENTERPRISE   cdx6500
		VARIABLES    { cdx6500SNMPLastTrap }
		DESCRIPTION
		     "BCUG - TABLE OVERFLOW"
		     --#TYPE
		     --#SUMMARY "Trap #$G, specific: $S, arg(1) : $1"
		     --#ARGUMENTS {}
		     --#SEVERITY  CRITICAL
		     --#TIMEINDEX
		     --#HELP
		     --#HELPTAG
		     --#STATE
		::= 352000

        x25-bcug-duplicate-bcug-entries  TRAP-TYPE
		ENTERPRISE   cdx6500
		VARIABLES    { cdx6500SNMPLastTrap }
		DESCRIPTION
		     "BCUG - DUPLICATE BCUG ENTRIES ON PORT %d"
		     --#TYPE
		     --#SUMMARY "Trap #$G, specific: $S, arg(1) : $1"
		     --#ARGUMENTS {}
		     --#SEVERITY  MINOR
		     --#TIMEINDEX
		     --#HELP
		     --#HELPTAG
		     --#STATE
		::= 352001

        ccs-line-is-active007  TRAP-TYPE
		ENTERPRISE   cdx6500
		VARIABLES    { cdx6500SNMPLastTrap }
		DESCRIPTION
		     "CCS LINE %d IS ACTIVE\007"
		     --#TYPE
		     --#SUMMARY "Trap #$G, specific: $S, arg(1) : $1"
		     --#ARGUMENTS {}
		     --#SEVERITY  CRITICAL
		     --#TIMEINDEX
		     --#HELP
		     --#HELPTAG
		     --#STATE
		::= 354000

        ccs-line-is-inactive  TRAP-TYPE
		ENTERPRISE   cdx6500
		VARIABLES    { cdx6500SNMPLastTrap }
		DESCRIPTION
		     "CCS LINE %d IS INACTIVE"
		     --#TYPE
		     --#SUMMARY "Trap #$G, specific: $S, arg(1) : $1"
		     --#ARGUMENTS {}
		     --#SEVERITY  CRITICAL
		     --#TIMEINDEX
		     --#HELP
		     --#HELPTAG
		     --#STATE
		::= 354001

        ccs-incompatible-detected  TRAP-TYPE
		ENTERPRISE   cdx6500
		VARIABLES    { cdx6500SNMPLastTrap }
		DESCRIPTION
		     "INCOMPATIBLE %s DETECTED FOR CCS"
		     --#TYPE
		     --#SUMMARY "Trap #$G, specific: $S, arg(1) : $1"
		     --#ARGUMENTS {}
		     --#SEVERITY  CRITICAL
		     --#TIMEINDEX
		     --#HELP
		     --#HELPTAG
		     --#STATE
		::= 354002

        ccs-boot-completed  TRAP-TYPE
		ENTERPRISE   cdx6500
		VARIABLES    { cdx6500SNMPLastTrap }
		DESCRIPTION
		     "CCS BOOT COMPLETED"
		     --#TYPE
		     --#SUMMARY "Trap #$G, specific: $S, arg(1) : $1"
		     --#ARGUMENTS {}
		     --#SEVERITY  CRITICAL
		     --#TIMEINDEX
		     --#HELP
		     --#HELPTAG
		     --#STATE
		::= 354003

        ccs-connected-to-port  TRAP-TYPE
		ENTERPRISE   cdx6500
		VARIABLES    { cdx6500SNMPLastTrap }
		DESCRIPTION
		     "CCS %s CONNECTED TO PORT %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 354005

        ccs-disconnected-from-port-cause  TRAP-TYPE
		ENTERPRISE   cdx6500
		VARIABLES    { cdx6500SNMPLastTrap }
		DESCRIPTION
		     "CCS %s DISCONNECTED FROM PORT %d, CAUSE: %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 354006

        ccs-frame-sequencing-override  TRAP-TYPE
		ENTERPRISE   cdx6500
		VARIABLES    { cdx6500SNMPLastTrap }
		DESCRIPTION
		     "%s - FRAME SEQUENCING OVERRIDE"
		     --#TYPE
		     --#SUMMARY "Trap #$G, specific: $S, arg(1) : $1"
		     --#ARGUMENTS {}
		     --#SEVERITY  MINOR
		     --#TIMEINDEX
		     --#HELP
		     --#HELPTAG
		     --#STATE
		::= 357000

	ns360000-null-address   TRAP-TYPE
		ENTERPRISE   cdx6500
		VARIABLES    { cdx6500SNMPLastTrap }
		DESCRIPTION
		     "GET ADDRESS : NULL ADDRESS"
		     --#TYPE
		     --#SUMMARY "Trap #$G, specific: $S, arg(1) : $1"
		     --#ARGUMENTS {}
		     --#SEVERITY  MINOR
		     --#TIMEINDEX
		     --#HELP
		     --#HELPTAG
		     --#STATE
		::= 360000

	ns360001-failed-to-map   TRAP-TYPE
		ENTERPRISE   cdx6500
		VARIABLES    { cdx6500SNMPLastTrap }
		DESCRIPTION
		     "GET ADDRESS : FAILED TO MAP %s"
		     --#TYPE
		     --#SUMMARY "Trap #$G, specific: $S, arg(1) : $1"
		     --#ARGUMENTS {}
		     --#SEVERITY  MINOR
		     --#TIMEINDEX
		     --#HELP
		     --#HELPTAG
		     --#STATE
		::= 360001

	ns360002-get-add-map   TRAP-TYPE
		ENTERPRISE   cdx6500
		VARIABLES    { cdx6500SNMPLastTrap }
		DESCRIPTION
		     "GET ADD. : MAPPED : %s TO %s"
		     --#TYPE
		     --#SUMMARY "Trap #$G, specific: $S, arg(1) : $1"
		     --#ARGUMENTS {}
		     --#SEVERITY  MINOR
		     --#TIMEINDEX
		     --#HELP
		     --#HELPTAG
		     --#STATE
		::= 360002

	ns361000-x25-rch-tbl   TRAP-TYPE
		ENTERPRISE   cdx6500
		VARIABLES    { cdx6500SNMPLastTrap }
		DESCRIPTION
		     "X25 RCH TBL.: INCCALLS : ONE MORE CALL FOR %s ON %s"
		     --#TYPE
		     --#SUMMARY "Trap #$G, specific: $S, arg(1) : $1"
		     --#ARGUMENTS {}
		     --#SEVERITY  MINOR
		     --#TIMEINDEX
		     --#HELP
		     --#HELPTAG
		     --#STATE
		::= 361000

	ns361001-inccalls   TRAP-TYPE
		ENTERPRISE   cdx6500
		VARIABLES    { cdx6500SNMPLastTrap }
		DESCRIPTION
		     "INCCALLS : FIRST CALL FOR %s ON %s"
		     --#TYPE
		     --#SUMMARY "Trap #$G, specific: $S, arg(1) : $1"
		     --#ARGUMENTS {}
		     --#SEVERITY  MINOR
		     --#TIMEINDEX
		     --#HELP
		     --#HELPTAG
		     --#STATE
		::= 361001

	ns361002-deleted-link   TRAP-TYPE
		ENTERPRISE   cdx6500
		VARIABLES    { cdx6500SNMPLastTrap }
		DESCRIPTION
		     "DELETED LINK : %s"
		     --#TYPE
		     --#SUMMARY "Trap #$G, specific: $S, arg(1) : $1"
		     --#ARGUMENTS {}
		     --#SEVERITY  MINOR
		     --#TIMEINDEX
		     --#HELP
		     --#HELPTAG
		     --#STATE
		::= 361002

	ns361003-entry-created   TRAP-TYPE
		ENTERPRISE   cdx6500
		VARIABLES    { cdx6500SNMPLastTrap }
		DESCRIPTION
		     "CREATE ENTRY : CREATED : %s %s"
		     --#TYPE
		     --#SUMMARY "Trap #$G, specific: $S, arg(1) : $1"
		     --#ARGUMENTS {}
		     --#SEVERITY  MINOR
		     --#TIMEINDEX
		     --#HELP
		     --#HELPTAG
		     --#STATE
		::= 361003

	ns361004-nos-apce-to-create-entry   TRAP-TYPE
		ENTERPRISE   cdx6500
		VARIABLES    { cdx6500SNMPLastTrap }
		DESCRIPTION
		     "CREATE ENTRY : NO SPACE : %s %s"
		     --#TYPE
		     --#SUMMARY "Trap #$G, specific: $S, arg(1) : $1"
		     --#ARGUMENTS {}
		     --#SEVERITY  MINOR
		     --#TIMEINDEX
		     --#HELP
		     --#HELPTAG
		     --#STATE
		::= 361004

	ns361005-duplicate-entry   TRAP-TYPE
		ENTERPRISE   cdx6500
		VARIABLES    { cdx6500SNMPLastTrap }
		DESCRIPTION
		     "CREATE ENTRY:DUPLICATE: CHANGING OLD : %s %s"
		     --#TYPE
		     --#SUMMARY "Trap #$G, specific: $S, arg(1) : $1"
		     --#ARGUMENTS {}
		     --#SEVERITY  MINOR
		     --#TIMEINDEX
		     --#HELP
		     --#HELPTAG
		     --#STATE
		::= 361005

	ns361006-getlink-found-conn   TRAP-TYPE
		ENTERPRISE   cdx6500
		VARIABLES    { cdx6500SNMPLastTrap }
		DESCRIPTION
		     "GETLINK : FOUND %s CONN. THRU %s, STATE %s"
		     --#TYPE
		     --#SUMMARY "Trap #$G, specific: $S, arg(1) : $1"
		     --#ARGUMENTS {}
		     --#SEVERITY  MINOR
		     --#TIMEINDEX
		     --#HELP
		     --#HELPTAG
		     --#STATE
		::= 361006

	ns361007-statechange   TRAP-TYPE
		ENTERPRISE   cdx6500
		VARIABLES    { cdx6500SNMPLastTrap }
		DESCRIPTION
		     "STATECHANGE : LINK : %s, %s TO %s"
		     --#TYPE
		     --#SUMMARY "Trap #$G, specific: $S, arg(1) : $1"
		     --#ARGUMENTS {}
		     --#SEVERITY  MINOR
		     --#TIMEINDEX
		     --#HELP
		     --#HELPTAG
		     --#STATE
		::= 361007

	ns361008-deccalls-cleared-link   TRAP-TYPE
		ENTERPRISE   cdx6500
		VARIABLES    { cdx6500SNMPLastTrap }
		DESCRIPTION
		     "DECCALLS : CLEARED LINK %s WITH CAUSE %d"
		     --#TYPE
		     --#SUMMARY "Trap #$G, specific: $S, arg(1) : $1"
		     --#ARGUMENTS {}
		     --#SEVERITY  MINOR
		     --#TIMEINDEX
		     --#HELP
		     --#HELPTAG
		     --#STATE
		::= 361008

	ns361009-deccalls-one   TRAP-TYPE
		ENTERPRISE   cdx6500
		VARIABLES    { cdx6500SNMPLastTrap }
		DESCRIPTION
		     "DECCALLS : ONE LESS CALL ON %s"
		     --#TYPE
		     --#SUMMARY "Trap #$G, specific: $S, arg(1) : $1"
		     --#ARGUMENTS {}
		     --#SEVERITY  MINOR
		     --#TIMEINDEX
		     --#HELP
		     --#HELPTAG
		     --#STATE
		::= 361009

	ns361010-deccalls-last-call   TRAP-TYPE
		ENTERPRISE   cdx6500
		VARIABLES    { cdx6500SNMPLastTrap }
		DESCRIPTION
		     "DECCALLS : LAST CALL ON %s"
		     --#TYPE
		     --#SUMMARY "Trap #$G, specific: $S, arg(1) : $1"
		     --#ARGUMENTS {}
		     --#SEVERITY  MINOR
		     --#TIMEINDEX
		     --#HELP
		     --#HELPTAG
		     --#STATE
		::= 361010

	ns361011-statechange-fail   TRAP-TYPE
		ENTERPRISE   cdx6500
		VARIABLES    { cdx6500SNMPLastTrap }
		DESCRIPTION
		     "STATECHANGE FAIL: LINK : %s, %s TO %s"
		     --#TYPE
		     --#SUMMARY "Trap #$G, specific: $S, arg(1) : $1"
		     --#ARGUMENTS {}
		     --#SEVERITY  MINOR
		     --#TIMEINDEX
		     --#HELP
		     --#HELPTAG
		     --#STATE
		::= 361011

        vbcst-state-not-found-for  TRAP-TYPE
		ENTERPRISE   cdx6500
		VARIABLES    { cdx6500SNMPLastTrap }
		DESCRIPTION
		     "%s - State not found for %d"
		     --#TYPE
		     --#SUMMARY "Trap #$G, specific: $S, arg(1) : $1"
		     --#ARGUMENTS {}
		     --#SEVERITY  CRITICAL
		     --#TIMEINDEX
		     --#HELP
		     --#HELPTAG
		     --#STATE
		::= 364000

        vbcst-state-table-not-found  TRAP-TYPE
		ENTERPRISE   cdx6500
		VARIABLES    { cdx6500SNMPLastTrap }
		DESCRIPTION
		     "%s - State table not found"
		     --#TYPE
		     --#SUMMARY "Trap #$G, specific: $S, arg(1) : $1"
		     --#ARGUMENTS {}
		     --#SEVERITY  CRITICAL
		     --#TIMEINDEX
		     --#HELP
		     --#HELPTAG
		     --#STATE
		::= 364001

        vbcst-no-entry-for-event-in  TRAP-TYPE
		ENTERPRISE   cdx6500
		VARIABLES    { cdx6500SNMPLastTrap }
		DESCRIPTION
		     "%s - No entry for %d event in %d"
		     --#TYPE
		     --#SUMMARY "Trap #$G, specific: $S, arg(1) : $1"
		     --#ARGUMENTS {}
		     --#SEVERITY  CRITICAL
		     --#TIMEINDEX
		     --#HELP
		     --#HELPTAG
		     --#STATE
		::= 364002

        vbcst-process-event-in  TRAP-TYPE
		ENTERPRISE   cdx6500
		VARIABLES    { cdx6500SNMPLastTrap }
		DESCRIPTION
		     "%s - Process %d event in %d"
		     --#TYPE
		     --#SUMMARY "Trap #$G, specific: $S, arg(1) : $1"
		     --#ARGUMENTS {}
		     --#SEVERITY  CRITICAL
		     --#TIMEINDEX
		     --#HELP
		     --#HELPTAG
		     --#STATE
		::= 364003

        vbcst-10-loops-for-event-in  TRAP-TYPE
		ENTERPRISE   cdx6500
		VARIABLES    { cdx6500SNMPLastTrap }
		DESCRIPTION
		     "%s - 10 Loops for %d event in %d"
		     --#TYPE
		     --#SUMMARY "Trap #$G, specific: $S, arg(1) : $1"
		     --#ARGUMENTS {}
		     --#SEVERITY  CRITICAL
		     --#TIMEINDEX
		     --#HELP
		     --#HELPTAG
		     --#STATE
		::= 364004

        vbcst-call-cleared-incompatible  TRAP-TYPE
		ENTERPRISE   cdx6500
		VARIABLES    { cdx6500SNMPLastTrap }
		DESCRIPTION
		     "%s - Call Cleared - Incompatible Compression Algorithm from caller %s"
		     --#TYPE
		     --#SUMMARY "Trap #$G, specific: $S, arg(1) : $1"
		     --#ARGUMENTS {}
		     --#SEVERITY  MINOR
		     --#TIMEINDEX
		     --#HELP
		     --#HELPTAG
		     --#STATE
		::= 364005

        vbcst-call-cleared-incompatible-2  TRAP-TYPE
		ENTERPRISE   cdx6500
		VARIABLES    { cdx6500SNMPLastTrap }
		DESCRIPTION
		     "%s - Call Cleared - Incompatible Compression Algorithm"
		     --#TYPE
		     --#SUMMARY "Trap #$G, specific: $S, arg(1) : $1"
		     --#ARGUMENTS {}
		     --#SEVERITY  MINOR
		     --#TIMEINDEX
		     --#HELP
		     --#HELPTAG
		     --#STATE
		::= 364006

        t1e1vg-remote-loopback-in-progre  TRAP-TYPE
		ENTERPRISE   cdx6500
		VARIABLES    { cdx6500SNMPLastTrap }
		DESCRIPTION
		     "%s - Remote loopback in progress"
		     --#TYPE
		     --#SUMMARY "Trap #$G, specific: $S, arg(1) : $1"
		     --#ARGUMENTS {}
		     --#SEVERITY  CRITICAL
		     --#TIMEINDEX
		     --#HELP
		     --#HELPTAG
		     --#STATE
		::= 371001

        t1e1vg-remote-loopback-ended  TRAP-TYPE
		ENTERPRISE   cdx6500
		VARIABLES    { cdx6500SNMPLastTrap }
		DESCRIPTION
		     "%s - Remote loopback ended"
		     --#TYPE
		     --#SUMMARY "Trap #$G, specific: $S, arg(1) : $1"
		     --#ARGUMENTS {}
		     --#SEVERITY  CRITICAL
		     --#TIMEINDEX
		     --#HELP
		     --#HELPTAG
		     --#STATE
		::= 371002

        vport-cvs-module-failed-initiali  TRAP-TYPE
		ENTERPRISE   cdx6500
		VARIABLES    { cdx6500SNMPLastTrap }
		DESCRIPTION
		     "CVS - Module failed initialization, %s"
		     --#TYPE
		     --#SUMMARY "Trap #$G, specific: $S, arg(1) : $1"
		     --#ARGUMENTS {}
		     --#SEVERITY  CRITICAL
		     --#TIMEINDEX
		     --#HELP
		     --#HELPTAG
		     --#STATE
		::= 373001

        vport-cvs-no-digit-string-matchi  TRAP-TYPE
		ENTERPRISE   cdx6500
		VARIABLES    { cdx6500SNMPLastTrap }
		DESCRIPTION
		     "CVS - No digit string matching %s found, calling address: %s"
		     --#TYPE
		     --#SUMMARY "Trap #$G, specific: $S, arg(1) : $1"
		     --#ARGUMENTS {}
		     --#SEVERITY  MINOR
		     --#TIMEINDEX
		     --#HELP
		     --#HELPTAG
		     --#STATE
		::= 373002

        vport-cvs-connection-to-terminat  TRAP-TYPE
		ENTERPRISE   cdx6500
		VARIABLES    { cdx6500SNMPLastTrap }
		DESCRIPTION
		     "CVS - Connection to %s terminated before match"
		     --#TYPE
		     --#SUMMARY "Trap #$G, specific: $S, arg(1) : $1"
		     --#ARGUMENTS {}
		     --#SEVERITY  MINOR
		     --#TIMEINDEX
		     --#HELP
		     --#HELPTAG
		     --#STATE
		::= 373003

        vport-cvs-invalid-execution-line  TRAP-TYPE
		ENTERPRISE   cdx6500
		VARIABLES    { cdx6500SNMPLastTrap }
		DESCRIPTION
		     "CVS - Invalid Execution, Line No. %d"
		     --#TYPE
		     --#SUMMARY "Trap #$G, specific: $S, arg(1) : $1"
		     --#ARGUMENTS {}
		     --#SEVERITY  MINOR
		     --#TIMEINDEX
		     --#HELP
		     --#HELPTAG
		     --#STATE
		::= 373004

        vport-cvs-centralized-voice-swit  TRAP-TYPE
		ENTERPRISE   cdx6500
		VARIABLES    { cdx6500SNMPLastTrap }
		DESCRIPTION
		     "CVS - Centralized Voice Switching disabled"
		     --#TYPE
		     --#SUMMARY "Trap #$G, specific: $S, arg(1) : $1"
		     --#ARGUMENTS {}
		     --#SEVERITY  CRITICAL
		     --#TIMEINDEX
		     --#HELP
		     --#HELPTAG
		     --#STATE
		::= 373005

        vport-cvs-centralized-voice-swit2  TRAP-TYPE
		ENTERPRISE   cdx6500
		VARIABLES    { cdx6500SNMPLastTrap }
		DESCRIPTION
		     "CVS - Centralized Voice Switching enabled"
		     --#TYPE
		     --#SUMMARY "Trap #$G, specific: $S, arg(1) : $1"
		     --#ARGUMENTS {}
		     --#SEVERITY  CRITICAL
		     --#TIMEINDEX
		     --#HELP
		     --#HELPTAG
		     --#STATE
		::= 373006

        vport-cvs  TRAP-TYPE
		ENTERPRISE   cdx6500
		VARIABLES    { cdx6500SNMPLastTrap }
		DESCRIPTION
		     "CVS - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 373007

        vport-cvs-cvs-table-copy-complet  TRAP-TYPE
		ENTERPRISE   cdx6500
		VARIABLES    { cdx6500SNMPLastTrap }
		DESCRIPTION
		     "CVS - CVS Table Copy Complete."
		     --#TYPE
		     --#SUMMARY "Trap #$G, specific: $S, arg(1) : $1"
		     --#ARGUMENTS {}
		     --#SEVERITY  CRITICAL
		     --#TIMEINDEX
		     --#HELP
		     --#HELPTAG
		     --#STATE
		::= 373008

        vport-cvs-state-event-new-state  TRAP-TYPE
		ENTERPRISE   cdx6500
		VARIABLES    { cdx6500SNMPLastTrap }
		DESCRIPTION
		     "CVS-%d - State: %d, Event: %d, New State: %d"
		     --#TYPE
		     --#SUMMARY "Trap #$G, specific: $S, arg(1) : $1"
		     --#ARGUMENTS {}
		     --#SEVERITY  MINOR
		     --#TIMEINDEX
		     --#HELP
		     --#HELPTAG
		     --#STATE
		::= 373009

        ccs-lapf-ctl-protocol-link-up  TRAP-TYPE
		ENTERPRISE   cdx6500
		VARIABLES    { cdx6500SNMPLastTrap }
		DESCRIPTION
		     "%s - LAPF CTL PROTOCOL LINK UP"
		     --#TYPE
		     --#SUMMARY "Trap #$G, specific: $S, arg(1) : $1"
		     --#ARGUMENTS {}
		     --#SEVERITY  MINOR
		     --#TIMEINDEX
		     --#HELP
		     --#HELPTAG
		     --#STATE
		::= 374000

        ccs-lapf-ctl-protocol-link-down  TRAP-TYPE
		ENTERPRISE   cdx6500
		VARIABLES    { cdx6500SNMPLastTrap }
		DESCRIPTION
		     "%s - LAPF CTL PROTOCOL LINK DOWN"
		     --#TYPE
		     --#SUMMARY "Trap #$G, specific: $S, arg(1) : $1"
		     --#ARGUMENTS {}
		     --#SEVERITY  MINOR
		     --#TIMEINDEX
		     --#HELP
		     --#HELPTAG
		     --#STATE
		::= 374001

        ccs-svc-station-activated  TRAP-TYPE
		ENTERPRISE   cdx6500
		VARIABLES    { cdx6500SNMPLastTrap }
		DESCRIPTION
		     "%sS%-3d - SVC STATION ACTIVATED ON DLCI %04d"
		     --#TYPE
		     --#SUMMARY "Trap #$G, specific: $S, arg(1) : $1"
		     --#ARGUMENTS {}
		     --#SEVERITY  MINOR
		     --#TIMEINDEX
		     --#HELP
		     --#HELPTAG
		     --#STATE
		::= 374002

        ccs-svc-station-deactivated  TRAP-TYPE
		ENTERPRISE   cdx6500
		VARIABLES    { cdx6500SNMPLastTrap }
		DESCRIPTION
		     "%sS%-3d - SVC STATION DEACTIVATED ON DLCI %04d"
		     --#TYPE
		     --#SUMMARY "Trap #$G, specific: $S, arg(1) : $1"
		     --#ARGUMENTS {}
		     --#SEVERITY  MINOR
		     --#TIMEINDEX
		     --#HELP
		     --#HELPTAG
		     --#STATE
		::= 374003

	encrypt-simm-is-defective   TRAP-TYPE
		ENTERPRISE   cdx6500
		VARIABLES    { cdx6500SNMPLastTrap }
		DESCRIPTION
		     "ENCRYPTION SIMM IS DEFECTIVE"
		     --#TYPE
		     --#SUMMARY "Trap #$G, specific: $S, arg(1) : $1"
		     --#ARGUMENTS {}
		     --#SEVERITY  MINOR
		     --#TIMEINDEX
		     --#HELP
		     --#HELPTAG
		     --#STATE
		::= 379000

	encrypt-insufficient-memory   TRAP-TYPE
		ENTERPRISE   cdx6500
		VARIABLES    { cdx6500SNMPLastTrap }
		DESCRIPTION
		     "INSUFFICIENT MEMORY TO INITIALIZE ENCRYPTION"
		     --#TYPE
		     --#SUMMARY "Trap #$G, specific: $S, arg(1) : $1"
		     --#ARGUMENTS {}
		     --#SEVERITY  MINOR
		     --#TIMEINDEX
		     --#HELP
		     --#HELPTAG
		     --#STATE
		::= 379001

	encrypt-established-session   TRAP-TYPE
		ENTERPRISE   cdx6500
		VARIABLES    { cdx6500SNMPLastTrap }
		DESCRIPTION
		     "%s: ESTABLISHED ENCRYPTION SESSION"
		     --#TYPE
		     --#SUMMARY "Trap #$G, specific: $S, arg(1) : $1"
		     --#ARGUMENTS {}
		     --#SEVERITY  MINOR
		     --#TIMEINDEX
		     --#HELP
		     --#HELPTAG
		     --#STATE
		::= 379002

	encrypt-cannot-create-session   TRAP-TYPE
		ENTERPRISE   cdx6500
		VARIABLES    { cdx6500SNMPLastTrap }
		DESCRIPTION
		     "%s: CANNOT CREATE ENCRYPTION SESSION, %s"
		     --#TYPE
		     --#SUMMARY "Trap #$G, specific: $S, arg(1) : $1"
		     --#ARGUMENTS {}
		     --#SEVERITY  MINOR
		     --#TIMEINDEX
		     --#HELP
		     --#HELPTAG
		     --#STATE
		::= 379003

	encrypt-failed-key-exchange   TRAP-TYPE
		ENTERPRISE   cdx6500
		VARIABLES    { cdx6500SNMPLastTrap }
		DESCRIPTION
		     "%s: FAILED KEY EXCHANGE"
		     --#TYPE
		     --#SUMMARY "Trap #$G, specific: $S, arg(1) : $1"
		     --#ARGUMENTS {}
		     --#SEVERITY  MINOR
		     --#TIMEINDEX
		     --#HELP
		     --#HELPTAG
		     --#STATE
		::= 379004

	encrypt-failed-key-exchange-no-response   TRAP-TYPE
		ENTERPRISE   cdx6500
		VARIABLES    { cdx6500SNMPLastTrap }
		DESCRIPTION
		     "%s: FAILED KEY EXCHANGE, NO RESPONSE"
		     --#TYPE
		     --#SUMMARY "Trap #$G, specific: $S, arg(1) : $1"
		     --#ARGUMENTS {}
		     --#SEVERITY  MINOR
		     --#TIMEINDEX
		     --#HELP
		     --#HELPTAG
		     --#STATE
		::= 379005

	encrypt-node-key-not-configured TRAP-TYPE
		ENTERPRISE   cdx6500
		VARIABLES    { cdx6500SNMPLastTrap }
		DESCRIPTION
		     "NODE KEY NOT CONFIGURED"
		     --#TYPE
		     --#SUMMARY "Trap #$G, specific: $S, arg(1) : $1"
		     --#ARGUMENTS {}
		     --#SEVERITY  MINOR
		     --#TIMEINDEX
		     --#HELP
		     --#HELPTAG
		     --#STATE
		::= 379006

	encrypt-bad-base-keys-in-cmem TRAP-TYPE
		ENTERPRISE   cdx6500
		VARIABLES    { cdx6500SNMPLastTrap }
		DESCRIPTION
		     "FOUND %d BAD BASE KEYS IN CMEM"
		     --#TYPE
		     --#SUMMARY "Trap #$G, specific: $S, arg(1) : $1"
		     --#ARGUMENTS {}
		     --#SEVERITY  MINOR
		     --#TIMEINDEX
		     --#HELP
		     --#HELPTAG
		     --#STATE
		::= 379007

	encrypt-abnormal-ns-command TRAP-TYPE
		ENTERPRISE   cdx6500
		VARIABLES    { cdx6500SNMPLastTrap }
		DESCRIPTION
		     "ABNORMAL NS COMMAND, CMD = %d"
		     --#TYPE
		     --#SUMMARY "Trap #$G, specific: $S, arg(1) : $1"
		     --#ARGUMENTS {}
		     --#SEVERITY  MINOR
		     --#TIMEINDEX
		     --#HELP
		     --#HELPTAG
		     --#STATE
		::= 379008

	encrypt-configuring-more-channels-than-hw-can-support TRAP-TYPE
		ENTERPRISE   cdx6500
		VARIABLES    { cdx6500SNMPLastTrap }
		DESCRIPTION
		     "CONFIGURING MORE CHANNELS THAN HW CAN SUPPORT"
		     --#TYPE
		     --#SUMMARY "Trap #$G, specific: $S, arg(1) : $1"
		     --#ARGUMENTS {}
		     --#SEVERITY  MINOR
		     --#TIMEINDEX
		     --#HELP
		     --#HELPTAG
		     --#STATE
		::= 379009

	encrypt-node-key-changed TRAP-TYPE
		ENTERPRISE   cdx6500
		VARIABLES    { cdx6500SNMPLastTrap }
		DESCRIPTION
		     "NODE KEY CHANGED"
		     --#TYPE
		     --#SUMMARY "Trap #$G, specific: $S, arg(1) : $1"
		     --#ARGUMENTS {}
		     --#SEVERITY  MINOR
		     --#TIMEINDEX
		     --#HELP
		     --#HELPTAG
		     --#STATE
		::= 379010

	encrypt-base-key-changed TRAP-TYPE
		ENTERPRISE   cdx6500
		VARIABLES    { cdx6500SNMPLastTrap }
		DESCRIPTION
		     "BASE KEY CHANGED: %s"
		     --#TYPE
		     --#SUMMARY "Trap #$G, specific: $S, arg(1) : $1"
		     --#ARGUMENTS {}
		     --#SEVERITY  MINOR
		     --#TIMEINDEX
		     --#HELP
		     --#HELPTAG
		     --#STATE
		::= 379011

	encrypt-good-base-key-in-cmem TRAP-TYPE
		ENTERPRISE   cdx6500
		VARIABLES    { cdx6500SNMPLastTrap }
		DESCRIPTION
		     "FOUND %d GOOD BASE KEYS IN CMEM"
		     --#TYPE
		     --#SUMMARY "Trap #$G, specific: $S, arg(1) : $1"
		     --#ARGUMENTS {}
		     --#SEVERITY  MINOR
		     --#TIMEINDEX
		     --#HELP
		     --#HELPTAG
		     --#STATE
		::= 379012

	encrypt-remote-reset-from-remote-encryption-peer TRAP-TYPE
		ENTERPRISE   cdx6500
		VARIABLES    { cdx6500SNMPLastTrap }
		DESCRIPTION
		     "%s: REMOTE RESET FROM REMOTE ENCRYPTION PEER"
		     --#TYPE
		     --#SUMMARY "Trap #$G, specific: $S, arg(1) : $1"
		     --#ARGUMENTS {}
		     --#SEVERITY  MINOR
		     --#TIMEINDEX
		     --#HELP
		     --#HELPTAG
		     --#STATE
		::= 379013

	encrypt-test-error TRAP-TYPE
		ENTERPRISE   cdx6500
		VARIABLES    { cdx6500SNMPLastTrap }
		DESCRIPTION
		     "TEST ERROR:  TX-CHANNEL = %d, EXPECTS %ld, GOT %ld"
		     --#TYPE
		     --#SUMMARY "Trap #$G, specific: $S, arg(1) : $1"
		     --#ARGUMENTS {}
		     --#SEVERITY  MINOR
		     --#TIMEINDEX
		     --#HELP
		     --#HELPTAG
		     --#STATE
		::= 379014

	encrypt-mis-configured TRAP-TYPE
		ENTERPRISE   cdx6500
		VARIABLES    { cdx6500SNMPLastTrap }
		DESCRIPTION
		     "ENCRYPTION MIS-CONFIGURED, %s IS A NETWORK PROTOCOL"
		     --#TYPE
		     --#SUMMARY "Trap #$G, specific: $S, arg(1) : $1"
		     --#ARGUMENTS {}
		     --#SEVERITY  MINOR
		     --#TIMEINDEX
		     --#HELP
		     --#HELPTAG
		     --#STATE
		::= 379015

	encrypt-invalid-attempt-to-connect-ap-to-ap TRAP-TYPE
		ENTERPRISE   cdx6500
		VARIABLES    { cdx6500SNMPLastTrap }
		DESCRIPTION
		     "INVALID ATTEMPT TO CONNECT AP TO AP"
		     --#TYPE
		     --#SUMMARY "Trap #$G, specific: $S, arg(1) : $1"
		     --#ARGUMENTS {}
		     --#SEVERITY  MINOR
		     --#TIMEINDEX
		     --#HELP
		     --#HELPTAG
		     --#STATE
		::= 379016

	encrypt-booted-encryption-key TRAP-TYPE
		ENTERPRISE   cdx6500
		VARIABLES    { cdx6500SNMPLastTrap }
		DESCRIPTION
		     "BOOTED ENCRYPTION KEY: %s"
		     --#TYPE
		     --#SUMMARY "Trap #$G, specific: $S, arg(1) : $1"
		     --#ARGUMENTS {}
		     --#SEVERITY  MINOR
		     --#TIMEINDEX
		     --#HELP
		     --#HELPTAG
		     --#STATE
		::= 379017

	encrypt-booted-encryption-profile TRAP-TYPE
		ENTERPRISE   cdx6500
		VARIABLES    { cdx6500SNMPLastTrap }
		DESCRIPTION
		     "BOOTED ENCRYPTION PROFILE: %s"
		     --#TYPE
		     --#SUMMARY "Trap #$G, specific: $S, arg(1) : $1"
		     --#ARGUMENTS {}
		     --#SEVERITY  MINOR
		     --#TIMEINDEX
		     --#HELP
		     --#HELPTAG
		     --#STATE
		::= 379018

	encrypt-deleted-all-encryption-keys TRAP-TYPE
		ENTERPRISE   cdx6500
		VARIABLES    { cdx6500SNMPLastTrap }
		DESCRIPTION
		     "DELETED ALL ENCRYPTION KEYS"
		     --#TYPE
		     --#SUMMARY "Trap #$G, specific: $S, arg(1) : $1"
		     --#ARGUMENTS {}
		     --#SEVERITY  MINOR
		     --#TIMEINDEX
		     --#HELP
		     --#HELPTAG
		     --#STATE
		::= 379019

	encrypt-data-encryption-disabled TRAP-TYPE
		ENTERPRISE   cdx6500
		VARIABLES    { cdx6500SNMPLastTrap }
		DESCRIPTION
		     "DATA ENCRYPTION NOT ENABLED, H/W IS O.K"
		     --#TYPE
		     --#SUMMARY "Trap #$G, specific: $S, arg(1) : $1"
		     --#ARGUMENTS {}
		     --#SEVERITY  MINOR
		     --#TIMEINDEX
		     --#HELP
		     --#HELPTAG
		     --#STATE
		::= 379020

	encrypt-IV-usage-forced-by-remote-peer TRAP-TYPE
		ENTERPRISE   cdx6500
		VARIABLES    { cdx6500SNMPLastTrap }
		DESCRIPTION
		     "%s: IV USAGE FORCED BY REMOTE ENCRYPTION PEER"
		     --#TYPE
		     --#SUMMARY "Trap #$G, specific: $S, arg(1) : $1"
		     --#ARGUMENTS {}
		     --#SEVERITY  MINOR
		     --#TIMEINDEX
		     --#HELP
		     --#HELPTAG
		     --#STATE
		::= 379021

	encrypt-simm-bad-or-not-installed TRAP-TYPE
		ENTERPRISE   cdx6500
		VARIABLES    { cdx6500SNMPLastTrap }
		DESCRIPTION
		     "ENCRYPTION SIMM BAD OR NOT INSTALLED"
		     --#TYPE
		     --#SUMMARY "Trap #$G, specific: $S, arg(1) : $1"
		     --#ARGUMENTS {}
		     --#SEVERITY  MINOR
		     --#TIMEINDEX
		     --#HELP
		     --#HELPTAG
		     --#STATE
		::= 379022

        crc-last-two-chars  TRAP-TYPE
		ENTERPRISE   cdx6500
		VARIABLES    { cdx6500SNMPLastTrap }
		DESCRIPTION
		     "Last two Chars: %X %X"
		     --#TYPE
		     --#SUMMARY "Trap #$G, specific: $S, arg(1) : $1"
		     --#ARGUMENTS {}
		     --#SEVERITY  MINOR
		     --#TIMEINDEX
		     --#HELP
		     --#HELPTAG
		     --#STATE
		::= 380000

        tcpdriver-tcp-listen-failed  TRAP-TYPE
		ENTERPRISE   cdx6500
		VARIABLES    { cdx6500SNMPLastTrap }
		DESCRIPTION
		     "%s - TCP LISTEN FAILED"
		     --#TYPE
		     --#SUMMARY "Trap #$G, specific: $S, arg(1) : $1"
		     --#ARGUMENTS {}
		     --#SEVERITY  MAJOR
		     --#TIMEINDEX
		     --#HELP
		     --#HELPTAG
		     --#STATE
		::= 381000

        tcpdriver-session-established  TRAP-TYPE
		ENTERPRISE   cdx6500
		VARIABLES    { cdx6500SNMPLastTrap }
		DESCRIPTION
		     "%s - SESSION ESTABLISHED"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 381001

        tcpdriver-session-closed  TRAP-TYPE
		ENTERPRISE   cdx6500
		VARIABLES    { cdx6500SNMPLastTrap }
		DESCRIPTION
		     "%s - SESSION CLOSED"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 381002

        tcpdriver-l2-packet-size-exceed  TRAP-TYPE
		ENTERPRISE   cdx6500
		VARIABLES    { cdx6500SNMPLastTrap }
		DESCRIPTION
		     "%s - L2 PACKET SIZE EXCEEDED"
		     --#TYPE
		     --#SUMMARY "Trap #$G, specific: $S, arg(1) : $1"
		     --#ARGUMENTS {}
		     --#SEVERITY  MAJOR
		     --#TIMEINDEX
		     --#HELP
		     --#HELPTAG
		     --#STATE
		::= 381003

        tcpdriver-tcp-packet-size-exceed  TRAP-TYPE
		ENTERPRISE   cdx6500
		VARIABLES    { cdx6500SNMPLastTrap }
		DESCRIPTION
		     "%s - TCP PACKET SIZE EXCEEDED"
		     --#TYPE
		     --#SUMMARY "Trap #$G, specific: $S, arg(1) : $1"
		     --#ARGUMENTS {}
		     --#SEVERITY  MAJOR
		     --#TIMEINDEX
		     --#HELP
		     --#HELPTAG
		     --#STATE
		::= 381004

        tcpdriver-list-full  TRAP-TYPE
		ENTERPRISE   cdx6500
		VARIABLES    { cdx6500SNMPLastTrap }
		DESCRIPTION
		     "%s - LIST TOWARDS TCP IS FULL"
		     --#TYPE
		     --#SUMMARY "Trap #$G, specific: $S, arg(1) : $1"
		     --#ARGUMENTS {}
		     --#SEVERITY  MAJOR
		     --#TIMEINDEX
		     --#HELP
		     --#HELPTAG
		     --#STATE
		::= 381005

        tcpdriver-tcp-send-failed  TRAP-TYPE
		ENTERPRISE   cdx6500
		VARIABLES    { cdx6500SNMPLastTrap }
		DESCRIPTION
		     "%s - TCP SEND FAILED"
		     --#TYPE
		     --#SUMMARY "Trap #$G, specific: $S, arg(1) : $1"
		     --#ARGUMENTS {}
		     --#SEVERITY  MAJOR
		     --#TIMEINDEX
		     --#HELP
		     --#HELPTAG
		     --#STATE
		::= 381006

        dlcm-syserr  TRAP-TYPE
		ENTERPRISE   cdx6500
		VARIABLES    { cdx6500SNMPLastTrap }
		DESCRIPTION
		     "DLCM SYSERR %x, p1=%x, p2=%x, p3=%x, p4=%x"
		     --#TYPE
		     --#SUMMARY "Trap #$G, specific: $S, arg(1) : $1"
		     --#ARGUMENTS {}
		     --#SEVERITY  MAJOR
		     --#TIMEINDEX
		     --#HELP
		     --#HELPTAG
		     --#STATE
		::= 382000

        appncm-appn-cm-syserr  TRAP-TYPE
		ENTERPRISE   cdx6500
		VARIABLES    { cdx6500SNMPLastTrap }
		DESCRIPTION
		     "APPN CM SYSERR %x, p1=%x, p2=%x, p3=%x"
		     --#TYPE
		     --#SUMMARY "Trap #$G, specific: $S, arg(1) : $1"
		     --#ARGUMENTS {}
		     --#SEVERITY  MAJOR
		     --#TIMEINDEX
		     --#HELP
		     --#HELPTAG
		     --#STATE
		::= 383000

        appncm-insufficient-memory  TRAP-TYPE
		ENTERPRISE   cdx6500
		VARIABLES    { cdx6500SNMPLastTrap }
		DESCRIPTION
		     "INSUFFICIENT MEMORY TO SUPPORT APPN CONFIGURATION"
		     --#TYPE
		     --#SUMMARY "Trap #$G, specific: $S, arg(1) : $1"
		     --#ARGUMENTS {}
		     --#SEVERITY  CRITICAL
		     --#TIMEINDEX
		     --#HELP
		     --#HELPTAG
		     --#STATE
		::= 383001

        snap-syserr  TRAP-TYPE
		ENTERPRISE   cdx6500
		VARIABLES    { cdx6500SNMPLastTrap }
		DESCRIPTION
		     "SNAP: SYSERR %s."
		     --#TYPE
		     --#SUMMARY "Trap #$G, specific: $S, arg(1) : $1"
		     --#ARGUMENTS {}
		     --#SEVERITY  CRITICAL
		     --#TIMEINDEX
		     --#HELP
		     --#HELPTAG
		     --#STATE
		::= 384000

        snap-snap  TRAP-TYPE
		ENTERPRISE   cdx6500
		VARIABLES    { cdx6500SNMPLastTrap }
		DESCRIPTION
		     "SNAP: %s."
		     --#TYPE
		     --#SUMMARY "Trap #$G, specific: $S, arg(1) : $1"
		     --#ARGUMENTS {}
		     --#SEVERITY  INFORMATIONAL
		     --#TIMEINDEX
		     --#HELP
		     --#HELPTAG
		     --#STATE
		::= 384001

        snap-tp-started-req  TRAP-TYPE
		ENTERPRISE   cdx6500
		VARIABLES    { cdx6500SNMPLastTrap }
		DESCRIPTION
		     "SNAP: tp started req lu=%s socket=%x pid=%x qid=%x tp=%x,%x,%x,%x,%x,%x,%x,%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 384002

        snap-rcv-alloc-req  TRAP-TYPE
		ENTERPRISE   cdx6500
		VARIABLES    { cdx6500SNMPLastTrap }
		DESCRIPTION
		     "SNAP: rcv alloc req  lu=%s socket=%x pid=%x qid=%x tp=%x,%x,%x,%x,%x,%x,%x,%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 384003

        snap-tp-started-rsp  TRAP-TYPE
		ENTERPRISE   cdx6500
		VARIABLES    { cdx6500SNMPLastTrap }
		DESCRIPTION
		     "SNAP: tp started rsp lu=%s socket=%x pid=%x qid=%x tp=%x,%x,%x,%x,%x,%x,%x,%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 384004

        snap-rcv-alloc-rsp  TRAP-TYPE
		ENTERPRISE   cdx6500
		VARIABLES    { cdx6500SNMPLastTrap }
		DESCRIPTION
		     "SNAP: rcv alloc rsp  lu=%s socket=%x pid=%x qid=%x tp=%x,%x,%x,%x,%x,%x,%x,%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 384005

        snap-tp-ended-req  TRAP-TYPE
		ENTERPRISE   cdx6500
		VARIABLES    { cdx6500SNMPLastTrap }
		DESCRIPTION
		     "SNAP: tp ended req   lu=%s socket=%x pid=%x qid=%x tp=%x,%x,%x,%x,%x,%x,%x,%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 384006

        snap-tp-ended-rsp  TRAP-TYPE
		ENTERPRISE   cdx6500
		VARIABLES    { cdx6500SNMPLastTrap }
		DESCRIPTION
		     "SNAP: tp ended rsp   lu=%s socket=%x pid=%x qid=%x tp=%x,%x,%x,%x,%x,%x,%x,%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 384007

        lu62map-error-in-appc-verb-resp  TRAP-TYPE
		ENTERPRISE   cdx6500
		VARIABLES    { cdx6500SNMPLastTrap }
		DESCRIPTION
		     "LU62MAP : ERROR IN APPC VERB RESPONSE. Station : %s,  verb : %d, primary RC : %x, secondary RC : %x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385000

        lu62map-5494-retry-limit-reached  TRAP-TYPE
		ENTERPRISE   cdx6500
		VARIABLES    { cdx6500SNMPLastTrap }
		DESCRIPTION
		     "%s - 5494 %s RETRY LIMIT REACHED"
		     --#TYPE
		     --#SUMMARY "Trap #$G, specific: $S, arg(1) : $1"
		     --#ARGUMENTS {}
		     --#SEVERITY  MAJOR
		     --#TIMEINDEX
		     --#HELP
		     --#HELPTAG
		     --#STATE
		::= 385001

        lu62map-event-in-wrong-state  TRAP-TYPE
		ENTERPRISE   cdx6500
		VARIABLES    { cdx6500SNMPLastTrap }
		DESCRIPTION
		     "LU62MAP : EVENT OCCURRED IN WRONG STATE (Station : %s, event : %s, state : %d)"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385002

        lu62map-null-pointer-on-line  TRAP-TYPE
		ENTERPRISE   cdx6500
		VARIABLES    { cdx6500SNMPLastTrap }
		DESCRIPTION
		     "LU62MAP : NULL POINTER ON LINE %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385003

        lu62map-failed-to-get-snap-sock  TRAP-TYPE
		ENTERPRISE   cdx6500
		VARIABLES    { cdx6500SNMPLastTrap }
		DESCRIPTION
		     "LU62MAP : FAILED TO GET SNAP SOCKET POINTER. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385004

        lu62map-received-unknown-sna-ev  TRAP-TYPE
		ENTERPRISE   cdx6500
		VARIABLES    { cdx6500SNMPLastTrap }
		DESCRIPTION
		     "LU62MAP : RECEIVED UNKNOWN SNA EVENT SUBTYPE (%d). Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385005

        lu62map-failure-returned  TRAP-TYPE
		ENTERPRISE   cdx6500
		VARIABLES    { cdx6500SNMPLastTrap }
		DESCRIPTION
		     "LU62MAP : FAILURE RETURNED FROM %s ON LINE %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385006

        lu62map-incorrect-header  TRAP-TYPE
		ENTERPRISE   cdx6500
		VARIABLES    { cdx6500SNMPLastTrap }
		DESCRIPTION
		     "LU62MAP : RECEIVED DATA FROM APPC WITH INCORRECT HEADER. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385007

        lu62map-received-unknown-resp  TRAP-TYPE
		ENTERPRISE   cdx6500
		VARIABLES    { cdx6500SNMPLastTrap }
		DESCRIPTION
		     "LU62MAP : RECEIVED UNKNOWN APPC VERB RESPONSE (%d). Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385008

        lu62map-5494-controller-up  TRAP-TYPE
		ENTERPRISE   cdx6500
		VARIABLES    { cdx6500SNMPLastTrap }
		DESCRIPTION
		     "%s - 5494 CONTROLLER UP"
		     --#TYPE
		     --#SUMMARY "Trap #$G, specific: $S, arg(1) : $1"
		     --#ARGUMENTS {}
		     --#SEVERITY  MAJOR
		     --#TIMEINDEX
		     --#HELP
		     --#HELPTAG
		     --#STATE
		::= 385009

        lu62map-5494-controller-down  TRAP-TYPE
		ENTERPRISE   cdx6500
		VARIABLES    { cdx6500SNMPLastTrap }
		DESCRIPTION
		     "%s - 5494 CONTROLLER DOWN"
		     --#TYPE
		     --#SUMMARY "Trap #$G, specific: $S, arg(1) : $1"
		     --#ARGUMENTS {}
		     --#SEVERITY  MAJOR
		     --#TIMEINDEX
		     --#HELP
		     --#HELPTAG
		     --#STATE
		::= 385010

        lu62map-received-unexpected-mess  TRAP-TYPE
		ENTERPRISE   cdx6500
		VARIABLES    { cdx6500SNMPLastTrap }
		DESCRIPTION
		     "LU62MAP : RECEIVED UNEXPECTED MESSAGE FOR LU x38. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385011

        lu62map-received-unknown-tpid  TRAP-TYPE
		ENTERPRISE   cdx6500
		VARIABLES    { cdx6500SNMPLastTrap }
		DESCRIPTION
		     "LU62MAP : RECEIVED UNKNOWN TP-ID AND CONV-ID. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385012

        lu62map-received-too-many-recv  TRAP-TYPE
		ENTERPRISE   cdx6500
		VARIABLES    { cdx6500SNMPLastTrap }
		DESCRIPTION
		     "LU62MAP : RECEIVED TOO MANY RECEIVE-AND-ALLOCATES. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385013

        lu62map-received-unknown-lu4lu7  TRAP-TYPE
		ENTERPRISE   cdx6500
		VARIABLES    { cdx6500SNMPLastTrap }
		DESCRIPTION
		     "LU62MAP : RECEIVED UNKNOWN LU4/LU7 LU ID (%d). Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385014

        lu62map-lu4lu7-incorrect-header  TRAP-TYPE
		ENTERPRISE   cdx6500
		VARIABLES    { cdx6500SNMPLastTrap }
		DESCRIPTION
		     "LU62MAP : RECEIVED LU4/LU7 DATA WITH INCORRECT HEADER. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385015

        lu62map-5494-workstation-down  TRAP-TYPE
		ENTERPRISE   cdx6500
		VARIABLES    { cdx6500SNMPLastTrap }
		DESCRIPTION
		     "%s - 5494 WORKSTATION DOWN, LU ID : %d"
		     --#TYPE
		     --#SUMMARY "Trap #$G, specific: $S, arg(1) : $1"
		     --#ARGUMENTS {}
		     --#SEVERITY  MAJOR
		     --#TIMEINDEX
		     --#HELP
		     --#HELPTAG
		     --#STATE
		::= 385016

        lu62map-5494-workstation-up  TRAP-TYPE
		ENTERPRISE   cdx6500
		VARIABLES    { cdx6500SNMPLastTrap }
		DESCRIPTION
		     "%s - 5494 WORKSTATION UP, LU ID : %d"
		     --#TYPE
		     --#SUMMARY "Trap #$G, specific: $S, arg(1) : $1"
		     --#ARGUMENTS {}
		     --#SEVERITY  MAJOR
		     --#TIMEINDEX
		     --#HELP
		     --#HELPTAG
		     --#STATE
		::= 385017

        lu62map-lu62map  TRAP-TYPE
		ENTERPRISE   cdx6500
		VARIABLES    { cdx6500SNMPLastTrap }
		DESCRIPTION
		     "LU62MAP : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385018

        lu62map-dactlu-in-unexpected-state  TRAP-TYPE
		ENTERPRISE   cdx6500
		VARIABLES    { cdx6500SNMPLastTrap }
		DESCRIPTION
		     "LU62MAP : RECEIVED DACTLU IN UNEXPECTED STATE. LU ID : %d. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385019

        lu62map-received-lustat  TRAP-TYPE
		ENTERPRISE   cdx6500
		VARIABLES    { cdx6500SNMPLastTrap }
		DESCRIPTION
		     "LU62MAP : RECEIVED LUSTAT IN UNEXPECTED STATE. LU ID : %d. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385020

        lu62map-received-actlu  TRAP-TYPE
		ENTERPRISE   cdx6500
		VARIABLES    { cdx6500SNMPLastTrap }
		DESCRIPTION
		     "LU62MAP : RECEIVED ACTLU IN UNEXPECTED STATE. LU ID : %d. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385021

        lu62map-bad-struct-id  TRAP-TYPE
		ENTERPRISE   cdx6500
		VARIABLES    { cdx6500SNMPLastTrap }
		DESCRIPTION
		     "LU62MAP : BAD STRUCT ID ON LINE %d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385022

        lu62map-received-nonpip-alloc  TRAP-TYPE
		ENTERPRISE   cdx6500
		VARIABLES    { cdx6500SNMPLastTrap }
		DESCRIPTION
		     "LU62MAP : RECEIVED NON-PIP ALLOC DATA WHEN EXPECTING PIP ALLOC DATA. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385023

        lu62map-received-data-from-qllc  TRAP-TYPE
		ENTERPRISE   cdx6500
		VARIABLES    { cdx6500SNMPLastTrap }
		DESCRIPTION
		     "LU62MAP : RECEIVED DATA FROM QLLC IN WRONG STATE. Station : %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385024

        lu62map-null-pointer-on-line2  TRAP-TYPE
		ENTERPRISE   cdx6500
		VARIABLES    { cdx6500SNMPLastTrap }
		DESCRIPTION
		     "LU62MAP : NULL POINTER ON LINE %d. Verb : %d."
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385025

        lu62map-event-in-wrong-state2  TRAP-TYPE
		ENTERPRISE   cdx6500
		VARIABLES    { cdx6500SNMPLastTrap }
		DESCRIPTION
		     "LU62MAP : EVENT OCCURRED IN WRONG DATA STATE (Station : %s, event : %s, state : %d)"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385026

        lu62map-unknown-lu  TRAP-TYPE
		ENTERPRISE   cdx6500
		VARIABLES    { cdx6500SNMPLastTrap }
		DESCRIPTION
		     "LU62MAP : RECEIVED ALLOCATE FOR UNKNOWN LU ALIAS (%s)"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385027

	lu62map385028-5494-station   TRAP-TYPE
		ENTERPRISE   cdx6500
		VARIABLES    { cdx6500SNMPLastTrap }
		DESCRIPTION
		     "%s - 5494 STATION RECEIVED A REMOTE DISC"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385028

	lu62map385029-5494-remote-conn   TRAP-TYPE
		ENTERPRISE   cdx6500
		VARIABLES    { cdx6500SNMPLastTrap }
		DESCRIPTION
		     "%s - 5494 REMOTE CONNECTION ESTABLISHED"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385029

	lu62map385030-5494-remote-call   TRAP-TYPE
		ENTERPRISE   cdx6500
		VARIABLES    { cdx6500SNMPLastTrap }
		DESCRIPTION
		     "%s - 5494 REMOTE CALL ESTABLISHED"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385030

	lu62map385031-qllcpa   TRAP-TYPE
		ENTERPRISE   cdx6500
		VARIABLES    { cdx6500SNMPLastTrap }
		DESCRIPTION
		     "qllc-packet   %x 	upstream pending=%x count=%x downstream pending=%x count=%x queue-size=%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385031

	lu62map385032-handle   TRAP-TYPE
		ENTERPRISE   cdx6500
		VARIABLES    { cdx6500SNMPLastTrap }
		DESCRIPTION
		     "handle-pacing %x 	upstream pending=%x count=%x downstream pending=%x count=%x queue-size=%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385032

	lu62map385033-sendou   TRAP-TYPE
		ENTERPRISE   cdx6500
		VARIABLES    { cdx6500SNMPLastTrap }
		DESCRIPTION
		     "send-outbound %x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385033

	lu62map385034-purgeq   TRAP-TYPE
		ENTERPRISE   cdx6500
		VARIABLES    { cdx6500SNMPLastTrap }
		DESCRIPTION
		     "purge-queue   %x 	upstream pending=%x count=%x downstream pending=%x count=%x queue-size=%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385034

	lu62map385035-sendqu   TRAP-TYPE
		ENTERPRISE   cdx6500
		VARIABLES    { cdx6500SNMPLastTrap }
		DESCRIPTION
		     "send-queued   %x 	upstream pending=%x count=%x downstream pending=%x count=%x queue-size=%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385035

	lu62map385036-sendup   TRAP-TYPE
		ENTERPRISE   cdx6500
		VARIABLES    { cdx6500SNMPLastTrap }
		DESCRIPTION
		     "send-upstream %x 	upstream pending=%x count=%x downstream pending=%x count=%x queue-size=%x"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 385036

        qos-not-operational  TRAP-TYPE
		ENTERPRISE   cdx6500
		VARIABLES    { cdx6500SNMPLastTrap }
		DESCRIPTION
		     "QOS : NOT OPERATIONAL AS CONFIGURED FOR %s, %s"
		     --#TYPE
		     --#SUMMARY "Trap #$G, specific: $S, arg(1) : $1"
		     --#ARGUMENTS {}
		     --#SEVERITY  CRITICAL
		     --#TIMEINDEX
		     --#HELP
		     --#HELPTAG
		     --#STATE
		::= 387000

        qos-memory-allocation-failure  TRAP-TYPE
		ENTERPRISE   cdx6500
		VARIABLES    { cdx6500SNMPLastTrap }
		DESCRIPTION
		     "MEMORY ALLOCATION FAILURE FOR PACKET CLASSIFIER"
		     --#TYPE
		     --#SUMMARY "Trap #$G, specific: $S, arg(1) : $1"
		     --#ARGUMENTS {}
		     --#SEVERITY  CRITICAL
		     --#TIMEINDEX
		     --#HELP
		     --#HELPTAG
		     --#STATE
		::= 388000

        qos-total-percentage-exceeds-100  TRAP-TYPE
		ENTERPRISE   cdx6500
		VARIABLES    { cdx6500SNMPLastTrap }
		DESCRIPTION
		     "QOS : TOTAL PERCENTAGE > 100 FOR %s, NORMALIZED TO 100%%"
		     --#TYPE
		     --#SUMMARY "Trap #$G, specific: $S, arg(1) : $1"
		     --#ARGUMENTS {}
		     --#SEVERITY  CRITICAL
		     --#TIMEINDEX
		     --#HELP
		     --#HELPTAG
		     --#STATE
		::= 389000

        qos-total-percentage-changed  TRAP-TYPE
		ENTERPRISE   cdx6500
		VARIABLES    { cdx6500SNMPLastTrap }
		DESCRIPTION
		     "QOS : TOTAL PERCENTAGE < 100 FOR %s, PERCENTAGE ASSIGNMENT OF DEFAULT CLASS OF PROFILE %d CHANGED TO %d%%"
		     --#TYPE
		     --#SUMMARY "Trap #$G, specific: $S, arg(1) : $1"
		     --#ARGUMENTS {}
		     --#SEVERITY  MAJOR
		     --#TIMEINDEX
		     --#HELP
		     --#HELPTAG
		     --#STATE
		::= 389001

	h323392000-h323-node   TRAP-TYPE
		ENTERPRISE   cdx6500
		VARIABLES    { cdx6500SNMPLastTrap }
		DESCRIPTION
		     "H323 NODE WIDE PARAMETERS NOT INSTALLED - Out of memory."
		     --#TYPE
		     --#SUMMARY "Trap #$G, specific: $S, arg(1) : $1"
		     --#ARGUMENTS {}
		     --#SEVERITY  CRITICAL
		     --#TIMEINDEX
		     --#HELP
		     --#HELPTAG
		     --#STATE
		::= 392000

	h323392001-h323-node   TRAP-TYPE
		ENTERPRISE   cdx6500
		VARIABLES    { cdx6500SNMPLastTrap }
		DESCRIPTION
		     "H323 Node Wide Parameters Boot Complete"
		     --#TYPE
		     --#SUMMARY "Trap #$G, specific: $S, arg(1) : $1"
		     --#ARGUMENTS {}
		     --#SEVERITY  CRITICAL
		     --#TIMEINDEX
		     --#HELP
		     --#HELPTAG
		     --#STATE
		::= 392001

	h323392002-no-h323-n   TRAP-TYPE
		ENTERPRISE   cdx6500
		VARIABLES    { cdx6500SNMPLastTrap }
		DESCRIPTION
		     "NO H323 NODE RECORDS FOUND - Installing Defaults"
		     --#TYPE
		     --#SUMMARY "Trap #$G, specific: $S, arg(1) : $1"
		     --#ARGUMENTS {}
		     --#SEVERITY  CRITICAL
		     --#TIMEINDEX
		     --#HELP
		     --#HELPTAG
		     --#STATE
		::= 392002

	iodrivers396000-port   TRAP-TYPE
		ENTERPRISE   cdx6500
		VARIABLES    { cdx6500SNMPLastTrap }
		DESCRIPTION
		     "%s - PORT ERROR COUNT > THRESHOLD"
		     --#TYPE
		     --#SUMMARY "Trap #$G, specific: $S, arg(1) : $1"
		     --#ARGUMENTS {}
		     --#SEVERITY  MAJOR
		     --#TIMEINDEX
		     --#HELP
		     --#HELPTAG
		     --#STATE
		::= 396000

	iodrivers396001-unsu   TRAP-TYPE
		ENTERPRISE   cdx6500
		VARIABLES    { cdx6500SNMPLastTrap }
		DESCRIPTION
		     "%s - UNSUPPORTED SPEED: OPERATING AT %d BITS PER SECOND"
		     --#TYPE
		     --#SUMMARY "Trap #$G, specific: $S, arg(1) : $1"
		     --#ARGUMENTS {}
		     --#SEVERITY  MAJOR
		     --#TIMEINDEX
		     --#HELP
		     --#HELPTAG
		     --#STATE
		::= 396001

	iodrivers396002-unsu   TRAP-TYPE
		ENTERPRISE   cdx6500
		VARIABLES    { cdx6500SNMPLastTrap }
		DESCRIPTION
		     "%s - UNSUPPORTED RECEIVE BYTE COUNT: OPERATING WITH %d RX BYTE COUNT"
		     --#TYPE
		     --#SUMMARY "Trap #$G, specific: $S, arg(1) : $1"
		     --#ARGUMENTS {}
		     --#SEVERITY  MAJOR
		     --#TIMEINDEX
		     --#HELP
		     --#HELPTAG
		     --#STATE
		::= 396002

	iodrivers396003-erro   TRAP-TYPE
		ENTERPRISE   cdx6500
		VARIABLES    { cdx6500SNMPLastTrap }
		DESCRIPTION
		     "%s - ERRONEOUS BOOLEAN PARAMETER: %s"
		     --#TYPE
		     --#SUMMARY "Trap #$G, specific: $S, arg(1) : $1"
		     --#ARGUMENTS {}
		     --#SEVERITY  MAJOR
		     --#TIMEINDEX
		     --#HELP
		     --#HELPTAG
		     --#STATE
		::= 396003

	iodrivers396004-cloc   TRAP-TYPE
		ENTERPRISE   cdx6500
		VARIABLES    { cdx6500SNMPLastTrap }
		DESCRIPTION
		     "%s - CLOCK SOURCE OVERRIDE"
		     --#TYPE
		     --#SUMMARY "Trap #$G, specific: $S, arg(1) : $1"
		     --#ARGUMENTS {}
		     --#SEVERITY  MINOR
		     --#TIMEINDEX
		     --#HELP
		     --#HELPTAG
		     --#STATE
		::= 396004

	iodrivers396005-tx-s   TRAP-TYPE
		ENTERPRISE   cdx6500
		VARIABLES    { cdx6500SNMPLastTrap }
		DESCRIPTION
		     "%s - TX SANITY TIMEOUT"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 396005

	iodrivers396006-corr   TRAP-TYPE
		ENTERPRISE   cdx6500
		VARIABLES    { cdx6500SNMPLastTrap }
		DESCRIPTION
		     "%s - CORRUTPED PCK, NULL POINTER GENERATED"
		     --#TYPE
		     --#SUMMARY "Trap #$G, specific: $S, arg(1) : $1"
		     --#ARGUMENTS {}
		     --#SEVERITY  MAJOR
		     --#TIMEINDEX
		     --#HELP
		     --#HELPTAG
		     --#STATE
		::= 396006

	qoskit400000-qos-failure   TRAP-TYPE
		ENTERPRISE   cdx6500
		VARIABLES    { cdx6500SNMPLastTrap }
		DESCRIPTION
		     "QOS FAILURE - QCL PROF #%d OF %s: %s"
		     --#TYPE
		     --#SUMMARY "Trap #$G, specific: $S, arg(1) : $1"
		     --#ARGUMENTS {}
		     --#SEVERITY  CRITICAL
		     --#TIMEINDEX
		     --#HELP
		     --#HELPTAG
		     --#STATE
		::= 400000

	qoskit400001-qos-warning   TRAP-TYPE
		ENTERPRISE   cdx6500
		VARIABLES    { cdx6500SNMPLastTrap }
		DESCRIPTION
		     "QOS: %s"
		     --#TYPE
		     --#SUMMARY "Trap #$G, specific: $S, arg(1) : $1"
		     --#ARGUMENTS {}
		     --#SEVERITY  MINOR
		     --#TIMEINDEX
		     --#HELP
		     --#HELPTAG
		     --#STATE
		::= 400001

	qoskit402000-qos-sched-be   TRAP-TYPE
		ENTERPRISE   cdx6500
		VARIABLES    { cdx6500SNMPLastTrap }
		DESCRIPTION
		     "QOS: Pck treated BE - %s not confd in Service Prof #%d used in QCL Prof #%d"
		     --#TYPE
		     --#SUMMARY "Trap #$G, specific: $S, arg(1) : $1"
		     --#ARGUMENTS {}
		     --#SEVERITY  MINOR
		     --#TIMEINDEX
		     --#HELP
		     --#HELPTAG
		     --#STATE
		::= 402000

        pbr-rept-space-unavailable  TRAP-TYPE
		ENTERPRISE   cdx6500
		VARIABLES    { cdx6500SNMPLastTrap }
		DESCRIPTION
			"PBR - Not enough memory - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 403000

        pbr-rept-ctp-error  TRAP-TYPE
		ENTERPRISE   cdx6500
		VARIABLES    { cdx6500SNMPLastTrap }
		DESCRIPTION
			"PBR - Configuration error - %s"
		     --#TYPE
		     --#SUMMARY "Trap #$G, specific: $S, arg(1) : $1"
		     --#ARGUMENTS {}
		     --#SEVERITY  WARNING
		     --#TIMEINDEX
		     --#HELP
		     --#HELPTAG
		     --#STATE
		::= 403001

        pbr-rept-flow-active  TRAP-TYPE
		ENTERPRISE   cdx6500
		VARIABLES    { cdx6500SNMPLastTrap }
		DESCRIPTION
			"PBR - Flow < %s, %s, %d, %d, %d > is active on nxthop %s"
		     --#TYPE
		     --#SUMMARY "Trap #$G, specific: $S, arg(1) : $1"
		     --#ARGUMENTS {}
		     --#SEVERITY  MINOR
		     --#TIMEINDEX
		     --#HELP
		     --#HELPTAG
		     --#STATE
		::= 403002

        pbr-rept-flow-dropped  TRAP-TYPE
		ENTERPRISE   cdx6500
		VARIABLES    { cdx6500SNMPLastTrap }
		DESCRIPTION
			"PBR - Flow < %s, %s, %d, %d, %d > is dropped by PBR"
		     --#TYPE
		     --#SUMMARY "Trap #$G, specific: $S, arg(1) : $1"
		     --#ARGUMENTS {}
		     --#SEVERITY  MINOR
		     --#TIMEINDEX
		     --#HELP
		     --#HELPTAG
		     --#STATE
		::= 403003

        pbr-rept-flow-expired  TRAP-TYPE
		ENTERPRISE   cdx6500
		VARIABLES    { cdx6500SNMPLastTrap }
		DESCRIPTION
			"PBR - Flow < %s, %s, %d, %d, %d > expired"
		     --#TYPE
		     --#SUMMARY "Trap #$G, specific: $S, arg(1) : $1"
		     --#ARGUMENTS {}
		     --#SEVERITY  MINOR
		     --#TIMEINDEX
		     --#HELP
		     --#HELPTAG
		     --#STATE
		::= 403004

        pbr-rept-flow-out-of-tow  TRAP-TYPE
		ENTERPRISE   cdx6500
		VARIABLES    { cdx6500SNMPLastTrap }
		DESCRIPTION
			"PBR - Flow < %s, %s, %d, %d, %d > is out of allowed Time of week"
		     --#TYPE
		     --#SUMMARY "Trap #$G, specific: $S, arg(1) : $1"
		     --#ARGUMENTS {}
		     --#SEVERITY  MINOR
		     --#TIMEINDEX
		     --#HELP
		     --#HELPTAG
		     --#STATE
		::= 403005

        pbr-rept-flow-nxthop-down  TRAP-TYPE
		ENTERPRISE   cdx6500
		VARIABLES    { cdx6500SNMPLastTrap }
		DESCRIPTION
			"PBR - Flow < %s, %s, %d, %d, %d > is no more active on %s"
		     --#TYPE
		     --#SUMMARY "Trap #$G, specific: $S, arg(1) : $1"
		     --#ARGUMENTS {}
		     --#SEVERITY  MINOR
		     --#TIMEINDEX
		     --#HELP
		     --#HELPTAG
		     --#STATE
		::= 403006

        pbr-rept-flow-revert-to-primary  TRAP-TYPE
		ENTERPRISE   cdx6500
		VARIABLES    { cdx6500SNMPLastTrap }
		DESCRIPTION
			"PBR - Flow < %s, %s, %d, %d, %d > has primary link available"
		     --#TYPE
		     --#SUMMARY "Trap #$G, specific: $S, arg(1) : $1"
		     --#ARGUMENTS {}
		     --#SEVERITY  MINOR
		     --#TIMEINDEX
		     --#HELP
		     --#HELPTAG
		     --#STATE
		::= 403007

        pbr-rept-cache-cleared  TRAP-TYPE
		ENTERPRISE   cdx6500
		VARIABLES    { cdx6500SNMPLastTrap }
		DESCRIPTION
			"PBR - PBR cache cleared"
		     --#TYPE
		     --#SUMMARY "Trap #$G, specific: $S, arg(1) : $1"
		     --#ARGUMENTS {}
		     --#SEVERITY  MINOR
		     --#TIMEINDEX
		     --#HELP
		     --#HELPTAG
		     --#STATE
		::= 403008

        pbr-rept-cache-overflow  TRAP-TYPE
		ENTERPRISE   cdx6500
		VARIABLES    { cdx6500SNMPLastTrap }
		DESCRIPTION
			"PBR - PBR cache overflow"
		     --#TYPE
		     --#SUMMARY "Trap #$G, specific: $S, arg(1) : $1"
		     --#ARGUMENTS {}
		     --#SEVERITY  WARNING
		     --#TIMEINDEX
		     --#HELP
		     --#HELPTAG
		     --#STATE
		::= 403009

        ruihc-rept-nomem   TRAP-TYPE
                ENTERPRISE   cdx6500
                VARIABLES    { cdx6500SNMPLastTrap }
                DESCRIPTION
                        "RUIHC-NO Memory LCON %d"
                     --#TYPE
                     --#SUMMARY "Trap #$G, specific: $S, arg(1) : $1"
                     --#ARGUMENTS {}
                     --#SEVERITY  WARNING
                     --#TIMEINDEX
                     --#HELP
                     --#HELPTAG
                     --#STATE
                ::= 404000

        ruihc-rept-ctxtoverflow TRAP-TYPE
                ENTERPRISE   cdx6500
                VARIABLES    { cdx6500SNMPLastTrap }
                DESCRIPTION
                        "RUIHC-Compressor Ctxt Overflow, LCON %d"
                     --#TYPE
                     --#SUMMARY "Trap #$G, specific: $S, arg(1) : $1"
                     --#ARGUMENTS {}
                     --#SEVERITY  WARNING
                     --#TIMEINDEX
                     --#HELP
                     --#HELPTAG
                     --#STATE
                ::= 404001

        ruihc-rept-newentryinctxt TRAP-TYPE
                ENTERPRISE   cdx6500
                VARIABLES    { cdx6500SNMPLastTrap }
                DESCRIPTION
                        "RUIHC-New CtxtEnt Added, LCON %d, srcadd %s, dstadd %s, srcport %d, dstport %d, ssrc %d"
                     --#TYPE
                     --#SUMMARY "Trap #$G, specific: $S, arg(1) : $1"
                     --#ARGUMENTS {}
                     --#SEVERITY  WARNING
                     --#TIMEINDEX
                     --#HELP
                     --#HELPTAG
                     --#STATE
                ::= 404002

        ruihc-rept-compressionstart TRAP-TYPE
                ENTERPRISE   cdx6500
                VARIABLES    { cdx6500SNMPLastTrap }
                DESCRIPTION
                        "RUIHC-Compression started  LCON %d, srcadd %s, dstadd %s, srcport %d, dstport %d, ssrc %d"
                     --#TYPE
                     --#SUMMARY "Trap #$G, specific: $S, arg(1) : $1"
                     --#ARGUMENTS {}
                     --#SEVERITY  WARNING
                     --#TIMEINDEX
                     --#HELP
                     --#HELPTAG
                     --#STATE
                ::= 404003

        ruihc-rept-ctxtentry-tmout TRAP-TYPE
                ENTERPRISE   cdx6500
                VARIABLES    { cdx6500SNMPLastTrap }
                DESCRIPTION
                        "RUIHC-Ctxt Ent Tmout, LCON %d, srcadd %s, dstadd %s, srcport %d, dstport %d, ssrc %d"
                     --#TYPE
                     --#SUMMARY "Trap #$G, specific: $S, arg(1) : $1"
                     --#ARGUMENTS {}
                     --#SEVERITY  WARNING
                     --#TIMEINDEX
                     --#HELP
                     --#HELPTAG
                     --#STATE
                ::= 404004

        ruihc-rept-movetonegcache  TRAP-TYPE
                ENTERPRISE   cdx6500
                VARIABLES    { cdx6500SNMPLastTrap }
                DESCRIPTION
                        "RUIHC-Ctxt Ent in NegCache, LCON  %d, src add %s, dst add %s, src port %d, dst port %d, ssrc %d"
                     --#TYPE
                     --#SUMMARY "Trap #$G, specific: $S, arg(1) : $1"
                     --#ARGUMENTS {}
                     --#SEVERITY  WARNING
                     --#TIMEINDEX
                     --#HELP
                     --#HELPTAG
                     --#STATE
                ::= 404005

        ruihc-rept-ctxtstpktrcvd  TRAP-TYPE
                ENTERPRISE   cdx6500
                VARIABLES    { cdx6500SNMPLastTrap }
                DESCRIPTION
                        "RUIHC-Ctxt St Packet Received, LCON  %d"
                     --#TYPE
                     --#SUMMARY "Trap #$G, specific: $S, arg(1) : $1"
                     --#ARGUMENTS {}
                     --#SEVERITY  WARNING
                     --#TIMEINDEX
                     --#HELP
                     --#HELPTAG
                     --#STATE
                ::= 404006

        ruihc-rept-ctxtnoexist  TRAP-TYPE
                ENTERPRISE   cdx6500
                VARIABLES    { cdx6500SNMPLastTrap }
                DESCRIPTION
                        "RUIHC-Ctxt State packet CID %d rejected"
                     --#TYPE
                     --#SUMMARY "Trap #$G, specific: $S, arg(1) : $1"
                     --#ARGUMENTS {}
                     --#SEVERITY  WARNING
                     --#TIMEINDEX
                     --#HELP
                     --#HELPTAG
                     --#STATE
                ::= 404007

        ruihc-rept-ctxtidmismatch TRAP-TYPE
                ENTERPRISE   cdx6500
                VARIABLES    { cdx6500SNMPLastTrap }
                DESCRIPTION
                        "RUIHC-Ctxt State packet CID size mismatch on LCON %d"
                     --#TYPE
                     --#SUMMARY "Trap #$G, specific: $S, arg(1) : $1"
                     --#ARGUMENTS {}
                     --#SEVERITY  WARNING
                     --#TIMEINDEX
                     --#HELP
                     --#HELPTAG
                     --#STATE
                ::= 404008

        ruihc-rept-nomem4newpkt  TRAP-TYPE
                ENTERPRISE   cdx6500
                VARIABLES    { cdx6500SNMPLastTrap }
                DESCRIPTION
                        "RUIHC-No MEM to send Ctxt State packet on LCON %d"
                     --#TYPE
                     --#SUMMARY "Trap #$G, specific: $S, arg(1) : $1"
                     --#ARGUMENTS {}
                     --#SEVERITY  WARNING
                     --#TIMEINDEX
                     --#HELP
                     --#HELPTAG
                     --#STATE
                ::= 404009

        ruihc-rept-conntypmismatch  TRAP-TYPE
                ENTERPRISE   cdx6500
                VARIABLES    { cdx6500SNMPLastTrap }
                DESCRIPTION
                        "RUIHC-Compressed pkt rcvd but comp typ is TRANSMIT on LCON %d"
                     --#TYPE
                     --#SUMMARY "Trap #$G, specific: $S, arg(1) : $1"
                     --#ARGUMENTS {}
                     --#SEVERITY  WARNING
                     --#TIMEINDEX
                     --#HELP
                     --#HELPTAG
                     --#STATE
                ::= 404010

        ruihc-rept-decompctxtnoexist  TRAP-TYPE
                ENTERPRISE   cdx6500
                VARIABLES    { cdx6500SNMPLastTrap }
                DESCRIPTION
                        "RUIHC-Compressed Pkt CID %d does not exist on LCON %d Decompressor"
                     --#TYPE
                     --#SUMMARY "Trap #$G, specific: $S, arg(1) : $1"
                     --#ARGUMENTS {}
                     --#SEVERITY  WARNING
                     --#TIMEINDEX
                     --#HELP
                     --#HELPTAG
                     --#STATE
                ::= 404011

        t1e1vg-HardwareFailed-OS   TRAP-TYPE
                ENTERPRISE   cdx6500
                VARIABLES    { cdx6500SNMPLastTrap }
                DESCRIPTION
                        "T1E1 Int. %d - Hardware Failed (OS Memory)"
                     --#TYPE
                     --#SUMMARY "Trap #$G, specific: $S, arg(1) : $1"
                     --#ARGUMENTS {}
                     --#SEVERITY  WARNING
                     --#TIMEINDEX
                     --#HELP
                     --#HELPTAG
                     --#STATE
                ::= 404012

        t1e1vg-HardwareFailed-DRV   TRAP-TYPE
                ENTERPRISE   cdx6500
                VARIABLES    { cdx6500SNMPLastTrap }
                DESCRIPTION
                        "T1E1 Int. %d - Hardware Failed (DRV Memory)"
                     --#TYPE
                     --#SUMMARY "Trap #$G, specific: $S, arg(1) : $1"
                     --#ARGUMENTS {}
                     --#SEVERITY  WARNING
                     --#TIMEINDEX
                     --#HELP
                     --#HELPTAG
                     --#STATE
                ::= 404013

        t1e1vg-HardwareFailed-ME   TRAP-TYPE
                ENTERPRISE   cdx6500
                VARIABLES    { cdx6500SNMPLastTrap }
                DESCRIPTION
                        "T1E1 Int. %d - Hardware Failed (ME Memory)"
                     --#TYPE
                     --#SUMMARY "Trap #$G, specific: $S, arg(1) : $1"
                     --#ARGUMENTS {}
                     --#SEVERITY  WARNING
                     --#TIMEINDEX
                     --#HELP
                     --#HELPTAG
                     --#STATE
                ::= 404014

        t1e1vg-HardwareFailed-DSL   TRAP-TYPE
                ENTERPRISE   cdx6500
                VARIABLES    { cdx6500SNMPLastTrap }
                DESCRIPTION
                        "T1E1 Int. %d - Hardware Failed (DSL Memory)"
                     --#TYPE
                     --#SUMMARY "Trap #$G, specific: $S, arg(1) : $1"
                     --#ARGUMENTS {}
                     --#SEVERITY  WARNING
                     --#TIMEINDEX
                     --#HELP
                     --#HELPTAG
                     --#STATE
                ::= 404015

        t1e1vg-ConfigurationMismatch   TRAP-TYPE
                ENTERPRISE   cdx6500
                VARIABLES    { cdx6500SNMPLastTrap }
                DESCRIPTION
                        "T1E1 Int. %d - Configuration Mismatch"
                     --#TYPE
                     --#SUMMARY "Trap #$G, specific: $S, arg(1) : $1"
                     --#ARGUMENTS {}
                     --#SEVERITY  WARNING
                     --#TIMEINDEX
                     --#HELP
                     --#HELPTAG
                     --#STATE
                ::= 404016

        t1e1vg-CMEM-error   TRAP-TYPE
                ENTERPRISE   cdx6500
                VARIABLES    { cdx6500SNMPLastTrap }
                DESCRIPTION
                        "T1E1 Int. %d - CMEM Error (CODE: %d)"
                     --#TYPE
                     --#SUMMARY "Trap #$G, specific: $S, arg(1) : $1"
                     --#ARGUMENTS {}
                     --#SEVERITY  WARNING
                     --#TIMEINDEX
                     --#HELP
                     --#HELPTAG
                     --#STATE
                ::= 404017

        t1e1vg-RemoteLoopback-InProgress   TRAP-TYPE
                ENTERPRISE   cdx6500
                VARIABLES    { cdx6500SNMPLastTrap }
                DESCRIPTION
                        "T1E1 Int. %d - Remote loopback in progress"
                     --#TYPE
                     --#SUMMARY "Trap #$G, specific: $S, arg(1) : $1"
                     --#ARGUMENTS {}
                     --#SEVERITY  WARNING
                     --#TIMEINDEX
                     --#HELP
                     --#HELPTAG
                     --#STATE
                ::= 404018

        t1e1vg-RemoteLoopback-End   TRAP-TYPE
                ENTERPRISE   cdx6500
                VARIABLES    { cdx6500SNMPLastTrap }
                DESCRIPTION
                        "T1E1 Int. %d - Remote loopback ended"
                     --#TYPE
                     --#SUMMARY "Trap #$G, specific: $S, arg(1) : $1"
                     --#ARGUMENTS {}
                     --#SEVERITY  WARNING
                     --#TIMEINDEX
                     --#HELP
                     --#HELPTAG
                     --#STATE
                ::= 404019

        t1e1vg-RAI-cleared   TRAP-TYPE
                ENTERPRISE   cdx6500
                VARIABLES    { cdx6500SNMPLastTrap }
                DESCRIPTION
                        "T1E1 Int. %d - REMOTE ALARM INDICATION: CLEARED"
                     --#TYPE
                     --#SUMMARY "Trap #$G, specific: $S, arg(1) : $1"
                     --#ARGUMENTS {}
                     --#SEVERITY  WARNING
                     --#TIMEINDEX
                     --#HELP
                     --#HELPTAG
                     --#STATE
                ::= 404020

        t1e1vg-LOF-cleared   TRAP-TYPE
                ENTERPRISE   cdx6500
                VARIABLES    { cdx6500SNMPLastTrap }
                DESCRIPTION
                        "T1E1 Int. %d - LOSS OF FRAME: CLEARED"
                     --#TYPE
                     --#SUMMARY "Trap #$G, specific: $S, arg(1) : $1"
                     --#ARGUMENTS {}
                     --#SEVERITY  WARNING
                     --#TIMEINDEX
                     --#HELP
                     --#HELPTAG
                     --#STATE
                ::= 404021

        t1e1vg-LOS-cleared   TRAP-TYPE
                ENTERPRISE   cdx6500
                VARIABLES    { cdx6500SNMPLastTrap }
                DESCRIPTION
                        "T1E1 Int. %d - LOSS OF SIGNAL: CLEARED"
                     --#TYPE
                     --#SUMMARY "Trap #$G, specific: $S, arg(1) : $1"
                     --#ARGUMENTS {}
                     --#SEVERITY  WARNING
                     --#TIMEINDEX
                     --#HELP
                     --#HELPTAG
                     --#STATE
                ::= 404022

        t1e1vg-AIS-cleared   TRAP-TYPE
                ENTERPRISE   cdx6500
                VARIABLES    { cdx6500SNMPLastTrap }
                DESCRIPTION
                        "T1E1 Int. %d - ALARM INDICATION SIGNAL: CLEARED"
                     --#TYPE
                     --#SUMMARY "Trap #$G, specific: $S, arg(1) : $1"
                     --#ARGUMENTS {}
                     --#SEVERITY  WARNING
                     --#TIMEINDEX
                     --#HELP
                     --#HELPTAG
                     --#STATE
                ::= 404023

        t1e1vg-RAI-alarm   TRAP-TYPE
                ENTERPRISE   cdx6500
                VARIABLES    { cdx6500SNMPLastTrap }
                DESCRIPTION
                        "T1E1 Int. %d - REMOTE ALARM INDICATION"
                     --#TYPE
                     --#SUMMARY "Trap #$G, specific: $S, arg(1) : $1"
                     --#ARGUMENTS {}
                     --#SEVERITY  WARNING
                     --#TIMEINDEX
                     --#HELP
                     --#HELPTAG
                     --#STATE
                ::= 404024

        t1e1vg-LOF-alarm   TRAP-TYPE
                ENTERPRISE   cdx6500
                VARIABLES    { cdx6500SNMPLastTrap }
                DESCRIPTION
                        "T1E1 Int. %d - LOSS OF FRAME"
                     --#TYPE
                     --#SUMMARY "Trap #$G, specific: $S, arg(1) : $1"
                     --#ARGUMENTS {}
                     --#SEVERITY  WARNING
                     --#TIMEINDEX
                     --#HELP
                     --#HELPTAG
                     --#STATE
                ::= 404025

        t1e1vg-LOS-alarm   TRAP-TYPE
                ENTERPRISE   cdx6500
                VARIABLES    { cdx6500SNMPLastTrap }
                DESCRIPTION
                        "T1E1 Int. %d - LOSS OF SIGNAL"
                     --#TYPE
                     --#SUMMARY "Trap #$G, specific: $S, arg(1) : $1"
                     --#ARGUMENTS {}
                     --#SEVERITY  WARNING
                     --#TIMEINDEX
                     --#HELP
                     --#HELPTAG
                     --#STATE
                ::= 404026

        t1e1vg-AIS-alarm   TRAP-TYPE
                ENTERPRISE   cdx6500
                VARIABLES    { cdx6500SNMPLastTrap }
                DESCRIPTION
                        "T1E1 Int. %d - ALARM INDICATION SIGNAL"
                     --#TYPE
                     --#SUMMARY "Trap #$G, specific: $S, arg(1) : $1"
                     --#ARGUMENTS {}
                     --#SEVERITY  WARNING
                     --#TIMEINDEX
                     --#HELP
                     --#HELPTAG
                     --#STATE
                ::= 404027

        t1e1vg-YELLOW-cleared   TRAP-TYPE
                ENTERPRISE   cdx6500
                VARIABLES    { cdx6500SNMPLastTrap }
                DESCRIPTION
                        "T1E1 Int. %d - YELLOW ALARM: CLEARED"
                     --#TYPE
                     --#SUMMARY "Trap #$G, specific: $S, arg(1) : $1"
                     --#ARGUMENTS {}
                     --#SEVERITY  WARNING
                     --#TIMEINDEX
                     --#HELP
                     --#HELPTAG
                     --#STATE
                ::= 404028

        t1e1vg-RED-cleared   TRAP-TYPE
                ENTERPRISE   cdx6500
                VARIABLES    { cdx6500SNMPLastTrap }
                DESCRIPTION
                        "T1E1 Int. %d - RED ALARM: CLEARED"
                     --#TYPE
                     --#SUMMARY "Trap #$G, specific: $S, arg(1) : $1"
                     --#ARGUMENTS {}
                     --#SEVERITY  WARNING
                     --#TIMEINDEX
                     --#HELP
                     --#HELPTAG
                     --#STATE
                ::= 404029

        t1e1vg-BLUE-cleared   TRAP-TYPE
                ENTERPRISE   cdx6500
                VARIABLES    { cdx6500SNMPLastTrap }
                DESCRIPTION
                        "T1E1 Int. %d - BLUE ALARM: CLEARED"
                     --#TYPE
                     --#SUMMARY "Trap #$G, specific: $S, arg(1) : $1"
                     --#ARGUMENTS {}
                     --#SEVERITY  WARNING
                     --#TIMEINDEX
                     --#HELP
                     --#HELPTAG
                     --#STATE
                ::= 404030

        t1e1vg-YELLOW-alarm   TRAP-TYPE
                ENTERPRISE   cdx6500
                VARIABLES    { cdx6500SNMPLastTrap }
                DESCRIPTION
                        "T1E1 Int. %d - YELLOW ALARM"
                     --#TYPE
                     --#SUMMARY "Trap #$G, specific: $S, arg(1) : $1"
                     --#ARGUMENTS {}
                     --#SEVERITY  WARNING
                     --#TIMEINDEX
                     --#HELP
                     --#HELPTAG
                     --#STATE
                ::= 404031

        t1e1vg-RED-alarm   TRAP-TYPE
                ENTERPRISE   cdx6500
                VARIABLES    { cdx6500SNMPLastTrap }
                DESCRIPTION
                        "T1E1 Int. %d - RED ALARM"
                     --#TYPE
                     --#SUMMARY "Trap #$G, specific: $S, arg(1) : $1"
                     --#ARGUMENTS {}
                     --#SEVERITY  WARNING
                     --#TIMEINDEX
                     --#HELP
                     --#HELPTAG
                     --#STATE
                ::= 404032

        t1e1vg-BLUE-alarm   TRAP-TYPE
                ENTERPRISE   cdx6500
                VARIABLES    { cdx6500SNMPLastTrap }
                DESCRIPTION
                        "T1E1 Int. %d - BLUE ALARM"
                     --#TYPE
                     --#SUMMARY "Trap #$G, specific: $S, arg(1) : $1"
                     --#ARGUMENTS {}
                     --#SEVERITY  WARNING
                     --#TIMEINDEX
                     --#HELP
                     --#HELPTAG
                     --#STATE
                ::= 404033

        t1e1vg-LES-thresholdExceed   TRAP-TYPE
                ENTERPRISE   cdx6500
                VARIABLES    { cdx6500SNMPLastTrap }
                DESCRIPTION
                        "T1/E1 Int. %d-LES THRESHOLD EXCEEDED"
                     --#TYPE
                     --#SUMMARY "Trap #$G, specific: $S, arg(1) : $1"
                     --#ARGUMENTS {}
                     --#SEVERITY  WARNING
                     --#TIMEINDEX
                     --#HELP
                     --#HELPTAG
                     --#STATE
                ::= 404034

        t1e1vg-LCV-thresholdExceed   TRAP-TYPE
                ENTERPRISE   cdx6500
                VARIABLES    { cdx6500SNMPLastTrap }
                DESCRIPTION
                        "T1/E1 Int. %d-LCV THRESHOLD EXCEEDED"
                     --#TYPE
                     --#SUMMARY "Trap #$G, specific: $S, arg(1) : $1"
                     --#ARGUMENTS {}
                     --#SEVERITY  WARNING
                     --#TIMEINDEX
                     --#HELP
                     --#HELPTAG
                     --#STATE
                ::= 404035

        t1e1vg-PCV-thresholdExceed   TRAP-TYPE
                ENTERPRISE   cdx6500
                VARIABLES    { cdx6500SNMPLastTrap }
                DESCRIPTION
                        "T1/E1 Int. %d-PCV THRESHOLD EXCEEDED"
                     --#TYPE
                     --#SUMMARY "Trap #$G, specific: $S, arg(1) : $1"
                     --#ARGUMENTS {}
                     --#SEVERITY  WARNING
                     --#TIMEINDEX
                     --#HELP
                     --#HELPTAG
                     --#STATE
                ::= 404036

        t1e1vg-CSS-thresholdExceed   TRAP-TYPE
                ENTERPRISE   cdx6500
                VARIABLES    { cdx6500SNMPLastTrap }
                DESCRIPTION
                        "T1/E1 Int. %d-CSS THRESHOLD EXCEEDED"
                     --#TYPE
                     --#SUMMARY "Trap #$G, specific: $S, arg(1) : $1"
                     --#ARGUMENTS {}
                     --#SEVERITY  WARNING
                     --#TIMEINDEX
                     --#HELP
                     --#HELPTAG
                     --#STATE
                ::= 404037

        t1e1vg-ES-thresholdExceed   TRAP-TYPE
                ENTERPRISE   cdx6500
                VARIABLES    { cdx6500SNMPLastTrap }
                DESCRIPTION
                        "T1/E1 Int. %d-ES THRESHOLD EXCEEDED"
                     --#TYPE
                     --#SUMMARY "Trap #$G, specific: $S, arg(1) : $1"
                     --#ARGUMENTS {}
                     --#SEVERITY  WARNING
                     --#TIMEINDEX
                     --#HELP
                     --#HELPTAG
                     --#STATE
                ::= 404038

        t1e1vg-BES-thresholdExceed   TRAP-TYPE
                ENTERPRISE   cdx6500
                VARIABLES    { cdx6500SNMPLastTrap }
                DESCRIPTION
                        "T1/E1 Int. %d-BES THRESHOLD EXCEEDED"
                     --#TYPE
                     --#SUMMARY "Trap #$G, specific: $S, arg(1) : $1"
                     --#ARGUMENTS {}
                     --#SEVERITY  WARNING
                     --#TIMEINDEX
                     --#HELP
                     --#HELPTAG
                     --#STATE
                ::= 404039

        t1e1vg-SES-thresholdExceed   TRAP-TYPE
                ENTERPRISE   cdx6500
                VARIABLES    { cdx6500SNMPLastTrap }
                DESCRIPTION
                        "T1/E1 Int. %d-SES THRESHOLD EXCEEDED"
                     --#TYPE
                     --#SUMMARY "Trap #$G, specific: $S, arg(1) : $1"
                     --#ARGUMENTS {}
                     --#SEVERITY  WARNING
                     --#TIMEINDEX
                     --#HELP
                     --#HELPTAG
                     --#STATE
                ::= 404040

        t1e1vg-SEFS-thresholdExceed   TRAP-TYPE
                ENTERPRISE   cdx6500
                VARIABLES    { cdx6500SNMPLastTrap }
                DESCRIPTION
                        "T1/E1 Int. %d-SEFS THRESHOLD EXCEEDED"
                     --#TYPE
                     --#SUMMARY "Trap #$G, specific: $S, arg(1) : $1"
                     --#ARGUMENTS {}
                     --#SEVERITY  WARNING
                     --#TIMEINDEX
                     --#HELP
                     --#HELPTAG
                     --#STATE
                ::= 404041

        t1e1vg-UAS-thresholdExceed   TRAP-TYPE
                ENTERPRISE   cdx6500
                VARIABLES    { cdx6500SNMPLastTrap }
                DESCRIPTION
                        "T1/E1 Int. %d-UAS THRESHOLD EXCEEDED"
                     --#TYPE
                     --#SUMMARY "Trap #$G, specific: $S, arg(1) : $1"
                     --#ARGUMENTS {}
                     --#SEVERITY  WARNING
                     --#TIMEINDEX
                     --#HELP
                     --#HELPTAG
                     --#STATE
                ::= 404042

        tdm-clk-ModuleFail-OS   TRAP-TYPE
                ENTERPRISE   cdx6500
                VARIABLES    { cdx6500SNMPLastTrap }
                DESCRIPTION
                        "TDM-CLK Module fail (OS Memory)"
                     --#TYPE
                     --#SUMMARY "Trap #$G, specific: $S, arg(1) : $1"
                     --#ARGUMENTS {}
                     --#SEVERITY  WARNING
                     --#TIMEINDEX
                     --#HELP
                     --#HELPTAG
                     --#STATE
                ::= 404043

        tdm-clk-NetworkClock-lost   TRAP-TYPE
                ENTERPRISE   cdx6500
                VARIABLES    { cdx6500SNMPLastTrap }
                DESCRIPTION
                        "Network Clock lost from TDM-%d"
                     --#TYPE
                     --#SUMMARY "Trap #$G, specific: $S, arg(1) : $1"
                     --#ARGUMENTS {}
                     --#SEVERITY  WARNING
                     --#TIMEINDEX
                     --#HELP
                     --#HELPTAG
                     --#STATE
                ::= 404044

        tdm-clk-NetworkClock-dedrives   TRAP-TYPE
                ENTERPRISE   cdx6500
                VARIABLES    { cdx6500SNMPLastTrap }
                DESCRIPTION
                        "Network Clock derives from TDM-%d"
                     --#TYPE
                     --#SUMMARY "Trap #$G, specific: $S, arg(1) : $1"
                     --#ARGUMENTS {}
                     --#SEVERITY  WARNING
                     --#TIMEINDEX
                     --#HELP
                     --#HELPTAG
                     --#STATE
                ::= 404045

        vpmt-ModuleFail-OS   TRAP-TYPE
                ENTERPRISE   cdx6500
                VARIABLES    { cdx6500SNMPLastTrap }
                DESCRIPTION
                        "VPMT Module fail (OS Memory)"
                     --#TYPE
                     --#SUMMARY "Trap #$G, specific: $S, arg(1) : $1"
                     --#ARGUMENTS {}
                     --#SEVERITY  WARNING
                     --#TIMEINDEX
                     --#HELP
                     --#HELPTAG
                     --#STATE
                ::= 404046

        vpmt-ModuleFail-VPMT   TRAP-TYPE
                ENTERPRISE   cdx6500
                VARIABLES    { cdx6500SNMPLastTrap }
                DESCRIPTION
                        "VPMT Module fail (VPMT Memory)"
                     --#TYPE
                     --#SUMMARY "Trap #$G, specific: $S, arg(1) : $1"
                     --#ARGUMENTS {}
                     --#SEVERITY  WARNING
                     --#TIMEINDEX
                     --#HELP
                     --#HELPTAG
                     --#STATE
                ::= 404047

        vpmt-ModuleFail-VPMT-CB   TRAP-TYPE
                ENTERPRISE   cdx6500
                VARIABLES    { cdx6500SNMPLastTrap }
                DESCRIPTION
                        "VPMT Module fail (VPMT-CB Memory)"
                     --#TYPE
                     --#SUMMARY "Trap #$G, specific: $S, arg(1) : $1"
                     --#ARGUMENTS {}
                     --#SEVERITY  WARNING
                     --#TIMEINDEX
                     --#HELP
                     --#HELPTAG
                     --#STATE
                ::= 404048

        isdn-isdn-pri-ACTIVE   TRAP-TYPE
                ENTERPRISE   cdx6500
                VARIABLES    { cdx6500SNMPLastTrap }
                DESCRIPTION
                        "ISDN PRI INTERFACE %d IS ACTIVE"
                     --#TYPE
                     --#SUMMARY "Trap #$G, specific: $S, arg(1) : $1"
                     --#ARGUMENTS {}
                     --#SEVERITY  WARNING
                     --#TIMEINDEX
                     --#HELP
                     --#HELPTAG
                     --#STATE
                ::= 404049

        isdn-isdn-pri-INACTIVE   TRAP-TYPE
                ENTERPRISE   cdx6500
                VARIABLES    { cdx6500SNMPLastTrap }
                DESCRIPTION
                        "ISDN PRI INTERFACE %d IS INACTIVE"
                     --#TYPE
                     --#SUMMARY "Trap #$G, specific: $S, arg(1) : $1"
                     --#ARGUMENTS {}
                     --#SEVERITY  WARNING
                     --#TIMEINDEX
                     --#HELP
                     --#HELPTAG
                     --#STATE
                ::= 404050

        isdn-isdn-pri-CALL-IN-FROM-NUM   TRAP-TYPE
                ENTERPRISE   cdx6500
                VARIABLES    { cdx6500SNMPLastTrap }
                DESCRIPTION
                        "INCOMING CALL FROM %s ON DSL %d"
                     --#TYPE
                     --#SUMMARY "Trap #$G, specific: $S, arg(1) : $1"
                     --#ARGUMENTS {}
                     --#SEVERITY  WARNING
                     --#TIMEINDEX
                     --#HELP
                     --#HELPTAG
                     --#STATE
                ::= 404051

        isdn-isdn-pri-CALL-IN-FROM-UNKNOWN   TRAP-TYPE
                ENTERPRISE   cdx6500
                VARIABLES    { cdx6500SNMPLastTrap }
                DESCRIPTION
                        "INCOMING CALL FROM UNKNOWN NUMBER ON DSL %d"
                     --#TYPE
                     --#SUMMARY "Trap #$G, specific: $S, arg(1) : $1"
                     --#ARGUMENTS {}
                     --#SEVERITY  WARNING
                     --#TIMEINDEX
                     --#HELP
                     --#HELPTAG
                     --#STATE
                ::= 404052

        isdn-isdn-pri-CALL-OUT   TRAP-TYPE
                ENTERPRISE   cdx6500
                VARIABLES    { cdx6500SNMPLastTrap }
                DESCRIPTION
                        "OUTGOING CALL TO %s ON DSL %d"
                     --#TYPE
                     --#SUMMARY "Trap #$G, specific: $S, arg(1) : $1"
                     --#ARGUMENTS {}
                     --#SEVERITY  WARNING
                     --#TIMEINDEX
                     --#HELP
                     --#HELPTAG
                     --#STATE
                ::= 404053

	aam405000-port-boot   TRAP-TYPE
		ENTERPRISE   cdx6500
		VARIABLES    { cdx6500SNMPLastTrap }
		DESCRIPTION
		     "%s - PORT BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 405000

	aam405001-port-disab   TRAP-TYPE
		ENTERPRISE   cdx6500
		VARIABLES    { cdx6500SNMPLastTrap }
		DESCRIPTION
		     "%s - PORT DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 405001

	aam405002-port-enabl   TRAP-TYPE
		ENTERPRISE   cdx6500
		VARIABLES    { cdx6500SNMPLastTrap }
		DESCRIPTION
		     "%s - PORT ENABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 405002

	aam405003-port-utili   TRAP-TYPE
		ENTERPRISE   cdx6500
		VARIABLES    { cdx6500SNMPLastTrap }
		DESCRIPTION
		     "%s - PORT UTILIZATION > THRESHOLD"
		     --#TYPE
		     --#SUMMARY "Trap #$G, specific: $S, arg(1) : $1"
		     --#ARGUMENTS {}
		     --#SEVERITY  MAJOR
		     --#TIMEINDEX
		     --#HELP
		     --#HELPTAG
		     --#STATE
		::= 405003

	aam405004-station-di   TRAP-TYPE
		ENTERPRISE   cdx6500
		VARIABLES    { cdx6500SNMPLastTrap }
		DESCRIPTION
		     "%s - STATION DISABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 405004

	aam405005-station-en   TRAP-TYPE
		ENTERPRISE   cdx6500
		VARIABLES    { cdx6500SNMPLastTrap }
		DESCRIPTION
		     "%s - STATION ENABLED"
		     --#TYPE
		     --#SUMMARY "Trap #$G, specific: $S, arg(1) : $1"
		     --#ARGUMENTS {}
		     --#SEVERITY  CRITICAL
		     --#TIMEINDEX
		     --#HELP
		     --#HELPTAG
		     --#STATE
		::= 405005

	aam405006-station-bo   TRAP-TYPE
		ENTERPRISE   cdx6500
		VARIABLES    { cdx6500SNMPLastTrap }
		DESCRIPTION
		     "%s - STATION BOOT COMPLETE"
		     --#TYPE
		     --#SUMMARY "Trap #$G, specific: $S, arg(1) : $1"
		     --#ARGUMENTS {}
		     --#SEVERITY  CRITICAL
		     --#TIMEINDEX
		     --#HELP
		     --#HELPTAG
		     --#STATE
		::= 405006

	aam405007-port-statu   TRAP-TYPE
		ENTERPRISE   cdx6500
		VARIABLES    { cdx6500SNMPLastTrap }
		DESCRIPTION
		     "%s - PORT STATUS WARNING - %s"
		     --#TYPE
		     --#SUMMARY "Trap #$G, specific: $S, arg(1) : $1"
		     --#ARGUMENTS {}
		     --#SEVERITY  MINOR
		     --#TIMEINDEX
		     --#HELP
		     --#HELPTAG
		     --#STATE
		::= 405007

	aam405008-out-of-mem   TRAP-TYPE
		ENTERPRISE   cdx6500
		VARIABLES    { cdx6500SNMPLastTrap }
		DESCRIPTION
		     "%s - OUT OF MEMORY - SOME STATIONS NOT CREATED"
		     --#TYPE
		     --#SUMMARY "Trap #$G, specific: $S, arg(1) : $1"
		     --#ARGUMENTS {}
		     --#SEVERITY  MAJOR
		     --#TIMEINDEX
		     --#HELP
		     --#HELPTAG
		     --#STATE
		::= 405008

	aamsar407000-port-er   TRAP-TYPE
		ENTERPRISE   cdx6500
		VARIABLES    { cdx6500SNMPLastTrap }
		DESCRIPTION
		     "%s - PORT ERROR"
		     --#TYPE
		     --#SUMMARY "Trap #$G, specific: $S, arg(1) : $1"
		     --#ARGUMENTS {}
		     --#SEVERITY  CRITICAL
		     --#TIMEINDEX
		     --#HELP
		     --#HELPTAG
		     --#STATE
		::= 407000

	aamsar407001-vcc-err   TRAP-TYPE
		ENTERPRISE   cdx6500
		VARIABLES    { cdx6500SNMPLastTrap }
		DESCRIPTION
		     "%s - VCC ERROR"
		     --#TYPE
		     --#SUMMARY "Trap #$G, specific: $S, arg(1) : $1"
		     --#ARGUMENTS {}
		     --#SEVERITY  CRITICAL
		     --#TIMEINDEX
		     --#HELP
		     --#HELPTAG
		     --#STATE
		::= 407001

	aamsar407002-wrong-a   TRAP-TYPE
		ENTERPRISE   cdx6500
		VARIABLES    { cdx6500SNMPLastTrap }
		DESCRIPTION
		     "%s - WRONG ATM SAR PARAMETER LIST"
		     --#TYPE
		     --#SUMMARY "Trap #$G, specific: $S, arg(1) : $1"
		     --#ARGUMENTS {}
		     --#SEVERITY  CRITICAL
		     --#TIMEINDEX
		     --#HELP
		     --#HELPTAG
		     --#STATE
		::= 407002

	aamsar407003-data-fr   TRAP-TYPE
		ENTERPRISE   cdx6500
		VARIABLES    { cdx6500SNMPLastTrap }
		DESCRIPTION
		     "%s - DATA FROM UNEXPECTED VCC CONNECTION"
		     --#TYPE
		     --#SUMMARY "Trap #$G, specific: $S, arg(1) : $1"
		     --#ARGUMENTS {}
		     --#SEVERITY  CRITICAL
		     --#TIMEINDEX
		     --#HELP
		     --#HELPTAG
		     --#STATE
		::= 407003

	aamsar407004-aal5-cp   TRAP-TYPE
		ENTERPRISE   cdx6500
		VARIABLES    { cdx6500SNMPLastTrap }
		DESCRIPTION
		     "%s - AAL5 CPCS FRAME LENGTH ERROR - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 407004

	aamsar407005-aal5-cp   TRAP-TYPE
		ENTERPRISE   cdx6500
		VARIABLES    { cdx6500SNMPLastTrap }
		DESCRIPTION
		     "%s - AAL5 CPCS FRAME UU ERROR - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 407005

	aamsar407006-aal5-cp   TRAP-TYPE
		ENTERPRISE   cdx6500
		VARIABLES    { cdx6500SNMPLastTrap }
		DESCRIPTION
		     "%s - AAL5 CPCS FRAME FLAGS ERROR - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 407006

	aamsar407007-aal5-cp   TRAP-TYPE
		ENTERPRISE   cdx6500
		VARIABLES    { cdx6500SNMPLastTrap }
		DESCRIPTION
		     "%s - AAL5 CPCS FRAME TRANSMIT ERROR"
		     --#TYPE
		     --#SUMMARY "Trap #$G, specific: $S, arg(1) : $1"
		     --#ARGUMENTS {}
		     --#SEVERITY  CRITICAL
		     --#TIMEINDEX
		     --#HELP
		     --#HELPTAG
		     --#STATE
		::= 407007

	aamsar407008-port-in   TRAP-TYPE
		ENTERPRISE   cdx6500
		VARIABLES    { cdx6500SNMPLastTrap }
		DESCRIPTION
		     "%s - PORT INITIALIZATION FAILURE"
		     --#TYPE
		     --#SUMMARY "Trap #$G, specific: $S, arg(1) : $1"
		     --#ARGUMENTS {}
		     --#SEVERITY  CRITICAL
		     --#TIMEINDEX
		     --#HELP
		     --#HELPTAG
		     --#STATE
		::= 407008

	aamsar407009-unable   TRAP-TYPE
		ENTERPRISE   cdx6500
		VARIABLES    { cdx6500SNMPLastTrap }
		DESCRIPTION
		     "%s - UNABLE TO INSTALL THE CBR SCL"
		     --#TYPE
		     --#SUMMARY "Trap #$G, specific: $S, arg(1) : $1"
		     --#ARGUMENTS {}
		     --#SEVERITY  CRITICAL
		     --#TIMEINDEX
		     --#HELP
		     --#HELPTAG
		     --#STATE
		::= 407009

	aamsar407010-unable   TRAP-TYPE
		ENTERPRISE   cdx6500
		VARIABLES    { cdx6500SNMPLastTrap }
		DESCRIPTION
		     "%s - UNABLE TO DISABLE RSM COPROCESSOR"
		     --#TYPE
		     --#SUMMARY "Trap #$G, specific: $S, arg(1) : $1"
		     --#ARGUMENTS {}
		     --#SEVERITY  CRITICAL
		     --#TIMEINDEX
		     --#HELP
		     --#HELPTAG
		     --#STATE
		::= 407010

	aamsar407011-unable   TRAP-TYPE
		ENTERPRISE   cdx6500
		VARIABLES    { cdx6500SNMPLastTrap }
		DESCRIPTION
		     "%s - UNABLE TO DISABLE SEG COPROCESSOR"
		     --#TYPE
		     --#SUMMARY "Trap #$G, specific: $S, arg(1) : $1"
		     --#ARGUMENTS {}
		     --#SEVERITY  CRITICAL
		     --#TIMEINDEX
		     --#HELP
		     --#HELPTAG
		     --#STATE
		::= 407011

	aamsar407012-unable   TRAP-TYPE
		ENTERPRISE   cdx6500
		VARIABLES    { cdx6500SNMPLastTrap }
		DESCRIPTION
		     "%s - UNABLE TO SHUTDOWN CS823X DEVICE"
		     --#TYPE
		     --#SUMMARY "Trap #$G, specific: $S, arg(1) : $1"
		     --#ARGUMENTS {}
		     --#SEVERITY  CRITICAL
		     --#TIMEINDEX
		     --#HELP
		     --#HELPTAG
		     --#STATE
		::= 407012

	aamsar407013-unable   TRAP-TYPE
		ENTERPRISE   cdx6500
		VARIABLES    { cdx6500SNMPLastTrap }
		DESCRIPTION
		     "%s - UNABLE TO ENABLE RSM COPROCESSOR"
		     --#TYPE
		     --#SUMMARY "Trap #$G, specific: $S, arg(1) : $1"
		     --#ARGUMENTS {}
		     --#SEVERITY  CRITICAL
		     --#TIMEINDEX
		     --#HELP
		     --#HELPTAG
		     --#STATE
		::= 407013

	aamsar407014-unable   TRAP-TYPE
		ENTERPRISE   cdx6500
		VARIABLES    { cdx6500SNMPLastTrap }
		DESCRIPTION
		     "%s - UNABLE TO ENABLE SEG COPROCESSOR"
		     --#TYPE
		     --#SUMMARY "Trap #$G, specific: $S, arg(1) : $1"
		     --#ARGUMENTS {}
		     --#SEVERITY  CRITICAL
		     --#TIMEINDEX
		     --#HELP
		     --#HELPTAG
		     --#STATE
		::= 407014

	aamsar407015-unable   TRAP-TYPE
		ENTERPRISE   cdx6500
		VARIABLES    { cdx6500SNMPLastTrap }
		DESCRIPTION
		     "%s - UNABLE TO ALLOCATE VCC TABLES"
		     --#TYPE
		     --#SUMMARY "Trap #$G, specific: $S, arg(1) : $1"
		     --#ARGUMENTS {}
		     --#SEVERITY  CRITICAL
		     --#TIMEINDEX
		     --#HELP
		     --#HELPTAG
		     --#STATE
		::= 407015

	aamsar407016-unable   TRAP-TYPE
		ENTERPRISE   cdx6500
		VARIABLES    { cdx6500SNMPLastTrap }
		DESCRIPTION
		     "%s - UNABLE TO ALLOCATE STATUS QUEUES"
		     --#TYPE
		     --#SUMMARY "Trap #$G, specific: $S, arg(1) : $1"
		     --#ARGUMENTS {}
		     --#SEVERITY  CRITICAL
		     --#TIMEINDEX
		     --#HELP
		     --#HELPTAG
		     --#STATE
		::= 407016

	aamsar407017-unable   TRAP-TYPE
		ENTERPRISE   cdx6500
		VARIABLES    { cdx6500SNMPLastTrap }
		DESCRIPTION
		     "%s - UNABLE TO ALLOCATE FREE BUFFER QUEUES"
		     --#TYPE
		     --#SUMMARY "Trap #$G, specific: $S, arg(1) : $1"
		     --#ARGUMENTS {}
		     --#SEVERITY  CRITICAL
		     --#TIMEINDEX
		     --#HELP
		     --#HELPTAG
		     --#STATE
		::= 407017

	aamsar407018-unable   TRAP-TYPE
		ENTERPRISE   cdx6500
		VARIABLES    { cdx6500SNMPLastTrap }
		DESCRIPTION
		     "%s - UNABLE TO ALLOCATE TRANSMIT QUEUES"
		     --#TYPE
		     --#SUMMARY "Trap #$G, specific: $S, arg(1) : $1"
		     --#ARGUMENTS {}
		     --#SEVERITY  CRITICAL
		     --#TIMEINDEX
		     --#HELP
		     --#HELPTAG
		     --#STATE
		::= 407018

	aamsar407019-unable   TRAP-TYPE
		ENTERPRISE   cdx6500
		VARIABLES    { cdx6500SNMPLastTrap }
		DESCRIPTION
		     "%s - UNABLE TO SETUP PEER WITH FBQ"
		     --#TYPE
		     --#SUMMARY "Trap #$G, specific: $S, arg(1) : $1"
		     --#ARGUMENTS {}
		     --#SEVERITY  CRITICAL
		     --#TIMEINDEX
		     --#HELP
		     --#HELPTAG
		     --#STATE
		::= 407019

	aamsar407020-unable   TRAP-TYPE
		ENTERPRISE   cdx6500
		VARIABLES    { cdx6500SNMPLastTrap }
		DESCRIPTION
		     "%s - UNABLE TO SETUP PEER WITH SEG/RSM STATUS QUEUES"
		     --#TYPE
		     --#SUMMARY "Trap #$G, specific: $S, arg(1) : $1"
		     --#ARGUMENTS {}
		     --#SEVERITY  CRITICAL
		     --#TIMEINDEX
		     --#HELP
		     --#HELPTAG
		     --#STATE
		::= 407020

	aamsar407021-unable   TRAP-TYPE
		ENTERPRISE   cdx6500
		VARIABLES    { cdx6500SNMPLastTrap }
		DESCRIPTION
		     "%s - UNABLE TO SETUP PEER WITH TRANSMIT QUEUE"
		     --#TYPE
		     --#SUMMARY "Trap #$G, specific: $S, arg(1) : $1"
		     --#ARGUMENTS {}
		     --#SEVERITY  CRITICAL
		     --#TIMEINDEX
		     --#HELP
		     --#HELPTAG
		     --#STATE
		::= 407021

	aamsar407022-unable   TRAP-TYPE
		ENTERPRISE   cdx6500
		VARIABLES    { cdx6500SNMPLastTrap }
		DESCRIPTION
		     "%s - UNABLE TO RELEASE FREE BUFFER QUEUE ID"
		     --#TYPE
		     --#SUMMARY "Trap #$G, specific: $S, arg(1) : $1"
		     --#ARGUMENTS {}
		     --#SEVERITY  CRITICAL
		     --#TIMEINDEX
		     --#HELP
		     --#HELPTAG
		     --#STATE
		::= 407022

	aamsar407023-unable   TRAP-TYPE
		ENTERPRISE   cdx6500
		VARIABLES    { cdx6500SNMPLastTrap }
		DESCRIPTION
		     "%s - UNABLE TO RELEASE RSM STATUS QUEUE ID"
		     --#TYPE
		     --#SUMMARY "Trap #$G, specific: $S, arg(1) : $1"
		     --#ARGUMENTS {}
		     --#SEVERITY  CRITICAL
		     --#TIMEINDEX
		     --#HELP
		     --#HELPTAG
		     --#STATE
		::= 407023

	aamsar407024-unable   TRAP-TYPE
		ENTERPRISE   cdx6500
		VARIABLES    { cdx6500SNMPLastTrap }
		DESCRIPTION
		     "%s - UNABLE TO RELEASE SEG STATUS QUEUE ID"
		     --#TYPE
		     --#SUMMARY "Trap #$G, specific: $S, arg(1) : $1"
		     --#ARGUMENTS {}
		     --#SEVERITY  CRITICAL
		     --#TIMEINDEX
		     --#HELP
		     --#HELPTAG
		     --#STATE
		::= 407024

	aamsar407025-vcc-ava   TRAP-TYPE
		ENTERPRISE   cdx6500
		VARIABLES    { cdx6500SNMPLastTrap }
		DESCRIPTION
		     "%s - VCC AVAILABLE QUEUE FULL"
		     --#TYPE
		     --#SUMMARY "Trap #$G, specific: $S, arg(1) : $1"
		     --#ARGUMENTS {}
		     --#SEVERITY  CRITICAL
		     --#TIMEINDEX
		     --#HELP
		     --#HELPTAG
		     --#STATE
		::= 407025

	aamsar407026-error-w   TRAP-TYPE
		ENTERPRISE   cdx6500
		VARIABLES    { cdx6500SNMPLastTrap }
		DESCRIPTION
		     "%s - ERROR WHILE REMOVING RSM VCC"
		     --#TYPE
		     --#SUMMARY "Trap #$G, specific: $S, arg(1) : $1"
		     --#ARGUMENTS {}
		     --#SEVERITY  CRITICAL
		     --#TIMEINDEX
		     --#HELP
		     --#HELPTAG
		     --#STATE
		::= 407026

	aamsar407027-error-w   TRAP-TYPE
		ENTERPRISE   cdx6500
		VARIABLES    { cdx6500SNMPLastTrap }
		DESCRIPTION
		     "%s - ERROR WHILE REMOVING SEG VCC"
		     --#TYPE
		     --#SUMMARY "Trap #$G, specific: $S, arg(1) : $1"
		     --#ARGUMENTS {}
		     --#SEVERITY  CRITICAL
		     --#TIMEINDEX
		     --#HELP
		     --#HELPTAG
		     --#STATE
		::= 407027

	aamsar407028-error-w   TRAP-TYPE
		ENTERPRISE   cdx6500
		VARIABLES    { cdx6500SNMPLastTrap }
		DESCRIPTION
		     "%s - ERROR WHILE REMOVING CBR SCL"
		     --#TYPE
		     --#SUMMARY "Trap #$G, specific: $S, arg(1) : $1"
		     --#ARGUMENTS {}
		     --#SEVERITY  CRITICAL
		     --#TIMEINDEX
		     --#HELP
		     --#HELPTAG
		     --#STATE
		::= 407028

	aamsar407029-unable   TRAP-TYPE
		ENTERPRISE   cdx6500
		VARIABLES    { cdx6500SNMPLastTrap }
		DESCRIPTION
		     "%s - UNABLE TO ENABLE RSM OAM PROCESSOR"
		     --#TYPE
		     --#SUMMARY "Trap #$G, specific: $S, arg(1) : $1"
		     --#ARGUMENTS {}
		     --#SEVERITY  CRITICAL
		     --#TIMEINDEX
		     --#HELP
		     --#HELPTAG
		     --#STATE
		::= 407029

	aamsar407030-unable   TRAP-TYPE
		ENTERPRISE   cdx6500
		VARIABLES    { cdx6500SNMPLastTrap }
		DESCRIPTION
		     "%s - UNABLE TO ALLOCATE RX HOST BUFFER DESCRIPTORS"
		     --#TYPE
		     --#SUMMARY "Trap #$G, specific: $S, arg(1) : $1"
		     --#ARGUMENTS {}
		     --#SEVERITY  CRITICAL
		     --#TIMEINDEX
		     --#HELP
		     --#HELPTAG
		     --#STATE
		::= 407030

	aamsar407031-unable   TRAP-TYPE
		ENTERPRISE   cdx6500
		VARIABLES    { cdx6500SNMPLastTrap }
		DESCRIPTION
		     "%s - UNABLE TO ALLOCATE RX BINDERS"
		     --#TYPE
		     --#SUMMARY "Trap #$G, specific: $S, arg(1) : $1"
		     --#ARGUMENTS {}
		     --#SEVERITY  CRITICAL
		     --#TIMEINDEX
		     --#HELP
		     --#HELPTAG
		     --#STATE
		::= 407031

	aamsar407032-unable   TRAP-TYPE
		ENTERPRISE   cdx6500
		VARIABLES    { cdx6500SNMPLastTrap }
		DESCRIPTION
		     "%s - UNABLE TO CREATE RSM VCC"
		     --#TYPE
		     --#SUMMARY "Trap #$G, specific: $S, arg(1) : $1"
		     --#ARGUMENTS {}
		     --#SEVERITY  CRITICAL
		     --#TIMEINDEX
		     --#HELP
		     --#HELPTAG
		     --#STATE
		::= 407032

	aamsar407033-unable   TRAP-TYPE
		ENTERPRISE   cdx6500
		VARIABLES    { cdx6500SNMPLastTrap }
		DESCRIPTION
		     "%s - UNABLE TO CREATE SEG VCC"
		     --#TYPE
		     --#SUMMARY "Trap #$G, specific: $S, arg(1) : $1"
		     --#ARGUMENTS {}
		     --#SEVERITY  CRITICAL
		     --#TIMEINDEX
		     --#HELP
		     --#HELPTAG
		     --#STATE
		::= 407033

	aamsar407034-wrong-p   TRAP-TYPE
		ENTERPRISE   cdx6500
		VARIABLES    { cdx6500SNMPLastTrap }
		DESCRIPTION
		     "%s - WRONG PCR RATE FOR VCC"
		     --#TYPE
		     --#SUMMARY "Trap #$G, specific: $S, arg(1) : $1"
		     --#ARGUMENTS {}
		     --#SEVERITY  CRITICAL
		     --#TIMEINDEX
		     --#HELP
		     --#HELPTAG
		     --#STATE
		::= 407034

	aamsar407035-wrong-v   TRAP-TYPE
		ENTERPRISE   cdx6500
		VARIABLES    { cdx6500SNMPLastTrap }
		DESCRIPTION
		     "%s - WRONG VCC CONFIGURATION"
		     --#TYPE
		     --#SUMMARY "Trap #$G, specific: $S, arg(1) : $1"
		     --#ARGUMENTS {}
		     --#SEVERITY  CRITICAL
		     --#TIMEINDEX
		     --#HELP
		     --#HELPTAG
		     --#STATE
		::= 407035

	iodrivers411000-port   TRAP-TYPE
		ENTERPRISE   cdx6500
		VARIABLES    { cdx6500SNMPLastTrap }
		DESCRIPTION
		     "%s - PORT ERROR COUNT > THRESHOLD"
		     --#TYPE
		     --#SUMMARY "Trap #$G, specific: $S, arg(1) : $1"
		     --#ARGUMENTS {}
		     --#SEVERITY  MAJOR
		     --#TIMEINDEX
		     --#HELP
		     --#HELPTAG
		     --#STATE
		::= 411000

	iodrivers411001-unsu   TRAP-TYPE
		ENTERPRISE   cdx6500
		VARIABLES    { cdx6500SNMPLastTrap }
		DESCRIPTION
		     "%s - UNSUPPORTED SPEED: OPERATING AT %d BITS PER SECOND"
		     --#TYPE
		     --#SUMMARY "Trap #$G, specific: $S, arg(1) : $1"
		     --#ARGUMENTS {}
		     --#SEVERITY  MAJOR
		     --#TIMEINDEX
		     --#HELP
		     --#HELPTAG
		     --#STATE
		::= 411001

	iodrivers411002-unsu   TRAP-TYPE
		ENTERPRISE   cdx6500
		VARIABLES    { cdx6500SNMPLastTrap }
		DESCRIPTION
		     "%s - UNSUPPORTED RECEIVE BYTE COUNT: OPERATING WITH %d RX BYTE COUNT"
		     --#TYPE
		     --#SUMMARY "Trap #$G, specific: $S, arg(1) : $1"
		     --#ARGUMENTS {}
		     --#SEVERITY  MAJOR
		     --#TIMEINDEX
		     --#HELP
		     --#HELPTAG
		     --#STATE
		::= 411002

	iodrivers411003-erro   TRAP-TYPE
		ENTERPRISE   cdx6500
		VARIABLES    { cdx6500SNMPLastTrap }
		DESCRIPTION
		     "%s - ERRONEOUS BOOLEAN PARAMETER: %s"
		     --#TYPE
		     --#SUMMARY "Trap #$G, specific: $S, arg(1) : $1"
		     --#ARGUMENTS {}
		     --#SEVERITY  MAJOR
		     --#TIMEINDEX
		     --#HELP
		     --#HELPTAG
		     --#STATE
		::= 411003

	iodrivers411004-cloc   TRAP-TYPE
		ENTERPRISE   cdx6500
		VARIABLES    { cdx6500SNMPLastTrap }
		DESCRIPTION
		     "%s - CLOCK SOURCE OVERRIDE"
		     --#TYPE
		     --#SUMMARY "Trap #$G, specific: $S, arg(1) : $1"
		     --#ARGUMENTS {}
		     --#SEVERITY  MINOR
		     --#TIMEINDEX
		     --#HELP
		     --#HELPTAG
		     --#STATE
		::= 411004

	iodrivers411005-tx-s   TRAP-TYPE
		ENTERPRISE   cdx6500
		VARIABLES    { cdx6500SNMPLastTrap }
		DESCRIPTION
		     "%s - TX SANITY TIMEOUT"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 411005

	iodrivers412000-port   TRAP-TYPE
		ENTERPRISE   cdx6500
		VARIABLES    { cdx6500SNMPLastTrap }
		DESCRIPTION
		     "%s - PORT ERROR COUNT > THRESHOLD"
		     --#TYPE
		     --#SUMMARY "Trap #$G, specific: $S, arg(1) : $1"
		     --#ARGUMENTS {}
		     --#SEVERITY  MAJOR
		     --#TIMEINDEX
		     --#HELP
		     --#HELPTAG
		     --#STATE
		::= 412000

	iodrivers412001-unsu   TRAP-TYPE
		ENTERPRISE   cdx6500
		VARIABLES    { cdx6500SNMPLastTrap }
		DESCRIPTION
		     "%s - UNSUPPORTED SPEED: OPERATING AT %d BITS PER SECOND"
		     --#TYPE
		     --#SUMMARY "Trap #$G, specific: $S, arg(1) : $1"
		     --#ARGUMENTS {}
		     --#SEVERITY  MAJOR
		     --#TIMEINDEX
		     --#HELP
		     --#HELPTAG
		     --#STATE
		::= 412001

	iodrivers412002-unsu   TRAP-TYPE
		ENTERPRISE   cdx6500
		VARIABLES    { cdx6500SNMPLastTrap }
		DESCRIPTION
		     "%s - UNSUPPORTED RECEIVE BYTE COUNT: OPERATING WITH %d RX BYTE COUNT"
		     --#TYPE
		     --#SUMMARY "Trap #$G, specific: $S, arg(1) : $1"
		     --#ARGUMENTS {}
		     --#SEVERITY  MAJOR
		     --#TIMEINDEX
		     --#HELP
		     --#HELPTAG
		     --#STATE
		::= 412002

	iodrivers412003-erro   TRAP-TYPE
		ENTERPRISE   cdx6500
		VARIABLES    { cdx6500SNMPLastTrap }
		DESCRIPTION
		     "%s - ERRONEOUS BOOLEAN PARAMETER: %s"
		     --#TYPE
		     --#SUMMARY "Trap #$G, specific: $S, arg(1) : $1"
		     --#ARGUMENTS {}
		     --#SEVERITY  MAJOR
		     --#TIMEINDEX
		     --#HELP
		     --#HELPTAG
		     --#STATE
		::= 412003

	iodrivers412004-cloc   TRAP-TYPE
		ENTERPRISE   cdx6500
		VARIABLES    { cdx6500SNMPLastTrap }
		DESCRIPTION
		     "%s - CLOCK SOURCE OVERRIDE"
		     --#TYPE
		     --#SUMMARY "Trap #$G, specific: $S, arg(1) : $1"
		     --#ARGUMENTS {}
		     --#SEVERITY  MINOR
		     --#TIMEINDEX
		     --#HELP
		     --#HELPTAG
		     --#STATE
		::= 412004

	iodrivers412005-tx-s   TRAP-TYPE
		ENTERPRISE   cdx6500
		VARIABLES    { cdx6500SNMPLastTrap }
		DESCRIPTION
		     "%s - TX SANITY TIMEOUT"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 412005

	iodrivers413000-sgno   TRAP-TYPE
		ENTERPRISE   cdx6500
		VARIABLES    { cdx6500SNMPLastTrap }
		DESCRIPTION
		     "SG-NO-THROTTLE-TIMER"
		     --#TYPE
		     --#SUMMARY "Trap #$G, specific: $S, arg(1) : $1"
		     --#ARGUMENTS {}
		     --#SEVERITY  MAJOR
		     --#TIMEINDEX
		     --#HELP
		     --#HELPTAG
		     --#STATE
		::= 413000

	iodrivers413001-sgno   TRAP-TYPE
		ENTERPRISE   cdx6500
		VARIABLES    { cdx6500SNMPLastTrap }
		DESCRIPTION
		     "SG-NO-INITIALIZATIO"
		     --#TYPE
		     --#SUMMARY "Trap #$G, specific: $S, arg(1) : $1"
		     --#ARGUMENTS {}
		     --#SEVERITY  MAJOR
		     --#TIMEINDEX
		     --#HELP
		     --#HELPTAG
		     --#STATE
		::= 413001

	iodrivers413002-sgco   TRAP-TYPE
		ENTERPRISE   cdx6500
		VARIABLES    { cdx6500SNMPLastTrap }
		DESCRIPTION
		     "SG-CONFIGURATION-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 413002

	iodrivers413003-sgia   TRAP-TYPE
		ENTERPRISE   cdx6500
		VARIABLES    { cdx6500SNMPLastTrap }
		DESCRIPTION
		     "SG-IA-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 413003

	iodrivers413004-sgco   TRAP-TYPE
		ENTERPRISE   cdx6500
		VARIABLES    { cdx6500SNMPLastTrap }
		DESCRIPTION
		     "SG-CONFIGURATION-TIMEDOU"
		     --#TYPE
		     --#SUMMARY "Trap #$G, specific: $S, arg(1) : $1"
		     --#ARGUMENTS {}
		     --#SEVERITY  MAJOR
		     --#TIMEINDEX
		     --#HELP
		     --#HELPTAG
		     --#STATE
		::= 413004

	iodrivers413005-sgno   TRAP-TYPE
		ENTERPRISE   cdx6500
		VARIABLES    { cdx6500SNMPLastTrap }
		DESCRIPTION
		     "SG-NO-SUSPENSIO"
		     --#TYPE
		     --#SUMMARY "Trap #$G, specific: $S, arg(1) : $1"
		     --#ARGUMENTS {}
		     --#SEVERITY  MAJOR
		     --#TIMEINDEX
		     --#HELP
		     --#HELPTAG
		     --#STATE
		::= 413005

	iodrivers413006-sgtx   TRAP-TYPE
		ENTERPRISE   cdx6500
		VARIABLES    { cdx6500SNMPLastTrap }
		DESCRIPTION
		     "SG-TX-LIST-PUT-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 413006

	iodrivers413007-sgex   TRAP-TYPE
		ENTERPRISE   cdx6500
		VARIABLES    { cdx6500SNMPLastTrap }
		DESCRIPTION
		     "SG-EXCESSIVE-TX-ERROR"
		     --#TYPE
		     --#SUMMARY "Trap #$G, specific: $S, arg(1) : $1"
		     --#ARGUMENTS {}
		     --#SEVERITY  MAJOR
		     --#TIMEINDEX
		     --#HELP
		     --#HELPTAG
		     --#STATE
		::= 413007

	iodrivers413008-sglo   TRAP-TYPE
		ENTERPRISE   cdx6500
		VARIABLES    { cdx6500SNMPLastTrap }
		DESCRIPTION
		     "SG-LOSS-OF-CARRIE"
		     --#TYPE
		     --#SUMMARY "Trap #$G, specific: $S, arg(1) : $1"
		     --#ARGUMENTS {}
		     --#SEVERITY  MAJOR
		     --#TIMEINDEX
		     --#HELP
		     --#HELPTAG
		     --#STATE
		::= 413008

	iodrivers413009-sgex   TRAP-TYPE
		ENTERPRISE   cdx6500
		VARIABLES    { cdx6500SNMPLastTrap }
		DESCRIPTION
		     "SG-EXCESSIVE-RX-ERROR"
		     --#TYPE
		     --#SUMMARY "Trap #$G, specific: $S, arg(1) : $1"
		     --#ARGUMENTS {}
		     --#SEVERITY  MAJOR
		     --#TIMEINDEX
		     --#HELP
		     --#HELPTAG
		     --#STATE
		::= 413009

	iodrivers413010-sgex   TRAP-TYPE
		ENTERPRISE   cdx6500
		VARIABLES    { cdx6500SNMPLastTrap }
		DESCRIPTION
		     "SG-EXCESSIVE-TX-CLEA"
		     --#TYPE
		     --#SUMMARY "Trap #$G, specific: $S, arg(1) : $1"
		     --#ARGUMENTS {}
		     --#SEVERITY  MAJOR
		     --#TIMEINDEX
		     --#HELP
		     --#HELPTAG
		     --#STATE
		::= 413010

	iodrivers413011-sglo   TRAP-TYPE
		ENTERPRISE   cdx6500
		VARIABLES    { cdx6500SNMPLastTrap }
		DESCRIPTION
		     "SG-LOSS-OF-CARRIER-CLEA"
		     --#TYPE
		     --#SUMMARY "Trap #$G, specific: $S, arg(1) : $1"
		     --#ARGUMENTS {}
		     --#SEVERITY  MAJOR
		     --#TIMEINDEX
		     --#HELP
		     --#HELPTAG
		     --#STATE
		::= 413011

	iodrivers413012-sgex   TRAP-TYPE
		ENTERPRISE   cdx6500
		VARIABLES    { cdx6500SNMPLastTrap }
		DESCRIPTION
		     "SG-EXCESSIVE-RX-CLEA"
		     --#TYPE
		     --#SUMMARY "Trap #$G, specific: $S, arg(1) : $1"
		     --#ARGUMENTS {}
		     --#SEVERITY  MAJOR
		     --#TIMEINDEX
		     --#HELP
		     --#HELPTAG
		     --#STATE
		::= 413012

	iodrivers413013-sgin   TRAP-TYPE
		ENTERPRISE   cdx6500
		VARIABLES    { cdx6500SNMPLastTrap }
		DESCRIPTION
		     "SG-INVALID-STATE-ENABLE"
		     --#TYPE
		     --#SUMMARY "Trap #$G, specific: $S, arg(1) : $1"
		     --#ARGUMENTS {}
		     --#SEVERITY  MAJOR
		     --#TIMEINDEX
		     --#HELP
		     --#HELPTAG
		     --#STATE
		::= 413013

	iodrivers413014-sgin   TRAP-TYPE
		ENTERPRISE   cdx6500
		VARIABLES    { cdx6500SNMPLastTrap }
		DESCRIPTION
		     "SG-INVALID-STATE-DISABLE"
		     --#TYPE
		     --#SUMMARY "Trap #$G, specific: $S, arg(1) : $1"
		     --#ARGUMENTS {}
		     --#SEVERITY  MAJOR
		     --#TIMEINDEX
		     --#HELP
		     --#HELPTAG
		     --#STATE
		::= 413014

	iodrivers413015-sglo   TRAP-TYPE
		ENTERPRISE   cdx6500
		VARIABLES    { cdx6500SNMPLastTrap }
		DESCRIPTION
		     "SG-LOOPBACK-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 413015

	iodrivers413016-sgtd   TRAP-TYPE
		ENTERPRISE   cdx6500
		VARIABLES    { cdx6500SNMPLastTrap }
		DESCRIPTION
		     "SG-TDR-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 413016

	iodrivers413017-sgca   TRAP-TYPE
		ENTERPRISE   cdx6500
		VARIABLES    { cdx6500SNMPLastTrap }
		DESCRIPTION
		     "SG-CA-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 413017

	iodrivers413018-sgrx   TRAP-TYPE
		ENTERPRISE   cdx6500
		VARIABLES    { cdx6500SNMPLastTrap }
		DESCRIPTION
		     "SG-RX-LIST-ERRO"
		     --#TYPE
		     --#SUMMARY "Trap #$G, specific: $S, arg(1) : $1"
		     --#ARGUMENTS {}
		     --#SEVERITY  MAJOR
		     --#TIMEINDEX
		     --#HELP
		     --#HELPTAG
		     --#STATE
		::= 413018

	iodrivers413019-sgtx   TRAP-TYPE
		ENTERPRISE   cdx6500
		VARIABLES    { cdx6500SNMPLastTrap }
		DESCRIPTION
		     "SG-TX-LIST-ERRO"
		     --#TYPE
		     --#SUMMARY "Trap #$G, specific: $S, arg(1) : $1"
		     --#ARGUMENTS {}
		     --#SEVERITY  MAJOR
		     --#TIMEINDEX
		     --#HELP
		     --#HELPTAG
		     --#STATE
		::= 413019

	iodrivers413020-sglo   TRAP-TYPE
		ENTERPRISE   cdx6500
		VARIABLES    { cdx6500SNMPLastTrap }
		DESCRIPTION
		     "SG-LOCKUP-ERRO"
		     --#TYPE
		     --#SUMMARY "Trap #$G, specific: $S, arg(1) : $1"
		     --#ARGUMENTS {}
		     --#SEVERITY  MAJOR
		     --#TIMEINDEX
		     --#HELP
		     --#HELPTAG
		     --#STATE
		::= 413020

	iodrivers413021-sgfp   TRAP-TYPE
		ENTERPRISE   cdx6500
		VARIABLES    { cdx6500SNMPLastTrap }
		DESCRIPTION
		     "SG-FPGA-INIT-FAILE"
		     --#TYPE
		     --#SUMMARY "Trap #$G, specific: $S, arg(1) : $1"
		     --#ARGUMENTS {}
		     --#SEVERITY  MAJOR
		     --#TIMEINDEX
		     --#HELP
		     --#HELPTAG
		     --#STATE
		::= 413021

	tdmclk415000-tdmclk   TRAP-TYPE
		ENTERPRISE   cdx6500
		VARIABLES    { cdx6500SNMPLastTrap }
		DESCRIPTION
		     "TDM-CLK Module fail (OS Memory)"
		     --#TYPE
		     --#SUMMARY "Trap #$G, specific: $S, arg(1) : $1"
		     --#ARGUMENTS {}
		     --#SEVERITY  CRITICAL
		     --#TIMEINDEX
		     --#HELP
		     --#HELPTAG
		     --#STATE
		::= 415000

	router417000-nat-pkt   TRAP-TYPE
		ENTERPRISE   cdx6500
		VARIABLES    { cdx6500SNMPLastTrap }
		DESCRIPTION
		     "nat pkt i-cflag=%d  i-cache=%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 417000

	router417001-nat-add   TRAP-TYPE
		ENTERPRISE   cdx6500
		VARIABLES    { cdx6500SNMPLastTrap }
		DESCRIPTION
		     "nat addfeature i-cflag=%d  i-cache=%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 417001

	router417002-nat-act   TRAP-TYPE
		ENTERPRISE   cdx6500
		VARIABLES    { cdx6500SNMPLastTrap }
		DESCRIPTION
		     "nat activate i-cflag=%d  i-cache=%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 417002

	router417003-nat-pkt   TRAP-TYPE
		ENTERPRISE   cdx6500
		VARIABLES    { cdx6500SNMPLastTrap }
		DESCRIPTION
		     "nat pkt DROP prtcl%d sport%d dport%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 417003

	wa421000-not-enough   TRAP-TYPE
		ENTERPRISE   cdx6500
		VARIABLES    { cdx6500SNMPLastTrap }
		DESCRIPTION
		     "Not enough memory - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 421000

	wa421001-unsupported   TRAP-TYPE
		ENTERPRISE   cdx6500
		VARIABLES    { cdx6500SNMPLastTrap }
		DESCRIPTION
		     "Unsupported or invalid Protocol Packet is to be sent on RFC1483-LLC-SNAP LCON-%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 421001

	wa421002-unsupported   TRAP-TYPE
		ENTERPRISE   cdx6500
		VARIABLES    { cdx6500SNMPLastTrap }
		DESCRIPTION
		     "Unsupported or invalid  Protocol Packet received on rfc1483-LLC-SNAP  LCON-%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 421002

	wa421003-unsupported   TRAP-TYPE
		ENTERPRISE   cdx6500
		VARIABLES    { cdx6500SNMPLastTrap }
		DESCRIPTION
		     "Unsupported or invalid  Protocol Packet is to be sent on rfc1483-VC-MUX LCON-%d"
		     --#TYPE
		     --#SUMMARY "Trap #$G, specific: $S, arg(1) : $1"
		     --#ARGUMENTS {}
		     --#SEVERITY  CRITICAL
		     --#TIMEINDEX
		     --#HELP
		     --#HELPTAG
		     --#STATE
		::= 421003

	wa421004-bridged-or   TRAP-TYPE
		ENTERPRISE   cdx6500
		VARIABLES    { cdx6500SNMPLastTrap }
		DESCRIPTION
		     "Bridged or Routed packet received  with invalid rfc1483 encapsulation on LCON-%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 421004

	router422000-ipoatm   TRAP-TYPE
		ENTERPRISE   cdx6500
		VARIABLES    { cdx6500SNMPLastTrap }
		DESCRIPTION
		     "IPOATM - Not enough memory - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 422000

	router422001-ipoatm   TRAP-TYPE
		ENTERPRISE   cdx6500
		VARIABLES    { cdx6500SNMPLastTrap }
		DESCRIPTION
		     "IPOATM - Error in ATMARP Packet received on LCON-%d - %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 422001

	router422002-ipoatm   TRAP-TYPE
		ENTERPRISE   cdx6500
		VARIABLES    { cdx6500SNMPLastTrap }
		DESCRIPTION
		     "IPOATM - Error in InATMARP Packet received on LCON-%d - %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 422002

	router422003-ipoatm   TRAP-TYPE
		ENTERPRISE   cdx6500
		VARIABLES    { cdx6500SNMPLastTrap }
		DESCRIPTION
		     "IPOATM - InATMARP %s received on LCON-%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 422003

	router422004-ipoatm   TRAP-TYPE
		ENTERPRISE   cdx6500
		VARIABLES    { cdx6500SNMPLastTrap }
		DESCRIPTION
		     "IPOATM - InATMARP %s sent on LCON-%d"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 422004

	router422005-ipoatm   TRAP-TYPE
		ENTERPRISE   cdx6500
		VARIABLES    { cdx6500SNMPLastTrap }
		DESCRIPTION
		     "IPOATM - InATMARP %s received on LCON-%d with out of LIS remote IP Address %s"
		     --#TYPE
		     --#SUMMARY "Trap #$G, specific: $S, arg(1) : $1"
		     --#ARGUMENTS {}
		     --#SEVERITY  MAJOR
		     --#TIMEINDEX
		     --#HELP
		     --#HELPTAG
		     --#STATE
		::= 422005

	router422006-ipoatm   TRAP-TYPE
		ENTERPRISE   cdx6500
		VARIABLES    { cdx6500SNMPLastTrap }
		DESCRIPTION
		     "IPOATM - InATMARP %s received on LCON-%d with duplicate remote IP Address %s"
		     --#TYPE
		     --#SUMMARY "Trap #$G, specific: $S, arg(1) : $1"
		     --#ARGUMENTS {}
		     --#SEVERITY  MAJOR
		     --#TIMEINDEX
		     --#HELP
		     --#HELPTAG
		     --#STATE
		::= 422006

	router422007-ipoatm   TRAP-TYPE
		ENTERPRISE   cdx6500
		VARIABLES    { cdx6500SNMPLastTrap }
		DESCRIPTION
		     "IPOATM - Remote IP Address changed on LCON-%d, new IP Address %s"
		     --#TYPE
		     --#SUMMARY "Trap #$G, specific: $S, arg(1) : $1"
		     --#ARGUMENTS {}
		     --#SEVERITY  CRITICAL
		     --#TIMEINDEX
		     --#HELP
		     --#HELPTAG
		     --#STATE
		::= 422007

	router422008-ipoatm   TRAP-TYPE
		ENTERPRISE   cdx6500
		VARIABLES    { cdx6500SNMPLastTrap }
		DESCRIPTION
		     "IPOATM - MAX InATMARP retries over on LCON-%d"
		     --#TYPE
		     --#SUMMARY "Trap #$G, specific: $S, arg(1) : $1"
		     --#ARGUMENTS {}
		     --#SEVERITY  MINOR
		     --#TIMEINDEX
		     --#HELP
		     --#HELPTAG
		     --#STATE
		::= 422008

	tnl-nomem-rec   TRAP-TYPE
		ENTERPRISE   cdx6500
		VARIABLES    { cdx6500SNMPLastTrap }
		DESCRIPTION
		     "TUNNEL - Not enough memory - %s"
		     --#TYPE
		     --#SUMMARY "Trap #$G, specific: $S, arg(1) : $1"
		     --#ARGUMENTS {}
		     --#SEVERITY  CRITICAL
		     --#TIMEINDEX
		     --#HELP
		     --#HELPTAG
		     --#STATE
		::= 426000

	tnl-duplicate-rec   TRAP-TYPE
		ENTERPRISE   cdx6500
		VARIABLES    { cdx6500SNMPLastTrap }
		DESCRIPTION
		     "TUNNEL Table entry no %d duplicate of entry no %d"
		     --#TYPE
		     --#SUMMARY "Trap #$G, specific: $S, arg(1) : $1"
		     --#ARGUMENTS {}
		     --#SEVERITY  WARNING
		     --#TIMEINDEX
		     --#HELP
		     --#HELPTAG
		     --#STATE
		::= 426001

	tnl-improper-config   TRAP-TYPE
		ENTERPRISE   cdx6500
		VARIABLES    { cdx6500SNMPLastTrap }
		DESCRIPTION
		     "TUNNEL - Configuration Error - %s"
		     --#TYPE
		     --#SUMMARY "Trap #$G, specific: $S, arg(1) : $1"
		     --#ARGUMENTS {}
		     --#SEVERITY  MAJOR
		     --#TIMEINDEX
		     --#HELP
		     --#HELPTAG
		     --#STATE
		::= 426002

	tnl-pck   TRAP-TYPE
		ENTERPRISE   cdx6500
		VARIABLES    { cdx6500SNMPLastTrap }
		DESCRIPTION
		     "TUNNEL - %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426003

	tnl-chan-open   TRAP-TYPE
		ENTERPRISE   cdx6500
		VARIABLES    { cdx6500SNMPLastTrap }
		DESCRIPTION
		     "TNL-ENCR Channel opened for %s -> %s "
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426004

	tnl-chan-closed   TRAP-TYPE
		ENTERPRISE   cdx6500
		VARIABLES    { cdx6500SNMPLastTrap }
		DESCRIPTION
		     "TNL-ENCR Channel closed for %s -> %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426005

	tnl-encr-pck   TRAP-TYPE
		ENTERPRISE   cdx6500
		VARIABLES    { cdx6500SNMPLastTrap }
		DESCRIPTION
		     "Packet is Encrypted on tunnel# %d with src %s dst %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426006

	tnl-decr-pck   TRAP-TYPE
		ENTERPRISE   cdx6500
		VARIABLES    { cdx6500SNMPLastTrap }
		DESCRIPTION
		     "Packet is Decrypted on tunnel# %d with src %s dst %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426007

	tnl-queue-full   TRAP-TYPE
		ENTERPRISE   cdx6500
		VARIABLES    { cdx6500SNMPLastTrap }
		DESCRIPTION
		     "TNL-ENCR- Tunnel queue Full"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426008

	tnl-wrong-encrpck   TRAP-TYPE
		ENTERPRISE   cdx6500
		VARIABLES    { cdx6500SNMPLastTrap }
		DESCRIPTION
		     "TNL-ENCR - Unknown packet %d"
		     --#TYPE
		     --#SUMMARY "Trap #$G, specific: $S, arg(1) : $1"
		     --#ARGUMENTS {}
		     --#SEVERITY  WARNING
		     --#TIMEINDEX
		     --#HELP
		     --#HELPTAG
		     --#STATE
		::= 426009

	tnl-queue-flush   TRAP-TYPE
		ENTERPRISE   cdx6500
		VARIABLES    { cdx6500SNMPLastTrap }
		DESCRIPTION
		     "TNL-ENCR - Tunnel queue Flush"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426010

	tnl-cache-del   TRAP-TYPE
		ENTERPRISE   cdx6500
		VARIABLES    { cdx6500SNMPLastTrap }
		DESCRIPTION
		     "TUNNEL - Tunnel cache entry %s -> %s deleted"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426011

	tnl-cache-clr   TRAP-TYPE
		ENTERPRISE   cdx6500
		VARIABLES    { cdx6500SNMPLastTrap }
		DESCRIPTION
		     "TUNNEL - Tunnel cache cleared"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426012

	tnl-cache-garbage   TRAP-TYPE
		ENTERPRISE   cdx6500
		VARIABLES    { cdx6500SNMPLastTrap }
		DESCRIPTION
		     "TUNNEL - Tunnel cache garbage collecting..."
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426013

	tnl-gen   TRAP-TYPE
		ENTERPRISE   cdx6500
		VARIABLES    { cdx6500SNMPLastTrap }
		DESCRIPTION
		     "TUNNEL no %d - %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426014

	tnl-cache-notim   TRAP-TYPE
		ENTERPRISE   cdx6500
		VARIABLES    { cdx6500SNMPLastTrap }
		DESCRIPTION
		     "TUNNEL  %s"
		     --#TYPE
		     --#SUMMARY "Trap #$G, specific: $S, arg(1) : $1"
		     --#ARGUMENTS {}
		     --#SEVERITY  WARNING
		     --#TIMEINDEX
		     --#HELP
		     --#HELPTAG
		     --#STATE
		::= 426015

	tnl-brdg-mod-err   TRAP-TYPE
		ENTERPRISE   cdx6500
		VARIABLES    { cdx6500SNMPLastTrap }
		DESCRIPTION
		     "TUNNEL  Tnl no %d Bridge Link no %d %s"
		     --#TYPE
		     --#SUMMARY "Trap #$G, specific: $S, arg(1) : $1"
		     --#ARGUMENTS {}
		     --#SEVERITY  MINOR
		     --#TIMEINDEX
		     --#HELP
		     --#HELPTAG
		     --#STATE
		::= 426016

	tnl-seq-no-debug   TRAP-TYPE
		ENTERPRISE   cdx6500
		VARIABLES    { cdx6500SNMPLastTrap }
		DESCRIPTION
		      "TUNNEL %s"
		     --#TYPE
		     --#SUMMARY "Trap #$G, specific: $S, arg(1) : $1"
		     --#ARGUMENTS {}
		     --#SEVERITY  INFORMATIONAL
		     --#TIMEINDEX
		     --#HELP
		     --#HELPTAG
		     --#STATE
		::= 426017

	tnl-ruihc-err   TRAP-TYPE
		ENTERPRISE   cdx6500
		VARIABLES    { cdx6500SNMPLastTrap }
		DESCRIPTION
		     "TUNNEL no %d - %s"
		     --#TYPE
		     --#SUMMARY "Trap #$G, specific: $S, arg(1) : $1"
		     --#ARGUMENTS {}
		     --#SEVERITY  MINOR
		     --#TIMEINDEX
		     --#HELP
		     --#HELPTAG
		     --#STATE
		::= 426018

	tnl-encr-err   TRAP-TYPE
		ENTERPRISE   cdx6500
		VARIABLES    { cdx6500SNMPLastTrap }
		DESCRIPTION
		     "TUNNEL no %d - %s"
		     --#TYPE
		     --#SUMMARY "Trap #$G, specific: $S, arg(1) : $1"
		     --#ARGUMENTS {}
		     --#SEVERITY  MINOR
		     --#TIMEINDEX
		     --#HELP
		     --#HELPTAG
		     --#STATE
		::= 426019

END
