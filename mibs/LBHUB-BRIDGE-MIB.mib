-- Copyright 1995 by 3Com Corporation.  All rights reserved.
-- MIB file name:  lbhub-bridge.mib
-- available in these 3Com devices:  MSH hubs
-- For support or more info, check 3Com's web page at http://www.3com.com

-- **********************************************************************
--
-- Product:		XXXXXXX
-- MIB Version:		XXXXXXX
-- Comments:		xxxxxxxxxxxxxxxxxxxxxxxxxxxxxxxxxxxxxxxxx
--			xxxxxxxxxxxxxxxxxxxxxxxxxxxxxxxxxxxxxxxxx
-- History:		Date			Reason For Change
--			====			=================
--			December 22, 1993	Initial Version.
--
-- **********************************************************************
--	Copyright 3Com Technologies Limited (1993)
-- **********************************************************************



-- --------------------------------------------------------------------
-- ************ THE STARTING POINT FOR ALL MIB DEFINITIONS ************
-- --------------------------------------------------------------------

          LBHUB-BRIDGE-MIB DEFINITIONS ::= BEGIN

          IMPORTS
                  mgmt, NetworkAddress, IpAddress, Counter, Gauge,
                          TimeTicks, enterprises
                      FROM RFC1155-SMI
                  OBJECT-TYPE
		      FROM RFC-1212
		  TRAP-TYPE
		      FROM RFC-1215
		  DisplayString, PhysAddress -- , snmp, ifIndex
		      FROM RFC1213-MIB;

          --  This MIB module uses the extended OBJECT-TYPE macro as
          --  defined in RFC 1212;

          --  MIB-II (same prefix as MIB-I)

          mib-2      OBJECT IDENTIFIER ::= { mgmt 1 }

          -- textual conventions

          DisplayString ::= OCTET STRING
          -- This data type is used to model textual information taken
          -- from the NVT ASCII character set.  By convention, objects
          -- with this syntax are declared as having
          --
          --      SIZE (0..255)

          PhysAddress ::= OCTET STRING
          -- This data type is used to model media addresses.  For many
          -- types of media, this will be in a binary representation.
          -- For example, an ethernet address would be represented as
          -- a string of 6 octets.
--
--	Generic Bridge Control MIB.
--

-- --------------------------------------------------------------------
-- ******************* PRIVATE BRANCH FOR 3Com ************************
-- --------------------------------------------------------------------

-- private		OBJECT IDENTIFIER ::= { internet 4 }
-- enterprises	OBJECT IDENTIFIER ::= { private 1 }

a3Com		OBJECT IDENTIFIER ::= { enterprises 43 }

products	OBJECT IDENTIFIER ::= { a3Com 1 }

	terminalServer		OBJECT IDENTIFIER ::= { products 1 }
	dedicatedBridgeServer	OBJECT IDENTIFIER ::= { products 2 }
	dedicatedRouteServer	OBJECT IDENTIFIER ::= { products 3 }
	brouter			OBJECT IDENTIFIER ::= { products 4 }
	genericMSWorkstation	OBJECT IDENTIFIER ::= { products 5 }
	genericMSServer		OBJECT IDENTIFIER ::= { products 6 }
	genericUnixServer	OBJECT IDENTIFIER ::= { products 7 }
	hub			OBJECT IDENTIFIER ::= { products 8 }
	cards			OBJECT IDENTIFIER ::= { products 9 }

		linkBuilder3GH		OBJECT IDENTIFIER ::= { hub 1 }
		linkBuilder10BTi	OBJECT IDENTIFIER ::= { hub 2 }
		linkBuilderECS		OBJECT IDENTIFIER ::= { hub 3 }
		linkBuilderMSH		OBJECT IDENTIFIER ::= { hub 4 }
		linkBuilderFMS		OBJECT IDENTIFIER ::= { hub 5 }
		linkBuilderFMSII	OBJECT IDENTIFIER ::= { hub 7 }
		linkBuilderFMSLBridge	OBJECT IDENTIFIER ::= { hub 10 }

		linkBuilder3GH-cards	OBJECT IDENTIFIER ::= { cards 1 }
		linkBuilder10BTi-cards	OBJECT IDENTIFIER ::= { cards 2 }
		linkBuilderECS-cards	OBJECT IDENTIFIER ::= { cards 3 }
		linkBuilderMSH-cards	OBJECT IDENTIFIER ::= { cards 4 }
		linkBuilderFMS-cards	OBJECT IDENTIFIER ::= { cards 5 }
		linkBuilderFMSII-cards	OBJECT IDENTIFIER ::= { cards 6 }

			linkBuilder10BTi-cards-utp	OBJECT IDENTIFIER ::= { linkBuilder10BTi-cards 1 }
			linkBuilder10BT-cards-utp	OBJECT IDENTIFIER ::= { linkBuilder10BTi-cards 2 }

			linkBuilderFMS-cards-utp	OBJECT IDENTIFIER ::= { linkBuilderFMS-cards 1 }
			linkBuilderFMS-cards-coax	OBJECT IDENTIFIER ::= { linkBuilderFMS-cards 2 }
			linkBuilderFMS-cards-fiber	OBJECT IDENTIFIER ::= { linkBuilderFMS-cards 3 }
			linkBuilderFMS-cards-12fiber	OBJECT IDENTIFIER ::= { linkBuilderFMS-cards 4 }
			linkBuilderFMS-cards-24utp	OBJECT IDENTIFIER ::= { linkBuilderFMS-cards 5 }

			linkBuilderFMSII-cards-12tp-rj45	OBJECT IDENTIFIER ::= { linkBuilderFMSII-cards 1 }
			linkBuilderFMSII-cards-10coax-bnc	OBJECT IDENTIFIER ::= { linkBuilderFMSII-cards 2 }
			linkBuilderFMSII-cards-6fiber-st	OBJECT IDENTIFIER ::= { linkBuilderFMSII-cards 3 }
			linkBuilderFMSII-cards-12fiber-st	OBJECT IDENTIFIER ::= { linkBuilderFMSII-cards 4 }
			linkBuilderFMSII-cards-24tp-rj45	OBJECT IDENTIFIER ::= { linkBuilderFMSII-cards 5 }
			linkBuilderFMSII-cards-24tp-telco	OBJECT IDENTIFIER ::= { linkBuilderFMSII-cards 6 }

--experimental		OBJECT IDENTIFIER ::= { a3Com 2 }
amp-mib			OBJECT IDENTIFIER ::= { a3Com 3 }
genericTrap		OBJECT IDENTIFIER ::= { a3Com 4 }
viewBuilderApps		OBJECT IDENTIFIER ::= { a3Com 5 }
specificTrap		OBJECT IDENTIFIER ::= { a3Com 6 }
linkBuilder3GH-mib	OBJECT IDENTIFIER ::= { a3Com 7 }
linkBuilder10BTi-mib 	OBJECT IDENTIFIER ::= { a3Com 8 }
linkBuilderECS-mib	OBJECT IDENTIFIER ::= { a3Com 9 }
generic			OBJECT IDENTIFIER ::= { a3Com 10 }

        genExperimental 	OBJECT IDENTIFIER ::= { generic 1 }
	setup			OBJECT IDENTIFIER ::= { generic 2 }
	sysLoader		OBJECT IDENTIFIER ::= { generic 3 }
	security		OBJECT IDENTIFIER ::= { generic 4 }
	gauges			OBJECT IDENTIFIER ::= { generic 5 }
	asciiAgent		OBJECT IDENTIFIER ::= { generic 6 }
	serialIf		OBJECT IDENTIFIER ::= { generic 7 }
	repeaterMgmt		OBJECT IDENTIFIER ::= { generic 8 }
	endStation		OBJECT IDENTIFIER ::= { generic 9 }
	localSnmp		OBJECT IDENTIFIER ::= { generic 10 }
	manager			OBJECT IDENTIFIER ::= { generic 11 }
	unusedGeneric12		OBJECT IDENTIFIER ::= { generic 12 }
	chassis			OBJECT IDENTIFIER ::= { generic 14 }
	mrmResilience		OBJECT IDENTIFIER ::= { generic 15 }
	tokenRing		OBJECT IDENTIFIER ::= { generic 16 }
	multiRepeater 		OBJECT IDENTIFIER ::= { generic 17 }
	bridgeMgmt		OBJECT IDENTIFIER ::= { generic 18 }
	fault			OBJECT IDENTIFIER ::= { generic 19 }
	poll			OBJECT IDENTIFIER ::= { generic 20 }
	powerSupply		OBJECT IDENTIFIER ::= { generic 21 }

		testData	OBJECT IDENTIFIER ::= { genExperimental 1 }
		ifExtensions	OBJECT IDENTIFIER ::= { genExperimental 2 }

netBuilder-mib		OBJECT IDENTIFIER ::= { a3Com 11 }
lBridgeECS-mib		OBJECT IDENTIFIER ::= { a3Com 12 }
deskMan-mib		OBJECT IDENTIFIER ::= { a3Com 13 }
linkBuilderMSH-mib	OBJECT IDENTIFIER ::= { a3Com 14 }


brControlPackage	OBJECT IDENTIFIER ::= { bridgeMgmt 1}
brMonitorPackage	OBJECT IDENTIFIER ::= { bridgeMgmt 2}
brDialoguePackage	OBJECT IDENTIFIER ::= { bridgeMgmt 3}

brClearCounters OBJECT-TYPE
	SYNTAX			INTEGER {
					no-action(1),
					clear(2)
					}
	ACCESS			read-write
	STATUS			mandatory
	DESCRIPTION
				"Clears all the counters associated with the bridgeing
				 function for all bridge ports. A read will always return
				 a value of no-action(1), a write of no-action(1) will have
				 no effect, while a write of clear(2) will clear all the
				 counters."

	::=  { brControlPackage 1 }

brSTAPMode OBJECT-TYPE
	SYNTAX			INTEGER {
					off(1),
					on(2)
					}
	ACCESS			read-write
	STATUS			mandatory
	DESCRIPTION
				"Determines whether the STAP algorithm is on or off.
				 If STAP mode is on then brForwardingMode may not be set to
				 transparent. Conversley if brForwardingMode is set to transparent
				 then brSTAPMode may not be set to on."

	::=  { brControlPackage 2 }

brLearnMode OBJECT-TYPE
	SYNTAX			INTEGER {
					off(1),
					on(2)
					}
	ACCESS			read-write
	STATUS			mandatory
	DESCRIPTION
				"Determines whether the bridge is not learning addresses
				 (off), or learning addresses as permanent, deleteOnReset or
				 deleteOnTimeout."

	::=  { brControlPackage 3 }

brAgingMode OBJECT-TYPE
	SYNTAX			INTEGER {
					on(1),
					off(2)
					}
	ACCESS			read-write
	STATUS			mandatory
	DESCRIPTION
				"Determines whether the bridge will age out entries in its
				 filtering database or not."

	::=  { brControlPackage 7 }

--
-- The Generic Bridge Monitor Port Table
--

brMonPortTable OBJECT-TYPE
	SYNTAX			SEQUENCE OF BrMonPortEntry
	ACCESS			not-accessible
	STATUS			mandatory
	DESCRIPTION
				"A table that contains generic information about
				 every port that is associated with this bridge."

	::= { brMonitorPackage 1 }

brMonPortEntry OBJECT-TYPE
	SYNTAX			BrMonPortEntry
	ACCESS			not-accessible
	STATUS			mandatory
	DESCRIPTION
				"A list of information for each port of the
				 bridge."

	INDEX			{ brMonPort }
	::= { brMonPortTable 1 }

BrMonPortEntry ::=
	SEQUENCE {
				brMonPort				INTEGER,
				brMonPortIfIndex			INTEGER,
				brMonPortPercentTrafficForwarded	INTEGER,
				brMonPortBandwidthUsed			INTEGER,
				brMonPortErrorsPer10000Packets		INTEGER,
				brMonPortBroadcastBandwidth		INTEGER
		}

brMonPort OBJECT-TYPE
	SYNTAX			INTEGER
	ACCESS			read-only
	STATUS			mandatory
	DESCRIPTION
				"The port number of the port for which this entry
				 contains bridge management information."

	::= { brMonPortEntry 1 }

brMonPortIfIndex OBJECT-TYPE
	SYNTAX			INTEGER
	ACCESS			read-only
	STATUS			mandatory
	DESCRIPTION
				"The value of the instance of the ifIndex object,
				 defined in [4,6], for the interface corresponding
				 to this port."

	::= { brMonPortEntry 2 }

brMonPortPercentTrafficForwarded OBJECT-TYPE
	SYNTAX			INTEGER
	ACCESS			read-only
	STATUS			mandatory
	DESCRIPTION
				"This is a high level 'smart MIB' object. This object provides
				a running average of the proportion of the received frames that
				are forwarded. This value is calculated locally on the agent and
				so does not require processor bandwidth from the management station
				or occupy valuable network bandwidth communicating with that
				station. By default an agent supporting this parameter will exhibit
				the following characteristics:-

				(1)	The parameter will be recalculated at approx 60 second intervals

				(2)	Every calculation period the device will read the value
					of dot1dTpPortInFrames and dot1dTpPortInDiscards.

				(3)	The calculation will be performed on the most recent 4 samples as
					follows:

					 4
					Sum(dot1dTpPortInDiscards(i)/dot1dTpPortInFrames(i)) * 1000/4
					i=1

				Which gives the percentage * 10 filtered, and then subtracting this from
				1000 to give percentage * 10 forwarded.

					dot1dTpPortInDiscards(i) is dot1dTpPortInDiscards(i) - dot1dTpPortInDiscards(i-1).
					dot1dTpPortInFrames(i) is dot1dTpPortInFrames(i) - dot1dTpPortInFrames(i-1).

				The value is expressed as a percentage * 10.

				A default threshold exists on this average so that if a calculated
				average exceeds 85% a trap will be sent to the management station.
				Further traps will not be sent until the average drops to below 50%.

				A particular device may provide a means of changing the number of samples,
				the averaging period, threshold and threshold action if it so wishes."

	::= { brMonPortEntry 3 }

brMonPortBandwidthUsed OBJECT-TYPE
	SYNTAX			INTEGER
	ACCESS			read-only
	STATUS			mandatory
	DESCRIPTION
				"This is a high level 'smart MIB' object. This object provides a running
				average of the bandwidth in use. This value is calculated locally on the
				agent and so does not require processor bandwidth from the management
				station or occupy valuable network bandwidth communicating with that
				station.
				By default an agent supporting this parameter will exhibit the following
				characteristics:

				(1)	The parameter will be recalculated at approx 60 second intervals

				(2)	Every calculation period the device will read the value
					of ifInOctets plus ifOutOctets.

				(3)	The calculation will be performed on the most recent 4 samples as
					follows:

					 4
					Sum(sample(i)/(time(i) * K)) * 1000/4
					i=1

					Sample(i) is (ifInOctets(i)+ifOutOctets(i))-(ifInOctets(i-1)+ifOutOctets(i-1))
					time(i) is the time between sample(i-1) and sample(i)
					K is the max bytes per unit time (i.e. the available bandwidth)

				The value is expressed as a percentage * 10.

				A default threshold exists on this average so that if a calculated
				average exceeds 50% a trap will be sent to the management station.
				Further traps will not be sent until the average drops to below 30%.

				A particular device may provide a means of changing the number of samples,
				the averaging period, threshold and threshold action if it so wishes."

	::= { brMonPortEntry 4 }

brMonPortErrorsPer10000Packets OBJECT-TYPE
	SYNTAX			INTEGER
	ACCESS			read-only
	STATUS			mandatory
	DESCRIPTION
				"This is a high level 'smart MIB' object. This object provides a running
				average of the number of errors per 10000 packets. The value of this value is calculated
				locally on the agent and so does not require processor bandwidth from a
				management station or occupy valuable network bandwidth communicating with
				that station.

				By default an agent supporting this parameter will exhibit the following
				behaviour:

				(1)	The parameter will be recalculated at approx 60 second intervals.

				(2)	Every calculation period the device will read the value of
					portTotalErrors and dot1dTpPortInFrames.

				(3)	The calculation will be performed on the most recent 4 samples as
					follows:

						 4
					10000 *	Sum(Errors(i)/Frames(i))
						i=1

					Errors(i) = portTotalErrors(i)-portTotalErrors(i-1)
					Frames(i) = dot1dTpPortInFrames(i)-dot1dTpPortInFrames(i-1)

				The value is an integer number of errors per 10,000 packets received by this
				port.

				A default threshold exists on this average so that if a calculated average
				exceeds 200 (i.e. 2% of frames are in error) a trap will be sent to the
				management station.  Further traps will not be sent until the average drops
				to below 100 (i.e. 1% of frames are in error).

				A particular device may provide a means of changing the number of samples,
				the averaging period and threshold if it so wishes."

	::= { brMonPortEntry 5 }

brMonPortBroadcastBandwidth OBJECT-TYPE
	SYNTAX			INTEGER
	ACCESS			read-only
	STATUS			mandatory
	DESCRIPTION
				"This is a high level 'smart MIB' object. This object provides a running
				average of the Broadcast frame bandwidth in use. This value is calculated locally on the
				agent and so does not require processor bandwidth from the management
				station or occupy valuable network bandwidth communicating with that
				station.

				By default an agent supporting this parameter will exhibit the following
				characteristics:

				(1)	The parameter will be recalculated at approx 20 second intervals

				(2)	Every calculation period the device will read the value
					of ifExtnsBroadcastsReceivedOks and ifExtnsBroadcastsTransmittedOks.

				(3)	The calculation will be performed on the most recent 4 samples as
					follows:

					 4
					Sum(sample(i)/(time(i) * K)) * 1000/4
					i=1

					Sample(i) is (ifExtnsBroadcastsReceivedOks(i)+ifExtnsBroadcastsTransmittedOks(i))-
					(ifExtnsBroadcastsReceivedOks(i-1)+ifExtnsBroadcastsTransmittedOks(i-1)).
					time(i) is the time between sample(i-1) and sample(i)
					K is the max frames per unit time (i.e. the available bandwidth)

				The value is expressed as a percentage * 10.

				A default threshold exists on this average so that if a calculated
				average exceeds 20% a trap will be sent to the management station.
				Further traps will not be sent until the average drops to below 10%.

				A particular device may provide a means of changing the number of samples,
				the averaging period, threshold and threshold action if it so wishes."

	::= { brMonPortEntry 6 }

--
--	Generic Bridge Database Control MIB
--

brDataBase	OBJECT IDENTIFIER ::= { bridgeMgmt 4}
brDummyPackage	OBJECT IDENTIFIER ::= { bridgeMgmt 5}

brSizeOfFilteringDataBase OBJECT-TYPE
	SYNTAX			INTEGER
	ACCESS			read-only
	STATUS			mandatory
	DESCRIPTION
				"The maximum possible number of Filtering database entries."

	::= { brDataBase 1 }

brPercentageOfNonageingFDBEntries OBJECT-TYPE
	SYNTAX			INTEGER
	ACCESS			read-only
	STATUS			mandatory
	DESCRIPTION
				"The number of  entries currently in the filtering database
				 that cannot be aged out, and are not in the permanent database.
				 This is expressed as a percentage * 10 of the size of the filtering
				 database :-

					 ((number of non ageing entries)*1000)/(filtering db size)."

	::= { brDataBase 2 }

brPercentageOfAgeingFDBEntries OBJECT-TYPE
	SYNTAX			INTEGER
	ACCESS			read-only
	STATUS			mandatory
	DESCRIPTION
				"The number of entries currently in the filtering database
				 that can be aged out, and not held in the permanent database.
				 This is expressed as a percentage * 10 of the size of the filtering
				 database :-

					 ((number of ageing entries)*1000)/(filtering db size)."

	::= { brDataBase 3 }

brPercentageOfPermanentFDBEntries OBJECT-TYPE
	SYNTAX			INTEGER
	ACCESS			read-only
	STATUS			mandatory
	DESCRIPTION
				"The number of permanent entries currently in the filtering database.
				 This is expressed as a percentage * 10 of the size of the filtering
				 database :-

					 ((number of permanent entries)*1000)/(filtering db size)."

	::= { brDataBase 4 }

brClearFilteringDataBase OBJECT-TYPE
	SYNTAX			INTEGER {
					noAction(1),
					clear(2)
					}
	ACCESS			read-write
	STATUS			mandatory
	DESCRIPTION
				"An attribute to clear all entries in the filtering database
				 except for those which are permanent."

	::= { brDataBase 5 }

brMaxNumberOfPermanentEntries OBJECT-TYPE
	SYNTAX			INTEGER
	ACCESS			read-only
	STATUS			mandatory
	DESCRIPTION
				"The maximum number of entries in the filtering database that can
				 be permanent."

	::= { brDataBase 6 }

brPercentageOfPermanentDatabaseUsed OBJECT-TYPE
	SYNTAX			INTEGER
	ACCESS			read-only
	STATUS			mandatory
	DESCRIPTION
				"The number of permanent entries in the filtering database.
				 This is expressed as a percentage * 10 of the size of the permanent
				 database :-

					 ((number of permanent entries)*1000)/(permanent db size)."

	::= { brDataBase 7 }

brClearPermanentEntries OBJECT-TYPE
	SYNTAX			INTEGER {
					noAction(1),
					clear(2)
					}
	ACCESS			read-write
	STATUS			mandatory
	DESCRIPTION
				"An attribute to clear the permanent entries from the filtering database."

	::= { brDataBase 8 }

brSaveLearntAddresses OBJECT-TYPE
	SYNTAX			INTEGER {
					noAction(1),
					save(2)
					}
	ACCESS			read-write
	STATUS			mandatory
	DESCRIPTION
				"An attribute to make the learnt addresses held in the
				 filtering database become permanent entries."

	::= { brDataBase 9 }

brDatabaseModified OBJECT-TYPE
SYNTAX			INTEGER {
				noChange(1),
				modified(2)
				}
	ACCESS			read-write
	STATUS			mandatory
	DESCRIPTION
				"This flag is used to indicate to a management application that the
				 database (Forwarding or Static views) has altered while a manager
				 is viewing it.

				 The normal value of this parameter is noChange(1), it will remain at
				 this value untill the database is modified by either:-

					- a manager mofifying the DB through the Static Table

					- the relay causing an entry to be inserted into the DB

					- the ageing process causing an entry to be deleted from the DB

				when it will be set to modified(2), where it will remain untill reset to
				noChange(1) by a manager."
	::=  { brDataBase 11 }
--
--			Dummy variables
--

brDatabaseType	OBJECT-TYPE
	SYNTAX			INTEGER {
					filtering (1),
					permanent (2)
					}
	ACCESS			read-only
	STATUS			mandatory
	DESCRIPTION
				"This dummy object enables the database full trap to differentiate between
				 the filtering database and the permanent database."

	::= { brDummyPackage 1}

brDatabaseLevel	OBJECT-TYPE
	SYNTAX			INTEGER {
					ninetyPercent (90),
					oneHundredPercent (100)
					}
	ACCESS			read-only
	STATUS			mandatory
	DESCRIPTION
				"This dummy object enables the database full trap to differentiate between
				 the database being 90% and 100% full."

	::= { brDummyPackage 2}

brTrafficForwarded	OBJECT-TYPE
	SYNTAX			Counter
	ACCESS			read-only
	STATUS			mandatory
	DESCRIPTION
				"This dummy object is used internally to calculate a running average
				 of the percentage of traffic forwarded on a port. It should not be
				 accessed by a management station."

	::= { brDummyPackage 3}

brPortBandwidth	OBJECT-TYPE
	SYNTAX			Counter
	ACCESS			read-only
	STATUS			mandatory
	DESCRIPTION
				"This dummy object is used internally to calculate a running average
				 of the port bandwidth in use. It should not be accessed by a management
				 station."

	::= { brDummyPackage 4}

brPortBroadcastBandwidth	OBJECT-TYPE
	SYNTAX			Counter
	ACCESS			read-only
	STATUS			mandatory
	DESCRIPTION
				"This dummy object is used internally to calculate a running average
				 of the port bandwidth in use. It should not be accessed by a management
				 station."

	::= { brDummyPackage 5}

brPortErrors	OBJECT-TYPE
	SYNTAX			Counter
	ACCESS			read-only
	STATUS			mandatory
	DESCRIPTION
				"This dummy object is used internally to calculate a running average
				 of the errors per 10000 frames on a port. It should not be accessed
				 by a management station."

	::= { brDummyPackage 6}

--
--			Trap definitions
--

brDatabaseFull TRAP-TYPE
	ENTERPRISE		a3Com
	VARIABLES		{
				 brDatabaseType,
				 brDatabaseLevel
				}
	DESCRIPTION
				"This trap indicates that either the Filtering databse or the permanent
				 database has become full. If the database occupancy exceeds 90% this trap
				 will be sent also. The variable bindings enable the trap to be identified as
				 refering to the filtering or permanet database, and to differentiate between 90%
				 or 100% full."

	::=			65
BridgeId 	::= OCTET STRING (SIZE (8))	-- the Bridge-Identifier as
						-- used in the Spanning Tree

MacAddress 	::= OCTET STRING (SIZE (6))	-- a 6 octet address in
						-- the "canonical" order

       END
