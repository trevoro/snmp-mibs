USR-ATMCFG-MIB DEFINITIONS ::= BEGIN
	IMPORTS
        OBJECT-TYPE
            FROM SNMPv2-SMI
        DisplayString, usrAtmCfg
            FROM USR-DEFINITIONS-MIB;
    usrAtmCfgTable OBJECT-TYPE
        SYNTAX  SEQUENCE OF UsrAtmCfgEntry
        MAX-ACCESS  not-accessible
        STATUS  current
        DESCRIPTION
            "USR Specific ATM Config table."
    ::= { usrAtmCfg 1 }
    usrAtmCfgEntry OBJECT-TYPE
        SYNTAX     UsrAtmCfgEntry
        MAX-ACCESS not-accessible
        STATUS     current
        DESCRIPTION
            "An entry in the Atm Configuration table."
        INDEX   { usrAtmIfName }
    ::= { usrAtmCfgTable 1 }
    UsrAtmCfgEntry ::=
        SEQUENCE {
           usrAtmIfName         DisplayString,
           usrSigAdminStatus    INTEGER,
           usrSigOperStatus     INTEGER,
           usrIlmiAdminStatus   INTEGER,
           usrIlmiOperStatus    INTEGER
        }
    usrAtmIfName OBJECT-TYPE
        SYNTAX      DisplayString
        MAX-ACCESS  not-accessible
        STATUS      current
        DESCRIPTION
        "This object is the identifier of a ATM (AAL)
        Interface on a managed device."
	::= { usrAtmCfgEntry 1 }
    usrSigAdminStatus OBJECT-TYPE
        SYNTAX  INTEGER {
            enable(1),
            disable(2)
        }
        MAX-ACCESS  read-write
        STATUS      current
        DESCRIPTION
            "The desired state of Signalling on a desired interface.
             The interface name, specified by usrAtmIfName represents
             the AAL interface to enable or disable signalling on. If
             the state is 'enable' then signalling messages will flow
             on the interface. If the state is changed to disable,
             then all signalling messages will stop on the interface."
    --CONFIGURABLE
	::= { usrAtmCfgEntry 2 }
    usrSigOperStatus OBJECT-TYPE
        SYNTAX  INTEGER {
            enabled(1),
            disabled(2)
        }
        MAX-ACCESS  read-only
        STATUS      current
        DESCRIPTION
            "The actual state of Signalling on a desired interface.
             This state should follow the state set by
             usrSigAdminStatus."
	::= { usrAtmCfgEntry 3 }
    usrIlmiAdminStatus OBJECT-TYPE
        SYNTAX  INTEGER {
            enable(1),
            disable(2)
        }
        MAX-ACCESS  read-write
        STATUS      current
        DESCRIPTION
            "The desired state of ILMI on a desired interface.  The
             interface name, specified by usrAtmIfName represents the
             AAL interface to enable or disable ILMI on. If the state
             is 'enable' then ILMI messages will flow on the
             interface. If the state is changed to disable, then all
             ILMI messages will stop on the interface."
    --CONFIGURABLE
	::= { usrAtmCfgEntry 4 }
    usrIlmiOperStatus OBJECT-TYPE
        SYNTAX  INTEGER {
            enabled(1),
            disabled(2)
        }
        MAX-ACCESS  read-only
        STATUS      current
        DESCRIPTION
            "The actual state of ILMI on a desired interface.  This
             state should follow the state set by usrSigAdminStatus."
	::= { usrAtmCfgEntry 5 }
END         -- End usrAtmCfg MIB definitions
