Nortel-MsCarrier-MscPassport-SourceRouteEndStationMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32,
      Unsigned32
   FROM Nortel-MsCarrier-MscPassport-StandardTextualConventionsMIB

      AsciiString,
      DashedHexString,
      NonReplicated,
      HexString,
      AsciiStringIndex
   FROM Nortel-MsCarrier-MscPassport-TextualConventionsMIB

      mscVrIndex,
      mscVr
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     SourceRouteEndStation Enterprise MIB."

sourceRouteEndStationMIB OBJECT IDENTIFIER ::= { mscPassportMIBs 54 }










-- Vr/<string> SourceRouteEndStation
-- This component defines source routing for source routing end stations.

mscVrSres OBJECT IDENTIFIER ::= { mscVr 13 }



mscVrSresRowStatusTable OBJECT-TYPE
   SYNTAX     SEQUENCE OF MscVrSresRowStatusEntry
   ACCESS     not-accessible
   STATUS     mandatory
   DESCRIPTION
     "This entry controls the addition and deletion of 
      mscVrSres components."
::= { mscVrSres 1 }

mscVrSresRowStatusEntry OBJECT-TYPE
   SYNTAX     MscVrSresRowStatusEntry
   ACCESS     not-accessible
   STATUS     mandatory
   DESCRIPTION
     "A single entry in the table represents a single 
      mscVrSres component."
   INDEX {
      mscVrIndex,
      mscVrSresIndex }
::= { mscVrSresRowStatusTable 1 }

MscVrSresRowStatusEntry ::= SEQUENCE {
   mscVrSresRowStatus
      RowStatus,
   mscVrSresComponentName
      DisplayString,
   mscVrSresStorageType
      StorageType,
   mscVrSresIndex
      NonReplicated }

mscVrSresRowStatus OBJECT-TYPE
   SYNTAX     RowStatus 
   ACCESS     read-write
   STATUS     mandatory
   DESCRIPTION
     "This variable is used as the basis for SNMP naming of
      mscVrSres components.
      These components can be added and deleted."
::= { mscVrSresRowStatusEntry 1 }

mscVrSresComponentName OBJECT-TYPE
   SYNTAX     DisplayString 
   ACCESS     read-only
   STATUS     mandatory
   DESCRIPTION
     "This variable provides the component's string name for
      use with the ASCII Console Interface"
::= { mscVrSresRowStatusEntry 2 }

mscVrSresStorageType OBJECT-TYPE
   SYNTAX     StorageType 
   ACCESS     read-only
   STATUS     mandatory
   DESCRIPTION
     "This variable represents the storage type value for the
      mscVrSres tables."
::= { mscVrSresRowStatusEntry 4 }

mscVrSresIndex OBJECT-TYPE
   SYNTAX     NonReplicated 
   ACCESS     not-accessible
   STATUS     mandatory
   DESCRIPTION
     "This variable represents the index for the mscVrSres tables."
::= { mscVrSresRowStatusEntry 10 }

mscVrSresAdminControlTable OBJECT-TYPE
   SYNTAX     SEQUENCE OF MscVrSresAdminControlEntry
   ACCESS     not-accessible
   STATUS     mandatory
   DESCRIPTION
     "This group includes the Administrative Control attribute. This attribute 
      defines the current administrative state of this component."
::= { mscVrSres 10 }

mscVrSresAdminControlEntry OBJECT-TYPE
   SYNTAX     MscVrSresAdminControlEntry
   ACCESS     not-accessible
   STATUS     mandatory
   DESCRIPTION
     "An entry in the mscVrSresAdminControlTable."
   INDEX {
      mscVrIndex,
      mscVrSresIndex }
::= { mscVrSresAdminControlTable 1 }

MscVrSresAdminControlEntry ::= SEQUENCE {
   mscVrSresSnmpAdminStatus
      INTEGER }

mscVrSresSnmpAdminStatus OBJECT-TYPE
   SYNTAX     INTEGER  {
                 up(1),
                 down(2),
                 testing(3) }
   ACCESS     read-only
   STATUS     mandatory
   DESCRIPTION
     "This attribute is used to set the desired state of the interface. The up state 
      indicates the interface is operational and packet forwarding is allowed. 
      The down state indicates the interface is not operational and packet 
      forwarding is unavailable. The testing state indicates that no operational 
      packets can be passed. Changing this attribute from its default value of 
      up is not allowed at this time."
   DEFVAL     { up }
::= { mscVrSresAdminControlEntry 1 }

mscVrSresProvTable OBJECT-TYPE
   SYNTAX     SEQUENCE OF MscVrSresProvEntry
   ACCESS     not-accessible
   STATUS     mandatory
   DESCRIPTION
     "This group contains the provisioned attributes for the 
      SourceRouteEndStation component."
::= { mscVrSres 11 }

mscVrSresProvEntry OBJECT-TYPE
   SYNTAX     MscVrSresProvEntry
   ACCESS     not-accessible
   STATUS     mandatory
   DESCRIPTION
     "An entry in the mscVrSresProvTable."
   INDEX {
      mscVrIndex,
      mscVrSresIndex }
::= { mscVrSresProvTable 1 }

MscVrSresProvEntry ::= SEQUENCE {
   mscVrSresRouteTableNumEntries
      Unsigned32,
   mscVrSresAgingTime
      Unsigned32,
   mscVrSresRouteDescriptorLength
      Unsigned32 }

mscVrSresRouteTableNumEntries OBJECT-TYPE
   SYNTAX     Unsigned32 (0..65535)
   ACCESS     read-write
   STATUS     mandatory
   DESCRIPTION
     "This attribute identifies the maximum number of entries in the 
      SourceRouteEndStation routing table. Before you change it, check the 
      network configuration to see how many protocol ports, such as IpPort or 
      IpxPort, under Vr Pp have endStationSupport set to enable. The value of 
      routeTableNumEntries also depends on the VirtualRouter attribute 
      sresMaxHeapSpace.
      
      Consider the following attributes of the SourceRouteEndStation 
      component when adjusting this number: 
      - rtEntriesUsed
      - rtEntriesFree
      - rtEntriesDenied"
   DEFVAL     { 5000 }
::= { mscVrSresProvEntry 1 }

mscVrSresAgingTime OBJECT-TYPE
   SYNTAX     Unsigned32 (200..1000000)
   ACCESS     read-write
   STATUS     mandatory
   DESCRIPTION
     "This attribute specifies the time period used in seconds, to age out 
      learned entries in the routing table."
   DEFVAL     { 900 }
::= { mscVrSresProvEntry 2 }

mscVrSresRouteDescriptorLength OBJECT-TYPE
   SYNTAX     Unsigned32 (8..14)
   ACCESS     read-only
   STATUS     mandatory
   DESCRIPTION
     "This attribute indicates the maximum number of route descriptors 
      supported by this implementation. The maximum number of hops will 
      be one less because one route descriptor is always required for the 
      destination. This attribute affects the amount of memory used by the 
      route entry table. The larger this attribute is, the more memory the route 
      entry table will use."
   DEFVAL     { 14 }
::= { mscVrSresProvEntry 3 }

mscVrSresOperStatusTable OBJECT-TYPE
   SYNTAX     SEQUENCE OF MscVrSresOperStatusEntry
   ACCESS     not-accessible
   STATUS     mandatory
   DESCRIPTION
     "This group includes the Operational Status attribute. This attribute 
      defines the current operational state of this component."
::= { mscVrSres 12 }

mscVrSresOperStatusEntry OBJECT-TYPE
   SYNTAX     MscVrSresOperStatusEntry
   ACCESS     not-accessible
   STATUS     mandatory
   DESCRIPTION
     "An entry in the mscVrSresOperStatusTable."
   INDEX {
      mscVrIndex,
      mscVrSresIndex }
::= { mscVrSresOperStatusTable 1 }

MscVrSresOperStatusEntry ::= SEQUENCE {
   mscVrSresSnmpOperStatus
      INTEGER }

mscVrSresSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrSresOperStatusEntry 1 }

mscVrSresStateTable OBJECT-TYPE
   SYNTAX     SEQUENCE OF MscVrSresStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrSres 13 }

mscVrSresStateEntry OBJECT-TYPE
   SYNTAX     MscVrSresStateEntry
   ACCESS     not-accessible
   STATUS     mandatory
   DESCRIPTION
     "An entry in the mscVrSresStateTable."
   INDEX {
      mscVrIndex,
      mscVrSresIndex }
::= { mscVrSresStateTable 1 }

MscVrSresStateEntry ::= SEQUENCE {
   mscVrSresAdminState
      INTEGER,
   mscVrSresOperationalState
      INTEGER,
   mscVrSresUsageState
      INTEGER }

mscVrSresAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrSresStateEntry 1 }

mscVrSresOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrSresStateEntry 2 }

mscVrSresUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrSresStateEntry 3 }

mscVrSresOperTable OBJECT-TYPE
   SYNTAX     SEQUENCE OF MscVrSresOperEntry
   ACCESS     not-accessible
   STATUS     mandatory
   DESCRIPTION
     "This group contains the operational attributes for the 
      SourceRouteEndStation component."
::= { mscVrSres 14 }

mscVrSresOperEntry OBJECT-TYPE
   SYNTAX     MscVrSresOperEntry
   ACCESS     not-accessible
   STATUS     mandatory
   DESCRIPTION
     "An entry in the mscVrSresOperTable."
   INDEX {
      mscVrIndex,
      mscVrSresIndex }
::= { mscVrSresOperTable 1 }

MscVrSresOperEntry ::= SEQUENCE {
   mscVrSresRtEntriesUsed
      Gauge32,
   mscVrSresRtEntriesFree
      Gauge32,
   mscVrSresRtEntriesDenied
      Counter32 }

mscVrSresRtEntriesUsed OBJECT-TYPE
   SYNTAX     Gauge32 (0..65535)
   ACCESS     read-only
   STATUS     mandatory
   DESCRIPTION
     "This attribute specifies the total number of SourceRouteEndStation 
      routing table entries. The value is limited by the attribute 
      routeTableNumEntries, which is a provisionable attribute. If the value is 
      consistently approaching the value of routeTableNumEntries, it is 
      advisable to increase the value provisioned for routeTableNumEntries. It 
      indicates a potential shortage of routing table entries in the future."
   DEFVAL     { 0 }
::= { mscVrSresOperEntry 1 }

mscVrSresRtEntriesFree OBJECT-TYPE
   SYNTAX     Gauge32 (0..65535)
   ACCESS     read-only
   STATUS     mandatory
   DESCRIPTION
     "This attribute is indicative of the number of Sres routing table entries 
      free. A consistently high value for this attribute indicates that there is a 
      resource surplus here, in terms of the memory requirements of the 
      routing table. This surplus could be utilized elsewhere if need be. The 
      value of this attribute is directly influenced by the value of the attribute 
      routeTableNumEntries."
   DEFVAL     { 0 }
::= { mscVrSresOperEntry 2 }

mscVrSresRtEntriesDenied OBJECT-TYPE
   SYNTAX     Counter32 
   ACCESS     read-only
   STATUS     mandatory
   DESCRIPTION
     "This attribute counts the number of times a SourceRouteEndStation 
      routing table entry was unavailable. Each count indicates an instance of 
      a new route which could not be learned because of a lack of routing 
      table entries. A rapid increase indicates a shortage of routing table 
      entries. To rectify this, increase the number of routing table entries 
      through the provisioned attribute routeTableNumEntries under the 
      SourceRouteEndStation component. This counter wraps around its 
      maximum value of 4294967295."
::= { mscVrSresOperEntry 3 }

-- 
-- *** THIS SUBTREE CURRENTLY NOT IMPLEMENTED ***
-- 

-- Vr/<string> Sres RouteEntry/xx-xx-xx-xx-xx-xx,<string>
-- This component is used to contain the data associated with a source 
-- routing destination address. Each entry represents one row in the Route 
-- Table. The table is indexed by the route destination MAC address in 
-- canonical format and ProtocolPort name.

mscVrSresRe OBJECT IDENTIFIER ::= { mscVrSres 2 }



mscVrSresReRowStatusTable OBJECT-TYPE
   SYNTAX     SEQUENCE OF MscVrSresReRowStatusEntry
   ACCESS     not-accessible
   STATUS     mandatory
   DESCRIPTION
     "*** THIS TABLE CURRENTLY NOT IMPLEMENTED ***

      This entry controls the addition and deletion of 
      mscVrSresRe components."
::= { mscVrSresRe 1 }

mscVrSresReRowStatusEntry OBJECT-TYPE
   SYNTAX     MscVrSresReRowStatusEntry
   ACCESS     not-accessible
   STATUS     mandatory
   DESCRIPTION
     "A single entry in the table represents a single 
      mscVrSresRe component."
   INDEX {
      mscVrIndex,
      mscVrSresIndex,
      mscVrSresReDestMacAddressIndex,
      mscVrSresReProtocolPortNameIndex }
::= { mscVrSresReRowStatusTable 1 }

MscVrSresReRowStatusEntry ::= SEQUENCE {
   mscVrSresReRowStatus
      RowStatus,
   mscVrSresReComponentName
      DisplayString,
   mscVrSresReStorageType
      StorageType,
   mscVrSresReDestMacAddressIndex
      DashedHexString,
   mscVrSresReProtocolPortNameIndex
      AsciiStringIndex }

mscVrSresReRowStatus OBJECT-TYPE
   SYNTAX     RowStatus 
   ACCESS     read-only
   STATUS     mandatory
   DESCRIPTION
     "This variable is used as the basis for SNMP naming of
      mscVrSresRe components.
      These components cannot be added nor deleted."
::= { mscVrSresReRowStatusEntry 1 }

mscVrSresReComponentName OBJECT-TYPE
   SYNTAX     DisplayString 
   ACCESS     read-only
   STATUS     mandatory
   DESCRIPTION
     "This variable provides the component's string name for
      use with the ASCII Console Interface"
::= { mscVrSresReRowStatusEntry 2 }

mscVrSresReStorageType OBJECT-TYPE
   SYNTAX     StorageType 
   ACCESS     read-only
   STATUS     mandatory
   DESCRIPTION
     "This variable represents the storage type value for the
      mscVrSresRe tables."
::= { mscVrSresReRowStatusEntry 4 }

mscVrSresReDestMacAddressIndex OBJECT-TYPE
   SYNTAX     DashedHexString (SIZE (6))
   ACCESS     not-accessible
   STATUS     mandatory
   DESCRIPTION
     "This variable represents an index for the mscVrSresRe tables."
::= { mscVrSresReRowStatusEntry 10 }

mscVrSresReProtocolPortNameIndex OBJECT-TYPE
   SYNTAX     AsciiStringIndex (SIZE (1..20))
   ACCESS     not-accessible
   STATUS     mandatory
   DESCRIPTION
     "This variable represents an index for the mscVrSresRe tables."
::= { mscVrSresReRowStatusEntry 11 }

mscVrSresReOperTable OBJECT-TYPE
   SYNTAX     SEQUENCE OF MscVrSresReOperEntry
   ACCESS     not-accessible
   STATUS     mandatory
   DESCRIPTION
     "*** THIS TABLE CURRENTLY NOT IMPLEMENTED ***

      This group contains information relating to a source routing destination 
      address."
::= { mscVrSresRe 10 }

mscVrSresReOperEntry OBJECT-TYPE
   SYNTAX     MscVrSresReOperEntry
   ACCESS     not-accessible
   STATUS     mandatory
   DESCRIPTION
     "An entry in the mscVrSresReOperTable."
   INDEX {
      mscVrIndex,
      mscVrSresIndex,
      mscVrSresReDestMacAddressIndex,
      mscVrSresReProtocolPortNameIndex }
::= { mscVrSresReOperTable 1 }

MscVrSresReOperEntry ::= SEQUENCE {
   mscVrSresReRouteControl
      HexString,
   mscVrSresReRifLength
      Unsigned32,
   mscVrSresReRdDirection
      INTEGER,
   mscVrSresReRouteDescr
      AsciiString }

mscVrSresReRouteControl OBJECT-TYPE
   SYNTAX     HexString (SIZE (2))
   ACCESS     read-only
   STATUS     mandatory
   DESCRIPTION
     "This is the value of the routing control field for this route."
::= { mscVrSresReOperEntry 1 }

mscVrSresReRifLength OBJECT-TYPE
   SYNTAX     Unsigned32 (2..30)
   ACCESS     read-only
   STATUS     mandatory
   DESCRIPTION
     "This attribute is used to display the length of the routing information 
      field in the routing control field."
::= { mscVrSresReOperEntry 2 }

mscVrSresReRdDirection OBJECT-TYPE
   SYNTAX     INTEGER  {
                 leftToRight(0),
                 rightToLeft(1),
                 noRif(2) }
   ACCESS     read-only
   STATUS     mandatory
   DESCRIPTION
     "This attribute indicates the direction to use routing descriptors (RDs). If 
      set to leftToRight the routing descriptors, displayed in routeDescr, will 
      be interpreted from left to right. If set to rightToLeft they will be 
      interpreted from right to left. If rifLength is zero, this attribute will be 
      set to noRif to indicate that there are no routing descriptors to be read."
::= { mscVrSresReOperEntry 3 }

mscVrSresReRouteDescr OBJECT-TYPE
   SYNTAX     AsciiString (SIZE (0..90))
   ACCESS     read-only
   STATUS     mandatory
   DESCRIPTION
     "This is the embedded sequence of bridge and ring IDs for this route. For 
      destinations on the local ring, the value of this attribute is the zero-
      length string. Refer to rdDirection for the direction in which to read the 
      route descriptors. The format of the hexadecimal data displayed is as 
      follows:
      
      12 bit Ring Number - 4 bit Bridge Number...
      XXX-X XXX-X XXX-X..."
::= { mscVrSresReOperEntry 4 }




-- 
-- Version and Compliance statements
-- 



-- Object-Group Statement:
-- A list of all current accessible leaf objects.

-- OBJECTS { mscVrSresSnmpOperStatus,
--           mscVrSresRtEntriesFree,
--           mscVrSresReRouteControl,
--           mscVrSresRtEntriesUsed,
--           mscVrSresUsageState,
--           mscVrSresReRdDirection,
--           mscVrSresAdminState,
--           mscVrSresComponentName,
--           mscVrSresReStorageType,
--           mscVrSresStorageType,
--           mscVrSresRowStatus,
--           mscVrSresRouteTableNumEntries,
--           mscVrSresSnmpAdminStatus,
--           mscVrSresRouteDescriptorLength,
--           mscVrSresAgingTime,
--           mscVrSresReRifLength,
--           mscVrSresOperationalState,
--           mscVrSresReRouteDescr,
--           mscVrSresRtEntriesDenied,
--           mscVrSresReComponentName,
--           mscVrSresReRowStatus }
-- STATUS  mandatory
-- DESCRIPTION
--   "A list of all current accessible leaf objects."

sourceRouteEndStationGroup OBJECT IDENTIFIER ::= { sourceRouteEndStationMIB 1 }
sourceRouteEndStationGroupCA OBJECT IDENTIFIER ::= { sourceRouteEndStationGroup 1 }
sourceRouteEndStationGroupCA02 OBJECT IDENTIFIER ::= { sourceRouteEndStationGroupCA 3 }
sourceRouteEndStationGroupCA02A OBJECT IDENTIFIER ::= { sourceRouteEndStationGroupCA02 2 }



-- Agent-Capabilities Statement:

-- PRODUCT-RELEASE "MscPassport Release 1.2 SourceRouteEndStation."
-- STATUS          mandatory
-- DESCRIPTION     "Carrier Passport SourceRouteEndStation MIB: MIB Version CA02A,
--                  Software Version CA02S9C."
-- SUPPORTS        Nortel-MsCarrier-MscPassport-SourceRouteEndStationMIB
--    INCLUDES     { sourceRouteEndStationGroupCA02A }

sourceRouteEndStationCapabilities OBJECT IDENTIFIER ::= { sourceRouteEndStationMIB 3 }
sourceRouteEndStationCapabilitiesCA OBJECT IDENTIFIER ::= { sourceRouteEndStationCapabilities 1 }
sourceRouteEndStationCapabilitiesCA02 OBJECT IDENTIFIER ::= { sourceRouteEndStationCapabilitiesCA 3 }
sourceRouteEndStationCapabilitiesCA02A OBJECT IDENTIFIER ::= { sourceRouteEndStationCapabilitiesCA02 2 }





END
