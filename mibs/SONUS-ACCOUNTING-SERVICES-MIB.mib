--
-- This SMIv2 module has been generated by smidump 0.2-cvs. Do not edit.
--

SONUS-ACCOUNTING-SERVICES-MIB DEFINITIONS ::= BEGIN

IMPORTS
    Counter64, Integer32, MODULE-IDENTITY, NOTIFICATION-TYPE, 
    OBJECT-TYPE
        FROM SNMPv2-SMI
    sonusEventClass, sonusEventDescription, sonusEventLevel
        FROM SONUS-COMMON-MIB
    sonusServicesMIBs
        FROM SONUS-SMI
    SonusAdminState
        FROM SONUS-TC;

sonusAccountingServicesMIB MODULE-IDENTITY
    LAST-UPDATED    "200102030000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for Accounting Services Management."
    ::= { sonusServicesMIBs 5 }


sonusAccountingServicesMIBObjects OBJECT IDENTIFIER
    ::= { sonusAccountingServicesMIB 1 }

sonusCallAccountingObjects OBJECT IDENTIFIER
    ::= { sonusAccountingServicesMIBObjects 1 }

sonusCallAccountingConfigObjects OBJECT IDENTIFIER
    ::= { sonusCallAccountingObjects 1 }

sonusAcctGenerationMode OBJECT-TYPE
    SYNTAX          INTEGER { origination(1), destination(2), 
                        allcalls(3), none(4) }
    MAX-ACCESS      read-write
    STATUS          current
    DESCRIPTION     
            "This configures the accounting generation mode for the node"
    DEFVAL          { 1 }
    ::= { sonusCallAccountingConfigObjects 1 }

sonusAcctLogDestination OBJECT-TYPE
    SYNTAX          INTEGER { eventlog(1) }
    MAX-ACCESS      read-write
    STATUS          current
    DESCRIPTION     
            "This configures the destination of the accounting files for the node"
    DEFVAL          { 1 }
    ::= { sonusCallAccountingConfigObjects 2 }

sonusAcctIntAcctState OBJECT-TYPE
    SYNTAX          SonusAdminState
    MAX-ACCESS      read-write
    STATUS          current
    DESCRIPTION     
            "This configures whether Intermediate Accounting is Enabled or 
             Disabled for the Node"
    DEFVAL          { disabled }
    ::= { sonusCallAccountingConfigObjects 3 }

sonusAcctIntAcctInterval OBJECT-TYPE
    SYNTAX          Integer32 (5..86400)
    MAX-ACCESS      read-write
    STATUS          current
    DESCRIPTION     
            "This configures the Intermediate Accounting Interval in seconds"
    DEFVAL          { 60 }
    ::= { sonusCallAccountingConfigObjects 4 }

sonusCallAccountingStatusObjects OBJECT IDENTIFIER
    ::= { sonusCallAccountingObjects 2 }

sonusAcctNumCallAttempts OBJECT-TYPE
    SYNTAX          Counter64
    MAX-ACCESS      read-only
    STATUS          current
    DESCRIPTION     
            "The total Number of Call Attempts since last reboot"
    ::= { sonusCallAccountingStatusObjects 1 }

sonusAcctNumCallCompletions OBJECT-TYPE
    SYNTAX          Counter64
    MAX-ACCESS      read-only
    STATUS          current
    DESCRIPTION     
            "The total Number of Succesful Call Completions since last reboot"
    ::= { sonusCallAccountingStatusObjects 2 }

sonusAcctNumCallAttemptFailures OBJECT-TYPE
    SYNTAX          Counter64
    MAX-ACCESS      read-only
    STATUS          current
    DESCRIPTION     
            "The total Number of Unsuccesful Call Attempts since last reboot"
    ::= { sonusCallAccountingStatusObjects 3 }

sonusAcctBusyHourAttempts OBJECT-TYPE
    SYNTAX          Integer32
    MAX-ACCESS      read-only
    STATUS          current
    DESCRIPTION     
            "The Average BHCA rate in the last one hour"
    ::= { sonusCallAccountingStatusObjects 4 }

sonusAcctCallAttemptRate OBJECT-TYPE
    SYNTAX          Integer32
    MAX-ACCESS      read-only
    STATUS          current
    DESCRIPTION     
            "The Call arrival rate in calls/sec in the last one minute"
    ::= { sonusCallAccountingStatusObjects 5 }

sonusAcctAvgCallDuration OBJECT-TYPE
    SYNTAX          Integer32
    MAX-ACCESS      read-only
    STATUS          current
    DESCRIPTION     
            "The Average Call Duration in seconds"
    ::= { sonusCallAccountingStatusObjects 6 }

sonusAcctNumCallAttemptBlocked OBJECT-TYPE
    SYNTAX          Counter64
    MAX-ACCESS      read-only
    STATUS          current
    DESCRIPTION     
            "The total Number of Calls which were blocked/screened since last reboot"
    ::= { sonusCallAccountingStatusObjects 7 }

sonusAccountingMIBNotifications OBJECT IDENTIFIER
    ::= { sonusAccountingServicesMIB 2 }

sonusAccountingMIBNotificationsPrefix OBJECT IDENTIFIER
    ::= { sonusAccountingMIBNotifications 0 }

sonusAccountingMIBNotificationsObjects OBJECT IDENTIFIER
    ::= { sonusAccountingMIBNotifications 1 }

sonusAcctOutOfServiceReason OBJECT-TYPE
    SYNTAX          INTEGER { configChange(1), eventLoggingError(2) }
    MAX-ACCESS      read-only
    STATUS          current
    DESCRIPTION     
            "The Reason for Call Accounting for the Node being
             Out-of-Service."
    ::= { sonusAccountingMIBNotificationsObjects 1 }

sonusCallAccountingInServiceNotification NOTIFICATION-TYPE
    OBJECTS         { sonusAcctGenerationMode, sonusAcctLogDestination, 
                      sonusAcctIntAcctState, sonusAcctIntAcctInterval, 
                      sonusEventDescription, sonusEventClass, 
                      sonusEventLevel }
    STATUS          current
    DESCRIPTION     
            "This Trap is Generated when a change is made to the Accounting 
             Configuration for the Node, and the resultant configuration
             state of accounting for the node is that it is enabled/in-service"
    ::= { sonusAccountingMIBNotificationsPrefix 1 }

sonusCallAccountingOutOfServiceNotification NOTIFICATION-TYPE
    OBJECTS         { sonusAcctOutOfServiceReason, sonusEventDescription, 
                      sonusEventClass, sonusEventLevel }
    STATUS          current
    DESCRIPTION     
            "This Trap is Generated when Accounting Records are no
             longer being generated on the Node. It could be either
             because of a change to the Accounting Configuration
             or because of errors in the logging mechanism such as file logging
             errors. When the reason specified for accounting outofservice
             is event logging error, then the SYS event logs on the Node
             should be examined to obtain further information about the
             event logging failure"
    ::= { sonusAccountingMIBNotificationsPrefix 2 }

END -- end of module SONUS-ACCOUNTING-SERVICES-MIB.
