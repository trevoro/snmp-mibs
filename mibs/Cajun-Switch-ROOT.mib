-- LUCENT CAJUN SWITCH ROOT MIB VERSION V3.0
-- Lucent enterprise-specific Management Information Base for SNMP version 1
-- 
-- Revision History
-- ----------------
-- v3.0   04/14/1999   Tom Chin      Added the Revision History header section.
-- v3.1   05/13/1999   John Liddy    Added Remote Fault Detection MIB object.
-- 
-- © Copyright LUCENT TECHNOLOGIES 1999 ALL RIGHTS RESERVED
-- Printed in USA, April 1999
-- 
-- The products, specifications, and other technical information regarding the
-- products contained in this document are subject to change without notice. All
-- information in this document is believed to be accurate and reliable, but is
-- presented without warranty of any kind, express or implied, and users must
-- take full responsibility for their application of any products specified in
-- this document. Lucent disclaims responsibility for errors which may appear in
-- this document, and it reserves the right, in its sole discretion and without
-- notice, to make substitutions and modifications in the products and practices
-- described in this document.  Lucent, NetCare, Cajun, CajunDocs, OpenTrunk,
-- P550, and CajunView are trademarks of Lucent Technologies.
-- 
-- For technical assistance, please contact Lucent Techologies Netcare Data
-- Networking Systems by phoning (800) 237-0016, pressing 0, then 73300.  You
-- can also contact them on the World Wide Web at https://www.netcaredata.com.



-- MODULE DEFINITION

Cajun-Switch-ROOT DEFINITIONS ::= BEGIN
IMPORTS 
	enterprises, MODULE-IDENTITY
                 FROM SNMPv2-SMI;
    lucent  MODULE-IDENTITY
              LAST-UPDATED "9901300000Z"
              ORGANIZATION "Lucent's Concord Technology Center (CTC) "
              CONTACT-INFO
                      "Erick M. Crowell -- ecrowell@lucent.com,
			Raj Duggal -- rduggal@lucent.com,
		       Ira Steckler -- isteckler@lucent.com"
              DESCRIPTION
                      "Cajun p220 / p550 / p660 / p880  Private Mib
			top level Architecture."
              ::= {enterprises 1751  }

-- lucent 		OBJECT IDENTIFIER ::= {enterprises 1751}
products 	OBJECT IDENTIFIER ::= {lucent 1}
mibs 		OBJECT IDENTIFIER ::= {lucent 2}

-- Cajun Router is number 45 under the Lucent Enterprise MIB

cajunSwitch 		OBJECT IDENTIFIER ::= {mibs 45}
cajunSwitchProduct	OBJECT IDENTIFIER ::= {products 45}

-- Top Level Cajun Catagories
--
cajunAgentGen 		OBJECT IDENTIFIER ::= 	{ cajunSwitch 1 }
cajunAgentCommunity 	OBJECT IDENTIFIER ::= 	{ cajunSwitch 2 }
cajunChassis		OBJECT IDENTIFIER ::= 	{ cajunSwitch 3 }
cajunLayer2Switching 	OBJECT IDENTIFIER ::= 	{ cajunSwitch 4 }
cajunVlanMgt 		OBJECT IDENTIFIER ::= 	{ cajunSwitch 5 }
cajunEvents 		OBJECT IDENTIFIER ::= 	{ cajunSwitch 6 }
cajunlarmMgt 		OBJECT IDENTIFIER ::= 	{ cajunSwitch 7 }
cajunSnmpTraps 		OBJECT IDENTIFIER ::= 	{ cajunSwitch 8 }

-- Cajun Switch Product Types
--
cajunL2P550 	OBJECT IDENTIFIER ::= 		{ cajunSwitchProduct 1 }
cajunL3P550 	OBJECT IDENTIFIER ::= 		{ cajunSwitchProduct 2 }
cajunP220G 	OBJECT IDENTIFIER ::= 		{ cajunSwitchProduct 3 }
cajunP220FE 	OBJECT IDENTIFIER ::= 		{ cajunSwitchProduct 4 }
cajunL2P660 	OBJECT IDENTIFIER ::= 		{ cajunSwitchProduct 5 }
cajunL3P660 	OBJECT IDENTIFIER ::= 		{ cajunSwitchProduct 6 }
cajunL2P850 	OBJECT IDENTIFIER ::= 		{ cajunSwitchProduct 7 }
cajunL3P850 	OBJECT IDENTIFIER ::= 		{ cajunSwitchProduct 8 }
cajunL2P880 	OBJECT IDENTIFIER ::= 		{ cajunSwitchProduct 9 }
cajunL3P880 	OBJECT IDENTIFIER ::= 		{ cajunSwitchProduct 10 }

END
