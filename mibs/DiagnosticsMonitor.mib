--
--
--        Copyright (c) 1997-2000 Concord Communications Inc.
--                     All rights reserved.
--
--  Path:      @(#) concord-diagmon.mib /main/2 07/24/00 16:10:22
--
--  Date:      12/16/97
--
--  Revision:  1.0
--
--
--  Changes:
-- 
--  05/15/00	karen		reworded descriptions
--  04/12/00	karen		removed resetDisplayStr
--  03/29/00	karen		modified health report traps for drilldowns
--  03/27/00	karen		added duration and problemStart to le trap
--  03/23/00	leyboi		added drilldown fields to health report traps
--  03/21/00	karen		changed nhLiveUpdateExceptions -> nhLiveUpdateException
--  02/02/00	karen		add nhLiveResetExceptions and severity to
--							nhLiveException and nhLiveClearException 
--							added nhProfile to exceptions and alarms
--  01/10/00	karen		removed exceptionKey and techType 
-- 							added to exceptionId and elementId 
--  01/03/00	karen		added exceptionKey, techType; removed 
--							alarmTime, alarmId, elementId
--  12/13/99	karen		Changed trigger to alarm
--  11/01/99	karen		Modified traps for live exceptions (again)
--  11/01/99	karen		Modified traps for live exceptions
--  11/01/99	karen		Added traps for live exceptions
--  10/05/98	aludlam		Added netHealthException
--	12/16/97	leyboi		Initial version
--
----------------------------------------------------------------------

DiagnosticsMonitor DEFINITIONS ::= BEGIN

IMPORTS	
	enterprises, IpAddress		FROM RFC1155-SMI
	OBJECT-TYPE					FROM RFC-1212
	TRAP-TYPE					FROM RFC-1215
	DisplayString FROM SNMPv2-TC;

concord								OBJECT IDENTIFIER ::= { enterprises 149 }
netHealth							OBJECT IDENTIFIER ::= { concord 2 }
netHealthMib						OBJECT IDENTIFIER ::= { netHealth 1 }	
nhSysInfo								OBJECT IDENTIFIER ::= { netHealth 2 }	
nhArgs								OBJECT IDENTIFIER ::= { netHealth 3 }	
nhdTraps							OBJECT IDENTIFIER ::= { netHealthMib 1 }


nhdServer							OBJECT IDENTIFIER ::= { nhdTraps 1 }
nhdError							OBJECT IDENTIFIER ::= { nhdTraps 2 }

-- MIB Object Identifiers

nhServerIp OBJECT-TYPE
    SYNTAX	IpAddress
	ACCESS  read-only
	STATUS  mandatory
	DESCRIPTION
		    "This object specifies the IP address of the  
             Network Health server."
	::= { nhSysInfo 1 }

nhServerName OBJECT-TYPE
    SYNTAX	DisplayString
	ACCESS  read-only
	STATUS  mandatory
	DESCRIPTION
		    "This object specifies the name of the  
             Network Health server."
	::= { nhSysInfo 2 }

nhServerPort OBJECT-TYPE
    SYNTAX	INTEGER
	ACCESS  read-only
	STATUS  mandatory
	DESCRIPTION
		    "This object specifies the port number of the  
             Network Health server."
	::= { nhSysInfo 3 }

nhElementIp OBJECT-TYPE
    SYNTAX	IpAddress
	ACCESS  read-only
	STATUS  mandatory
	DESCRIPTION
		    "This object specifies the IP address of a 
             Network Health element."
	::= { nhArgs 1 }

nhElementName OBJECT-TYPE
    SYNTAX	DisplayString
	ACCESS  read-only
	STATUS  mandatory
	DESCRIPTION
		    "This object specifies the name of a 
             Network Health element."
	::= { nhArgs 2 }

nhElementId OBJECT-TYPE
    SYNTAX	INTEGER
	ACCESS  read-only
	STATUS  mandatory
	DESCRIPTION
		    "This object specifies the database identifier of a Network Health
			 element."
	::= { nhArgs 3 }

nhStartTime OBJECT-TYPE
    SYNTAX	INTEGER
	ACCESS  read-only
	STATUS  mandatory
	DESCRIPTION
		    "This object is the UTC time that the exception or alarm was 
			 detected by LiveExceptions."
	::= { nhArgs 4 }

nhExceptionType OBJECT-TYPE
	SYNTAX	DisplayString
	ACCESS  read-only
	STATUS  mandatory
	DESCRIPTION
		    "This object specifies the algorithm(s) used to detect the 
			 alarm. They could include Time Over Threshold,
			 Deviation From Normal, Dynamic Threshold, Availability < 100%
			 and Reachability < 100%."
	::= { nhArgs 5 }

nhVariable OBJECT-TYPE
    SYNTAX	DisplayString
	ACCESS  read-only
	STATUS  mandatory
	DESCRIPTION
		    "This object defines the variable(s) used in the rule 
			 that created the alarm."
	::= { nhArgs 6 }

nhSeverity OBJECT-TYPE
    SYNTAX	INTEGER {
 		normal		(1),
 		warning		(2),
 		minor		(3),
 		major		(4),
 		critical	(5)
 	}
	ACCESS  read-only
	STATUS  mandatory
	DESCRIPTION
		    "This object is the severity level of the alarm. The user 
			 can view/modify the severity of a rule in the LiveExceptions
			 Rule Editor."
	::= { nhArgs 7 }

nhGroup OBJECT-TYPE
    SYNTAX	DisplayString
	ACCESS  read-only
	STATUS  mandatory
	DESCRIPTION
		    "This object defines the group that LiveExceptions is monitoring and
			 that contains the element that has an alarm or exception. This object
			 value will be blank if LiveExceptions is monitoring a group list."
	::= { nhArgs 8 }

nhGroupList OBJECT-TYPE
    SYNTAX	DisplayString
	ACCESS  read-only
	STATUS  mandatory
	DESCRIPTION
		    "This object defines the group list that LiveExceptions is monitoring and
			 that contains the element that has an alarm or exception. This object
			 value will be blank if LiveExceptions is monitoring a group."
	::= { nhArgs 9 }

nhDisplayStr OBJECT-TYPE
    SYNTAX	DisplayString
	ACCESS  read-only
	STATUS  mandatory
	DESCRIPTION
		    "This object describes the rule which triggered the alarm. This field
		     is blank for exceptions. The Rule Message can be viewed/modified
			 in the LiveExceptions Rule Editor."
	::= { nhArgs 10 }

nhExceptionId OBJECT-TYPE
    SYNTAX	INTEGER
	ACCESS  read-only
	STATUS  mandatory
	DESCRIPTION
		    "This object defines a unique ID for the exception (Profile ID)
			 or the alarm (Alarm ID). It is used to run Network Health reports."
	::= { nhArgs 11 }

nhTechType OBJECT-TYPE
    SYNTAX	DisplayString
	ACCESS  read-only
	STATUS  mandatory
	DESCRIPTION
		    "This object defines the technology type of the group or group list."
	::= { nhArgs 12 }

nhResetTime OBJECT-TYPE
    SYNTAX	INTEGER
	ACCESS  read-only
	STATUS  mandatory
	DESCRIPTION
		    "This object is the UTC time that the LiveExceptions server started."
	::= { nhArgs 13 }

nhProfile OBJECT-TYPE
    SYNTAX	DisplayString
	ACCESS  read-only
	STATUS  mandatory
	DESCRIPTION
		    "This object is the name of the profile for this alarm or exception."
	::= { nhArgs 14 }

nhProblemStartTime OBJECT-TYPE
    SYNTAX	INTEGER
	ACCESS  read-only
	STATUS  mandatory
	DESCRIPTION
		    "This object is the UTC time when the threshold was first crossed and
			 that later resulted in an alarm or exception for that element."
	::= { nhArgs 15 }

nhProblemDuration OBJECT-TYPE
    SYNTAX	INTEGER
	ACCESS  read-only
	STATUS  mandatory
	DESCRIPTION
		    "This object is the amount of time (in seconds) spent over the 
			 threshold since the problem start time (the time the threshold was  
			 first crossed)."
	::= { nhArgs 16 }


nhdErrorDate OBJECT-TYPE
    SYNTAX	OCTET STRING
	ACCESS  read-only
	STATUS  mandatory
	DESCRIPTION
		    "This object is the date the exception occurred."
	::= { nhdError 1 }							

nhdErrorTime OBJECT-TYPE
    SYNTAX	OCTET STRING
	ACCESS  read-only
	STATUS  mandatory
	DESCRIPTION
		    "This object is the time the exception occurred."
	::= { nhdError 2  }

nhdErrorCode OBJECT-TYPE
    SYNTAX	OCTET STRING
	ACCESS  read-only
	STATUS  mandatory
	DESCRIPTION
		    "This object is the variable that has caused the exception."
	::= { nhdError 3 }

nhdErrorMessage OBJECT-TYPE
    SYNTAX	OCTET STRING
	ACCESS  read-only
	STATUS  mandatory
	DESCRIPTION
		    "This object describes the reason for the exception."
	::= { nhdError 5 }

nhdServerIp OBJECT-TYPE
    SYNTAX	IpAddress
	ACCESS  read-only
	STATUS  mandatory
	DESCRIPTION
		    "This object is the IP address of the element that has the exception."
	::= { nhdServer 1 }

nhdServerName OBJECT-TYPE
    SYNTAX	OCTET STRING
	ACCESS  read-only
	STATUS  mandatory
	DESCRIPTION
		    "This object is the name of the element that has the exception."
	::= { nhdServer 2 }

netHealthInfo TRAP-TYPE
	ENTERPRISE	concord
	VARIABLES	{ nhdErrorDate, nhdErrorTime,
				  nhdErrorCode, nhdErrorMessage, 
				  nhdServerIp, nhdServerName, nhServerPort, nhElementId			
				}
	DESCRIPTION
		"An event (not an error) has occurred in Network Health.
		 This trap is an informational message from the Network Health 
		 Diagnostic Monitor. No action is required."
	::= 15

netHealthWarning TRAP-TYPE
	ENTERPRISE	concord
	VARIABLES	{ nhdErrorDate, nhdErrorTime,
				  nhdErrorCode, nhdErrorMessage,
				  nhdServerIp, nhdServerName		
				}
	DESCRIPTION
		"An error has occurred in Network Health.
		 Polling will continue, please investigate as 
		 soon as possible. This trap is sent from the Network Health 
		 Diagnostic Monitor."
	::= 16

netHealthReset TRAP-TYPE
	ENTERPRISE	concord
	VARIABLES	{ nhdErrorDate, nhdErrorTime,
				  nhdErrorCode, nhdErrorMessage,
				  nhdServerIp, nhdServerName		
				}
	DESCRIPTION
		"A system critical error has occurred in Network Health.
		 Polling may not occur. Restart the Network Health servers as
		 soon as possible. This trap is sent from the Network Health 
		 Diagnostic Monitor."
	::= 17

netHealthUrgent TRAP-TYPE
	ENTERPRISE	concord
	VARIABLES	{ nhdErrorDate, nhdErrorTime,
				  nhdErrorCode, nhdErrorMessage,
				  nhdServerIp, nhdServerName		
				}
	DESCRIPTION
		"A system critical error has occurred in Network Health.
		 Polling may not occur. System administrator intervention 
		 is required. This trap is sent from the Network Health 
		 Diagnostic Monitor."
	::= 18

netHealthException TRAP-TYPE
	ENTERPRISE	concord
	VARIABLES	{ nhdErrorDate, nhdErrorTime,
				  nhdErrorCode, nhdErrorMessage,
				  nhdServerIp, nhdServerName, nhServerPort, nhElementId,
				  nhServerIp	
				}
	DESCRIPTION
		"A scheduled Network Health report has detected one or more health
		 exceptions for an element."
	::= 19

nhLiveException TRAP-TYPE
	ENTERPRISE	concord
	VARIABLES	{ nhServerIp, nhServerName,
				  nhServerPort, nhElementIp, nhElementName, 
				  nhElementId,
				  nhStartTime,
				  nhDisplayStr,	
				  nhGroup, nhGroupList,
				  nhSeverity,
--				  openViewSeverity (1.3.6.1.4.1.11.2.17.2.5.0) 
--				  is also sent in this trap
				  nhProfile,
				  nhExceptionId, nhTechType
				}
	DESCRIPTION
		"A Network Health exception has occurred. This trap
		 sends generic information about an exception when it first becomes
		 active."
	::= 20


nhLiveAlarm TRAP-TYPE
	ENTERPRISE	concord
	VARIABLES	{ nhServerIp, nhServerName,
				  nhServerPort, nhElementIp, nhElementName, 
				  nhElementId,
				  nhStartTime,
				  nhDisplayStr,	
				  nhGroup, nhGroupList,	
				  nhExceptionType, nhVariable,
				  nhSeverity,
--				  openViewSeverity (1.3.6.1.4.1.11.2.17.2.5.0) 
--				  is also sent in this trap
				  nhProfile,
				  nhExceptionId, nhTechType
				}
	DESCRIPTION
		"A Network Health alarm has occurred. This trap
		 sends detailed information about an alarm."
	::= 21

nhLiveClearException TRAP-TYPE
	ENTERPRISE	concord
	VARIABLES	{ nhServerIp, nhServerName,
				  nhServerPort, nhElementIp, nhElementName, 
				  nhElementId,
				  nhStartTime, 
				  nhDisplayStr,	
				  nhGroup, nhGroupList,		
				  nhSeverity,
--				  openViewSeverity (1.3.6.1.4.1.11.2.17.2.5.0) 
--				  is also sent in this trap
				  nhProfile,
				  nhExceptionId, nhTechType,
				  nhProblemStartTime, nhProblemDuration
				}
	DESCRIPTION
		"A Network Health exception has been cleared. The conditions causing
		 the corresponding exception no longer exist."
	::= 22

nhLiveClearAlarm TRAP-TYPE
	ENTERPRISE	concord
	VARIABLES	{ nhServerIp, nhServerName,
				  nhServerPort, nhElementIp, nhElementName, 
				  nhElementId,
				  nhStartTime,
				  nhDisplayStr,	
				  nhGroup, nhGroupList,	
				  nhExceptionType, nhVariable,
				  nhSeverity,
--				  openViewSeverity (1.3.6.1.4.1.11.2.17.2.5.0) 
--				  is also sent in this trap
				  nhProfile,
				  nhExceptionId, nhTechType,
				  nhProblemStartTime, nhProblemDuration	
				}
	DESCRIPTION
		"A Network Health alarm has been cleared. The conditions causing
		 the corresponding alarm no longer exist."
	::= 23


nhLiveUpdateException TRAP-TYPE
	ENTERPRISE	concord
	VARIABLES	{ nhServerIp, nhServerName,
				  nhServerPort, nhElementIp, nhElementName, 
				  nhElementId,
				  nhStartTime,
				  nhDisplayStr,	
				  nhGroup, nhGroupList,
				  nhSeverity,
--				  openViewSeverity (1.3.6.1.4.1.11.2.17.2.5.0) 
--				  is also sent in this trap
				  nhProfile,
				  nhExceptionId, nhTechType
				}
	DESCRIPTION
		"The severity of a Network Health exception has changed."
	::= 24

nhLiveResetExceptions TRAP-TYPE
	ENTERPRISE	concord
	VARIABLES	{ nhServerIp, nhServerName,
				  nhServerPort, nhResetTime
				}
	DESCRIPTION
		    "The LiveExceptions server has restarted. All LiveExceptions alarms 
		     and exceptions sent before this time will NOT be cleared automatically. All trap 
			 destinations should reset any pre-existing Network Health exceptions 
			 and alarms by setting them to a clear state or unhighlighting
			 any icons."
	::= 25

END
