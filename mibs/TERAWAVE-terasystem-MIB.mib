TERAWAVE-terasystem-MIB DEFINITIONS ::= BEGIN
        -- Created by sml2mib compiler 
        IMPORTS

 IpAddress, enterprises,  OBJECT-TYPE,  Counter,  Gauge,  TimeTicks
        FROM RFC1155-SMI;

terawave OBJECT IDENTIFIER ::=  { enterprises 4513 }

     -- teraSystemTimeTable (special)

teraSystem OBJECT IDENTIFIER ::=  { terawave 5 }

teraSystemTime OBJECT-TYPE
          SYNTAX INTEGER
          ACCESS read-write
          STATUS mandatory
          DESCRIPTION
               ""
          ::= { teraSystem 1 }

teraSystemCurrTime OBJECT-TYPE
          SYNTAX INTEGER
          ACCESS read-only
          STATUS mandatory
          DESCRIPTION
               ""
          ::= { teraSystem 2 }

teraLogGroup OBJECT IDENTIFIER ::=  { teraSystem 8 }

     -- teraLogNumberTable

teraLogNumberTable OBJECT-TYPE
     SYNTAX SEQUENCE OF TeraLogNumberTableEntryType
     ACCESS not-accessible
     STATUS mandatory
     DESCRIPTION
          " table teraLogNumberTable"
     ::= { teraLogGroup 1 }

teraLogNumberTableEntry OBJECT-TYPE
          SYNTAX TeraLogNumberTableEntryType
          ACCESS not-accessible
          STATUS mandatory
          DESCRIPTION
               " table entry teraLogNumberTableEntry "
          INDEX {                   teraLogNumber }
     ::= { teraLogNumberTable 1 }

TeraLogNumberTableEntryType ::= SEQUENCE {
          teraLogNumber   
             INTEGER,
          teraLogNumberDescr   
             OCTET STRING,
          teraLogNumberStatus   
             INTEGER
}

teraLogNumber OBJECT-TYPE
          SYNTAX INTEGER
          ACCESS read-only
          STATUS mandatory
          DESCRIPTION
               ""
          ::= { teraLogNumberTableEntry 1 }

teraLogNumberDescr OBJECT-TYPE
          SYNTAX OCTET STRING
          ACCESS read-only
          STATUS mandatory
          DESCRIPTION
               ""
          ::= { teraLogNumberTableEntry 2 }

teraLogNumberStatus OBJECT-TYPE
          SYNTAX INTEGER
                  {
                  ok(1),
                  clear(2)
                  }
          ACCESS read-write
          STATUS mandatory
          DESCRIPTION
               ""
          ::= { teraLogNumberTableEntry 3 }

     -- teraLogGroup (special)

teraLogClear OBJECT-TYPE
          SYNTAX INTEGER
                  {
                  ok(1),
                  clear(2)
                  }
          ACCESS read-write
          STATUS mandatory
          DESCRIPTION
               ""
          ::= { teraLogGroup 2 }

     -- teraLogTable

teraLogTable OBJECT-TYPE
     SYNTAX SEQUENCE OF TeraLogTableEntryType
     ACCESS not-accessible
     STATUS mandatory
     DESCRIPTION
          " table teraLogTable"
     ::= { teraLogGroup 3 }

teraLogTableEntry OBJECT-TYPE
          SYNTAX TeraLogTableEntryType
          ACCESS not-accessible
          STATUS mandatory
          DESCRIPTION
               " table entry teraLogTableEntry "
          INDEX {                   teraInstallSlotNumber,                  teraLogNumber,                  teraLogMsgIndex }
     ::= { teraLogTable 4 }

TeraLogTableEntryType ::= SEQUENCE {
          teraLogMsgIndex   
             INTEGER,
          teraLogMsgNumber   
             INTEGER,
          teraLogNumberOfParams   
             INTEGER,
          teraLogParams   
             OCTET STRING,
          teraLogStatus   
             INTEGER
}

teraLogMsgIndex OBJECT-TYPE
          SYNTAX INTEGER
          ACCESS read-only
          STATUS mandatory
          DESCRIPTION
               ""
          ::= { teraLogTableEntry 1 }

teraLogMsgNumber OBJECT-TYPE
          SYNTAX INTEGER
          ACCESS read-only
          STATUS mandatory
          DESCRIPTION
               ""
          ::= { teraLogTableEntry 2 }

teraLogNumberOfParams OBJECT-TYPE
          SYNTAX INTEGER
          ACCESS read-only
          STATUS mandatory
          DESCRIPTION
               ""
          ::= { teraLogTableEntry 3 }

teraLogParams OBJECT-TYPE
          SYNTAX OCTET STRING
          ACCESS read-only
          STATUS mandatory
          DESCRIPTION
               ""
          ::= { teraLogTableEntry 4 }

teraLogStatus OBJECT-TYPE
          SYNTAX INTEGER
                  {
                  ok(1),
                  clear(2)
                  }
          ACCESS read-only
          STATUS mandatory
          DESCRIPTION
               ""
          ::= { teraLogTableEntry 5 }

     -- teraAllLogsFilterGroup

teraAllLogsFilterGroup OBJECT-TYPE
     SYNTAX SEQUENCE OF TeraAllLogsFilterGroupEntryType
     ACCESS not-accessible
     STATUS mandatory
     DESCRIPTION
          " table teraAllLogsFilterGroup"
     ::= { teraLogTable 5 }

teraAllLogsFilterGroupEntry OBJECT-TYPE
          SYNTAX TeraAllLogsFilterGroupEntryType
          ACCESS not-accessible
          STATUS mandatory
          DESCRIPTION
               " table entry teraAllLogsFilterGroupEntry "
          INDEX {                   teraLogNumber }
     ::= { teraAllLogsFilterGroup 1 }

TeraAllLogsFilterGroupEntryType ::= SEQUENCE {
          teraLogFilterByNumber   
             INTEGER,
          teraLogFilterBySize   
             INTEGER,
          teraLogFilterBySeverity   
             INTEGER,
          teraLogFilterByTask   
             OCTET STRING
}

teraLogFilterByNumber OBJECT-TYPE
          SYNTAX INTEGER
          ACCESS read-write
          STATUS mandatory
          DESCRIPTION
               ""
          ::= { teraAllLogsFilterGroupEntry 1 }

teraLogFilterBySize OBJECT-TYPE
          SYNTAX INTEGER
                  {
                  all(1),
                  last20(2)
                  }
          ACCESS read-write
          STATUS mandatory
          DESCRIPTION
               ""
          ::= { teraAllLogsFilterGroupEntry 2 }

teraLogFilterBySeverity OBJECT-TYPE
          SYNTAX INTEGER
                  {
                  nominal(1),
                  minor(2),
                  major(3),
                  critical(5)
                  }
          ACCESS read-write
          STATUS mandatory
          DESCRIPTION
               ""
          ::= { teraAllLogsFilterGroupEntry 3 }

teraLogFilterByTask OBJECT-TYPE
          SYNTAX OCTET STRING
          ACCESS read-write
          STATUS mandatory
          DESCRIPTION
               ""
          ::= { teraAllLogsFilterGroupEntry 4 }

teraSlotInstTablePar OBJECT IDENTIFIER ::=  { teraSystem 3 }

     -- teraSlotInstallTable

teraSlotInstallTable OBJECT-TYPE
     SYNTAX SEQUENCE OF TeraSlotInstallTableEntryType
     ACCESS not-accessible
     STATUS mandatory
     DESCRIPTION
          " table teraSlotInstallTable"
     ::= { teraSlotInstTablePar 1 }

teraSlotInstallTableEntry OBJECT-TYPE
          SYNTAX TeraSlotInstallTableEntryType
          ACCESS not-accessible
          STATUS mandatory
          DESCRIPTION
               " table entry teraSlotInstallTableEntry "
          INDEX {                   teraInstallSlotNumber }
     ::= { teraSlotInstallTable 1 }

TeraSlotInstallTableEntryType ::= SEQUENCE {
          teraInstallSlotNumber   
             INTEGER (1..7),
          teraInstallUnitType   
             INTEGER (-1..5000),
          teraInstallEquippedUnitType   
             INTEGER,
          teraInstallUnitAdminStatus   
             INTEGER,
          teraInstallUnitOperStatus   
             INTEGER,
          teraInstallUnitName   
             OCTET STRING,
          teraInstallUnitRevision   
             OCTET STRING,
          teraInstallUnitSerial   
             INTEGER,
          teraInstallUnitSWVersion   
             INTEGER,
          teraInstallUnitMfgData   
             OCTET STRING
}

teraInstallSlotNumber OBJECT-TYPE
          SYNTAX INTEGER (1..7)
          ACCESS read-only
          STATUS mandatory
          DESCRIPTION
               ""
          ::= { teraSlotInstallTableEntry 1 }

teraInstallUnitType OBJECT-TYPE
          SYNTAX INTEGER (-1..5000)
          ACCESS read-write
          STATUS mandatory
          DESCRIPTION
               ""
          ::= { teraSlotInstallTableEntry 2 }

teraInstallEquippedUnitType OBJECT-TYPE
          SYNTAX INTEGER
          ACCESS read-only
          STATUS mandatory
          DESCRIPTION
               ""
          ::= { teraSlotInstallTableEntry 3 }

teraInstallUnitAdminStatus OBJECT-TYPE
          SYNTAX INTEGER
                  {
                  provision(1),
                  none(2),
                  is(3),
                  moos(4),
                  reset(5),
                  trunk(6),
                  moos-trunk(7)
                  }
          ACCESS read-write
          STATUS mandatory
          DESCRIPTION
               ""
          ::= { teraSlotInstallTableEntry 4 }

teraInstallUnitOperStatus OBJECT-TYPE
          SYNTAX INTEGER
                  {
                  empty(1),
                  is(2),
                  moos(3),
                  removed(4),
                  unprovisioned(5),
                  mismatch(6),
                  oos(7),
                  init(8)
                  }
          ACCESS read-only
          STATUS mandatory
          DESCRIPTION
               ""
          ::= { teraSlotInstallTableEntry 5 }

teraInstallUnitName OBJECT-TYPE
          SYNTAX OCTET STRING
          ACCESS read-only
          STATUS mandatory
          DESCRIPTION
               ""
          ::= { teraSlotInstallTableEntry 6 }

teraInstallUnitRevision OBJECT-TYPE
          SYNTAX OCTET STRING
          ACCESS read-only
          STATUS mandatory
          DESCRIPTION
               ""
          ::= { teraSlotInstallTableEntry 7 }

teraInstallUnitSerial OBJECT-TYPE
          SYNTAX INTEGER
          ACCESS read-only
          STATUS mandatory
          DESCRIPTION
               ""
          ::= { teraSlotInstallTableEntry 8 }

teraInstallUnitSWVersion OBJECT-TYPE
          SYNTAX INTEGER
          ACCESS read-only
          STATUS mandatory
          DESCRIPTION
               ""
          ::= { teraSlotInstallTableEntry 9 }

teraInstallUnitMfgData OBJECT-TYPE
          SYNTAX OCTET STRING
          ACCESS read-only
          STATUS mandatory
          DESCRIPTION
               ""
          ::= { teraSlotInstallTableEntry 10 }

     -- teraSystemInstallTable

teraSystemInstallTable OBJECT-TYPE
     SYNTAX SEQUENCE OF TeraSystemInstallTableEntryType
     ACCESS not-accessible
     STATUS mandatory
     DESCRIPTION
          " table teraSystemInstallTable"
     ::= { teraSlotInstTablePar 2 }

teraSystemInstallTableEntry OBJECT-TYPE
          SYNTAX TeraSystemInstallTableEntryType
          ACCESS not-accessible
          STATUS mandatory
          DESCRIPTION
               " table entry teraSystemInstallTableEntry "
          INDEX {                   teraInstallSlotNumber,                  teraPonIndex }
     ::= { teraSystemInstallTable 1 }

TeraSystemInstallTableEntryType ::= SEQUENCE {
          teraSystemNEProvisionAdminStatus   
             INTEGER,
          teraSystemNEName   
             OCTET STRING,
          teraSystemNERangingCode   
             OCTET STRING,
          teraSystemNEType   
             INTEGER,
          teraSystemNEMaxLatency   
             INTEGER (8..60),
          teraSystemNEAponMaxLength   
             INTEGER (0..200),
          teraSystemNEOperStatus   
             INTEGER,
          teraSystemNEEocMinBandWidth   
             INTEGER (128..1536),
          teraSystemNEEocMaxBandWidth   
             INTEGER (128..1536),
          teraSystemNEInventoryOverride   
             INTEGER,
          teraSystemNERanging   
             INTEGER,
          teraSystemNECurrentDistance   
             INTEGER (0..20000)
}

teraSystemNEProvisionAdminStatus OBJECT-TYPE
          SYNTAX INTEGER
                  {
                  provision(1),
                  none(2)
                  }
          ACCESS read-write
          STATUS mandatory
          DESCRIPTION
               ""
          ::= { teraSystemInstallTableEntry 1 }

teraSystemNEName OBJECT-TYPE
          SYNTAX OCTET STRING
          ACCESS read-only
          STATUS mandatory
          DESCRIPTION
               ""
          ::= { teraSystemInstallTableEntry 2 }

teraSystemNERangingCode OBJECT-TYPE
          SYNTAX OCTET STRING
          ACCESS read-write
          STATUS mandatory
          DESCRIPTION
               ""
          ::= { teraSystemInstallTableEntry 3 }

teraSystemNEType OBJECT-TYPE
          SYNTAX INTEGER
                  {
                  unknown(0),
                  tw300(1),
                  tw600(2),
                  tw1600(3),
                  tw100(4),
                  tw150RT(5),
                  oat(7)
                  }
          ACCESS read-only
          STATUS mandatory
          DESCRIPTION
               ""
          ::= { teraSystemInstallTableEntry 4 }

teraSystemNEMaxLatency OBJECT-TYPE
          SYNTAX INTEGER (8..60)
          ACCESS read-write
          STATUS mandatory
          DESCRIPTION
               ""
          ::= { teraSystemInstallTableEntry 5 }

teraSystemNEAponMaxLength OBJECT-TYPE
          SYNTAX INTEGER (0..200)
          ACCESS read-write
          STATUS mandatory
          DESCRIPTION
               ""
          ::= { teraSystemInstallTableEntry 6 }

teraSystemNEOperStatus OBJECT-TYPE
          SYNTAX INTEGER
                  {
                  empty(1),
                  provisioned(2),
                  linkDown(3)
                  }
          ACCESS read-only
          STATUS mandatory
          DESCRIPTION
               ""
          ::= { teraSystemInstallTableEntry 7 }

teraSystemNEEocMinBandWidth OBJECT-TYPE
          SYNTAX INTEGER (128..1536)
          ACCESS read-write
          STATUS mandatory
          DESCRIPTION
               ""
          ::= { teraSystemInstallTableEntry 8 }

teraSystemNEEocMaxBandWidth OBJECT-TYPE
          SYNTAX INTEGER (128..1536)
          ACCESS read-write
          STATUS mandatory
          DESCRIPTION
               ""
          ::= { teraSystemInstallTableEntry 9 }

teraSystemNEInventoryOverride OBJECT-TYPE
          SYNTAX INTEGER
                  {
                  olt2ont(1),
                  ont2olt(2)
                  }
          ACCESS read-write
          STATUS mandatory
          DESCRIPTION
               ""
          ::= { teraSystemInstallTableEntry 10 }

teraSystemNERanging OBJECT-TYPE
          SYNTAX INTEGER
                  {
                  on(1),
                  off(2)
                  }
          ACCESS read-write
          STATUS mandatory
          DESCRIPTION
               ""
          ::= { teraSystemInstallTableEntry 11 }

teraSystemNECurrentDistance OBJECT-TYPE
          SYNTAX INTEGER (0..20000)
          ACCESS read-only
          STATUS mandatory
          DESCRIPTION
               ""
          ::= { teraSystemInstallTableEntry 12 }

teraNEInfoTableGroup OBJECT IDENTIFIER ::=  { teraSlotInstTablePar 3 }

     -- teraNEInfoTable (special)

teraNEInfoTable OBJECT IDENTIFIER ::=  { teraNEInfoTableGroup 1 }

teraNERangingCode OBJECT-TYPE
          SYNTAX OCTET STRING
          ACCESS read-write
          STATUS mandatory
          DESCRIPTION
               ""
          ::= { teraNEInfoTable 1 }

teraNEType OBJECT-TYPE
          SYNTAX INTEGER
                  {
                  unknown(0),
                  tw300(1),
                  tw600(2),
                  tw1600(3),
                  tw100(4),
                  tw150RT-ATM(5),
                  tw150RT-TDM(6),
                  oat(7)
                  }
          ACCESS read-only
          STATUS mandatory
          DESCRIPTION
               ""
          ::= { teraNEInfoTable 2 }

teraNEModel OBJECT-TYPE
          SYNTAX OCTET STRING
          ACCESS read-only
          STATUS mandatory
          DESCRIPTION
               ""
          ::= { teraNEInfoTable 3 }

teraNESWVersion OBJECT-TYPE
          SYNTAX OCTET STRING
          ACCESS read-only
          STATUS mandatory
          DESCRIPTION
               ""
          ::= { teraNEInfoTable 4 }

teraNESWRevision OBJECT-TYPE
          SYNTAX OCTET STRING
          ACCESS read-only
          STATUS mandatory
          DESCRIPTION
               ""
          ::= { teraNEInfoTable 5 }

     -- teraClockSyncTable (special)

teraClockSyncTable OBJECT IDENTIFIER ::=  { teraSystem 4 }

teraClockSyncPrimarySource OBJECT-TYPE
          SYNTAX INTEGER
                  {
                  bits-A(1),
                  nim(2),
                  freerun(3),
                  holdover(4)
                  }
          ACCESS read-write
          STATUS mandatory
          DESCRIPTION
               ""
          ::= { teraClockSyncTable 1 }

teraClockSyncPrimaryNIMSlot OBJECT-TYPE
          SYNTAX INTEGER (1..16)
          ACCESS read-write
          STATUS mandatory
          DESCRIPTION
               ""
          ::= { teraClockSyncTable 2 }

teraClockSyncPrimaryNIMIfIndex OBJECT-TYPE
          SYNTAX INTEGER
          ACCESS read-write
          STATUS mandatory
          DESCRIPTION
               ""
          ::= { teraClockSyncTable 3 }

teraClockSyncSecondarySource OBJECT-TYPE
          SYNTAX INTEGER
                  {
                  bits-B(1),
                  nim(2),
                  freerun(3),
                  holdover(4)
                  }
          ACCESS read-write
          STATUS mandatory
          DESCRIPTION
               ""
          ::= { teraClockSyncTable 4 }

teraClockSyncSecondaryNIMSlot OBJECT-TYPE
          SYNTAX INTEGER (1..16)
          ACCESS read-write
          STATUS mandatory
          DESCRIPTION
               ""
          ::= { teraClockSyncTable 5 }

teraClockSyncSecondaryNIMIfIndex OBJECT-TYPE
          SYNTAX INTEGER
          ACCESS read-write
          STATUS mandatory
          DESCRIPTION
               ""
          ::= { teraClockSyncTable 6 }

teraClockSyncLastSource OBJECT-TYPE
          SYNTAX INTEGER
                  {
                  freerun(1),
                  holdover(2)
                  }
          ACCESS read-write
          STATUS mandatory
          DESCRIPTION
               ""
          ::= { teraClockSyncTable 7 }

teraClockSyncRevertive OBJECT-TYPE
          SYNTAX INTEGER
                  {
                  yes(1),
                  no(2)
                  }
          ACCESS read-write
          STATUS mandatory
          DESCRIPTION
               ""
          ::= { teraClockSyncTable 8 }

teraClockSyncActiveSource OBJECT-TYPE
          SYNTAX INTEGER
                  {
                  bits-A(1),
                  bits-B(2),
                  nim(3),
                  freerun(4),
                  holdover(5)
                  }
          ACCESS read-only
          STATUS mandatory
          DESCRIPTION
               ""
          ::= { teraClockSyncTable 9 }

teraClockSyncActiveNIMSlot OBJECT-TYPE
          SYNTAX INTEGER (1..16)
          ACCESS read-only
          STATUS mandatory
          DESCRIPTION
               ""
          ::= { teraClockSyncTable 10 }

teraClockSyncActiveNIMIfIndex OBJECT-TYPE
          SYNTAX INTEGER
          ACCESS read-only
          STATUS mandatory
          DESCRIPTION
               ""
          ::= { teraClockSyncTable 11 }

teraClockSyncActiveStatus OBJECT-TYPE
          SYNTAX INTEGER
                  {
                  auto(1),
                  manual(2)
                  }
          ACCESS read-only
          STATUS mandatory
          DESCRIPTION
               ""
          ::= { teraClockSyncTable 12 }

teraClockSyncPrimaryStatus OBJECT-TYPE
          SYNTAX INTEGER
                  {
                  active(1),
                  idle(2),
                  fail(3),
                  oos(4)
                  }
          ACCESS read-only
          STATUS mandatory
          DESCRIPTION
               ""
          ::= { teraClockSyncTable 13 }

teraClockSyncSecondaryStatus OBJECT-TYPE
          SYNTAX INTEGER
                  {
                  active(1),
                  idle(2),
                  fail(3),
                  oos(4)
                  }
          ACCESS read-only
          STATUS mandatory
          DESCRIPTION
               ""
          ::= { teraClockSyncTable 14 }

teraClockSyncOperStatus OBJECT-TYPE
          SYNTAX INTEGER
                  {
                  configure(1),
                  switchToPrimary(2),
                  switchToSecondary(3),
                  switchToHoldover(4),
                  switchToFreerun(5)
                  }
          ACCESS read-write
          STATUS mandatory
          DESCRIPTION
               ""
          ::= { teraClockSyncTable 15 }

     -- teraCommunityGroupTable (special)

teraCommunityGroupTable OBJECT IDENTIFIER ::=  { teraSystem 5 }

teraPublicCommunity OBJECT-TYPE
          SYNTAX OCTET STRING
          ACCESS read-write
          STATUS mandatory
          DESCRIPTION
               ""
          ::= { teraCommunityGroupTable 1 }

teraSETCommunity OBJECT-TYPE
          SYNTAX OCTET STRING
          ACCESS read-write
          STATUS mandatory
          DESCRIPTION
               ""
          ::= { teraCommunityGroupTable 2 }

teraGETCommunity OBJECT-TYPE
          SYNTAX OCTET STRING
          ACCESS read-write
          STATUS mandatory
          DESCRIPTION
               ""
          ::= { teraCommunityGroupTable 3 }

teraAdminCommunity OBJECT-TYPE
          SYNTAX OCTET STRING
          ACCESS read-write
          STATUS mandatory
          DESCRIPTION
               ""
          ::= { teraCommunityGroupTable 4 }

teraTestCommunity OBJECT-TYPE
          SYNTAX OCTET STRING
          ACCESS read-write
          STATUS mandatory
          DESCRIPTION
               ""
          ::= { teraCommunityGroupTable 5 }

     -- teraMasterSlaveTable (special)

teraMasterSlaveTable OBJECT IDENTIFIER ::=  { teraSystem 6 }

teraMasterSlotNumber OBJECT-TYPE
          SYNTAX INTEGER (0..7)
          ACCESS read-write
          STATUS mandatory
          DESCRIPTION
               ""
          ::= { teraMasterSlaveTable 1 }

teraSlaveSlotNumber OBJECT-TYPE
          SYNTAX INTEGER (0..7)
          ACCESS read-write
          STATUS mandatory
          DESCRIPTION
               ""
          ::= { teraMasterSlaveTable 2 }

     -- teraSystemIPGroupTable (special)

teraSystemIPGroupTable OBJECT IDENTIFIER ::=  { teraSystem 7 }

teraSystemIPAddress OBJECT-TYPE
          SYNTAX IpAddress
          ACCESS read-write
          STATUS mandatory
          DESCRIPTION
               ""
          ::= { teraSystemIPGroupTable 1 }

teraSystemIPNetMask OBJECT-TYPE
          SYNTAX IpAddress
          ACCESS read-write
          STATUS mandatory
          DESCRIPTION
               ""
          ::= { teraSystemIPGroupTable 2 }

teraSystemIPGateway OBJECT-TYPE
          SYNTAX IpAddress
          ACCESS read-write
          STATUS mandatory
          DESCRIPTION
               ""
          ::= { teraSystemIPGroupTable 3 }

     -- teraNESlotTable

teraNESlotTable OBJECT-TYPE
     SYNTAX SEQUENCE OF TeraNESlotTableEntryType
     ACCESS not-accessible
     STATUS mandatory
     DESCRIPTION
          " table teraNESlotTable"
     ::= { teraSystem 9 }

teraNESlotTableEntry OBJECT-TYPE
          SYNTAX TeraNESlotTableEntryType
          ACCESS not-accessible
          STATUS mandatory
          DESCRIPTION
               " table entry teraNESlotTableEntry "
          INDEX {                   teraInstallSlotNumber,                  teraPonIndex,                  teraEventSlot }
     ::= { teraNESlotTable 1 }

TeraNESlotTableEntryType ::= SEQUENCE {
          teraNESlotUnitType   
             INTEGER (-1..1000),
          teraNESlotUnitAdminStatus   
             INTEGER
}

teraNESlotUnitType OBJECT-TYPE
          SYNTAX INTEGER (-1..1000)
          ACCESS read-write
          STATUS mandatory
          DESCRIPTION
               ""
          ::= { teraNESlotTableEntry 1 }

teraNESlotUnitAdminStatus OBJECT-TYPE
          SYNTAX INTEGER
                  {
                  provision(1),
                  none(2),
                  is(3),
                  moos(4),
                  reset(5),
                  trunk(6)
                  }
          ACCESS read-write
          STATUS mandatory
          DESCRIPTION
               ""
          ::= { teraNESlotTableEntry 2 }

     -- teraWLinkIPTable

teraWLinkIPTable OBJECT-TYPE
     SYNTAX SEQUENCE OF TeraWLinkIPTableEntryType
     ACCESS not-accessible
     STATUS mandatory
     DESCRIPTION
          " table teraWLinkIPTable"
     ::= { teraSystem 10 }

teraWLinkIPTableEntry OBJECT-TYPE
          SYNTAX TeraWLinkIPTableEntryType
          ACCESS not-accessible
          STATUS mandatory
          DESCRIPTION
               " table entry teraWLinkIPTableEntry "
          INDEX {                   teraInstallSlotNumber,                  teraPonIndex }
     ::= { teraWLinkIPTable 1 }

TeraWLinkIPTableEntryType ::= SEQUENCE {
          teraWLinkIPAddress   
             IpAddress,
          teraWLinkIPNetMask   
             IpAddress,
          teraWLinkIPGateway   
             IpAddress,
          teraWLinkIPStatus   
             INTEGER
}

teraWLinkIPAddress OBJECT-TYPE
          SYNTAX IpAddress
          ACCESS read-write
          STATUS mandatory
          DESCRIPTION
               ""
          ::= { teraWLinkIPTableEntry 1 }

teraWLinkIPNetMask OBJECT-TYPE
          SYNTAX IpAddress
          ACCESS read-write
          STATUS mandatory
          DESCRIPTION
               ""
          ::= { teraWLinkIPTableEntry 2 }

teraWLinkIPGateway OBJECT-TYPE
          SYNTAX IpAddress
          ACCESS read-write
          STATUS mandatory
          DESCRIPTION
               ""
          ::= { teraWLinkIPTableEntry 3 }

teraWLinkIPStatus OBJECT-TYPE
          SYNTAX INTEGER
                  {
                  set(1),
                  delete(2)
                  }
          ACCESS read-write
          STATUS mandatory
          DESCRIPTION
               ""
          ::= { teraWLinkIPTableEntry 4 }

teraNEMiscTableGroup OBJECT IDENTIFIER ::=  { teraSystem 11 }

     -- teraNEMiscTable (special)

teraNEMiscTable OBJECT IDENTIFIER ::=  { teraNEMiscTableGroup 1 }

teraNELevel2Slot OBJECT-TYPE
          SYNTAX INTEGER (1..4)
          ACCESS read-only
          STATUS mandatory
          DESCRIPTION
               ""
          ::= { teraNEMiscTable 1 }

teraNEZipSystem OBJECT-TYPE
          SYNTAX INTEGER
                  {
                  no(1),
                  zip-active(2),
                  zip-stby(3),
                  zip-all(4)
                  }
          ACCESS read-write
          STATUS mandatory
          DESCRIPTION
               ""
          ::= { teraNEMiscTable 2 }

teraNEReset OBJECT-TYPE
          SYNTAX INTEGER
                  {
                  no(1),
                  reset(2)
                  }
          ACCESS read-write
          STATUS mandatory
          DESCRIPTION
               ""
          ::= { teraNEMiscTable 3 }

teraNETimeZone OBJECT-TYPE
          SYNTAX OCTET STRING
          ACCESS read-write
          STATUS mandatory
          DESCRIPTION
               ""
          ::= { teraNEMiscTable 4 }

teraNEInventoryOverride OBJECT-TYPE
          SYNTAX INTEGER
                  {
                  disable(1),
                  enable(2)
                  }
          ACCESS read-write
          STATUS mandatory
          DESCRIPTION
               ""
          ::= { teraNEMiscTable 5 }

teraNESerialPortType OBJECT-TYPE
          SYNTAX INTEGER
                  {
                  ppp(1),
                  dbshell(2)
                  }
          ACCESS read-write
          STATUS mandatory
          DESCRIPTION
               ""
          ::= { teraNEMiscTable 6 }

     -- teraSysObjectIdTable (special)

teraSysObjectIdTable OBJECT IDENTIFIER ::=  { teraSystem 12 }

teraTW300 OBJECT-TYPE
          SYNTAX OBJECT IDENTIFIER
          ACCESS read-only
          STATUS mandatory
          DESCRIPTION
               ""
          ::= { teraSysObjectIdTable 1 }

teraTW600 OBJECT-TYPE
          SYNTAX OBJECT IDENTIFIER
          ACCESS read-only
          STATUS mandatory
          DESCRIPTION
               ""
          ::= { teraSysObjectIdTable 2 }

teraTW1600 OBJECT-TYPE
          SYNTAX OBJECT IDENTIFIER
          ACCESS read-only
          STATUS mandatory
          DESCRIPTION
               ""
          ::= { teraSysObjectIdTable 3 }

teraTW100 OBJECT-TYPE
          SYNTAX OBJECT IDENTIFIER
          ACCESS read-only
          STATUS mandatory
          DESCRIPTION
               ""
          ::= { teraSysObjectIdTable 4 }

teraTW150RTATM OBJECT-TYPE
          SYNTAX OBJECT IDENTIFIER
          ACCESS read-only
          STATUS mandatory
          DESCRIPTION
               ""
          ::= { teraSysObjectIdTable 5 }

teraTW150RTTDM OBJECT-TYPE
          SYNTAX OBJECT IDENTIFIER
          ACCESS read-only
          STATUS mandatory
          DESCRIPTION
               ""
          ::= { teraSysObjectIdTable 6 }

teraOAT OBJECT-TYPE
          SYNTAX OBJECT IDENTIFIER
          ACCESS read-only
          STATUS mandatory
          DESCRIPTION
               ""
          ::= { teraSysObjectIdTable 7 }

     -- teraNEIDxTable

teraNEIDxTable OBJECT-TYPE
     SYNTAX SEQUENCE OF TeraNEIDxTableEntryType
     ACCESS not-accessible
     STATUS mandatory
     DESCRIPTION
          " table teraNEIDxTable"
     ::= { teraSystem 13 }

teraNEIDxTableEntry OBJECT-TYPE
          SYNTAX TeraNEIDxTableEntryType
          ACCESS not-accessible
          STATUS mandatory
          DESCRIPTION
               " table entry teraNEIDxTableEntry "
          INDEX {                   ifIndex }
     ::= { teraNEIDxTable 1 }

TeraNEIDxTableEntryType ::= SEQUENCE {
          teraNEIDxSlotLevel1   
             INTEGER (1..16),
          teraNEIDxPonID   
             INTEGER (1..256)
}

teraNEIDxSlotLevel1 OBJECT-TYPE
          SYNTAX INTEGER (1..16)
          ACCESS read-only
          STATUS mandatory
          DESCRIPTION
               ""
          ::= { teraNEIDxTableEntry 1 }

teraNEIDxPonID OBJECT-TYPE
          SYNTAX INTEGER (1..256)
          ACCESS read-only
          STATUS mandatory
          DESCRIPTION
               ""
          ::= { teraNEIDxTableEntry 2 }

     -- teraWLinkIPRangeTable

teraWLinkIPRangeTable OBJECT-TYPE
     SYNTAX SEQUENCE OF TeraWLinkIPRangeTableEntryType
     ACCESS not-accessible
     STATUS mandatory
     DESCRIPTION
          " table teraWLinkIPRangeTable"
     ::= { teraSystem 14 }

teraWLinkIPRangeTableEntry OBJECT-TYPE
          SYNTAX TeraWLinkIPRangeTableEntryType
          ACCESS not-accessible
          STATUS mandatory
          DESCRIPTION
               " table entry teraWLinkIPRangeTableEntry "
          INDEX {                   ifIndex }
     ::= { teraWLinkIPRangeTable 1 }

TeraWLinkIPRangeTableEntryType ::= SEQUENCE {
          teraWLinkIPRangeStart   
             IpAddress,
          teraWLinkIPRangeEnd   
             IpAddress,
          teraWLinkIPRangeRowStatus   
             INTEGER
}

teraWLinkIPRangeStart OBJECT-TYPE
          SYNTAX IpAddress
          ACCESS read-write
          STATUS mandatory
          DESCRIPTION
               ""
          ::= { teraWLinkIPRangeTableEntry 1 }

teraWLinkIPRangeEnd OBJECT-TYPE
          SYNTAX IpAddress
          ACCESS read-write
          STATUS mandatory
          DESCRIPTION
               ""
          ::= { teraWLinkIPRangeTableEntry 2 }

teraWLinkIPRangeRowStatus OBJECT-TYPE
          SYNTAX INTEGER
                  {
                  ok(1),
                  delete(2)
                  }
          ACCESS read-write
          STATUS mandatory
          DESCRIPTION
               ""
          ::= { teraWLinkIPRangeTableEntry 3 }

     -- teraSecondaryMasterSlaveTable (special)

teraSecondaryMasterSlaveTable OBJECT IDENTIFIER ::=  { teraSystem 16 }

teraSecondaryMasterSlotNumber OBJECT-TYPE
          SYNTAX INTEGER (0..7)
          ACCESS read-write
          STATUS mandatory
          DESCRIPTION
               ""
          ::= { teraSecondaryMasterSlaveTable 1 }

teraSecondarySlaveSlotNumber OBJECT-TYPE
          SYNTAX INTEGER (0..7)
          ACCESS read-write
          STATUS mandatory
          DESCRIPTION
               ""
          ::= { teraSecondaryMasterSlaveTable 2 }

     -- teraMasterSlaveStateTable

teraMasterSlaveStateTable OBJECT-TYPE
     SYNTAX SEQUENCE OF TeraMasterSlaveStateTableEntryType
     ACCESS not-accessible
     STATUS mandatory
     DESCRIPTION
          " table teraMasterSlaveStateTable"
     ::= { teraSystem 17 }

teraMasterSlaveStateTableEntry OBJECT-TYPE
          SYNTAX TeraMasterSlaveStateTableEntryType
          ACCESS not-accessible
          STATUS mandatory
          DESCRIPTION
               " table entry teraMasterSlaveStateTableEntry "
          INDEX {                   teraMasterSlaveStateIndex }
     ::= { teraMasterSlaveStateTable 1 }

TeraMasterSlaveStateTableEntryType ::= SEQUENCE {
          teraMasterSlaveStateIndex   
             INTEGER (1..2),
          teraMasterState   
             INTEGER,
          teraSlaveState   
             INTEGER
}

teraMasterSlaveStateIndex OBJECT-TYPE
          SYNTAX INTEGER (1..2)
          ACCESS read-only
          STATUS mandatory
          DESCRIPTION
               ""
          ::= { teraMasterSlaveStateTableEntry 1 }

teraMasterState OBJECT-TYPE
          SYNTAX INTEGER
                  {
                  unknown(0),
                  nobody(1),
                  master(2)
                  }
          ACCESS read-only
          STATUS mandatory
          DESCRIPTION
               ""
          ::= { teraMasterSlaveStateTableEntry 2 }

teraSlaveState OBJECT-TYPE
          SYNTAX INTEGER
                  {
                  unknown(0),
                  nobody(1),
                  slave(3),
                  slaveActive(4),
                  slaveFail(5)
                  }
          ACCESS read-only
          STATUS mandatory
          DESCRIPTION
               ""
          ::= { teraMasterSlaveStateTableEntry 3 }

teraPPPBaudRateTbl OBJECT IDENTIFIER ::=  { teraSystem 20 }

     -- teraPPPBaudRateTable (special)

teraPPPBaudRateTable OBJECT IDENTIFIER ::=  { teraPPPBaudRateTbl 1 }

teraPPPAdminBaudRate OBJECT-TYPE
          SYNTAX INTEGER
                  {
                  baud2400(0),
                  baud4800(1),
                  baud9600(2),
                  baud19200(3),
                  baud38400(4),
                  baud57600(5),
                  baud115200(6),
                  baud230400(7)
                  }
          ACCESS read-write
          STATUS mandatory
          DESCRIPTION
               ""
          ::= { teraPPPBaudRateTable 1 }

teraPPPOperBaudRate OBJECT-TYPE
          SYNTAX INTEGER
                  {
                  baud2400(0),
                  baud4800(1),
                  baud9600(2),
                  baud19200(3),
                  baud38400(4),
                  baud57600(5),
                  baud115200(6),
                  baud230400(7)
                  }
          ACCESS read-only
          STATUS mandatory
          DESCRIPTION
               ""
          ::= { teraPPPBaudRateTable 2 }

teraPPPAdminFlowControl OBJECT-TYPE
          SYNTAX INTEGER
                  {
                  none(0),
                  xon-Xoff(1),
                  rTS-CTS(2)
                  }
          ACCESS read-write
          STATUS mandatory
          DESCRIPTION
               ""
          ::= { teraPPPBaudRateTable 3 }

teraPPPOperFlowControl OBJECT-TYPE
          SYNTAX INTEGER
                  {
                  none(0),
                  xon-Xoff(1),
                  rTS-CTS(2)
                  }
          ACCESS read-only
          STATUS mandatory
          DESCRIPTION
               ""
          ::= { teraPPPBaudRateTable 4 }

     -- teraSystemNATGroupTable (special)

teraSystemNATGroupTable OBJECT IDENTIFIER ::=  { teraSystem 24 }

teraSystemNATSubnetAddress OBJECT-TYPE
          SYNTAX IpAddress
          ACCESS read-write
          STATUS mandatory
          DESCRIPTION
               ""
          ::= { teraSystemNATGroupTable 1 }

teraSystemNATSubnetMask OBJECT-TYPE
          SYNTAX IpAddress
          ACCESS read-write
          STATUS mandatory
          DESCRIPTION
               ""
          ::= { teraSystemNATGroupTable 2 }

     -- teraSystemPCUNumTable (special)

teraSystemPCUNumTable OBJECT IDENTIFIER ::=  { teraSystem 25 }

teraSystemNumOfPCU OBJECT-TYPE
          SYNTAX INTEGER
                  {
                  pCU4(0),
                  pCU5(1)
                  }
          ACCESS read-write
          STATUS mandatory
          DESCRIPTION
               ""
          ::= { teraSystemPCUNumTable 1 }

     -- teraInstalledSystemInfoTable

teraInstalledSystemInfoTable OBJECT-TYPE
     SYNTAX SEQUENCE OF TeraInstalledSystemInfoTableEntryType
     ACCESS not-accessible
     STATUS mandatory
     DESCRIPTION
          " table teraInstalledSystemInfoTable"
     ::= { teraSystem 26 }

teraInstalledSystemInfoTableEntry OBJECT-TYPE
          SYNTAX TeraInstalledSystemInfoTableEntryType
          ACCESS not-accessible
          STATUS mandatory
          DESCRIPTION
               " table entry teraInstalledSystemInfoTableEntry "
          INDEX {                   teraInstallSlotNumber,                  teraPonIndex }
     ::= { teraInstalledSystemInfoTable 1 }

TeraInstalledSystemInfoTableEntryType ::= SEQUENCE {
          teraInstalledSystemName   
             OCTET STRING,
          teraInstalledSystemLocation   
             OCTET STRING,
          teraInstalledNEType   
             INTEGER
}

teraInstalledSystemName OBJECT-TYPE
          SYNTAX OCTET STRING
          ACCESS read-write
          STATUS mandatory
          DESCRIPTION
               ""
          ::= { teraInstalledSystemInfoTableEntry 1 }

teraInstalledSystemLocation OBJECT-TYPE
          SYNTAX OCTET STRING
          ACCESS read-write
          STATUS mandatory
          DESCRIPTION
               ""
          ::= { teraInstalledSystemInfoTableEntry 2 }

teraInstalledNEType OBJECT-TYPE
          SYNTAX INTEGER
                  {
                  unknown(0),
                  tw300(1),
                  tw600(2),
                  tw1600(3),
                  tw100(4),
                  tw150RT(5),
                  oat(7)
                  }
          ACCESS read-write
          STATUS mandatory
          DESCRIPTION
               ""
          ::= { teraInstalledSystemInfoTableEntry 3 }

teraCraftInterfaceGroup OBJECT IDENTIFIER ::=  { teraSystem 28 }

     -- teraCraftInterfaceTable (special)

teraCraftInterfaceTable OBJECT IDENTIFIER ::=  { teraCraftInterfaceGroup 1 }

teraCraftPortStat OBJECT-TYPE
          SYNTAX INTEGER
                  {
                  enable(1),
                  disable(2)
                  }
          ACCESS read-write
          STATUS mandatory
          DESCRIPTION
               ""
          ::= { teraCraftInterfaceTable 1 }

teraCraftDefaultAddrStat OBJECT-TYPE
          SYNTAX INTEGER
                  {
                  enable(1),
                  disable(2)
                  }
          ACCESS read-write
          STATUS mandatory
          DESCRIPTION
               ""
          ::= { teraCraftInterfaceTable 2 }

teraSNMPState OBJECT-TYPE
          SYNTAX INTEGER
                  {
                  ready(1),
                  notReady(2)
                  }
          ACCESS read-only
          STATUS mandatory
          DESCRIPTION
               ""
          ::= { teraCraftInterfaceTable 3 }

END
