MTSALLSTREAM-MIB DEFINITIONS ::= BEGIN

IMPORTS
      enterprises, Unsigned32, MODULE-IDENTITY,
      OBJECT-TYPE, NOTIFICATION-TYPE    FROM SNMPv2-SMI
	DisplayString 			    FROM SNMPv2-TC
      NOTIFICATION-GROUP, OBJECT-GROUP,
	MODULE-COMPLIANCE  		    FROM SNMPv2-CONF;
mtsallstream MODULE-IDENTITY
        LAST-UPDATED    "200505240000Z"
        ORGANIZATION    "MTS Allstream"
        CONTACT-INFO
                "       Bogdan Moldoveanu
                Postal: Allstream
                        5160 Orbitor Drive
                        Mississauga, ON L4W 5H2
                Phone:  +1-905-361-2189
                Email:  bogdan.moldoveanu@allstream.com"
        DESCRIPTION
                "The MIB Module for Allstream service notifications."
        ::= { enterprises 23398 }

allstreamObjects OBJECT IDENTIFIER ::= { mtsallstream 1 }

allstreamMIBConformance OBJECT IDENTIFIER ::= { mtsallstream 2 }

allstreamCICEventEntities  OBJECT IDENTIFIER ::= { allstreamObjects 1 }

cicEventID OBJECT-TYPE
        SYNTAX      Unsigned32 (0..4294967295)
        MAX-ACCESS  read-only
        STATUS      current
        DESCRIPTION
                "Cisco Info Center Event ID known by database as Server Serial."
        ::= { allstreamCICEventEntities 1 }

cicNode OBJECT-TYPE
        SYNTAX      DisplayString
        MAX-ACCESS  read-only
        STATUS      current
        DESCRIPTION
                "Cisco Info Center Originator Node represents the real source of the event."
        ::= { allstreamCICEventEntities 2 }

cicEventMessage OBJECT-TYPE
        SYNTAX      DisplayString
        MAX-ACCESS  read-only
        STATUS      current
        DESCRIPTION
                "Cisco Info Center event's message."
        ::= { allstreamCICEventEntities 3 }

cicEventSeverity OBJECT-TYPE
        SYNTAX      Unsigned32
        MAX-ACCESS  read-only
        STATUS      current
        DESCRIPTION
                "Cisco Info Center assigns this event severity."
        ::= { allstreamCICEventEntities 4 }

cicEventTrapReason OBJECT-TYPE
        SYNTAX      DisplayString
        MAX-ACCESS  read-only
        STATUS      current
        DESCRIPTION
                "Another extra information about the forwarded event."
        ::= { allstreamCICEventEntities 5 }

allstreamNotifications  OBJECT IDENTIFIER ::= { allstreamObjects 20 }

allstreamForwardCICEventTrap NOTIFICATION-TYPE
        OBJECTS   {    cicEventID, cicNode, cicEventMessage, cicEventSeverity, cicEventTrapReason }
        STATUS       current
        DESCRIPTION  "This notification is used to forward Cisco Info Center events southbound to another Network Management System / Event Manager."
        ::= { allstreamNotifications 1 }

allstreamCompliances    OBJECT IDENTIFIER ::= { allstreamMIBConformance 1 }
allstreamGroups     	OBJECT IDENTIFIER ::= { allstreamMIBConformance 2 }

allstreamBasicCompliance MODULE-COMPLIANCE 
	STATUS 	current 
	DESCRIPTION "The compliance statement for mtsallstream entities which implement this MIB." 
	MODULE 	 
		MANDATORY-GROUPS { allstreamNotificationsGroup, allstreamObjectGroup}
	  ::= { allstreamCompliances 1 } 

allstreamNotificationsGroup NOTIFICATION-GROUP
        NOTIFICATIONS { allstreamForwardCICEventTrap }

        STATUS       current
        DESCRIPTION  "Allstream notifications group."
        ::= { allstreamGroups 1 }

allstreamObjectGroup OBJECT-GROUP
        OBJECTS { cicEventID, cicNode, cicEventMessage, cicEventSeverity, cicEventTrapReason }

        STATUS      current
        DESCRIPTION "A collection of objects providing basic instrumentation and control of mtsallstream entities."
        ::= { allstreamGroups 2 }


END
