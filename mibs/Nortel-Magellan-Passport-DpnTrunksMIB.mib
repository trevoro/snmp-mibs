Nortel-Magellan-Passport-DpnTrunksMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      PassportCounter64,
      InterfaceIndex,
      Gauge32,
      Integer32,
      Unsigned32
   FROM Nortel-Magellan-Passport-StandardTextualConventionsMIB

      AsciiString,
      NonReplicated,
      FixedPoint1
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     DpnTrunks Enterprise MIB."

dpnTrunksMIB OBJECT IDENTIFIER ::= { passportMIBs 40 }










-- DpnGateway/n
-- The DpnGateway component provides a Passport to DPN-100 
-- connection. It controls a protocol stack associated with a logical 
-- port on a Functional Processor providing a connection to a DPN-
-- 100 Utp Trunk or NetworkLink. The underlying link protocol may 
-- be provided by either Utp or FrAccess. A maximum of 256 
-- instances of DpnGateway may be provisioned on a module.

dpnGate OBJECT IDENTIFIER ::= { components 61 }



dpnGateRowStatusTable OBJECT-TYPE
   SYNTAX     SEQUENCE OF DpnGateRowStatusEntry
   ACCESS     not-accessible
   STATUS     mandatory
   DESCRIPTION
     "This entry controls the addition and deletion of 
      dpnGate components."
::= { dpnGate 1 }

dpnGateRowStatusEntry OBJECT-TYPE
   SYNTAX     DpnGateRowStatusEntry
   ACCESS     not-accessible
   STATUS     mandatory
   DESCRIPTION
     "A single entry in the table represents a single 
      dpnGate component."
   INDEX {
      dpnGateIndex }
::= { dpnGateRowStatusTable 1 }

DpnGateRowStatusEntry ::= SEQUENCE {
   dpnGateRowStatus
      RowStatus,
   dpnGateComponentName
      DisplayString,
   dpnGateStorageType
      StorageType,
   dpnGateIndex
      Integer32 }

dpnGateRowStatus OBJECT-TYPE
   SYNTAX     RowStatus 
   ACCESS     read-write
   STATUS     mandatory
   DESCRIPTION
     "This variable is used as the basis for SNMP naming of
      dpnGate components.
      These components can be added and deleted."
::= { dpnGateRowStatusEntry 1 }

dpnGateComponentName OBJECT-TYPE
   SYNTAX     DisplayString 
   ACCESS     read-only
   STATUS     mandatory
   DESCRIPTION
     "This variable provides the component's string name for
      use with the ASCII Console Interface"
::= { dpnGateRowStatusEntry 2 }

dpnGateStorageType OBJECT-TYPE
   SYNTAX     StorageType 
   ACCESS     read-only
   STATUS     mandatory
   DESCRIPTION
     "This variable represents the storage type value for the
      dpnGate tables."
::= { dpnGateRowStatusEntry 4 }

dpnGateIndex OBJECT-TYPE
   SYNTAX     Integer32 (0..65535)
   ACCESS     not-accessible
   STATUS     mandatory
   DESCRIPTION
     "This variable represents the index for the dpnGate tables."
::= { dpnGateRowStatusEntry 10 }

dpnGateIfEntryTable OBJECT-TYPE
   SYNTAX     SEQUENCE OF DpnGateIfEntryEntry
   ACCESS     not-accessible
   STATUS     mandatory
   DESCRIPTION
     "This group contains the provisionable attributes for the ifEntry."
::= { dpnGate 100 }

dpnGateIfEntryEntry OBJECT-TYPE
   SYNTAX     DpnGateIfEntryEntry
   ACCESS     not-accessible
   STATUS     mandatory
   DESCRIPTION
     "An entry in the dpnGateIfEntryTable."
   INDEX {
      dpnGateIndex }
::= { dpnGateIfEntryTable 1 }

DpnGateIfEntryEntry ::= SEQUENCE {
   dpnGateIfAdminStatus
      INTEGER,
   dpnGateIfIndex
      InterfaceIndex }

dpnGateIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { dpnGateIfEntryEntry 1 }

dpnGateIfIndex OBJECT-TYPE
   SYNTAX     InterfaceIndex (1..65535)
   ACCESS     read-only
   STATUS     mandatory
   DESCRIPTION
     "This is the index for the IfEntry. Its value is automatically initialized 
      during the provisioning process."
::= { dpnGateIfEntryEntry 2 }

dpnGateProvTable OBJECT-TYPE
   SYNTAX     SEQUENCE OF DpnGateProvEntry
   ACCESS     not-accessible
   STATUS     mandatory
   DESCRIPTION
     "This group of provisionable attributes provide parameters used by 
      DpnGateway for staging."
::= { dpnGate 101 }

dpnGateProvEntry OBJECT-TYPE
   SYNTAX     DpnGateProvEntry
   ACCESS     not-accessible
   STATUS     mandatory
   DESCRIPTION
     "An entry in the dpnGateProvTable."
   INDEX {
      dpnGateIndex }
::= { dpnGateProvTable 1 }

DpnGateProvEntry ::= SEQUENCE {
   dpnGateExpectedRemoteNamsId
      Unsigned32,
   dpnGateRemoteValidationAction
      INTEGER,
   dpnGateLinkType
      INTEGER }

dpnGateExpectedRemoteNamsId OBJECT-TYPE
   SYNTAX     Unsigned32 (0..65535)
   ACCESS     read-write
   STATUS     mandatory
   DESCRIPTION
     "This attribute specifies the expected Nams Identifier of the module 
      to which this DpnGateway is connected. The DpnGateway end 
      points exchange their Nams Identifiers through the DpnGateway's 
      staging protocol. The staged value is validated and the 
      remoteValidationAction will be executed for those values not 
      matching the value supplied for this attribute.
      If this value is zero, then the comparison is always successful."
   DEFVAL     { 0 }
::= { dpnGateProvEntry 1 }

dpnGateRemoteValidationAction OBJECT-TYPE
   SYNTAX     INTEGER  {
                 continue(0),
                 disable(1) }
   ACCESS     read-write
   STATUS     mandatory
   DESCRIPTION
     "This attribute specifies the action to be taken if there is a mismatch 
      between the provisioned value and the value received from the 
      remote end, in cases where the expectedRemoteNamsId is non-zero. 
      If this attribute is provisioned to continue then upon an unsucessful 
      validation staging continues, otherwise, if disable is set then the 
      DpnGateway does not continue to stage but, attempts to stage again 
      after a one minute time out.
      All unsuccessful validation when expectedRemoteNamsId has been 
      set result in the generation of an alarm."
   DEFVAL     { continue }
::= { dpnGateProvEntry 2 }

dpnGateLinkType OBJECT-TYPE
   SYNTAX     INTEGER  {
                 dedicated(0),
                 dialIn(3) }
   ACCESS     read-write
   STATUS     mandatory
   DESCRIPTION
     "This attribute specifies the type of network link. If this attribute is 
      provisioned to dedicated then the link is a dedicated network link to 
      a DPN module. If this attribute is provisioned to dialIn then the link 
      is connected to the DPN module through a public telephone 
      network, on a dial line."
   DEFVAL     { dedicated }
::= { dpnGateProvEntry 3 }

dpnGateOverridesTable OBJECT-TYPE
   SYNTAX     SEQUENCE OF DpnGateOverridesEntry
   ACCESS     not-accessible
   STATUS     mandatory
   DESCRIPTION
     "Theses attribute comprise the set of provisionable override 
      parameters supported by both the Trunk and DpnGateway 
      components. The attributes are used when reporting operational 
      attributes (used for metric calculations) to the routing system."
::= { dpnGate 102 }

dpnGateOverridesEntry OBJECT-TYPE
   SYNTAX     DpnGateOverridesEntry
   ACCESS     not-accessible
   STATUS     mandatory
   DESCRIPTION
     "An entry in the dpnGateOverridesTable."
   INDEX {
      dpnGateIndex }
::= { dpnGateOverridesTable 1 }

DpnGateOverridesEntry ::= SEQUENCE {
   dpnGateOverrideTransmitSpeed
      Gauge32,
   dpnGateOldOverrideRoundTripDelay
      Gauge32,
   dpnGateOverrideRoundTripUsec
      FixedPoint1 }

dpnGateOverrideTransmitSpeed OBJECT-TYPE
   SYNTAX     Gauge32 (0 | 1000..4294967295)
   ACCESS     read-write
   STATUS     mandatory
   DESCRIPTION
     "This is the overridden value of link speed (bit/s) that, if staged 
      successfully with the remote, is reported to the routing system for 
      metric calculations. A zero indicates that an override value has not 
      been provided and that only the measured value will be reported to 
      the routing system.
      If this value is changed on a Trunk or DpnGateway that is enabled, 
      the LOCK and UNLOCK commands must be issued to the 
      component to restage the override with the remote."
   DEFVAL     { 0 }
::= { dpnGateOverridesEntry 1 }

dpnGateOldOverrideRoundTripDelay OBJECT-TYPE
   SYNTAX     Gauge32 (0..1500)
   ACCESS     read-write
   STATUS     obsolete
   DESCRIPTION
     "This is the overridden value of link delay (ms) that, if staged 
      successfully with the remote, is reported to the routing system for 
      metric calculations. A zero indicates that an override value has not 
      been provided and that only the measured value will be reported to 
      the routing system. 
      If this value is changed on a Trunk or DpnGateway that is enabled, 
      the LOCK and UNLOCK commands must be issued to the 
      component to restage the override with the remote."
   DEFVAL     { 0 }
::= { dpnGateOverridesEntry 2 }

dpnGateOverrideRoundTripUsec OBJECT-TYPE
   SYNTAX     FixedPoint1 (0..15000)
   ACCESS     read-write
   STATUS     mandatory
   DESCRIPTION
     "This is the overridden value of link delay (ms) that, if staged 
      successfully with the remote, is reported to the routing system for 
      metric calculations. A zero indicates that an override value has not 
      been provided and that only the measured value will be reported to 
      the routing system. 
      If this value is changed on a Trunk or DpnGateway that is enabled, 
      the LOCK and UNLOCK commands must be issued to the 
      component to restage the override with the remote."
   DEFVAL     { 0 }
::= { dpnGateOverridesEntry 3 }

dpnGateStateTable OBJECT-TYPE
   SYNTAX     SEQUENCE OF DpnGateStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { dpnGate 103 }

dpnGateStateEntry OBJECT-TYPE
   SYNTAX     DpnGateStateEntry
   ACCESS     not-accessible
   STATUS     mandatory
   DESCRIPTION
     "An entry in the dpnGateStateTable."
   INDEX {
      dpnGateIndex }
::= { dpnGateStateTable 1 }

DpnGateStateEntry ::= SEQUENCE {
   dpnGateAdminState
      INTEGER,
   dpnGateOperationalState
      INTEGER,
   dpnGateUsageState
      INTEGER,
   dpnGateAvailabilityStatus
      OCTET STRING,
   dpnGateProceduralStatus
      OCTET STRING,
   dpnGateControlStatus
      OCTET STRING,
   dpnGateAlarmStatus
      OCTET STRING,
   dpnGateStandbyStatus
      INTEGER,
   dpnGateUnknownStatus
      INTEGER }

dpnGateAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { dpnGateStateEntry 1 }

dpnGateOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { dpnGateStateEntry 2 }

dpnGateUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { dpnGateStateEntry 3 }

dpnGateAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { dpnGateStateEntry 4 }

dpnGateProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { dpnGateStateEntry 5 }

dpnGateControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { dpnGateStateEntry 6 }

dpnGateAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { dpnGateStateEntry 7 }

dpnGateStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { dpnGateStateEntry 8 }

dpnGateUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { dpnGateStateEntry 9 }

dpnGateOperStatusTable OBJECT-TYPE
   SYNTAX     SEQUENCE OF DpnGateOperStatusEntry
   ACCESS     not-accessible
   STATUS     mandatory
   DESCRIPTION
     "This group includes the Operational Status attribute. This attribute 
      defines the current operational state of this component."
::= { dpnGate 104 }

dpnGateOperStatusEntry OBJECT-TYPE
   SYNTAX     DpnGateOperStatusEntry
   ACCESS     not-accessible
   STATUS     mandatory
   DESCRIPTION
     "An entry in the dpnGateOperStatusTable."
   INDEX {
      dpnGateIndex }
::= { dpnGateOperStatusTable 1 }

DpnGateOperStatusEntry ::= SEQUENCE {
   dpnGateSnmpOperStatus
      INTEGER }

dpnGateSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { dpnGateOperStatusEntry 1 }

dpnGateOperTable OBJECT-TYPE
   SYNTAX     SEQUENCE OF DpnGateOperEntry
   ACCESS     not-accessible
   STATUS     mandatory
   DESCRIPTION
     "This group of attributes contain the operational information 
      associated with this DpnGateway and the remote to which it has it 
      staged."
::= { dpnGate 105 }

dpnGateOperEntry OBJECT-TYPE
   SYNTAX     DpnGateOperEntry
   ACCESS     not-accessible
   STATUS     mandatory
   DESCRIPTION
     "An entry in the dpnGateOperTable."
   INDEX {
      dpnGateIndex }
::= { dpnGateOperTable 1 }

DpnGateOperEntry ::= SEQUENCE {
   dpnGateRemoteComponentName
      AsciiString,
   dpnGateRemoteNamsMnemonic
      AsciiString,
   dpnGateLinkMode
      INTEGER,
   dpnGateActivateReason
      INTEGER }

dpnGateRemoteComponentName OBJECT-TYPE
   SYNTAX     AsciiString (SIZE (1..26))
   ACCESS     read-only
   STATUS     mandatory
   DESCRIPTION
     "This attribute indicates the Component Name of the remote DPN-
      100 Utp Trunk or NetworkLink supplied by the staging protocol. It 
      is in the format PM/n PE/n PI/n PO/n where PM is the remote 
      module Nams Identifier, PE is the remote module Processor 
      Element that is staged with, PI is the remote module Peripheral 
      Interface card associated with the PE, and PO is the remote module 
      Port (physical or virtual) on the PI that the physical line is 
      connected to."
::= { dpnGateOperEntry 1 }

dpnGateRemoteNamsMnemonic OBJECT-TYPE
   SYNTAX     AsciiString (SIZE (1..12))
   ACCESS     read-only
   STATUS     mandatory
   DESCRIPTION
     "This attribute indicates the Nams Mnemonic of the remote DPN-
      100 Module supplied by the staging protocol. It can be used as a 
      parameter to Rtg Dpn for displaying all DpnGateway that are 
      connect to the same module."
::= { dpnGateOperEntry 2 }

dpnGateLinkMode OBJECT-TYPE
   SYNTAX     INTEGER  {
                 trunk(0),
                 networkLink(1),
                 unknown(2) }
   ACCESS     read-only
   STATUS     mandatory
   DESCRIPTION
     "This attribute indicates whether the DpnGateway is a Trunk 
      connected to a DPN-100 RM or a NetworkLink connected to a 
      DPN-100 AM."
::= { dpnGateOperEntry 3 }

dpnGateActivateReason OBJECT-TYPE
   SYNTAX     INTEGER  {
                 dedicated(0),
                 dnl(1),
                 dbnl(2),
                 dialIn(3),
                 bwod(5),
                 unknown(15) }
   ACCESS     read-only
   STATUS     mandatory
   DESCRIPTION
     "This attribute indicates the reason the DpnGateway has been 
      activated by the remote end. The value corresponds to the link type 
      of the DPN end. It is always unknown until the link comes into 
      service. If this attribute is set to dedicated, the DPN is a dedicated 
      network link. If this attribute is set to dnl, the DPN end is a dial 
      network link, meaning a network link which is connected through a 
      dial-up service. If this attribute is set to dbnl, the DPN end is dial 
      backup network link, activated because the main network link is out 
      of service. If this attribute is set to bwod, the DPN end is a 
      bandwidth on demand link, activated because extra bandwidth is 
      required. If the attribute is set to unknown, the link is either not 
      currently in use, or the DPN end has an unrecognized link type."
   DEFVAL     { unknown }
::= { dpnGateOperEntry 4 }

dpnGateTransportTable OBJECT-TYPE
   SYNTAX     SEQUENCE OF DpnGateTransportEntry
   ACCESS     not-accessible
   STATUS     mandatory
   DESCRIPTION
     "This group of attributes contains the set of operational parameters 
      measured and maintained by both the Trunk and DpnGateway 
      components."
::= { dpnGate 106 }

dpnGateTransportEntry OBJECT-TYPE
   SYNTAX     DpnGateTransportEntry
   ACCESS     not-accessible
   STATUS     mandatory
   DESCRIPTION
     "An entry in the dpnGateTransportTable."
   INDEX {
      dpnGateIndex }
::= { dpnGateTransportTable 1 }

DpnGateTransportEntry ::= SEQUENCE {
   dpnGateMeasuredSpeedToIf
      Gauge32,
   dpnGateMeasuredRoundTripDelay
      Gauge32,
   dpnGateMaxTxUnit
      Gauge32,
   dpnGateMeasuredRoundTripDelayUsec
      FixedPoint1 }

dpnGateMeasuredSpeedToIf OBJECT-TYPE
   SYNTAX     Gauge32 (0..4294967295)
   ACCESS     read-only
   STATUS     mandatory
   DESCRIPTION
     "This attribute indicates the current 'transmittable' bandwidth of the 
      underlying facility.
      For a Trunk with a Unack subcomponent, and a DpnGateway with a 
      Utp subcomponent, if a serial port is used, the value is the measured 
      transmit speed of the port; if a channelized port (E1/DS1) is used, 
      the value is the measured transmit speed of the Channel. 
      For a Trunk with an AtmAccess subcomponent, the value is 
      calculated by converting the VCC transmit cell rate to an equivalent 
      bit rate. The VCC transmit cell rate is determined based on the 
      vccReportingBw attribute of the Trunk AtmAccess component. If 
      vccReportingBw has a value of pcr and attribute bwElastic of 
      AtmAccess has a value of no, the peak cell rate (PCR) of the VCC, 
      defined in txTrafficDescParm of AtmIf Vcc Vcd, is used. If 
      vccReportingBw has a value of pcr and attribute bwElastic of 
      AtmAccess has a value of yes, the minimum of the PCR, defined in 
      txTrafficDescParm of AtmIf Vcc Vcd, and the current cell rate 
      (CCR) of the VCC is used. If vccReportingBw has a value of acr, 
      the best measurement of the actual cell rate (ACR) of the VCC is 
      used, which is the minimum of the PCR, the CCR and the actual 
      shaping rate (ASR).
      For a DpnGateway with a FrAccess subcomponent, the value 
      indicates the committedInformationRate of FrAccess FrMuxSetup.
      A value of zero is displayed when the underlying facility is disabled 
      or the current 'transmittable' bandwidth is unknown."
   DEFVAL     { 0 }
::= { dpnGateTransportEntry 1 }

dpnGateMeasuredRoundTripDelay OBJECT-TYPE
   SYNTAX     Gauge32 (0..1500)
   ACCESS     read-only
   STATUS     obsolete
   DESCRIPTION
     "This attribute indicates the measured Round Trip Delay (msec) 
      discovered with the remote through the Trunk and DpnGateway 
      staging protocols. The value includes emission, propagation, and 
      queuing delays. A 512 byte data packet is used to perform the 
      measurement. A value of zero is displayed when the link is disabled 
      or the measured Round Trip Delay is unknown."
   DEFVAL     { 0 }
::= { dpnGateTransportEntry 2 }

dpnGateMaxTxUnit OBJECT-TYPE
   SYNTAX     Gauge32 (0..65535)
   ACCESS     read-only
   STATUS     mandatory
   DESCRIPTION
     "This is the maximum transmission unit (byte size) that is supported 
      by the Trunk or DpnGateway component. This size includes the 
      data and routing headers. A value of zero indicates the MTU has not 
      yet been determined."
   DEFVAL     { 0 }
::= { dpnGateTransportEntry 3 }

dpnGateMeasuredRoundTripDelayUsec OBJECT-TYPE
   SYNTAX     FixedPoint1 (0..15000)
   ACCESS     read-only
   STATUS     mandatory
   DESCRIPTION
     "This attribute indicates the measured Round Trip Delay (msec) 
      discovered with the remote through the Trunk and DpnGateway 
      staging protocols. The value includes emission, propagation, and 
      queuing delays. A 512 byte data packet is used to perform the 
      measurement. A value of zero is displayed when the link is disabled 
      or the measured Round Trip Delay is unknown."
   DEFVAL     { 0 }
::= { dpnGateTransportEntry 4 }

dpnGateStatsTable OBJECT-TYPE
   SYNTAX     SEQUENCE OF DpnGateStatsEntry
   ACCESS     not-accessible
   STATUS     mandatory
   DESCRIPTION
     "This group of attributes contains statistics collected by the 
      DpnGateway component."
::= { dpnGate 107 }

dpnGateStatsEntry OBJECT-TYPE
   SYNTAX     DpnGateStatsEntry
   ACCESS     not-accessible
   STATUS     mandatory
   DESCRIPTION
     "An entry in the dpnGateStatsTable."
   INDEX {
      dpnGateIndex }
::= { dpnGateStatsTable 1 }

DpnGateStatsEntry ::= SEQUENCE {
   dpnGatePktFromIf
      PassportCounter64,
   dpnGateTrunkPktFromIf
      Counter32,
   dpnGateTrunkPktToIf
      Counter32,
   dpnGateDiscardUnforward
      PassportCounter64,
   dpnGateDiscardTrunkPktFromIf
      Counter32,
   dpnGateStagingAttempts
      Counter32,
   dpnGateDiscardTrunkPktToIf
      Counter32 }

dpnGatePktFromIf OBJECT-TYPE
   SYNTAX     PassportCounter64 
   ACCESS     read-only
   STATUS     mandatory
   DESCRIPTION
     "This attribute counts the number of packets received from the 
      remote module. This counter wraps around to zero when the 
      maximum value is reached."
::= { dpnGateStatsEntry 1 }

dpnGateTrunkPktFromIf OBJECT-TYPE
   SYNTAX     Counter32 
   ACCESS     read-only
   STATUS     mandatory
   DESCRIPTION
     "This attribute counts the number of internal trunk protocol packets 
      received from the remote module. These packets are forwarded to 
      the DpnGateway component. This counter wraps around to zero 
      when the maximum value is reached."
::= { dpnGateStatsEntry 2 }

dpnGateTrunkPktToIf OBJECT-TYPE
   SYNTAX     Counter32 
   ACCESS     read-only
   STATUS     mandatory
   DESCRIPTION
     "This attribute counts the number of internal trunk protocol packets 
      transmitted to the remote module. This counter wraps around to 
      zero when the maximum value is reached."
::= { dpnGateStatsEntry 3 }

dpnGateDiscardUnforward OBJECT-TYPE
   SYNTAX     PassportCounter64 
   ACCESS     read-only
   STATUS     mandatory
   DESCRIPTION
     "This attribute counts the number of packets received from the 
      remote module that have been discarded. This counter wraps around 
      to zero when the maximum value is reached. Two main reasons that 
      cause this counter to increment are: the remote protocol is not 
      compatible to the local protocol stack or, the packet cannot be 
      forwarded due to either a recent loss of connectivity or due to 
      congestion."
::= { dpnGateStatsEntry 4 }

dpnGateDiscardTrunkPktFromIf OBJECT-TYPE
   SYNTAX     Counter32 
   ACCESS     read-only
   STATUS     mandatory
   DESCRIPTION
     "This attribute counts the number of internal trunk protocol packets 
      received from the remote module that have been discarded. This 
      counter wraps around to zero when the maximum value is reached. 
      The two main reasons that cause this counter to increment is if the 
      DpnGateway is unsynchronized with DPN-100 and if the remote 
      protocol is not the same version as the local protocol."
::= { dpnGateStatsEntry 5 }

dpnGateStagingAttempts OBJECT-TYPE
   SYNTAX     Counter32 
   ACCESS     read-only
   STATUS     mandatory
   DESCRIPTION
     "This attribute counts the number of times that the staging protocol 
      has attempted to stage with the remote module. This counter wraps 
      around to zero when the maximum value is reached. The main 
      reason for this counter to increment is that the local hardware is up 
      but the local protocol cannot stage with the remote protocol due to a 
      faulty connection. If the value is zero, then the local hardware has 
      never enabled successfully."
::= { dpnGateStatsEntry 6 }

dpnGateDiscardTrunkPktToIf OBJECT-TYPE
   SYNTAX     Counter32 
   ACCESS     read-only
   STATUS     mandatory
   DESCRIPTION
     "This attribute counts the number of internal trunk protocol packets 
      that have been discarded before being transmitted to the remote 
      module. This counter wraps around to zero when the maximum 
      value is reached. The main reason that causes this counter to 
      increment is that the DpnGateway can not get sufficient resources to 
      create an internal trunk protocol packet."
::= { dpnGateStatsEntry 7 }


-- Trunk/n ForwardingStatistics
-- This is a dynamic subcomponent of a Trunk or DpnGateway which 
-- appears when packet forwarding traffic is used over the Trunk or 
-- DpnGateway. It contains statistics associated with packet 
-- forwarding traffic for Trunks and DpnGateways.

dpnGateFwdStats OBJECT IDENTIFIER ::= { dpnGate 3 }



dpnGateFwdStatsRowStatusTable OBJECT-TYPE
   SYNTAX     SEQUENCE OF DpnGateFwdStatsRowStatusEntry
   ACCESS     not-accessible
   STATUS     mandatory
   DESCRIPTION
     "This entry controls the addition and deletion of 
      dpnGateFwdStats components."
::= { dpnGateFwdStats 1 }

dpnGateFwdStatsRowStatusEntry OBJECT-TYPE
   SYNTAX     DpnGateFwdStatsRowStatusEntry
   ACCESS     not-accessible
   STATUS     mandatory
   DESCRIPTION
     "A single entry in the table represents a single 
      dpnGateFwdStats component."
   INDEX {
      dpnGateIndex,
      dpnGateFwdStatsIndex }
::= { dpnGateFwdStatsRowStatusTable 1 }

DpnGateFwdStatsRowStatusEntry ::= SEQUENCE {
   dpnGateFwdStatsRowStatus
      RowStatus,
   dpnGateFwdStatsComponentName
      DisplayString,
   dpnGateFwdStatsStorageType
      StorageType,
   dpnGateFwdStatsIndex
      NonReplicated }

dpnGateFwdStatsRowStatus OBJECT-TYPE
   SYNTAX     RowStatus 
   ACCESS     read-only
   STATUS     mandatory
   DESCRIPTION
     "This variable is used as the basis for SNMP naming of
      dpnGateFwdStats components.
      These components cannot be added nor deleted."
::= { dpnGateFwdStatsRowStatusEntry 1 }

dpnGateFwdStatsComponentName OBJECT-TYPE
   SYNTAX     DisplayString 
   ACCESS     read-only
   STATUS     mandatory
   DESCRIPTION
     "This variable provides the component's string name for
      use with the ASCII Console Interface"
::= { dpnGateFwdStatsRowStatusEntry 2 }

dpnGateFwdStatsStorageType OBJECT-TYPE
   SYNTAX     StorageType 
   ACCESS     read-only
   STATUS     mandatory
   DESCRIPTION
     "This variable represents the storage type value for the
      dpnGateFwdStats tables."
::= { dpnGateFwdStatsRowStatusEntry 4 }

dpnGateFwdStatsIndex OBJECT-TYPE
   SYNTAX     NonReplicated 
   ACCESS     not-accessible
   STATUS     mandatory
   DESCRIPTION
     "This variable represents the index for the dpnGateFwdStats tables."
::= { dpnGateFwdStatsRowStatusEntry 10 }

dpnGateFwdStatsOperTable OBJECT-TYPE
   SYNTAX     SEQUENCE OF DpnGateFwdStatsOperEntry
   ACCESS     not-accessible
   STATUS     mandatory
   DESCRIPTION
     "This operational group counts the Trunk or DpnGateway packet 
      forwarding traffic statistics for operator console display."
::= { dpnGateFwdStats 10 }

dpnGateFwdStatsOperEntry OBJECT-TYPE
   SYNTAX     DpnGateFwdStatsOperEntry
   ACCESS     not-accessible
   STATUS     mandatory
   DESCRIPTION
     "An entry in the dpnGateFwdStatsOperTable."
   INDEX {
      dpnGateIndex,
      dpnGateFwdStatsIndex }
::= { dpnGateFwdStatsOperTable 1 }

DpnGateFwdStatsOperEntry ::= SEQUENCE {
   dpnGateFwdStatsFwdPktFromIf
      PassportCounter64,
   dpnGateFwdStatsFwdDiscUnforwardFromIf
      PassportCounter64,
   dpnGateFwdStatsFwdOctetFromIf
      PassportCounter64 }

dpnGateFwdStatsFwdPktFromIf OBJECT-TYPE
   SYNTAX     PassportCounter64 
   ACCESS     read-only
   STATUS     mandatory
   DESCRIPTION
     "This attribute counts the number of forwarding packets received by 
      the Trunk or DpnGateway. This counter wraps around to zero when 
      the maximum value is exceeded."
::= { dpnGateFwdStatsOperEntry 1 }

dpnGateFwdStatsFwdDiscUnforwardFromIf OBJECT-TYPE
   SYNTAX     PassportCounter64 
   ACCESS     read-only
   STATUS     mandatory
   DESCRIPTION
     "This attribute counts the number of forwarding packets discarded by 
      the Trunk or DpnGateway. This counter wraps around to zero when 
      the maximum value is exceeded."
::= { dpnGateFwdStatsOperEntry 2 }

dpnGateFwdStatsFwdOctetFromIf OBJECT-TYPE
   SYNTAX     PassportCounter64 
   ACCESS     read-only
   STATUS     mandatory
   DESCRIPTION
     "This attribute counts the number of forwarding bytes received by 
      the Trunk or DpnGateway. This counter wraps around to zero when 
      the maximum value is exceeded."
::= { dpnGateFwdStatsOperEntry 3 }




-- 
-- Version and Compliance statements
-- 



-- Object-Group Statement:
-- A list of all current accessible leaf objects.

-- OBJECTS { dpnGateStorageType,
--           dpnGateIfIndex,
--           dpnGateAlarmStatus,
--           dpnGateUsageState,
--           dpnGateFwdStatsFwdDiscUnforwardFromIf,
--           dpnGateUnknownStatus,
--           dpnGateDiscardUnforward,
--           dpnGateStagingAttempts,
--           dpnGateDiscardTrunkPktToIf,
--           dpnGateComponentName,
--           dpnGateStandbyStatus,
--           dpnGateOverrideTransmitSpeed,
--           dpnGatePktFromIf,
--           dpnGateOverrideRoundTripUsec,
--           dpnGateMeasuredRoundTripDelayUsec,
--           dpnGateTrunkPktFromIf,
--           dpnGateRemoteValidationAction,
--           dpnGateExpectedRemoteNamsId,
--           dpnGateOperationalState,
--           dpnGateRemoteNamsMnemonic,
--           dpnGateMeasuredSpeedToIf,
--           dpnGateFwdStatsStorageType,
--           dpnGateFwdStatsRowStatus,
--           dpnGateRowStatus,
--           dpnGateRemoteComponentName,
--           dpnGateControlStatus,
--           dpnGateAdminState,
--           dpnGateFwdStatsFwdOctetFromIf,
--           dpnGateActivateReason,
--           dpnGateDiscardTrunkPktFromIf,
--           dpnGateFwdStatsFwdPktFromIf,
--           dpnGateLinkMode,
--           dpnGateMaxTxUnit,
--           dpnGateIfAdminStatus,
--           dpnGateLinkType,
--           dpnGateProceduralStatus,
--           dpnGateAvailabilityStatus,
--           dpnGateFwdStatsComponentName,
--           dpnGateTrunkPktToIf,
--           dpnGateSnmpOperStatus }
-- STATUS  mandatory
-- DESCRIPTION
--   "A list of all current accessible leaf objects."

dpnTrunksGroup OBJECT IDENTIFIER ::= { dpnTrunksMIB 1 }
dpnTrunksGroupBE OBJECT IDENTIFIER ::= { dpnTrunksGroup 5 }
dpnTrunksGroupBE01 OBJECT IDENTIFIER ::= { dpnTrunksGroupBE 2 }
dpnTrunksGroupBE01A OBJECT IDENTIFIER ::= { dpnTrunksGroupBE01 2 }



-- Agent-Capabilities Statement:

-- PRODUCT-RELEASE "Passport Release 7.0 DpnTrunks."
-- STATUS          mandatory
-- DESCRIPTION     "DpnTrunks MIB: MIB Version BE01A,
--                  Software Version BG00S4C."
-- SUPPORTS        Nortel-Magellan-Passport-DpnTrunksMIB
--    INCLUDES     { dpnTrunksGroupBE01A }

dpnTrunksCapabilities OBJECT IDENTIFIER ::= { dpnTrunksMIB 3 }
dpnTrunksCapabilitiesBE OBJECT IDENTIFIER ::= { dpnTrunksCapabilities 5 }
dpnTrunksCapabilitiesBE01 OBJECT IDENTIFIER ::= { dpnTrunksCapabilitiesBE 2 }
dpnTrunksCapabilitiesBE01A OBJECT IDENTIFIER ::= { dpnTrunksCapabilitiesBE01 2 }





END
