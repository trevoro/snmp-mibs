--			ADSL DMT Enterprise Mib
--
--			Ascend Communications, Inc
--			1275 Harbor Bay Pkwy
--			Alameda, CA 94502
--			+1 510 769 6001
--			info@ascend.com
--
--		Copyright (c) 1993-1999 Ascend Communications, Inc.
--		All rights reserved.
--
-- CVS ID:      $Id: adsldmt.mib,v 29.1.32.1 1999/07/28 04:00:20 jjablons Exp $
--
-- 09 Mar 99:	Initial release

	-- Ascend wanTypeAdslDmt group
	--
	-- This group contains MIB variables used to manage the ADSL DMT
	-- interface

	-- ADSL DMT interface status
	--
	-- The below entries contain interface status information. The slot
	-- number and interface are identified via that adslDmtSlotIndex and 
	-- adslDmtLineIndex parameters. 
	--
ASCEND-ADSL-DMT-MIB DEFINITIONS ::= BEGIN

    IMPORTS
	wanTypeAdslDmt
	    FROM ASCEND-WAN-MIB
	OBJECT-TYPE
	    FROM RFC-1212;
	
    adslDmtLineStatusTable	OBJECT-TYPE
	SYNTAX		SEQUENCE OF AdslDmtLineStatusEntry
	ACCESS		not-accessible
	STATUS		mandatory
	DESCRIPTION	"ADSL DMT status parameters."
	::= { wanTypeAdslDmt 1 }

    adslDmtLineStatusEntry	OBJECT-TYPE
	SYNTAX		AdslDmtLineStatusEntry
	ACCESS		not-accessible
	STATUS		mandatory
	DESCRIPTION	"An interface status entry containing objects to describe the
			interface."
	INDEX		{ adslDmtStatusIfEntryIndex }
	::= { adslDmtLineStatusTable 1 }

    AdslDmtLineStatusEntry ::=
	SEQUENCE {
	    adslDmtStatusIfEntryIndex
		INTEGER,
	    adslDmtStatusShelfIndex
	        INTEGER,
	    adslDmtStatusSlotIndex
		INTEGER,
	    adslDmtStatusLineIndex
		INTEGER,
	    adslDmtStatusUnitType
		INTEGER,
	    adslDmtStatusUpRate
		INTEGER,
	    adslDmtStatusDownRate
		INTEGER,
	    adslDmtStatusVendorId
		INTEGER,
	    adslDmtStatusFirmWareVer
		INTEGER,
	    adslDmtStatusHardWareVer
		INTEGER,
	    adslDmtStatusTrellis
	        INTEGER,
	    adslDmtStatusEoc
	        INTEGER
	}

   adslDmtStatusIfEntryIndex    OBJECT-TYPE
	SYNTAX		INTEGER	(1..'7fffffff'h)
	ACCESS		read-only
	STATUS		mandatory
	DESCRIPTION	"Index into the Status Table via the interface group
			 ifIndex value."
	::= { adslDmtLineStatusEntry 1 }
   
    adslDmtStatusShelfIndex OBJECT-TYPE
	SYNTAX		INTEGER
	ACCESS		read-only
	STATUS		mandatory
	DESCRIPTION	"ADSL DMT module Shelf ID."
	::= { adslDmtLineStatusEntry 2 }

    adslDmtStatusSlotIndex	OBJECT-TYPE
	SYNTAX		INTEGER
	ACCESS		read-only
	STATUS		mandatory
	DESCRIPTION	"ADSL DMT module Slot ID."
	::= { adslDmtLineStatusEntry 3 }

    adslDmtStatusLineIndex	OBJECT-TYPE
	SYNTAX		INTEGER
	ACCESS		read-only
	STATUS		mandatory
	DESCRIPTION	"ADSL DMT module line ID." 
	::= { adslDmtLineStatusEntry 4 }

   adslDmtStatusUnitType	OBJECT-TYPE
	SYNTAX		INTEGER {
			    coe( 1 ),		-- Central Office Equipment.
			    cpe( 2 ),		-- Customer Premises
						-- Equipment. 
			    other( 3 )		-- none of the following
			}
	ACCESS		read-only
	STATUS		mandatory
	DESCRIPTION	"Unit type defines if the unit is operating either as a
			Central Office Equipment (COE) or Customer Premiss
			equipment (CPE)."
	::= { adslDmtLineStatusEntry 5 }

   adslDmtStatusUpRate		OBJECT-TYPE
	SYNTAX		INTEGER
	ACCESS		read-only
	STATUS		mandatory
	DESCRIPTION	"Display the current upstream (cpe to coe) rate."
	::= { adslDmtLineStatusEntry 6 }

   adslDmtStatusDownRate		OBJECT-TYPE
	SYNTAX		INTEGER
 	ACCESS		read-only
	STATUS		mandatory
	DESCRIPTION	"Displays the current downstream (coe to cpe) rate."
	::= { adslDmtLineStatusEntry 7 }

   adslDmtStatusVendorId   OBJECT-TYPE
	SYNTAX		INTEGER
	ACCESS		read-only
	STATUS		mandatory
	DESCRIPTION	"Vendor identification."
	::= { adslDmtLineStatusEntry 8 }

   adslDmtStatusFirmWareVer	OBJECT-TYPE
	SYNTAX		INTEGER
	ACCESS		read-only
	STATUS		mandatory
	DESCRIPTION	"Major firmware version."
	::= { adslDmtLineStatusEntry 9 }

   adslDmtStatusHardWareVer	OBJECT-TYPE
	SYNTAX		INTEGER
	ACCESS		read-only
	STATUS		mandatory
	DESCRIPTION	"Hardware version."
	::= { adslDmtLineStatusEntry 10 }

   adslDmtStatusTrellis		OBJECT-TYPE
	SYNTAX		INTEGER{
			    no (1),
			    yes (2),
                            unknown (3)
			}
	ACCESS		read-only
	STATUS		mandatory
	DESCRIPTION	"Report whether trellis coding is used."
	::= { adslDmtLineStatusEntry 11 }

   adslDmtStatusEoc		OBJECT-TYPE
	SYNTAX		INTEGER{
			    unknown(1),
			    transaction(2),
			    streaming(3)
			}
	ACCESS		read-only
	STATUS		mandatory
	DESCRIPTION	"Report whether the eoc can support autonomous
			 data streaming mode or only transaction mode."
	::= { adslDmtLineStatusEntry 12 }

--
--  ADSL-DMT ATU-C PHYSICAL TABLE
--

    adslAtucDMTPhysTable	OBJECT-TYPE
	SYNTAX		SEQUENCE OF  AdslAtucDMTPhysEntry
	ACCESS		not-accessible
	STATUS		mandatory
	DESCRIPTION	"ADSL DMT status parameters."
	::= { wanTypeAdslDmt 2 }

    adslAtucDMTPhysEntry	OBJECT-TYPE
	SYNTAX		AdslAtucDMTPhysEntry
	ACCESS		not-accessible
	STATUS		mandatory
	DESCRIPTION	"An interface status entry containing objects to describe the
			interface."
	INDEX		{ adslAtucDMTIfEntryIndex }
	::= { adslAtucDMTPhysTable 1 }

    AdslAtucDMTPhysEntry ::=
	SEQUENCE {
	    adslAtucDMTIfEntryIndex
		INTEGER,
	    adslAtucDMTShelfIndex
	        INTEGER,
	    adslAtucDMTSlotIndex
		INTEGER,
	    adslAtucDMTLineIndex
		INTEGER,
	    adslAtucDMTIssue
	        INTEGER,
	    adslAtucDMTState
		INTEGER,
	    adslAtucDMTInterleavePath
	        INTEGER,
	    adslAtucDMTFastPath
	        INTEGER
	}

   adslAtucDMTIfEntryIndex    OBJECT-TYPE
	SYNTAX		INTEGER	(1..'7fffffff'h)
	ACCESS		read-only
	STATUS		mandatory
	DESCRIPTION	"Index into the Status Table via the interface group
			 ifIndex value."
	::= { adslAtucDMTPhysEntry 1 }
   
    adslAtucDMTShelfIndex OBJECT-TYPE
	SYNTAX		INTEGER
	ACCESS		read-only
	STATUS		mandatory
	DESCRIPTION	"ADSL DMT module Shelf ID."
	::= { adslAtucDMTPhysEntry 2 }

    adslAtucDMTSlotIndex	OBJECT-TYPE
	SYNTAX		INTEGER
	ACCESS		read-only
	STATUS		mandatory
	DESCRIPTION	"ADSL DMT module Slot ID."
	::= { adslAtucDMTPhysEntry 3 }

    adslAtucDMTLineIndex	OBJECT-TYPE
	SYNTAX		INTEGER
	ACCESS		read-only
	STATUS		mandatory
	DESCRIPTION	"ADSL DMT module line ID." 
	::= { adslAtucDMTPhysEntry 4 }

   adslAtucDMTIssue	OBJECT-TYPE
	SYNTAX		INTEGER{
			    t1-413-iss1 (1),	-- ANSI T1.413 Issue 1
			    t1-413-iss2 (2),	-- ANSI T1.413 Issue 2
			    t1-413-iss3 (3),	-- ANSI T1.413 Issue 3
			    gdmt-iss1 (4),	-- ITU G.dmt Issue 1
			    etsi-iss1 (5),	-- ETSI DMT Issue 1
			    other (6)
			}
	ACCESS		read-only
	STATUS		mandatory
	DESCRIPTION	"Reports the issue number of the relevant standard
			 that the DMT ADSL transceiver at the ATU-C is 
			 currently operating to."
	::= { adslAtucDMTPhysEntry 5 }

   adslAtucDMTState	OBJECT-TYPE
	SYNTAX		INTEGER {
			    other( 1 ),		-- none of the following
			    power-up( 2 ),	-- Not yet configured.
			    configure( 3 ),	-- Configuration state. 
			    idle( 4 ),		-- Initialized but idle. 
			    quiet( 5 ),		-- Awaiting activation request.
			    tone( 6 ),		-- requesting ATU-R to be quiet.
			    activating( 7 ),	-- activation in progress.
			    training( 8 ),	-- transceiver training in progress.
			    analyzing( 9 ),	-- Channel analysis in progress.
			    exchange( 10 ),	-- exchange final operating parameters.
			    steady-state( 11 ),	-- normal operating mode. 
			    not-responding( 12)	-- transceiver not responding.
			}

	ACCESS		read-only
	STATUS		mandatory
	DESCRIPTION	"Report current state of ATU-C DMT transceiver."
	::= { adslAtucDMTPhysEntry 6 }
	
   adslAtucDMTInterleavePath		OBJECT-TYPE
	SYNTAX		INTEGER{
			    none (1),
			    as0 (2),
			    as1 (3)
			}
	ACCESS		read-only
	STATUS		mandatory
	DESCRIPTION	"Report bearer channel of downstream interleaved
			 path."
	::= { adslAtucDMTPhysEntry 7 }

   adslAtucDMTFastPath		OBJECT-TYPE
	SYNTAX		INTEGER{
			    none (1),
			    as0 (2),
			    as1 (3)
			}
	ACCESS		read-only
	STATUS		mandatory
	DESCRIPTION	"Report bearer channel of downstream fast path."
	::= { adslAtucDMTPhysEntry 8 }

--
--  ADSL-DMT ATU-R PHYSICAL TABLE
--

    adslAturDMTPhysTable	OBJECT-TYPE
	SYNTAX		SEQUENCE OF  AdslAturDMTPhysEntry
	ACCESS		not-accessible
	STATUS		mandatory
	DESCRIPTION	"ADSL DMT status parameters."
	::= { wanTypeAdslDmt 3 }

    adslAturDMTPhysEntry	OBJECT-TYPE
	SYNTAX		AdslAturDMTPhysEntry
	ACCESS		not-accessible
	STATUS		mandatory
	DESCRIPTION	"An interface status entry containing objects to describe the
			interface."
	INDEX		{ adslAturDMTIfEntryIndex }
	::= { adslAturDMTPhysTable 1 }

    AdslAturDMTPhysEntry ::=
	SEQUENCE {
	    adslAturDMTIfEntryIndex
		INTEGER,
	    adslAturDMTShelfIndex
	        INTEGER,
	    adslAturDMTSlotIndex
		INTEGER,
	    adslAturDMTLineIndex
		INTEGER,
	    adslAturDMTIssue
	        INTEGER,
	    adslAturDMTState
		INTEGER,
	    adslAturDMTInterleavePath
	        INTEGER,
	    adslAturDMTFastPath
	        INTEGER
	}

   adslAturDMTIfEntryIndex    OBJECT-TYPE
	SYNTAX		INTEGER	(1..'7fffffff'h)
	ACCESS		read-only
	STATUS		mandatory
	DESCRIPTION	"Index into the Status Table via the interface group
			 ifIndex value."
	::= { adslAturDMTPhysEntry 1 }
   
    adslAturDMTShelfIndex OBJECT-TYPE
	SYNTAX		INTEGER
	ACCESS		read-only
	STATUS		mandatory
	DESCRIPTION	"ADSL DMT module Shelf ID."
	::= { adslAturDMTPhysEntry 2 }

    adslAturDMTSlotIndex	OBJECT-TYPE
	SYNTAX		INTEGER
	ACCESS		read-only
	STATUS		mandatory
	DESCRIPTION	"ADSL DMT module Slot ID."
	::= { adslAturDMTPhysEntry 3 }

    adslAturDMTLineIndex	OBJECT-TYPE
	SYNTAX		INTEGER
	ACCESS		read-only
	STATUS		mandatory
	DESCRIPTION	"ADSL DMT module line ID." 
	::= { adslAturDMTPhysEntry 4 }

   adslAturDMTIssue	OBJECT-TYPE
	SYNTAX		INTEGER{
			    t1-413-iss1 (1),	-- ANSI T1.413 Issue 1
			    t1-413-iss2 (2),	-- ANSI T1.413 Issue 2
			    t1-413-iss3 (3),	-- ANSI T1.413 Issue 3
			    gdmt-iss1 (4),	-- ITU G.dmt Issue 1
			    etsi-iss1 (5),	-- ETSI DMT Issue 1
			    other (6)
			}
	ACCESS		read-only
	STATUS		mandatory
	DESCRIPTION	"Reports the issue number of the relevant standard
			 that the DMT ADSL transceiver at the ATU-C is 
			 currently operating to."
	::= { adslAturDMTPhysEntry 5 }

   adslAturDMTState	OBJECT-TYPE
	SYNTAX		INTEGER {
			    other( 1 ),		-- none of the following
			    activating( 2 ),	-- activation in progress.
			    training( 3 ),	-- transceiver training in progress.
			    analyzing( 4 ),	-- Channel analysis in progress.
			    exchange( 5 ),	-- exchange final operating parameters.
			    steady-state( 6 ),	-- normal operating mode. 
			    not-responding( 7 )	-- transceiver not responding.
			}

	ACCESS		read-only
	STATUS		mandatory
	DESCRIPTION	"Report current state of ATU-C DMT transceiver."
	::= { adslAturDMTPhysEntry 6 }
	
   adslAturDMTInterleavePath		OBJECT-TYPE
	SYNTAX		INTEGER{
			    none (1),
			    ls0 (2),
			    ls1 (3)
			}
	ACCESS		read-only
	STATUS		mandatory
	DESCRIPTION	"Report bearer channel of upstream interleaved path."
	::= { adslAturDMTPhysEntry 7 }

   adslAturDMTFastPath		OBJECT-TYPE
	SYNTAX		INTEGER{
			    none (1),
			    ls0 (2),
			    ls1 (3)
			}
	ACCESS		read-only
	STATUS		mandatory
	DESCRIPTION	"Report bearer channel of upstream fast path."
	::= { adslAturDMTPhysEntry 8 }

--
--  ADSL-DMT Statistics.
--
    adslDmtLineStatisticTable OBJECT-TYPE
	SYNTAX		SEQUENCE OF AdslDmtLineStatisticEntry
	ACCESS		not-accessible
	STATUS		mandatory
	DESCRIPTION	"ADSL DMT statistical parameters."
	::= { wanTypeAdslDmt 4 }

   adslDmtLineStatisticEntry OBJECT-TYPE
	SYNTAX		AdslDmtLineStatisticEntry
	ACCESS		not-accessible
	STATUS		mandatory
	DESCRIPTION	"An interface statistical entry containing objects to
			describe the interface."
	INDEX		{ adslDmtStatIfEntryIndex }
	::= { adslDmtLineStatisticTable 1 }

    AdslDmtLineStatisticEntry ::=
	SEQUENCE {
	    adslDmtStatIfEntryIndex
		INTEGER,
	    adslDmtStatShelfIndex
		INTEGER,
	    adslDmtStatSlotIndex
		INTEGER,
	    adslDmtStatLineIndex
		INTEGER,
	    adslDmtStatConnUpDays
		INTEGER,
	    adslDmtStatConnUpHours
	        INTEGER,
	    adslDmtStatConnUpMinutes
		INTEGER,
	    adslDmtStatRxSignalPresent
		INTEGER,
	    adslDmtStatUpDwnCntr
		INTEGER,
	    adslDmtStatLineSelfTest
		INTEGER
	}

   adslDmtStatIfEntryIndex    OBJECT-TYPE
	SYNTAX		INTEGER	(1..'7fffffff'h)
	ACCESS		read-only
	STATUS		mandatory
	DESCRIPTION	"Index into the Status Table via the interface group
			 ifIndex value."
	::= { adslDmtLineStatisticEntry 1 }
   
   adslDmtStatShelfIndex	OBJECT-TYPE
	SYNTAX		INTEGER
	ACCESS		read-only
	STATUS		mandatory
	DESCRIPTION	"ADSL DMT module Shelf ID."
	::= { adslDmtLineStatisticEntry 2 }

   adslDmtStatSlotIndex	OBJECT-TYPE
	SYNTAX		INTEGER
	ACCESS		read-only
	STATUS		mandatory
	DESCRIPTION	"ADSL DMT module Slot ID."
	::= { adslDmtLineStatisticEntry 3 }

   adslDmtStatLineIndex	OBJECT-TYPE
	SYNTAX		INTEGER
	ACCESS		read-only
	STATUS		mandatory
	DESCRIPTION	"ADSL DMT module interface ID." 
	::= { adslDmtLineStatisticEntry 4 }

   adslDmtStatConnUpDays	OBJECT-TYPE
	SYNTAX		INTEGER
	ACCESS		read-only
	STATUS		mandatory
	DESCRIPTION	"Connection up day count."
	::= { adslDmtLineStatisticEntry 5 }

   adslDmtStatConnUpHours	OBJECT-TYPE
	SYNTAX		INTEGER
	ACCESS		read-only
	STATUS		mandatory
	DESCRIPTION	"Connection Up 24 hour count."
	::= { adslDmtLineStatisticEntry 6 }

   adslDmtStatConnUpMinutes	OBJECT-TYPE
	SYNTAX		INTEGER
	ACCESS		read-only
	STATUS		mandatory
	DESCRIPTION	"Connection up minute count."
	::= { adslDmtLineStatisticEntry 7 }

   adslDmtStatRxSignalPresent	OBJECT-TYPE
	SYNTAX		INTEGER {
			    no( 1 ),	-- LOS of signal detected. 
			    yes( 2 )	-- Receive signal present. 
			}
	ACCESS		read-only
	STATUS		mandatory
	DESCRIPTION	"Receive signal present detection."
	::= { adslDmtLineStatisticEntry 8 }

    adslDmtStatUpDwnCntr OBJECT-TYPE
	SYNTAX		INTEGER
	ACCESS		read-only
	STATUS		mandatory
	DESCRIPTION	"Line Up Down counter value displays the number
			of times the interface transitions from a down to up
			state."
	::= { adslDmtLineStatisticEntry 9 }

    adslDmtStatLineSelfTest    OBJECT-TYPE
	SYNTAX		INTEGER {
                            unknown( 1 ),
			    failed( 2 ),
			    passed( 3 )
			}
	ACCESS		read-only
	STATUS		mandatory
	DESCRIPTION	"Line hardware self test results (Passed or 
			 Failed)."
	::= { adslDmtLineStatisticEntry 10 }

END
