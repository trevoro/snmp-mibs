VERILINK-ENTERPRISE-NCMGENERIC-MIB

	-- General mibs to manage Quad T1, ACE E1/T1 and NCM-ISDN products


	-- Created:  Latha Ganapathy on 15 Feb 1996.
	-- set up MIB-wide defaults
	-- all functions can use %n for object name and
	-- %t for object type, %p for parent name,
	-- %d for name of default-bearing node and %% for %

	  DEFINITIONS ::= BEGIN

     IMPORTS
        Gauge
            FROM RFC1155-SMI
        DisplayString
             FROM RFC1213-MIB
        OBJECT-TYPE
             FROM RFC-1212
        ncm-generic
             FROM VERILINK-ENTERPRISE-NCMALARM-MIB;


     --  This MIB module uses the extended OBJECT-TYPE macro as
     --  defined in RFC 1212.
     --  This MIB module uses the TRAP-TYPE macro as
     --  defined in RFC 1215.
     --  enterprises{iso(1).org(3).dod(6).intrnet(1).pvt(4).entrprs(1).
     --                                             		vlnk(321).as2000(1).x }

 	 -- verilink                    OBJECT IDENTIFIER ::= { enterprises 321 }
 	 -- as2000                      OBJECT IDENTIFIER ::= { verilink 1 }
 	 -- ncm-generic                 OBJECT IDENTIFIER ::= { as2000 3012 }                            	
	   
 -- 	MIB Groups


     -- The mibs consists of following groups:
     --    ncmNodeCurrTable
     --    ncmNodeInfoTable
     --    ncmShelfInfo
     --    ncmCardInfo
     --    ncmShelfSyncncmSource
     --    ncmCardSyncncmSource
     --    ncmIDProm
     --    ncmE1PortConfig
     --    ncmE1PortStatus
     --    ncmE1Current
     --    ncmE1Interval
     --    ncmE1Total
     --    ncmE1PrevTotal
     --    ncmE1PerformanceSnapShot
     --    ncmE1PortLatchedStatus
     --    ncmE1ThesholdStatus
     --    ncmT1Config
     --    ncmT1PortStatus
     --    ncmT1Current
     --    ncmT1Interval
     --    ncmT1Total
     --    ncmT1PrevTotal
     --    ncmT1PreformanceSnapShot
     --    ncmAdvancedT1PortConfig
     --    ncmT1PortLatchedStatus
     --    ncmT1ThresholdStatus
     --    ncmDataPortConfig
     --    ncmDataPortStatus
     --    ncmAlarmConfig
     --    ncmAlarmCurrentMsg
     --    ncmAlarmMessage
     --    ncmEnhancedAlarmConfig
     --	   ncmLoopback
     --    ncmTestPattern
     --    ncmCircuitInfo
     --    ncmPortTimeslotAllocGrp
     --    ncmDialBackupGrp
     --    ncmClearCircuitGrp
     --    ncmGetMsgNum
     --	   ncmCircuitListccb
     --    ncmEquipmentID
     --    ncmE1AlarmThresholdConfig
     --    ncmE1AlarmThresholdStatus
     --    ncmAlarmThresholdConfig
     --    ncmAlarmThresholdStatus
     --    ncmShelfSyncSourceSeg

--      ncm Node Current Group
         
        ncmNodeCurrTable OBJECT-TYPE
             SYNTAX   SEQUENCE OF NcmNodeCurrEntry
             ACCESS   not-accessible
             STATUS   mandatory
	     --DEFAULT test-function    node-test
             --DEFAULT next-function    node-next

 
             ::= { ncm-generic  1001 }

                                
        ncmNodeCurrEntry OBJECT-TYPE
             SYNTAX   NcmNodeCurrEntry
             ACCESS   not-accessible
             STATUS   mandatory
             DESCRIPTION
                "An entry in the ncmNode Current table
                  for selecting the active node in operation."
             INDEX   { ncmNodeCurrIndex }
            ::= { ncmNodeCurrTable 1 }
      
      
        NcmNodeCurrEntry ::=
             SEQUENCE {
             ncmNodeCurrIndex
                 INTEGER,
             ncmNodeCurrAddress
                DisplayString,
             ncmActiveNodeStatus
                 INTEGER
                 
             }           

               
        ncmNodeCurrIndex OBJECT-TYPE
             SYNTAX  INTEGER (1..'7fffffff'h)
             ACCESS  read-only
             STATUS  mandatory
             DESCRIPTION
                "This variable indicates the node id
                 value inside the array containing all called nodes."
               ::= { ncmNodeCurrEntry 1 }
                
                                       
        ncmNodeCurrAddress  OBJECT-TYPE
             SYNTAX  DisplayString
             ACCESS  read-only
             STATUS  mandatory
             DESCRIPTION
             "This variable indicates the ncmNode Current Address."
               ::= { ncmNodeCurrEntry 2 }
 
 
        ncmActiveNodeStatus OBJECT-TYPE
             SYNTAX  INTEGER {
 
                     inactive(1),
                     active(2)
             }
             ACCESS  read-write
             STATUS  mandatory
             DESCRIPTION
                "This variable indicates what is the current node of the
                 network that is being managed; when this object is set,
                 another node table will be activated and treat as active."
               ::= { ncmNodeCurrEntry 3 }


--	ncmNode Group
 	 
        ncmNodeInfoTable OBJECT-TYPE
             SYNTAX   SEQUENCE OF NcmNodeInfoEntry
             ACCESS   not-accessible
             STATUS   mandatory
	     --DEFAULT test-function    node-test
             --DEFAULT next-function    node-next


             ::= { ncm-generic  1002 }
 
 
 
        ncmNodeInfoEntry OBJECT-TYPE
             SYNTAX   NcmNodeInfoEntry
             ACCESS   not-accessible
             STATUS   mandatory
             DESCRIPTION
                "An entry in the ncmNode Info table."
             INDEX   { ncmNodeIndex }
            ::= { ncmNodeInfoTable 1 }
 
 
        NcmNodeInfoEntry ::=
             SEQUENCE {
             ncmNodeIndex
                 INTEGER,
	     ncmNodeAddress  
	        DisplayString, 
	     ncmTime       
	        DisplayString,
	     ncmDate       
	        DisplayString,
             ncmNodeShelf
                 INTEGER,
             ncmNodeID
                 INTEGER,
	     ncmControllerEqID    
                 INTEGER
                }

 
             ncmNodeIndex OBJECT-TYPE
             SYNTAX  INTEGER (1..'7fffffff'h)
             ACCESS  read-only
             STATUS  mandatory
             DESCRIPTION
                "This variable indicates the node id
	         value of the node."  
               ::= { ncmNodeInfoEntry 1 }


	     ncmNodeAddress  OBJECT-TYPE
	     SYNTAX  DisplayString 
	    -- ACCESS  read-write
	     ACCESS  read-only
	     STATUS  mandatory
	     DESCRIPTION
	     "This variable indicates the ncmNode Address."
               ::= { ncmNodeInfoEntry 2 }


	     ncmTime       OBJECT-TYPE
	      SYNTAX  DisplayString
	      ACCESS  read-write
	      STATUS  mandatory
	      DESCRIPTION
	      "The time (in the hh:mm:sec) format for the card."
               ::= { ncmNodeInfoEntry 3 }


	     ncmDate           OBJECT-TYPE
	     SYNTAX  DisplayString (SIZE (0..255))
	     ACCESS  read-write
	     STATUS  mandatory
	     DESCRIPTION
	     "The date (in mm:dd:yy) format for the card."
               ::= { ncmNodeInfoEntry 4 }

		
	     ncmNodeShelf    OBJECT-TYPE
	     	SYNTAX  INTEGER
	     ACCESS  read-only
	     STATUS  mandatory
	     DESCRIPTION
	     "The variable indicates the bit mapping of shelf number
 	     associated with the node the bit 1 if equipped and 0 if not
                 equipped. i.e. ncmShelf 0 = bit 0"
               ::= { ncmNodeInfoEntry 5 }


	   ncmNodeID    OBJECT-TYPE
	     SYNTAX  INTEGER
	     ACCESS  read-only
	     STATUS  mandatory
	     DESCRIPTION
	     "The variable indicates the node id that uniquely identifies
              a node."
               ::= { ncmNodeInfoEntry 6 }


	   ncmControllerEqID    OBJECT-TYPE
             SYNTAX  INTEGER
             ACCESS  read-only
             STATUS  mandatory
             DESCRIPTION
             "The variable indicates the Equipment Id of the Controller."
               ::= { ncmNodeInfoEntry 7 }




	--      ncm Shelf Info group
 
 
        ncmShelfInfoTable OBJECT-TYPE
             SYNTAX   SEQUENCE OF NcmShelfInfoEntry
             ACCESS  	not-accessible
             STATUS   	mandatory
	     --DEFAULT 	test-function    	shelf-test
             --DEFAULT 	next-function    	shelf-next

             ::= { ncm-generic  1003 }
 
 
 
        ncmShelfInfoEntry OBJECT-TYPE
             SYNTAX   NcmShelfInfoEntry
             ACCESS   not-accessible
             STATUS   mandatory
             DESCRIPTION
                "An entry in the ncmShelf Info table."
            -- INDEX   { ncmShelfIndex }
             INDEX   { ncmShelfNIDIndex, ncmShelfIndex }
            ::= { ncmShelfInfoTable 1 }
 
 
        NcmShelfInfoEntry ::=
             SEQUENCE {
             ncmShelfNIDIndex
                 INTEGER,
             ncmShelfIndex
                 INTEGER,
             ncmShelfNumber
                INTEGER,
             ncmShelfHardware
                 INTEGER,
             ncmNumberofCards
                 INTEGER,
             ncmListCardsInShelf
                DisplayString
                }
 
        ncmShelfNIDIndex OBJECT-TYPE
             SYNTAX  INTEGER (1..'7fffffff'h)
             ACCESS  read-only
             STATUS  mandatory
             DESCRIPTION
                "This variable indicates the node id
	         value of the node."  
               ::= { ncmShelfInfoEntry 1 }


 
        ncmShelfIndex OBJECT-TYPE
             SYNTAX  INTEGER (1..'7fffffff'h)
             ACCESS  read-only
             STATUS  mandatory
             DESCRIPTION
                "This object is the identifier of an Interface
                on a managed device.  If there is an ifEntry
                that is directly associated with this and
                only this DS1 interface, it should have the
                same value as ifIndex.  Otherwise, the value
                exceeds ifNumber, and is a unique identifier
                following this rule: inside interfaces (e.g.,
                equipment side) with even numbers and outside
                interfaces (e.g., network side) with odd
                numbers."
            ::= { ncmShelfInfoEntry 2 }
 



	 ncmShelfNumber  OBJECT-TYPE
             SYNTAX  INTEGER
             ACCESS  read-only
             STATUS  mandatory
             DESCRIPTION
                "This variable indicates the number of the shelf."
             ::= { ncmShelfInfoEntry 3 }
 
 
 
         
        ncmShelfHardware  OBJECT-TYPE
             SYNTAX  INTEGER {
                         uninstalled(1),
                         duallineshelf(2),
                         multilineshelf(3),
                         nb-2200lineshelf(4), 
                         nb-2200-4ilineshelf(10),
                         nb-2200qlineshelf(52), 
                         nb-2200-4iqlineshelf(54)
                     }
             ACCESS  read-only
             STATUS  mandatory
             DESCRIPTION
                "This variable indicates the shelf hardware type."
             ::= { ncmShelfInfoEntry 4 }
 
 
 
        ncmNumberofCards  OBJECT-TYPE
             SYNTAX  INTEGER
             ACCESS  read-only
             STATUS  mandatory
             DESCRIPTION
             "This variable indicates the total number of cards in
              the shelf."
             ::= { ncmShelfInfoEntry 5 }
 
 
 
        ncmListCardsInShelf  OBJECT-TYPE
             SYNTAX  DisplayString
             ACCESS  read-only
             STATUS  mandatory
             DESCRIPTION
                 "This variable indicates the cards present in the shelf.
                  For Example 1,3,5 if the cards 1,3 and 5 are present."
             ::= { ncmShelfInfoEntry 6 }
 



	
 	--      ncm Card Info Group
 
 
 
        ncmCardInfoTable OBJECT-TYPE
             SYNTAX   SEQUENCE OF NcmCardInfoEntry
             ACCESS   not-accessible
             STATUS   mandatory
	     --DEFAULT test-function    	card-test
             --DEFAULT next-function    	card-next


             ::= { ncm-generic  1004 }
 
 
 
        ncmCardInfoEntry OBJECT-TYPE
             SYNTAX   NcmCardInfoEntry
             ACCESS   not-accessible
             STATUS   mandatory
             DESCRIPTION
                "An entry in the ncmCard Info table."
          --  INDEX   { ncmCardIndex }
             INDEX   { ncmCardNIDIndex, ncmCardIndex }
            ::= { ncmCardInfoTable 1 }
 
 
        NcmCardInfoEntry ::=
             SEQUENCE {
             ncmCardNIDIndex
                 INTEGER,
             ncmCardIndex
                 INTEGER,
             ncmFirmwareType
                INTEGER,
             ncmCimType
                INTEGER,
             ncmClearCardInfo 
                INTEGER
                }
 
        ncmCardNIDIndex OBJECT-TYPE
             SYNTAX  INTEGER (1..'7fffffff'h)
             ACCESS  read-only
             STATUS  mandatory
             DESCRIPTION
                "This variable indicates the node id
	         value of the node."  
               ::= { ncmCardInfoEntry 1 }


        ncmCardIndex OBJECT-TYPE
             SYNTAX  INTEGER (1..'7fffffff'h)
             ACCESS  read-only
             STATUS  mandatory
             DESCRIPTION
                "This object is the identifier of an Interface
                on a managed device.  If there is an ifEntry
                that is directly associated with this and
                only this DS1 interface, it should have the
                same value as ifIndex.  Otherwise, the value
                exceeds ifNumber, and is a unique identifier
                following this rule: inside interfaces (e.g.,
                equipment side) with even numbers and outside
                interfaces (e.g., network side) with odd
                numbers."
            ::= { ncmCardInfoEntry 2 }
 

	 ncmFirmwareType OBJECT-TYPE
             SYNTAX  INTEGER {

			 card-sigma-sam(48),
                         card-sigma-sam-1(64),
                         card-sigma-csu(49),
                         card-sigma-dsu(50),
                         card-sigma-ddsu(51),
                         card-sigma-tu(52),
                         card-sigma-smds(53),
                         card-sigma-idc-sam(54),
                         card-sigma-idc(55),
                         card-ct1-sam(56),
                         card-ct1-csu(57),
                         card-ct1-dsu(58),
                         card-ct1-tu(60),
                         card-sigma-dsu-dds(61),
                         card-sigma-dsu-dsu(62),
                         card-sigma-aps(63),
                         card-sigma-vcu(77),
                         e1-ace-firmware(80),
                         t1-ace-firmware(81),
                         quad-T1-ace-firmware(82),
                         quad-E1-ace-firmware(83),
                         imux-tabs-firmware(85),
                         ace-dual-t1-firmware(86),
                         ace-dual-e1-firmware(87),
                         ds3-cdsu-firmware(88),
                         ncm-t1-firmware(96),
			 card-sigma-diu-2144(97),
			 card-sigma-dsu-2131(98),
                         ace-fw-isdn-T1(112),
                         ace-fw-isdn-E1(113),
                         quad-fw-isdn-T1(114),
                         quad-fw-isdn-E1(115),
			 dual-port-ds3(116),
			 m13-2113-firmware(117),
			 imux-2164-firmware(119)
                     }
             ACCESS  read-only
             STATUS  mandatory
             DESCRIPTION
             "This variable indicates the firmware type for cards."
             ::= { ncmCardInfoEntry 3 }
 
 
        ncmCimType OBJECT-TYPE
             SYNTAX  INTEGER {

			 cim-2001-e1(16),
                         cim-2002-e1(17),
                         cim-2003-e1(18),
                         cim-2004-e1(19),
                         cim-2005-e1(20),
                         cim-2006-e1(21),
                         cim-nim-2000(22),
                         cim-2101-t1(32),
                         cim-2102-t1(33),
                         cim-2164(34),
                         cim-2168(35),
                         cim-2162(36),
                         cim-2061(56),
                         cim-2065(37),
                         cim-hssi(48),
                         cim-v35(49),
                         cim-eia530A(50),
                         cim-eia530(51),
                         cim-rs449(52),
                         cim-hsm-2113(62),
                         cim-vcu-4W(64),
                         cim-vcu-2W(65),
                         cim-dim-2435(82),
                         cim-dim-2530(83),
                         cim-dim-2035(88),
                         cim-dim-2449(89),
                         cim-dim-2232(90),
                         cim-uninstall(255)
                     }
             ACCESS  read-only
             STATUS  mandatory
             DESCRIPTION
                "This variable indicates the cim type for the cards."
             ::= { ncmCardInfoEntry 4 }


      	ncmClearCardInfo OBJECT-TYPE
	    SYNTAX INTEGER {
			no(1),
			yes(2)                     
		 }
 
	    ACCESS  read-write
	    STATUS  mandatory
	    DESCRIPTION
	    "This variable indicates the option to clear the ncmCard
               Configuration in EEProm." 
	    ::= { ncmCardInfoEntry  5 }




	--      ncm Shelf Sync ncm Source Table
 

         ncmShelfSyncSourceTable OBJECT-TYPE
             SYNTAX  SEQUENCE OF NcmShelfSyncSourceEntry
             ACCESS  not-accessible
             STATUS  mandatory
	     --DEFAULT test-function    shelf-test
             --DEFAULT next-function    acesync-next

 
            ::= { ncm-generic  1005 }


        ncmShelfSyncSourceEntry OBJECT-TYPE
             SYNTAX NcmShelfSyncSourceEntry
             ACCESS  not-accessible
             STATUS  mandatory
             DESCRIPTION
                "An entry in the ncm Shelf Sync Source Time table."
            -- INDEX   { ncmShelfSyncSourceLineIndex }
            INDEX   { ncmShelfSyncNIDIndex, ncmShelfSyncSourceIndex }
            ::= { ncmShelfSyncSourceTable 1 }


        NcmShelfSyncSourceEntry ::=
         SEQUENCE {
           ncmShelfSyncNIDIndex
                 INTEGER,
           ncmShelfSyncSourceIndex
                 INTEGER,
           ncmSourceOneShelfNum
                INTEGER,
            ncmSourceOneCardNum
                INTEGER,
            ncmSourceOneClockRef
                INTEGER,
            ncmAutoRestore1
                INTEGER,
            ncmSourceTwoShelfNum
                INTEGER,
            ncmSourceTwoCardNum
                INTEGER,
            ncmSourceTwoClockRef
                INTEGER,
            ncmAutoRestore2
                INTEGER,
            ncmSourceThreeShelfNum
                INTEGER,
            ncmSourceThreeCardNum
                INTEGER,
            ncmSourceThreeClockRef
                INTEGER,
            ncmAutoRestore3
                INTEGER,
            ncmShelfCurrentSyncSource
                INTEGER

                }

        ncmShelfSyncNIDIndex OBJECT-TYPE
             SYNTAX  INTEGER (1..'7fffffff'h)
             ACCESS  read-only
             STATUS  mandatory
             DESCRIPTION
                "This variable indicates the node id
	         value of the node."  
            ::= { ncmShelfSyncSourceEntry 1 }


         ncmShelfSyncSourceIndex OBJECT-TYPE
             SYNTAX  INTEGER (1..'7fffffff'h)
             ACCESS  read-only
             STATUS  mandatory
	      DESCRIPTION
                "This object is the identifier of an Interface
                on a managed device.  If there is an ifEntry
                that is directly associated with this and
                only this DS1 interface, it should have the
                same value as ifIndex.  Otherwise, the value
                exceeds ifNumber, and is a unique identifier
                following this rule: inside interfaces (e.g.,
                equipment side) with even numbers and outside
                interfaces (e.g., network side) with odd
                numbers."
            ::= { ncmShelfSyncSourceEntry 2 }
 
 
         
        ncmSourceOneShelfNum OBJECT-TYPE
            SYNTAX INTEGER
            ACCESS read-write
            STATUS mandatory
            DESCRIPTION
                "This variable indicates the source one shelf number."
            ::= { ncmShelfSyncSourceEntry 3 }
 
 
         
         ncmSourceOneCardNum OBJECT-TYPE
            SYNTAX INTEGER
            ACCESS  read-write
            STATUS  mandatory
            DESCRIPTION
                "This variable indicates the source one card number."
            ::= {ncmShelfSyncSourceEntry 4 }
 
 
 
        ncmSourceOneClockRef OBJECT-TYPE
            SYNTAX INTEGER {
                        e1-t1port1(5),
                        e1-t1port2(6),
                        external-timing(7),
                        internal-timing(8),
                        ncmdata-port1(9),
                        ncmdata-port2(10),
                        quad-t1-port3(11),
                        quad-t1-port4(12)
                           }
            ACCESS  read-write
            STATUS  mandatory
         DESCRIPTION
            "This variable indicates the source one clock reference."
            ::= {ncmShelfSyncSourceEntry 5 }
 
 
         ncmAutoRestore1 OBJECT-TYPE
            SYNTAX INTEGER {
                        disable(1),
			enable(2)
                    }
            ACCESS  read-write
            STATUS  mandatory
            DESCRIPTION
            "This variable indicates the source one auto restore."
            ::= {ncmShelfSyncSourceEntry 6 }
 
 
 
         ncmSourceTwoShelfNum OBJECT-TYPE
            SYNTAX INTEGER
            ACCESS  read-write
            STATUS  mandatory
            DESCRIPTION
            "This variable indicates the source two shelf number."
            ::= { ncmShelfSyncSourceEntry 7 }
 
 
         
        ncmSourceTwoCardNum OBJECT-TYPE
            SYNTAX INTEGER
            ACCESS  read-write
            STATUS  mandatory
            DESCRIPTION
            "This variable indicates the source two card number."
            ::= { ncmShelfSyncSourceEntry 8 }
 
         
        ncmSourceTwoClockRef OBJECT-TYPE
            SYNTAX INTEGER {
                        e1-t1port1(5),
                        e1-t1port2(6),
                        external-timing(7),
                        internal-timing(8),
                        ncmdata-port1(9),
                        ncmdata-port2(10),
                        quad-t1-port3(11),
                        quad-t1-port4(12)
                           }
            ACCESS  read-write
            STATUS  mandatory
            DESCRIPTION
            "This variable indicates the source two clock reference."
            ::= { ncmShelfSyncSourceEntry 9 }
 
 
        ncmAutoRestore2 OBJECT-TYPE
            SYNTAX INTEGER {
                        disable(1),
                        enable(2)
                    }
            ACCESS  read-write
            STATUS  mandatory
            DESCRIPTION
                "This variable indicates the source two auto restore."
            ::= { ncmShelfSyncSourceEntry 10 }


	ncmSourceThreeShelfNum OBJECT-TYPE
            SYNTAX INTEGER
            ACCESS  read-write
            STATUS  mandatory
            DESCRIPTION
                "This variable indicates the source three shelf number."
            ::= { ncmShelfSyncSourceEntry 11 }
 
 
        ncmSourceThreeCardNum OBJECT-TYPE
            SYNTAX INTEGER
            ACCESS  read-write
            STATUS  mandatory
            DESCRIPTION
                "This variable indicates the source three card number."
            ::= { ncmShelfSyncSourceEntry 12 }
 
 
        ncmSourceThreeClockRef OBJECT-TYPE
            SYNTAX INTEGER {
                        e1-t1port1(5),
                        e1-t1port2(6),
                        external-timing(7),
                        internal-timing(8),
                        ncmdata-port1(9),
                        ncmdata-port2(10),
                        quad-t1-port3(11),
                        quad-t1-port4(12)
                           }
            ACCESS  read-write
            STATUS  mandatory
            DESCRIPTION
            "This variable indicates the source three clock reference."
            ::= { ncmShelfSyncSourceEntry 13 }
 
 
         ncmAutoRestore3 OBJECT-TYPE
            SYNTAX INTEGER {
                        disable(1),
                        enable(2)
                    }
            ACCESS  read-write
            STATUS  mandatory
            DESCRIPTION
                "This variable indicates the source three auto restore."
            ::= { ncmShelfSyncSourceEntry 14 }
 
 
         ncmShelfCurrentSyncSource OBJECT-TYPE
            SYNTAX INTEGER {
                        source1(1),
                        source2(2),
                        source3(3)
                    }
		ACCESS  read-write
            	STATUS  mandatory
            	DESCRIPTION
                "This variable indicates the current sync source."
            ::= { ncmShelfSyncSourceEntry 15 }



--	ncm Card Sync ncmSource Table


	 ncmCardSyncSourceTable OBJECT-TYPE
	     SYNTAX  SEQUENCE OF NcmCardSyncSourceEntry
	     ACCESS  not-accessible
	     STATUS  mandatory
	     --DEFAULT test-function    card-test
             --DEFAULT next-function  cardsync-next
             --DEFAULT next-function    acesync-next


	    ::= { ncm-generic  1006 }


	ncmCardSyncSourceEntry OBJECT-TYPE
	     SYNTAX NcmCardSyncSourceEntry
	     ACCESS  not-accessible
	     STATUS  mandatory
	     DESCRIPTION
		"An entry in the ncmCard Sync ncmSource Time table."
	    -- INDEX   { ncmCardSyncncmSourceLineIndex }
	     INDEX   { ncmCardSyncNIDIndex, ncmCardSyncSourceIndex }
	    ::= { ncmCardSyncSourceTable 1 }



	NcmCardSyncSourceEntry ::=
	 SEQUENCE {
            ncmCardSyncNIDIndex 
		 INTEGER,
	    ncmCardSyncSourceIndex
		 INTEGER,
	    ncmCardReceiveClockFromShelf
		INTEGER,
	    ncmCardSourceOneShelfNum
		INTEGER,
	    ncmCardSourceOneCardNum
		INTEGER,
	    ncmCardSourceOneClockRef
		INTEGER,
	    ncmCardAutoRestore1
		INTEGER,
	    ncmCardSourceTwoShelfNum
		INTEGER,
	    ncmCardSourceTwoCardNum
		INTEGER,
	    ncmCardSourceTwoClockRef
		INTEGER,
	    ncmCardAutoRestore2
		INTEGER,
	    ncmCardSourceThreeShelfNum
		INTEGER,
	    ncmCardSourceThreeCardNum
		INTEGER,
	    ncmCardSourceThreeClockRef
		INTEGER,
	    ncmCardAutoRestore3
		INTEGER,
	    ncmCardCurrentSyncSource
		INTEGER
	}


        ncmCardSyncNIDIndex OBJECT-TYPE
             SYNTAX  INTEGER (1..'7fffffff'h)
             ACCESS  read-only
             STATUS  mandatory
             DESCRIPTION
                "This variable indicates the node id
	         value of the node."  
	    ::= { ncmCardSyncSourceEntry 1 }


	 ncmCardSyncSourceIndex OBJECT-TYPE
	     SYNTAX  INTEGER (1..'7fffffff'h)
	     ACCESS  read-only
	     STATUS  mandatory
	     DESCRIPTION
		"This object is the identifier of an Interface
		on a managed device.  If there is an ifEntry
		that is directly associated with this and
		only this DS1 interface, it should have the
		same value as ifIndex.  Otherwise, the value
		exceeds ifNumber, and is a unique identifier
		following this rule: inside interfaces (e.g.,
		equipment side) with even numbers and outside
		interfaces (e.g., network side) with odd
		numbers."
	    ::= { ncmCardSyncSourceEntry 2 }


       	ncmCardReceiveClockFromShelf OBJECT-TYPE
	    SYNTAX INTEGER {
			no(1),
			yes(2)
			
		    }
	    ACCESS  read-write
	    STATUS  mandatory
	    DESCRIPTION 
	    "This variable indicates receive sync clock from the shelf for
                 the card ."
	    ::= {ncmCardSyncSourceEntry 3 }

	
      	 ncmCardSourceOneShelfNum OBJECT-TYPE
	    SYNTAX INTEGER 
	    ACCESS  read-write
	    STATUS  mandatory
	    DESCRIPTION
	    "This variable indicates the source one shelf number."
	    ::= { ncmCardSyncSourceEntry 4 }


	    
      	 ncmCardSourceOneCardNum OBJECT-TYPE
	    SYNTAX INTEGER 
	    ACCESS  read-write
	    STATUS  mandatory
	    DESCRIPTION
	    "This variable indicates the source one card number."
	    ::= {ncmCardSyncSourceEntry 5 }




	ncmCardSourceOneClockRef OBJECT-TYPE
	    SYNTAX INTEGER {
			e1-t1port1(5),
			e1-t1port2(6),
			external-timing(7),
			internal-timing(8),
			data-port1(9),
			data-port2(10),
			quad-t1-port3(11),
			quad-t1-port4(12)
			   }
	    ACCESS  read-write
	    STATUS  mandatory
	    DESCRIPTION
	    "This variable indicates the source one clock reference."
	    ::= {ncmCardSyncSourceEntry 6 }


      	ncmCardAutoRestore1 OBJECT-TYPE
	    SYNTAX INTEGER {
			disable(1),
			enable(2)
			
		    }
	    ACCESS  read-write
	    STATUS  mandatory
	    DESCRIPTION 
		"This variable indicates the source one auto restore."
	    ::= {ncmCardSyncSourceEntry 7 }



      	ncmCardSourceTwoShelfNum OBJECT-TYPE
	    SYNTAX INTEGER 
	    ACCESS  read-write
	    STATUS  mandatory
	    DESCRIPTION
		"This variable indicates the source two shelf number."
	    ::= { ncmCardSyncSourceEntry 8 }


	    
     	 ncmCardSourceTwoCardNum OBJECT-TYPE
	    SYNTAX INTEGER 
	    ACCESS  read-write
	    STATUS  mandatory
	    DESCRIPTION
		"This variable indicates the source two card number."
	    ::= { ncmCardSyncSourceEntry 9 }



	ncmCardSourceTwoClockRef OBJECT-TYPE
	    SYNTAX INTEGER {
                        e1-t1port1(5),
                        e1-t1port2(6),
                        external-timing(7),
                        internal-timing(8),
                        data-port1(9),
                        data-port2(10),
                        quad-t1-port3(11),
                        quad-t1-port4(12)
			   }
	    ACCESS  read-write
	    STATUS  mandatory
	    DESCRIPTION
		"This variable indicates the source two clock reference."
	    ::= { ncmCardSyncSourceEntry 10 }


     	ncmCardAutoRestore2 OBJECT-TYPE
	    SYNTAX INTEGER {
			disable(1),
			enable(2)
			
		    }
	    ACCESS  read-write
	    STATUS  mandatory
	    DESCRIPTION 
		"This variable indicates the source two auto restore."
	    ::= { ncmCardSyncSourceEntry 11 }


	   
      	ncmCardSourceThreeShelfNum OBJECT-TYPE
	    SYNTAX INTEGER 
	    ACCESS  read-write
	    STATUS  mandatory
	    DESCRIPTION
		"This variable indicates the source three shelf number."
	    ::= { ncmCardSyncSourceEntry 12 }



     	 ncmCardSourceThreeCardNum OBJECT-TYPE
	    SYNTAX INTEGER 
	    ACCESS  read-write
	    STATUS  mandatory
	    DESCRIPTION
		"This variable indicates the source three card number."
	    ::= { ncmCardSyncSourceEntry 13 }



	 ncmCardSourceThreeClockRef OBJECT-TYPE
	    SYNTAX INTEGER {
                        e1-t1port1(5),
                        e1-t1port2(6),
                        external-timing(7),
                        internal-timing(8),
                        data-port1(9),
                        data-port2(10),
                        quad-t1-port3(11),
                        quad-t1-port4(12)
			   }
	    ACCESS  read-write
	    STATUS  mandatory
	    DESCRIPTION
	    "This variable indicates the source three clock reference."
	    ::= { ncmCardSyncSourceEntry 14 }



     	 ncmCardAutoRestore3 OBJECT-TYPE
	    SYNTAX INTEGER {
			disable(1),
			enable(2)
			
		    }
	    ACCESS  read-write
	    STATUS  mandatory
	    DESCRIPTION 
	    "This variable indicates the source three auto restore."
	    ::= { ncmCardSyncSourceEntry 15 }



      	ncmCardCurrentSyncSource OBJECT-TYPE
	    SYNTAX INTEGER {
			source1(1),
			source2(2),
			source3(3)
			
		    }
	    ACCESS  read-write
	    STATUS  mandatory
	    DESCRIPTION 
	    "This variable indicates the current sync ncm source."
	    ::= { ncmCardSyncSourceEntry 16 }


	 


--	ncm ID Prom Group


	ncmIDPromTable OBJECT-TYPE
	     SYNTAX  SEQUENCE OF NcmIDPromEntry
	     ACCESS  not-accessible
	     STATUS  mandatory
	     --DEFAULT test-function    card-test
             --DEFAULT next-function    cardsync-next
 


	    ::= { ncm-generic  1007 }


	ncmIDPromEntry OBJECT-TYPE
	     SYNTAX NcmIDPromEntry
	     ACCESS  not-accessible
	     STATUS  mandatory
	     DESCRIPTION
		"An entry in the ncm ID Prom Table."
	    -- INDEX   { ncmIDPromIndex }
	    INDEX   { ncmIDPromNIDIndex, ncmIDPromIndex }
	    ::= { ncmIDPromTable 1 }


	NcmIDPromEntry ::=
	 SEQUENCE {
	     ncmIDPromNIDIndex
		 INTEGER,
	     ncmIDPromIndex
		 INTEGER,
	     ncmCardType
		INTEGER,
	     ncmCardRevision
		DisplayString,
	     ncmCardDate
		DisplayString,
	     ncmCardSerialNumber
		DisplayString, 
             ncmManufacturePartNumber
		DisplayString, 
	     ncmVendorCageCode
		DisplayString, 
	     ncmIDCimType
		INTEGER,
	     ncmCimRevision
		DisplayString,
	     ncmCimDate
		DisplayString, 
	     ncmCimSerialNumber
		DisplayString,
	     ncmCimManufacturePartNumber
		DisplayString, 
	     ncmCimVendorCageCode
		DisplayString  

		}


        ncmIDPromNIDIndex OBJECT-TYPE
             SYNTAX  INTEGER (1..'7fffffff'h)
             ACCESS  read-only
             STATUS  mandatory
             DESCRIPTION
                "This variable indicates the node id
	         value of the node."  
	    ::= { ncmIDPromEntry 1 }


	ncmIDPromIndex OBJECT-TYPE
	     SYNTAX  INTEGER (1..'7fffffff'h)
	     ACCESS  read-only
	     STATUS  mandatory
	     DESCRIPTION
		"This object is the identifier of an Interface
		on a managed device.  If there is an ifEntry
		that is directly associated with this and
		only this DS1 interface, it should have the
		same value as ifIndex.  Otherwise, the value
		exceeds ifNumber,  and is a unique identifier
		following this rule: inside interfaces (e.g.,
		equipment side) with even numbers and outside
		interfaces (e.g., network side) with odd
		numbers."
	    ::= { ncmIDPromEntry 2 }


	ncmCardType OBJECT-TYPE
	    SYNTAX INTEGER {
			ace-card(1),
			quad-card-for-imux(2),
			dual-csu(3)
			   }
	    ACCESS  read-only
	    STATUS  mandatory
	    DESCRIPTION
	    "This variable indicates the ncmCard type of the card." 
	    ::= { ncmIDPromEntry  3 }




	ncmCardRevision OBJECT-TYPE
	    SYNTAX DisplayString (SIZE (0..255)) 
	    ACCESS  read-only
	    STATUS  mandatory
	    DESCRIPTION
	    "This variable indicates the revision number for the card." 
	    ::= { ncmIDPromEntry  4 }

	

	ncmCardDate OBJECT-TYPE
	    SYNTAX DisplayString (SIZE (0..255)) 
	    ACCESS  read-only
	    STATUS  mandatory
	    DESCRIPTION
	    "This variable indicates the date (mm-dd-yy)
                for the card." 
	    ::= { ncmIDPromEntry  5 }


	ncmCardSerialNumber OBJECT-TYPE
	    SYNTAX  DisplayString (SIZE (0..255))
	    ACCESS  read-only
	    STATUS  mandatory
	    DESCRIPTION
	    "This variable indicates the Serial Number for the card." 
	    ::= { ncmIDPromEntry  6 }


	ncmManufacturePartNumber OBJECT-TYPE
	    SYNTAX  DisplayString (SIZE (0..255))
	    ACCESS  read-only
	    STATUS  mandatory
	    DESCRIPTION
	    "This variable indicates the Manufacture Part Number for the
                card." 
	    ::= { ncmIDPromEntry  7 }

	
	ncmVendorCageCode OBJECT-TYPE
	    SYNTAX  DisplayString (SIZE (0..255))
	    ACCESS  read-only
	    STATUS  mandatory
	    DESCRIPTION
	    "This variable indicates the Vendor Cage Code for the card." 
	    ::= { ncmIDPromEntry  8 }


	ncmIDCimType OBJECT-TYPE
	    SYNTAX INTEGER {
				cIM29004(16),
                                cIM29005(17),
                                cIM29006(18),
                                cIM29007(19),
                                cIM29008(20),
                                cIM29009(21),
                                cIM29010(32),
                                cIM29011(33),
                                cIM-2164(34),
                                cIM-2168(35),
                                cIM29003(36),
                                cIM29002(56),
                                cIM29001(37),
                                nIM2000(22),
                                cIM-UNINSTALLED(255)
	
			  } 
	    ACCESS  read-only
	    STATUS  mandatory
	    DESCRIPTION
		"This variable indicates the cim Type for the card." 
	    ::= { ncmIDPromEntry  9 }



	ncmCimRevision OBJECT-TYPE
--	    SYNTAX INTEGER 
	    SYNTAX DisplayString (SIZE (0..255)) 
	    ACCESS  read-only
	    STATUS  mandatory
	    DESCRIPTION
	    "This variable indicates the revision number for the cim of
                the card." 
	    ::= { ncmIDPromEntry  10 }

	

	ncmCimDate OBJECT-TYPE
	    SYNTAX DisplayString (SIZE (0..255)) 
	    ACCESS  read-only
	    STATUS  mandatory
	    DESCRIPTION
	    "This variable indicates the date (mm-dd-yy) of
                the cim for the card." 
	    ::= { ncmIDPromEntry 11 }


	ncmCimSerialNumber OBJECT-TYPE
	    SYNTAX  DisplayString (SIZE (0..255))
	    ACCESS  read-only
	    STATUS  mandatory
	    DESCRIPTION
	    "This variable indicates the Serial Number for the card." 
	    ::= { ncmIDPromEntry  12 }


	ncmCimManufacturePartNumber OBJECT-TYPE
	    SYNTAX  DisplayString (SIZE (0..255))
	    ACCESS  read-only
	    STATUS  mandatory
	    DESCRIPTION
	    "This variable indicates the Manufacture Part Number for the
                card." 
	    ::= { ncmIDPromEntry  13 }


	ncmCimVendorCageCode OBJECT-TYPE
	    SYNTAX  DisplayString (SIZE (0..255))
	    ACCESS  read-only
	    STATUS  mandatory
	    DESCRIPTION
	    "This variable indicates the Vendor Cage Code for the card." 
	    ::= { ncmIDPromEntry  14 }


--     ncm E1 Port Config Group


      ncmE1PortConfigTable OBJECT-TYPE
        SYNTAX  SEQUENCE OF NcmE1PortConfigEntry
        ACCESS  not-accessible
        STATUS  mandatory
	--DEFAULT test-function    acee1-test
        --DEFAULT next-function    acee1-next

         ::= { ncm-generic  1008  }


      ncmE1PortConfigEntry OBJECT-TYPE
        SYNTAX  NcmE1PortConfigEntry
        ACCESS  not-accessible
        STATUS  mandatory
        DESCRIPTION
        "An entry in the  E1 Port Configuration table."
         INDEX   { ncmE1ConfigNIDIndex, ncmE1PortLineIndex }
         ::= { ncmE1PortConfigTable 1 }


      NcmE1PortConfigEntry ::=
         SEQUENCE {
           ncmE1ConfigNIDIndex
                INTEGER,
           ncmE1PortLineIndex
                 INTEGER,
           ncmE1PortCRC4
                INTEGER,
           ncmE1PortFaseAlarm
                INTEGER,
           ncmE1PortCarrierFailureAlarm
                INTEGER,
           ncmE1PortInbandISDNEnableDisable
                INTEGER,
           ncmE1PortRepeaterLoopbackTimeoutEnable
                INTEGER,
           ncmE1PortFraming
                INTEGER,
           ncmE1PortRepeaterLoopbackTimeout
                INTEGER,
           ncmE1PortCarrierFailureAlarmDeclareTime
                INTEGER,
           ncmE1PortServiceState
                INTEGER,
           ncmE1PortIdlePattern
                INTEGER,
           ncmE1TimeSlot
                DisplayString,
           ncmE1TimeSlotSelect
		INTEGER 
 
                }
         
        
        ncmE1ConfigNIDIndex OBJECT-TYPE
             SYNTAX  INTEGER (1..'7fffffff'h)
             ACCESS  read-only
             STATUS  mandatory
             DESCRIPTION
                "This object is the identifier of the node id index."
            ::= { ncmE1PortConfigEntry 1 }
 
             
      ncmE1PortLineIndex OBJECT-TYPE
          SYNTAX  INTEGER (1..'7fffffff'h)
          ACCESS  read-only
          STATUS  mandatory
          DESCRIPTION
         "The index value which uniquely identifies the
          interface  to which this entry is applicable."
 
          ::= { ncmE1PortConfigEntry  2 }
 
 
      ncmE1PortCRC4 OBJECT-TYPE
            SYNTAX INTEGER {
                        disable(1),
                        enable(2)
                           }
 
            ACCESS  read-write
            STATUS  mandatory
            DESCRIPTION
            "This variable indicates whether the CRC4 for the port is
                 Enabled or Disabled."
            ::= { ncmE1PortConfigEntry 3 }
 
         
        ncmE1PortCarrierFailureAlarm OBJECT-TYPE
            SYNTAX INTEGER {
                        disable(1),
                        enable(2)
                           }
           ACCESS  read-write
            STATUS  mandatory
            DESCRIPTION
            "This variable indicates whether the Carrier Failure ncmAlarm
                is Enabled or Disabled."
            ::= { ncmE1PortConfigEntry 4 }
 

	 ncmE1PortFaseAlarm OBJECT-TYPE
            SYNTAX INTEGER {
                        minor(1),
                        major(2)
                           }
 
            ACCESS  read-write
            STATUS  mandatory
            DESCRIPTION
            "This variable indicates whether the Fase ncmAlarm is Major or
                 Minor Category."
            ::= { ncmE1PortConfigEntry 5 }
 
 
         ncmE1PortInbandISDNEnableDisable OBJECT-TYPE
            SYNTAX INTEGER {
                disablebothinbandisdn(1),
                enableinband(2),
                enableisdn(3)
                             }
             ACCESS  read-write
             STATUS  mandatory
             DESCRIPTION
             "This variable indicates the Inband, ISDN enable and disable options."
            ::= { ncmE1PortConfigEntry 6 }
 
 
        ncmE1PortRepeaterLoopbackTimeoutEnable OBJECT-TYPE
            SYNTAX INTEGER {
                        disable(1),
                        enable(2)
                           }
 
            ACCESS  read-write
            STATUS  mandatory
            DESCRIPTION
            "This variable indicates the option to enable the repeater
                loopback timeout."
            ::= { ncmE1PortConfigEntry 7 }
 
 
         ncmE1PortFraming OBJECT-TYPE
            SYNTAX INTEGER {
                        cAS(1),
                        cCS(2),
                        thirty-one-Ch(3),
                        g703(4)
                           }
 
            ACCESS  read-write
            STATUS  mandatory
            DESCRIPTION
            "This variable indicates the framing for E1 Port."
            ::= { ncmE1PortConfigEntry 8 }


	 ncmE1PortRepeaterLoopbackTimeout OBJECT-TYPE
            SYNTAX INTEGER
            ACCESS  read-write
            STATUS  mandatory
            DESCRIPTION
            "This variable indicates the repeater loopback timeout in
                seconds for the card."
            ::= { ncmE1PortConfigEntry 9  }
 
 
         ncmE1PortCarrierFailureAlarmDeclareTime OBJECT-TYPE
            SYNTAX INTEGER
            ACCESS  read-write
            STATUS  mandatory
            DESCRIPTION
            "This variable indicates the carrier failure alarm declare
                 time in seconds for the card."
            ::= { ncmE1PortConfigEntry 10  }
 
 
         
         ncmE1PortServiceState OBJECT-TYPE
            SYNTAX INTEGER {
                        out-of-service(1),
                        in-service(2)
                           }
 
            ACCESS  read-write
            STATUS  mandatory
            DESCRIPTION
                "This variable indicates service state of the port."
            ::= { ncmE1PortConfigEntry 11 }
 
 
 
        ncmE1PortIdlePattern OBJECT-TYPE
            SYNTAX INTEGER
            ACCESS  read-write
            STATUS  mandatory
            DESCRIPTION
            "This variable indicates the idle pattern for the card."
            ::= { ncmE1PortConfigEntry 12  }
 
 
 
        ncmE1TimeSlot OBJECT-TYPE
          --  SYNTAX DisplayString
            SYNTAX  DisplayString (SIZE (0..255))
            ACCESS  read-only
            STATUS  mandatory
            DESCRIPTION
            "This variable indicates the Time slot used for the given port
                directly from the hardware cross point switch for example slot         
                1-10, if slots 1 to 10 is used or 1,3,4 if slots 1,3 and 4 are
                used."
            ::= { ncmE1PortConfigEntry 13  }
 

        ncmE1TimeSlotSelect OBJECT-TYPE  
            SYNTAX INTEGER
            ACCESS  read-write
            STATUS  mandatory
            DESCRIPTION
            "This variable indicates the number which is choosed for the inband/isdn timeslot."
            ::= { ncmE1PortConfigEntry 14  }


	--     ncm E1 Port Status Table
 
 
      ncmE1PortStatusTable OBJECT-TYPE
        SYNTAX  SEQUENCE OF NcmE1PortStatusEntry
        ACCESS  not-accessible
        STATUS  mandatory
	--DEFAULT test-function      acee1-test
        --DEFAULT next-function      acee1-next

         ::= { ncm-generic 1009  }
 
 
      ncmE1PortStatusEntry OBJECT-TYPE
        SYNTAX  NcmE1PortStatusEntry
        ACCESS  not-accessible
        STATUS  mandatory
        DESCRIPTION
        "An entry in the  E1 Port Status Table."
         INDEX   { ncmE1PortStatusNIDIndex, ncmE1PortStatusIndex }
         ::= { ncmE1PortStatusTable 1 }
 
 
      NcmE1PortStatusEntry ::=
         SEQUENCE {
           ncmE1PortStatusNIDIndex
                  INTEGER,
           ncmE1PortStatusIndex
                 INTEGER,
           ncmE1PortCRC4Error
                INTEGER,
           ncmE1PortFramingSlip
                INTEGER,
           ncmE1PortRAI
                INTEGER,
           ncmE1PortLOFA
                INTEGER,
           ncmE1PortAIS
                INTEGER,
           ncmE1PortLOS
                INTEGER,
           ncmE1PortBPVThresholdExceeded
                INTEGER,
           ncmE1BlockErrorCounter
                Gauge,
	   ncmE1CodeViolationMode
                INTEGER,
           ncmE1CurrentHDB3ORFEBEErrorCounts
                Gauge,
           ncmE1CurrentFrameErrorCounts
                Gauge,
           ncmE1CurrentCRC4ErrorCounts
                Gauge,
	   ncmE1ResetPerfCount
		INTEGER,
           ncmE1PortSendRAI
                INTEGER,
           ncmE1PortSendAIS
                INTEGER,
           ncmE1PortRFA
                INTEGER,
           ncmE1PortBERThresholdExceeded
                INTEGER,
           ncmE1PortLLB
                INTEGER,
           ncmE1PortPLB
                INTEGER,
           ncmE1PortLOC
                INTEGER,
           ncmE1PortTestPattern
                INTEGER
                  
                }
 
        ncmE1PortStatusNIDIndex OBJECT-TYPE
        SYNTAX  INTEGER (1..'7fffffff'h)
        ACCESS  read-only
        STATUS  mandatory
        DESCRIPTION
        "This object identifies the node id index."
         ::= { ncmE1PortStatusEntry 1 }


	 ncmE1PortStatusIndex OBJECT-TYPE
        SYNTAX  INTEGER (1..'7fffffff'h)
        ACCESS  read-only
        STATUS  mandatory
        DESCRIPTION
        "The index value which uniquely identifies  the
         interface to which this entry is applicable."
 
        ::= { ncmE1PortStatusEntry 2 }
 
 
 
         ncmE1PortCRC4Error OBJECT-TYPE
            SYNTAX INTEGER {
                                no(1),
                                yes(2)
                           }
            ACCESS  read-only
            STATUS  mandatory
            DESCRIPTION
            "This variable indicates the occurance of CRC4 error."
            ::= { ncmE1PortStatusEntry 3 }
 
 
         ncmE1PortFramingSlip OBJECT-TYPE
            SYNTAX INTEGER {
                                no(1),
                                yes(2)
                           }
            ACCESS  read-only
            STATUS  mandatory
            DESCRIPTION
            "This variable indicates the occurance of framing slip error."
            ::= { ncmE1PortStatusEntry 4 }
 
 

	 ncmE1PortRAI OBJECT-TYPE
            SYNTAX INTEGER {
                                no(1),
                                yes(2)
                        }
            ACCESS  read-only
            STATUS  mandatory
            DESCRIPTION
            "This variable indicates the occurance of RAI."
            ::= { ncmE1PortStatusEntry 5 }
 
 
 
         ncmE1PortLOFA OBJECT-TYPE
            SYNTAX INTEGER {
                                no(1),
                                yes(2)
                        }
            ACCESS  read-only
            STATUS  mandatory
            DESCRIPTION
            "This variable indicates the occurance of LOFA."
            ::= { ncmE1PortStatusEntry 6 }
 
 
 
         ncmE1PortAIS OBJECT-TYPE
            SYNTAX INTEGER {
                                no(1),
                                yes(2)
                           }
            ACCESS  read-only
            STATUS  mandatory
            DESCRIPTION
            "This variable indicates the occurance of AIS."
            ::= { ncmE1PortStatusEntry 7 }
 
 
 
        ncmE1PortLOS OBJECT-TYPE
            SYNTAX INTEGER {
                                no(1),
                                yes(2)
                           }
            ACCESS  read-only
            STATUS  mandatory
            DESCRIPTION
                "This variable indicates the occurance of LOS."
            ::= { ncmE1PortStatusEntry 8 }
 
 
	 ncmE1PortBPVThresholdExceeded OBJECT-TYPE
            SYNTAX INTEGER {
                                no(1),
                                yes(2)
                                           }
            ACCESS  read-only
            STATUS  mandatory
            DESCRIPTION
            "This variable indicates whether BPV threshold is exceeded
                or not."
            ::= { ncmE1PortStatusEntry 9 }
 
 
         ncmE1BlockErrorCounter OBJECT-TYPE
            SYNTAX Gauge
            ACCESS  read-only
            STATUS  mandatory
            DESCRIPTION
                "This variable indicates the Block Error Counter."
            ::= { ncmE1PortStatusEntry 10 }


	 ncmE1CodeViolationMode OBJECT-TYPE
            SYNTAX INTEGER {
                                count-HDB3(1),
                                count-FEBE(2)
                           }
            ACCESS  read-only
            STATUS  mandatory
            DESCRIPTION
            "This variable indicates whether HDB3 or FEBE should be counted."
            ::= { ncmE1PortStatusEntry 11 }
 
 
        ncmE1CurrentHDB3ORFEBEErrorCounts OBJECT-TYPE
             SYNTAX  Gauge
             ACCESS  read-only
             STATUS  mandatory
             DESCRIPTION
                "This variable indicates the Current HDB3/FEBE error counts."
            ::= { ncmE1PortStatusEntry 12 }
 
 
        ncmE1CurrentFrameErrorCounts OBJECT-TYPE
             SYNTAX  Gauge
             ACCESS  read-only
             STATUS  mandatory
             DESCRIPTION
                "This variable indicates the current Frame Error counts."
            ::= { ncmE1PortStatusEntry 13 }
 
 
        ncmE1CurrentCRC4ErrorCounts OBJECT-TYPE
             SYNTAX  Gauge
             ACCESS  read-only
             STATUS  mandatory
             DESCRIPTION
                "This variable indicates the current crc4 Error counts."
            ::= { ncmE1PortStatusEntry 14 }

 
        ncmE1ResetPerfCount  OBJECT-TYPE
             SYNTAX  INTEGER {
                         no(1),
                         yes(2)
                     }
             ACCESS  read-write
             STATUS  mandatory
             DESCRIPTION
                "Reset E1 Performance Counters."
            ::= { ncmE1PortStatusEntry 15 } 

 
	 ncmE1PortSendRAI OBJECT-TYPE
            SYNTAX INTEGER {
                                no(1),
                                yes(2)
                                           }
            ACCESS  read-only
            STATUS  mandatory
            DESCRIPTION
            "This variable indicates whether the E1 Port Send RAI is enable 
                or disable."
            ::= { ncmE1PortStatusEntry 16 }
 
 
	 ncmE1PortSendAIS OBJECT-TYPE
            SYNTAX INTEGER {
                                no(1),
                                yes(2)
                                           }
            ACCESS  read-only
            STATUS  mandatory
            DESCRIPTION
            "This variable indicates whether the E1 Port Send AIS is enable 
                or disable."
            ::= { ncmE1PortStatusEntry 17 }

 
	 ncmE1PortRFA OBJECT-TYPE
            SYNTAX INTEGER {
                                no(1),
                                yes(2)
                                           }
            ACCESS  read-only
            STATUS  mandatory
            DESCRIPTION
            "This variable indicates whether the E1 Port RFA is on 
                or off."
            ::= { ncmE1PortStatusEntry 18 }

         ncmE1PortBERThresholdExceeded OBJECT-TYPE
            SYNTAX INTEGER {
                                no(1),
                                yes(2)
                                           }
            ACCESS  read-only
            STATUS  mandatory
            DESCRIPTION
            "This variable indicates whether BER threshold is exceeded
                or not."
            ::= { ncmE1PortStatusEntry 19 }

        ncmE1PortLLB  OBJECT-TYPE
             SYNTAX  INTEGER {
                         no(1),
                         yes(2)
                     }
             ACCESS  read-only
             STATUS  mandatory
             DESCRIPTION
             "This variable indicates whether LLB is on or off."
 
             ::= { ncmE1PortStatusEntry 20 }

        ncmE1PortPLB  OBJECT-TYPE
             SYNTAX  INTEGER {
                         no(1),
                         yes(2)
                     }
             ACCESS  read-only
             STATUS  mandatory
             DESCRIPTION
             "This variable indicates whether PLB is on or off."
 
             ::= { ncmE1PortStatusEntry 21 }

        ncmE1PortLOC  OBJECT-TYPE
             SYNTAX  INTEGER {
                         no(1),
                         yes(2)
                     }
             ACCESS  read-only
             STATUS  mandatory
             DESCRIPTION
             "This variable indicates whether LOC is on or off."
 
             ::= { ncmE1PortStatusEntry 22 }

        ncmE1PortTestPattern  OBJECT-TYPE
             SYNTAX  INTEGER {
                         none(1),
                         three-24(2),
                         qRSS(3),
                         two-n-20-1(4),
                         one-in-8(5),
                         two-n-15-1(6),
                         all-zeros(7),
                         fifty-octets(8),
                         all-ones(9)
                     }
             ACCESS  read-only
             STATUS  mandatory
             DESCRIPTION
             "This variable indicates the test patern in progress:
              1 = none
              2 = 3/24
              3 = QRSS
              4 = 2n20-1
              5 = 1 in 8
              6 = 2N15 - 1
              7 = All Zeros
              8 = 55 Octets
              9 = all ones  "
 
             ::= { ncmE1PortStatusEntry 23 }

 
	--     ncm E1 Performance Monitor Current Table
 
     -- The current table contains various statistics of error being
     -- collected for the current 15 minute interval.
 
       ncmE1CurrentTable OBJECT-TYPE
             SYNTAX  SEQUENCE OF NcmE1CurrentEntry
             ACCESS  not-accessible
             STATUS  mandatory
	     --DEFAULT test-function    acee1-test
             --DEFAULT next-function    acee1-next

            ::= { ncm-generic 1010 }
 
 
       ncmE1CurrentEntry OBJECT-TYPE
             SYNTAX  NcmE1CurrentEntry
             ACCESS  not-accessible
             STATUS  mandatory
             DESCRIPTION
                "An entry in the ncm E1 Current table."
            INDEX   { ncmE1CurrentNIDIndex, ncmE1CurrentIndex, ncmE1CurrentEndType }
            ::= { ncmE1CurrentTable 1 }
 
 
       NcmE1CurrentEntry ::=
           SEQUENCE {
           ncmE1CurrentNIDIndex
                 INTEGER,
           ncmE1CurrentIndex
                 INTEGER,
           ncmE1CurrentEndType
                 INTEGER,
           ncmE1CRC4Status
                INTEGER,
           ncmE1Timestamp
                INTEGER,
           ncmE1Timestamp1
                INTEGER,
           ncmE1CurrentIntervalSec
                INTEGER,
           ncmE1CurrentASs
                 Gauge,
           ncmE1CurrentUASs
                 Gauge,
           ncmE1CurrentESs
                 Gauge,
           ncmE1CurrentSESs
                 Gauge,
           ncmE1CurrentFAE
                 Gauge,
           ncmE1CurrentBBE
                 Gauge,
	   ncmE1CurrentSEFSs
                 Gauge,
           ncmE1CurrentAISSs
                 Gauge,
           ncmE1CurrentLOSSs
                 Gauge,
           ncmE1CurrentLOFSs
                 Gauge,
           ncmE1CurrentOOFSs
                 Gauge,
           ncmE1CurrentCVPath
                 Gauge,
           ncmE1CurrentCVLine
                 Gauge,
           ncmE1CurrentESsLine
                 Gauge,
           ncmE1CurrentSESsLine
                 Gauge,
           ncmE1CurrentFECPath
                 Gauge,
           ncmE1CurrentFECLine
                 Gauge
 
           }


	 ncmE1CurrentNIDIndex OBJECT-TYPE
             SYNTAX  INTEGER (1..'7fffffff'h)
             ACCESS  read-only
             STATUS  mandatory
             DESCRIPTION
                "This object identifies the node id of the node."
            ::= { ncmE1CurrentEntry 1 }
 
 
        ncmE1CurrentIndex OBJECT-TYPE
             SYNTAX  INTEGER (1..'7fffffff'h)
             ACCESS  read-only
             STATUS  mandatory
             DESCRIPTION
                "The index value which uniquely identifies  the
                interface  to which this entry is applicable.
                The interface identified by a  particular
                value  of  this  index is the same interf as
                identified by the same value as a LineIndex
                object instance."
            ::= { ncmE1CurrentEntry 2 }
 
 
        ncmE1CurrentEndType OBJECT-TYPE
            SYNTAX INTEGER {
                       near-End(1),
                       far-End(2)
                        }
           ACCESS read-only
           STATUS mandatory
           DESCRIPTION
           "The variable specifies the End Type."
 
            ::= { ncmE1CurrentEntry 3 }


	ncmE1CRC4Status OBJECT-TYPE
            SYNTAX INTEGER {
                       disabled(1),
                       enabled(2)
                        }
           ACCESS read-only
           STATUS mandatory
           DESCRIPTION
           "The variable specifies the CRC4 Status."
 
            ::= { ncmE1CurrentEntry 4 }
 
 
        ncmE1Timestamp OBJECT-TYPE
           SYNTAX INTEGER
           ACCESS read-only
           STATUS mandatory
           DESCRIPTION
           "The variable specifies the timestamp in seconds."
 
           ::= { ncmE1CurrentEntry 5 }
 
         ncmE1Timestamp1 OBJECT-TYPE
           SYNTAX INTEGER
           ACCESS read-only
           STATUS mandatory
           DESCRIPTION
           "The variable specifies the timestamp in milliseconds."
 
           ::= { ncmE1CurrentEntry 6 }
 
 
         ncmE1CurrentIntervalSec OBJECT-TYPE
           SYNTAX INTEGER
           ACCESS read-only
           STATUS mandatory
           DESCRIPTION
           "The variable specifies the current interval in seconds."
 
           ::= { ncmE1CurrentEntry 7 }
 
         
         ncmE1CurrentASs OBJECT-TYPE
             SYNTAX  Gauge
             ACCESS  read-only
             STATUS  mandatory
             DESCRIPTION
                "The number of Availabe Seconds, encountered by
                a DS1 interface in the current 15 minute interval."
            ::= { ncmE1CurrentEntry 8 }


	 ncmE1CurrentUASs OBJECT-TYPE
             SYNTAX  Gauge
             ACCESS  read-only
             STATUS  mandatory
             DESCRIPTION
                "The number of Out of Unavailable Seconds encountered
                by a DS1 interface in the current 15 minute interval."
            ::= { ncmE1CurrentEntry 9 }
 
 
        ncmE1CurrentESs OBJECT-TYPE
             SYNTAX  Gauge
             ACCESS  read-only
             STATUS  mandatory
             DESCRIPTION
                "The number of Errored Seconds encountered
                by a DS1 interface in the current 15 minute interval."
            ::= { ncmE1CurrentEntry 10 }
 
 
         ncmE1CurrentSESs OBJECT-TYPE
             SYNTAX  Gauge
             ACCESS  read-only
             STATUS  mandatory
             DESCRIPTION
                "The number of Severely Errored Seconds encountered
                by a DS1 interface in the current 15 minute interval."
            ::= { ncmE1CurrentEntry 11 }
 
 
        ncmE1CurrentFAE OBJECT-TYPE
             SYNTAX  Gauge
             ACCESS  read-only
             STATUS  mandatory
             DESCRIPTION
                "The number of Frame Alignment Error in Seconds
                 encountered by a DS1 interface in the current 15
                 minute interval."
            ::= { ncmE1CurrentEntry 12 }
 
 
        ncmE1CurrentBBE OBJECT-TYPE
             SYNTAX  Gauge
             ACCESS  read-only
             STATUS  mandatory
             DESCRIPTION
                "The number of Background Block Error encountered
                by a DS1 interface in the current 15 minute interval."
            ::= { ncmE1CurrentEntry 13 }


	ncmE1CurrentSEFSs OBJECT-TYPE
             SYNTAX  Gauge
             ACCESS  read-only
             STATUS  mandatory
             DESCRIPTION
                "The number of Severly Error Framing seconds encountered
                by a DS1 interface in the current 15 minute interval."
            ::= { ncmE1CurrentEntry 14 }


        ncmE1CurrentAISSs OBJECT-TYPE
             SYNTAX  Gauge
             ACCESS  read-only
             STATUS  mandatory
             DESCRIPTION
                "The number of ncmAlarm Indication Signal seconds encountered
                by a DS1 interface in the current 15 minute interval."
            ::= { ncmE1CurrentEntry 15 }

        ncmE1CurrentLOSSs OBJECT-TYPE
             SYNTAX  Gauge
             ACCESS  read-only
             STATUS  mandatory
             DESCRIPTION
                "The number of Loss of Signal seconds encountered
                by a DS1 interface in the current 15 minute interval."
            ::= { ncmE1CurrentEntry 16 }
 
 
        ncmE1CurrentLOFSs OBJECT-TYPE
             SYNTAX  Gauge
             ACCESS  read-only
             STATUS  mandatory
             DESCRIPTION
                "The number of Loss of Signal seconds encountered
                by a DS1 interface in the current 15 minute interval."
            ::= { ncmE1CurrentEntry 17 }
 
 
        ncmE1CurrentOOFSs OBJECT-TYPE
             SYNTAX  Gauge
             ACCESS  read-only
             STATUS  mandatory
             DESCRIPTION
                "The number of Out Of Frame seconds encountered
                by a DS1 interface in the current 15 minute interval."
            ::= { ncmE1CurrentEntry 18 }
 
        ncmE1CurrentCVPath OBJECT-TYPE
             SYNTAX  Gauge
             ACCESS  read-only
             STATUS  mandatory
             DESCRIPTION
                "The number of Code Violation Path encountered
                by a DS1 interface in the current 15 minute interval."
            ::= { ncmE1CurrentEntry 19 }

 
	ncmE1CurrentCVLine OBJECT-TYPE
             SYNTAX  Gauge
             ACCESS  read-only
             STATUS  mandatory
             DESCRIPTION
                "The number of Code Violation Line encountered
                by a DS1 interface in the current 15 minute interval."
            ::= { ncmE1CurrentEntry 20 }
 
 
        ncmE1CurrentESsLine OBJECT-TYPE
             SYNTAX  Gauge
             ACCESS  read-only
             STATUS  mandatory
             DESCRIPTION
                "The number of Errored Seconds Line encountered
                by a DS1 interface in the current 15 minute interval."
            ::= { ncmE1CurrentEntry 21 }
 
        ncmE1CurrentSESsLine OBJECT-TYPE
             SYNTAX  Gauge
             ACCESS  read-only
             STATUS  mandatory
             DESCRIPTION
                "The number of Severely Errored Seconds Line encountered
                by a DS1 interface in the current 15 minute interval."
            ::= { ncmE1CurrentEntry 22 }
 
 
 
        ncmE1CurrentFECPath OBJECT-TYPE
             SYNTAX  Gauge
             ACCESS  read-only
             STATUS  mandatory
             DESCRIPTION
                "The number of Failure Event Count Path encountered
                by a DS1 interface in the current 15 minute interval."
            ::= { ncmE1CurrentEntry 23 }
 
 
 
        ncmE1CurrentFECLine OBJECT-TYPE
             SYNTAX  Gauge
             ACCESS  read-only
             STATUS  mandatory
             DESCRIPTION
                "The number of Failure Event Count Line encountered
                by a DS1 interface in the current 15 minute interval."
            ::= { ncmE1CurrentEntry 24 }


--	ncm E1 Performance Monitor Interval Table

     -- The ncm Interval Table contains various statistics
     -- collected by each DS1 Interface over the previous 24 hours of
     -- operation.  The past 24 hours are broken into 96 completed
     -- 15 minute intervals.

     
       	ncmE1IntervalTable OBJECT-TYPE
	     SYNTAX  SEQUENCE OF NcmE1IntervalEntry
	     ACCESS  not-accessible
	     STATUS  mandatory
	     --DEFAULT test-function   ace-e1-interval-test 
             --DEFAULT next-function    acee1interval-next

	    ::= { ncm-generic 1011 }


       	ncmE1IntervalEntry OBJECT-TYPE
	     SYNTAX  NcmE1IntervalEntry
	     ACCESS  not-accessible
	     STATUS  mandatory
	     DESCRIPTION
		"An entry in the  E1 Interval table."
	    INDEX   { ncmE1IntervalNIDIndex, ncmE1IntervalIndex, ncmE1IntervalEndType, ncmE1IntervalNumber }
	    ::= { ncmE1IntervalTable 1 }


     	 NcmE1IntervalEntry ::=
	 SEQUENCE {
           ncmE1IntervalNIDIndex
                  INTEGER,
	   ncmE1IntervalIndex
		 INTEGER,
	   ncmE1IntervalEndType
		 INTEGER,
	   ncmE1IntervalNumber
		 INTEGER,
	   ncmE1IntervalASs
		 Gauge,
	   ncmE1IntervalUASs
		 Gauge,
	   ncmE1IntervalESs
		 Gauge,
	   ncmE1IntervalSESs
		 Gauge,
	   ncmE1IntervalFAE
		 Gauge,
	   ncmE1IntervalBBE
		 Gauge,
	   ncmE1IntervalSEFSs
                 Gauge,
           ncmE1IntervalAISSs
                 Gauge,
           ncmE1IntervalLOSSs
                 Gauge,
           ncmE1IntervalLOFSs
                 Gauge,
           ncmE1IntervalOOFSs
                 Gauge,
           ncmE1IntervalCVPath
                 Gauge,
           ncmE1IntervalCVLine
                 Gauge,
           ncmE1IntervalESsLine
                 Gauge,
           ncmE1IntervalSESsLine
                 Gauge,
           ncmE1IntervalFECPath
                 Gauge,
           ncmE1IntervalFECLine
                 Gauge
			     
	 }

        ncmE1IntervalNIDIndex OBJECT-TYPE
             SYNTAX  INTEGER (1..'7fffffff'h)
             ACCESS  read-only
             STATUS  mandatory
             DESCRIPTION
                "The object specifies the node id index."
            ::= { ncmE1IntervalEntry 1 }
 

	 ncmE1IntervalIndex OBJECT-TYPE
	     SYNTAX  INTEGER (1..'7fffffff'h)
	     ACCESS  read-only
	     STATUS  mandatory
	     DESCRIPTION
		"The index value which uniquely identifies the
		DS1 interface to which this entry is applicable.
		The interface identified by a particular
		value of this index is the same interface as
		identified by the same value as a LineIndex
		object instance."
	    ::= { ncmE1IntervalEntry 2 }


          ncmE1IntervalEndType OBJECT-TYPE
            SYNTAX INTEGER {
                       near-End(1),
                       far-End(2)
                        }
           ACCESS read-only
           STATUS mandatory
           DESCRIPTION
           "The variable specifies the End Type."
 
          ::= { ncmE1IntervalEntry 3 }
 

        ncmE1IntervalNumber OBJECT-TYPE
             SYNTAX  INTEGER (1..96)
             ACCESS  read-only
             STATUS  mandatory
             DESCRIPTION
                "A number between 1 and 96, where 1 is the most
                recently completed 15 minute interval and 96 is
                the least recently completed 15 minutes interval
                (assuming that all 96 intervals are valid)."
            ::= { ncmE1IntervalEntry 4 }
 

    	  ncmE1IntervalASs OBJECT-TYPE
	     SYNTAX  Gauge
	     ACCESS  read-only
	     STATUS  mandatory
	     DESCRIPTION
		"The number of Available Seconds encountered by a
		DS1 interface in one of the previous 96, individual
		15 minute, intervals."
	    ::= { ncmE1IntervalEntry 5 }



     	 ncmE1IntervalUASs OBJECT-TYPE
	     SYNTAX  Gauge
	     ACCESS  read-only
	     STATUS  mandatory
	     DESCRIPTION
		"The number of Unavailable Seconds encountered
		by a DS1 interface in one of the previous
		96, individual 15 minute, intervals."
	    ::= { ncmE1IntervalEntry 6 }


     	 ncmE1IntervalESs OBJECT-TYPE
	     SYNTAX  Gauge
	     ACCESS  read-only
	     STATUS  mandatory
	     DESCRIPTION
		"The number of Error Seconds encountered
		by a DS1 interface in one of the previous
		96, individual 15 minute, intervals."
	    ::= { ncmE1IntervalEntry 7 }


     	 ncmE1IntervalSESs OBJECT-TYPE
	     SYNTAX  Gauge
	     ACCESS  read-only
	     STATUS  mandatory
	     DESCRIPTION
		"The number of Severe Error Seconds encountered
		by a DS1 interface in one of the previous
		96, individual 15 minute, intervals."
	    ::= { ncmE1IntervalEntry 8 }



    	
	  ncmE1IntervalFAE OBJECT-TYPE
	     SYNTAX  Gauge
	     ACCESS  read-only
	     STATUS  mandatory
	     DESCRIPTION
		"The number of Frame Alignment Errors encoun-
		tered by a DS1 interface in one of the previous
		96, individual 15 minute, intervals."
	    ::= { ncmE1IntervalEntry 9 }


		
    	  ncmE1IntervalBBE OBJECT-TYPE
	     SYNTAX  Gauge
	     ACCESS  read-only
	     STATUS  mandatory
	     DESCRIPTION
		"The number of Background Block Errors encoun-
		tered by a DS1 interface in one of the previous
		96, individual 15 minute, intervals."
	    ::= { ncmE1IntervalEntry 10 }


	 ncmE1IntervalSEFSs OBJECT-TYPE
             SYNTAX  Gauge
             ACCESS  read-only
             STATUS  mandatory
             DESCRIPTION
                "The number of Severly Error Framing seconds  encountered
                by a DS1 interface in one of the previous
                96, individual 15 minute, intervals."
            ::= { ncmE1IntervalEntry 11 }


        ncmE1IntervalAISSs OBJECT-TYPE
             SYNTAX  Gauge
             ACCESS  read-only
             STATUS  mandatory
             DESCRIPTION
                "The number of ncmAlarm Indication Signal seconds  encountered
                by a DS1 interface in one of the previous
                96, individual 15 minute, intervals."
            ::= { ncmE1IntervalEntry 12 }

        ncmE1IntervalLOSSs OBJECT-TYPE
             SYNTAX  Gauge
             ACCESS  read-only
             STATUS  mandatory
             DESCRIPTION
                "The number of Loss of Signal seconds  encountered
                by a DS1 interface in one of the previous
                96, individual 15 minute, intervals."
            ::= { ncmE1IntervalEntry 13 }
               
 
        ncmE1IntervalLOFSs OBJECT-TYPE
             SYNTAX  Gauge
             ACCESS  read-only
             STATUS  mandatory
             DESCRIPTION
                "The number of Loss of Signal seconds  encountered
                by a DS1 interface in one of the previous
                96, individual 15 minute, intervals."
            ::= { ncmE1IntervalEntry 14 }
               
 
        ncmE1IntervalOOFSs OBJECT-TYPE
             SYNTAX  Gauge
             ACCESS  read-only
             STATUS  mandatory
             DESCRIPTION
                "The number of Out Of Frame seconds  encountered
                by a DS1 interface in one of the previous
                96, individual 15 minute, intervals."
            ::= { ncmE1IntervalEntry 15 }
               
        ncmE1IntervalCVPath OBJECT-TYPE
             SYNTAX  Gauge
             ACCESS  read-only
             STATUS  mandatory
             DESCRIPTION
                "The number of Code Violation Path encountered
                by a DS1 interface in one of the previous
                96, individual 15 minute, intervals.
		This object only has significance for QUAD cards."
            ::= { ncmE1IntervalEntry 16 }


	 ncmE1IntervalCVLine OBJECT-TYPE
             SYNTAX  Gauge
             ACCESS  read-only
             STATUS  mandatory
             DESCRIPTION
                "The number of Code Violation Line encountered
                by a DS1 interface in one of the previous
                96, individual 15 minute, intervals.
		This object only has significance for QUAD cards."
            ::= { ncmE1IntervalEntry 17 }
               
 
        ncmE1IntervalESsLine OBJECT-TYPE
             SYNTAX  Gauge
             ACCESS  read-only
             STATUS  mandatory
             DESCRIPTION
                "The number of Errored Seconds Line encountered
                by a DS1 interface in one of the previous
                96, individual 15 minute, intervals."
            ::= { ncmE1IntervalEntry 18 }
               
        ncmE1IntervalSESsLine OBJECT-TYPE
             SYNTAX  Gauge
             ACCESS  read-only
             STATUS  mandatory
             DESCRIPTION
                "The number of Severely Errored Seconds Line encountered
                by a DS1 interface in one of the previous
                96, individual 15 minute, intervals."
            ::= { ncmE1IntervalEntry 19 }
               
 
 
        ncmE1IntervalFECPath OBJECT-TYPE
             SYNTAX  Gauge
             ACCESS  read-only
             STATUS  mandatory
             DESCRIPTION
                "The number of Failure Event Count Path encountered
                by a DS1 interface in one of the previous
                96, individual 15 minute, intervals."
            ::= { ncmE1IntervalEntry 20 }
               
 
 
        ncmE1IntervalFECLine OBJECT-TYPE
             SYNTAX  Gauge
             ACCESS  read-only
             STATUS  mandatory
             DESCRIPTION
                "The number of Failure Event Count Line encountered
                by a DS1 interface in one of the previous
                96, individual 15 minute, intervals."
            ::= { ncmE1IntervalEntry 21 }


  

	--    ncm  E1 Total Group 24 hour Interval
 
         ncmE1TotalTable OBJECT-TYPE
             SYNTAX  SEQUENCE OF NcmE1TotalEntry
             ACCESS  not-accessible
             STATUS  mandatory
	     --DEFAULT test-function    acee1-test
             --DEFAULT next-function    acee1-next

            ::= { ncm-generic 1012 }
 
 
         ncmE1TotalEntry OBJECT-TYPE
             SYNTAX  NcmE1TotalEntry
             ACCESS  not-accessible
             STATUS  mandatory
             DESCRIPTION
                "An entry in the  Total Entry table."
            INDEX   { ncmE1TotalNIDIndex, ncmE1TotalIndex, ncmE1TotalEndType }
            ::= { ncmE1TotalTable 1 }
 
 
 
 
         NcmE1TotalEntry ::=
         SEQUENCE {
           ncmE1TotalNIDIndex
                INTEGER,
           ncmE1TotalIndex
                 INTEGER,
	   ncmE1TotalEndType
		 INTEGER,
	   ncmE1NumberOfValidInterval
		INTEGER,
           ncmE1TotalASs
                 Gauge,
           ncmE1TotalUASs
                 Gauge,
           ncmE1TotalESs
                 Gauge,
           ncmE1TotalSESs
                 Gauge,
           ncmE1TotalFAE
                 Gauge,
           ncmE1TotalBBE
                 Gauge,
	   ncmE1TotalSEFSs
                 Gauge,
           ncmE1TotalAISSs
                 Gauge,
           ncmE1TotalLOSSs
                 Gauge,
           ncmE1TotalLOFSs
                 Gauge,
           ncmE1TotalOOFSs
                 Gauge,
           ncmE1TotalCVPath
                 Gauge,
           ncmE1TotalCVLine
                 Gauge,
           ncmE1TotalESsLine
                 Gauge,
           ncmE1TotalSESsLine
                 Gauge,
           ncmE1TotalFECPath
                 Gauge,
           ncmE1TotalFECLine
                 Gauge

                         
             }
 
        ncmE1TotalNIDIndex OBJECT-TYPE
             SYNTAX  INTEGER (1..'7fffffff'h)
             ACCESS  read-only
             STATUS  mandatory
             DESCRIPTION
                "The object specifies the node id index of the node."
            ::= { ncmE1TotalEntry 1 }
 


	 ncmE1TotalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interf as
                identified by the same value as a LineIndex
                object instance."
            ::= { ncmE1TotalEntry 2 }
 

          ncmE1TotalEndType OBJECT-TYPE
            SYNTAX INTEGER {
 
                       near-End(1),
                       far-End(2)
 
                        }
           ACCESS read-only
           STATUS mandatory
           DESCRIPTION
           "The variable specifies the End Type."
 
          ::= { ncmE1TotalEntry 3 }
 
        
        ncmE1NumberOfValidInterval OBJECT-TYPE
           SYNTAX INTEGER
           ACCESS read-only
           STATUS mandatory
           DESCRIPTION
                "The number of  previous  intervals  for  which
                valid data was collected.  The value will be 96
                unless the interface was brought on-line within
                the last 24 hours, in which case the value will
                be the number of complete 15  minute  intervals
               the since interface has been online."

          ::= { ncmE1TotalEntry 4 }

 
         ncmE1TotalASs OBJECT-TYPE
             SYNTAX  Gauge
             ACCESS  read-only
             STATUS  mandatory
             DESCRIPTION
                "The number of Available Seconds encountered by a
                DS1 interface in the previous 24 hour interval."
                  
            ::= { ncmE1TotalEntry 5 }
 
 
         ncmE1TotalUASs OBJECT-TYPE
             SYNTAX  Gauge
             ACCESS  read-only
             STATUS  mandatory
             DESCRIPTION
                "The number of Unavailable Seconds  encoun-
                tered  by  a  DS1  interface in the previous 24
                hour interval."
            ::= { ncmE1TotalEntry 6 }
 
         
         ncmE1TotalESs OBJECT-TYPE
             SYNTAX  Gauge
             ACCESS  read-only
             STATUS  mandatory
             DESCRIPTION
                "The number of Error Seconds   encoun-
                tered  by  a  DS1  interface in the previous 24
                hour interval."
            ::= { ncmE1TotalEntry 7 }
 
  
           ncmE1TotalSESs OBJECT-TYPE
             SYNTAX  Gauge
             ACCESS  read-only
             STATUS  mandatory
             DESCRIPTION
                "The number of Severly Errored Seconds  encoun-
                tered  by  a  DS1  interface in the previous 24
                hour interval."
            ::= { ncmE1TotalEntry 8 }


	 ncmE1TotalFAE OBJECT-TYPE
             SYNTAX  Gauge
             ACCESS  read-only
             STATUS  mandatory
             DESCRIPTION
                "The number of Frame Alignment Signal errors  encoun-
                tered  by  a  DS1  interface in the previous 24
                hour interval."
            ::= { ncmE1TotalEntry 9 }
 
         
        ncmE1TotalBBE OBJECT-TYPE
             SYNTAX  Gauge
             ACCESS  read-only
             STATUS  mandatory
             DESCRIPTION
                "The number of Background Block Errors  encoun-
                tered  by  a  DS1  interface in the previous 24
                hour interval."
            ::= { ncmE1TotalEntry 10 }

	 ncmE1TotalSEFSs OBJECT-TYPE
             SYNTAX  Gauge
             ACCESS  read-only
             STATUS  mandatory
             DESCRIPTION
                "The number of Severly Error Framing seconds  encountered
                by a DS1 interface in 24 hour in-
                terval."
            ::= { ncmE1TotalEntry 11 }


        ncmE1TotalAISSs OBJECT-TYPE
             SYNTAX  Gauge
             ACCESS  read-only
             STATUS  mandatory
             DESCRIPTION
                "The number of ncmAlarm Indication Signal seconds  encountered
                by a DS1 interface in the 24 hour in-
                terval."
            ::= { ncmE1TotalEntry 12 }

        ncmE1TotalLOSSs OBJECT-TYPE
             SYNTAX  Gauge
             ACCESS  read-only
             STATUS  mandatory
             DESCRIPTION
                "The number of Loss of Signal seconds  encountered
                by a DS1 interface in the 24 hour in-
                terval."
            ::= { ncmE1TotalEntry 13 }
 
 
        ncmE1TotalLOFSs OBJECT-TYPE
             SYNTAX  Gauge
             ACCESS  read-only
             STATUS  mandatory
             DESCRIPTION
                "The number of Loss of Signal seconds  encountered
                by a DS1 interface in the 24 hour in-
                terval."
            ::= { ncmE1TotalEntry 14 }
 
 
        ncmE1TotalOOFSs OBJECT-TYPE
             SYNTAX  Gauge
             ACCESS  read-only
             STATUS  mandatory
             DESCRIPTION
                "The number of Out Of Frame seconds  encountered
                by a DS1 interface in the 24 hour in-
                terval."
            ::= { ncmE1TotalEntry 15 }
 
 
        ncmE1TotalCVPath OBJECT-TYPE
             SYNTAX  Gauge
             ACCESS  read-only
             STATUS  mandatory
             DESCRIPTION
                "The number of Code Violation Path encountered
                by a DS1 interface in the 24 hour in-
                terval."
            ::= { ncmE1TotalEntry 16 }

	ncmE1TotalCVLine OBJECT-TYPE
             SYNTAX  Gauge
             ACCESS  read-only
             STATUS  mandatory
             DESCRIPTION
                "The number of Code Violation Line encountered
                by a DS1 interface in the 24 hour in-
                terval."
            ::= { ncmE1TotalEntry 17 }
 
 
        ncmE1TotalESsLine OBJECT-TYPE
             SYNTAX  Gauge
             ACCESS  read-only
             STATUS  mandatory
             DESCRIPTION
                "The number of Errored Seconds Line encountered
                by a DS1 interface in the 24 hour in-
                terval."
            ::= { ncmE1TotalEntry 18 }
 
        ncmE1TotalSESsLine OBJECT-TYPE
             SYNTAX  Gauge
             ACCESS  read-only
             STATUS  mandatory
             DESCRIPTION
                "The number of Severely Errored Seconds Line encountered
                by a DS1 interface in the 24 hour in-
                terval."
            ::= { ncmE1TotalEntry 19 }
 
 
 
        ncmE1TotalFECPath OBJECT-TYPE
             SYNTAX  Gauge
             ACCESS  read-only
             STATUS  mandatory
             DESCRIPTION
                "The number of Failure Event Count Path encountered
                by a DS1 interface in the 24 hour in-
                terval."
            ::= { ncmE1TotalEntry 20 }
 
 
         ncmE1TotalFECLine OBJECT-TYPE
             SYNTAX  Gauge
             ACCESS  read-only
             STATUS  mandatory
             DESCRIPTION
                "The number of Failure Event Count Line encountered
                by a DS1 interface in the 24 hour in-
                terval."
            ::= { ncmE1TotalEntry 21 }

 
 
--      The ncm  E1 Previous Total Group 24 hour Interval
 
        ncmE1PrevTotalTable OBJECT-TYPE
             SYNTAX  SEQUENCE OF NcmE1PrevTotalEntry
             ACCESS  not-accessible
             STATUS  mandatory
	     --DEFAULT test-function    acee1-test
             --DEFAULT next-function    acee1-next

            ::= { ncm-generic 1013 }
 
 
         ncmE1PrevTotalEntry OBJECT-TYPE
             SYNTAX  NcmE1PrevTotalEntry
             ACCESS  not-accessible
             STATUS  mandatory
             DESCRIPTION
                "An entry in the  Previous day total  table."
            INDEX   { ncmE1PrevTotalNIDIndex, ncmE1PrevTotalIndex, ncmE1PrevTotalEndType }
            ::= { ncmE1PrevTotalTable 1 }
 
 
        NcmE1PrevTotalEntry ::=
         SEQUENCE {
           ncmE1PrevTotalNIDIndex
                 INTEGER,
           ncmE1PrevTotalIndex
                 INTEGER,
	   ncmE1PrevTotalEndType
		 INTEGER,
           ncmE1PrevTotalASs
                 Gauge,
           ncmE1PrevTotalUASs
                 Gauge,
           ncmE1PrevTotalESs
                 Gauge,
           ncmE1PrevTotalSESs
                 Gauge,
           ncmE1PrevTotalFAE
                 Gauge,
           ncmE1PrevTotalBBE
                 Gauge,
	   ncmE1PrevTotalSEFSs
                 Gauge,
           ncmE1PrevTotalAISSs
                 Gauge,
           ncmE1PrevTotalLOSSs
                 Gauge,
           ncmE1PrevTotalLOFSs
                 Gauge,
           ncmE1PrevTotalOOFSs
                 Gauge,
           ncmE1PrevTotalCVPath
                 Gauge,
           ncmE1PrevTotalCVLine
                 Gauge,
           ncmE1PrevTotalESsLine
                 Gauge,
           ncmE1PrevTotalSESsLine
                 Gauge,
           ncmE1PrevTotalFECPath
                 Gauge,
           ncmE1PrevTotalFECLine
                 Gauge

                  
	}
 
         ncmE1PrevTotalNIDIndex OBJECT-TYPE
             SYNTAX  INTEGER (1..'7fffffff'h)
             ACCESS  read-only
             STATUS  mandatory
             DESCRIPTION
                "The object specifies the node id index of the node."
            ::= { ncmE1PrevTotalEntry 1 }
 
 
         ncmE1PrevTotalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interf as
                identified by the same value as a LineIndex
                object instance."
            ::= { ncmE1PrevTotalEntry 2 }
 
 
          ncmE1PrevTotalEndType OBJECT-TYPE
            SYNTAX INTEGER {

                       near-End(1),
                       far-End(2)

                        }
           ACCESS read-only
           STATUS mandatory
           DESCRIPTION
           "The variable specifies the End Type  ."

          ::= { ncmE1PrevTotalEntry 3 }

         
         ncmE1PrevTotalASs OBJECT-TYPE
             SYNTAX  Gauge
              ACCESS  read-only
             STATUS  mandatory
             DESCRIPTION
                "The number of Available Seconds encountered by a
                DS1 interface in the previous 24 hour interval."
                  
            ::= { ncmE1PrevTotalEntry 4 }
 
 
        ncmE1PrevTotalUASs OBJECT-TYPE
             SYNTAX  Gauge
             ACCESS  read-only
             STATUS  mandatory
             DESCRIPTION
                "The number of Unavailable Seconds  encoun-
                tered  by  a  DS1  interface in the previous 24
                hour interval."
            ::= { ncmE1PrevTotalEntry 5 }
 
 
        ncmE1PrevTotalESs OBJECT-TYPE
             SYNTAX  Gauge
             ACCESS  read-only
             STATUS  mandatory
             DESCRIPTION
                "The number of Error Seconds  encoun-
                tered  by  a  DS1  interface in the previous 24
                hour interval."
            ::= { ncmE1PrevTotalEntry 6 }

	 ncmE1PrevTotalSESs OBJECT-TYPE
             SYNTAX  Gauge
             ACCESS  read-only
             STATUS  mandatory
             DESCRIPTION
                "The number of Severly Errored Seconds  encoun-
                tered  by  a  DS1  interface in the previous 24
                hour interval."
            ::= { ncmE1PrevTotalEntry 7 }
 
 
         ncmE1PrevTotalFAE OBJECT-TYPE
             SYNTAX  Gauge
             ACCESS  read-only
             STATUS  mandatory
             DESCRIPTION
                "The number of Frame Alignment Signal errors  encoun-
                tered  by  a  DS1  interface in the previous 24
                hour interval."
            ::= { ncmE1PrevTotalEntry 8 }
 
         
         ncmE1PrevTotalBBE OBJECT-TYPE
             SYNTAX  Gauge
             ACCESS  read-only
             STATUS  mandatory
             DESCRIPTION
                "The number of Background Block Errors  encoun-
                tered  by  a  DS1  interface in the previous 24
                hour interval."
            ::= { ncmE1PrevTotalEntry 9 }

	
	ncmE1PrevTotalSEFSs OBJECT-TYPE
             SYNTAX  Gauge
             ACCESS  read-only
             STATUS  mandatory
             DESCRIPTION
                "The number of Severly Error Framing seconds  encountered
                by a DS1 interface in the prev 24 hour in-
                terval."
            ::= { ncmE1PrevTotalEntry 10 }


        ncmE1PrevTotalAISSs OBJECT-TYPE
             SYNTAX  Gauge
             ACCESS  read-only
             STATUS  mandatory
             DESCRIPTION
                "The number of ncmAlarm Indication Signal seconds  encountered
                by a DS1 interface in the prev 24 hour in-
                terval."
            ::= { ncmE1PrevTotalEntry 11 }

        ncmE1PrevTotalLOSSs OBJECT-TYPE
             SYNTAX  Gauge
             ACCESS  read-only
             STATUS  mandatory
             DESCRIPTION
                "The number of Loss of Signal seconds  encountered
                by a DS1 interface in the prev 24 hour in-
                terval."
            ::= { ncmE1PrevTotalEntry 12 }
             
 
        ncmE1PrevTotalLOFSs OBJECT-TYPE
             SYNTAX  Gauge
             ACCESS  read-only
             STATUS  mandatory
             DESCRIPTION
                "The number of Loss of Signal seconds  encountered
                by a DS1 interface in the prev 24 hour in-
                terval."
            ::= { ncmE1PrevTotalEntry 13 }
 
 
        ncmE1PrevTotalOOFSs OBJECT-TYPE
             SYNTAX  Gauge
             ACCESS  read-only
             STATUS  mandatory
             DESCRIPTION
                "The number of Out Of Frame seconds  encountered
                by a DS1 interface in the prev 24 hour in-
                terval."
            ::= { ncmE1PrevTotalEntry 14 }
 
 
         ncmE1PrevTotalCVPath OBJECT-TYPE
             SYNTAX  Gauge
             ACCESS  read-only
             STATUS  mandatory
             DESCRIPTION
                "The number of Code Violation Path encountered
                by a DS1 interface in the prev 24 hour in-
                terval."
            ::= { ncmE1PrevTotalEntry 15 }


	ncmE1PrevTotalCVLine OBJECT-TYPE
             SYNTAX  Gauge
             ACCESS  read-only
             STATUS  mandatory
             DESCRIPTION
                "The number of Code Violation Line encountered
                by a DS1 interface in the prev 24 hour in-
                terval."
            ::= { ncmE1PrevTotalEntry 16 }
 
 
        ncmE1PrevTotalESsLine OBJECT-TYPE
             SYNTAX  Gauge
             ACCESS  read-only
             STATUS  mandatory
             DESCRIPTION
                "The number of Errored Seconds Line encountered
                by a DS1 interface in the prev 24 hour in-
                terval."
            ::= { ncmE1PrevTotalEntry 17 }
 
        ncmE1PrevTotalSESsLine OBJECT-TYPE
             SYNTAX  Gauge
             ACCESS  read-only
             STATUS  mandatory
             DESCRIPTION
                "The number of Severely Errored Seconds Line encountered
                by a DS1 interface in the prev 24 hour in-
                terval."
            ::= { ncmE1PrevTotalEntry 18 }
 
 
 
        ncmE1PrevTotalFECPath OBJECT-TYPE
             SYNTAX  Gauge
             ACCESS  read-only
             STATUS  mandatory
             DESCRIPTION
                "The number of Failure Event Count Path encountered
                by a DS1 interface in the prev 24 hour in-
                terval."
            ::= { ncmE1PrevTotalEntry 19 }
 
 
        ncmE1PrevTotalFECLine OBJECT-TYPE
             SYNTAX  Gauge
             ACCESS  read-only
             STATUS  mandatory
             DESCRIPTION
                "The number of Failure Event Count Line encountered
                by a DS1 interface in the prev 24 hour in-
                terval."
            ::= { ncmE1PrevTotalEntry 20 }
 


	--   ncm  E1 24 Hour Performance Snap Shot
 
 
         ncmE1PerformanceSnapShotTable OBJECT-TYPE
             SYNTAX  SEQUENCE OF  NcmE1PerformanceSnapShotEntry
             ACCESS  not-accessible
             STATUS  mandatory
	     --DEFAULT test-function    acee1-test
             --DEFAULT next-function    acee1-next

            ::= { ncm-generic 1014 }
 
 
         ncmE1PerformanceSnapShotEntry OBJECT-TYPE
             SYNTAX    NcmE1PerformanceSnapShotEntry
             ACCESS  not-accessible
             STATUS  mandatory
             DESCRIPTION
             "An entry in the  E1 Performance Snap Shot Entry table."
             INDEX   { ncmE1SnapShotNIDIndex,ncmE1SnapShotIndex,   ncmE1SnapShotEndType }
            ::= { ncmE1PerformanceSnapShotTable 1 }
 
 
        NcmE1PerformanceSnapShotEntry ::=
         SEQUENCE {
           ncmE1SnapShotNIDIndex
                INTEGER,
           ncmE1SnapShotIndex
                 INTEGER,
	   ncmE1SnapShotEndType
		 INTEGER,
           ncmE1SnapShot
                INTEGER,
           ncmE1TimeStampSec
                INTEGER,
           ncmE1TimeMilliSec
                 INTEGER,
           ncmE1SecInCurrInterval
                INTEGER,
           ncmE1ResetPerfReg
                INTEGER
                } 
                  
        
        ncmE1SnapShotNIDIndex OBJECT-TYPE
             SYNTAX  INTEGER (1..'7fffffff'h)
             ACCESS  read-only
             STATUS  mandatory
             DESCRIPTION
                "The object specifies the node id index of the node."
            ::= { ncmE1PerformanceSnapShotEntry 1 }
 
 
        ncmE1SnapShotIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a LineIndex
                object instance."
            ::= { ncmE1PerformanceSnapShotEntry 2 }


          ncmE1SnapShotEndType OBJECT-TYPE
            SYNTAX INTEGER {
 
                       near-End(1),
                       far-End(2)
 
                        }
           ACCESS read-only
           STATUS mandatory
           DESCRIPTION
           "The variable specifies the End Type  ."
 
          ::= { ncmE1PerformanceSnapShotEntry 3 }
  

	ncmE1SnapShot OBJECT-TYPE
            SYNTAX INTEGER {
 
                        no(1),
                        yes(2)
                               } 
           ACCESS read-write
            STATUS mandatory
           DESCRIPTION
           "The variable specifies the option to intiate snap shot
               command."
            ::= { ncmE1PerformanceSnapShotEntry 4 }
 
 
        ncmE1TimeStampSec OBJECT-TYPE
           SYNTAX INTEGER
           ACCESS read-only
           STATUS mandatory
           DESCRIPTION
           "The variable specifies the Time Stamp in Seconds ."
 
           ::= { ncmE1PerformanceSnapShotEntry 5 }
 
 
 
         ncmE1TimeMilliSec OBJECT-TYPE
            SYNTAX INTEGER
           ACCESS read-only
           STATUS mandatory
           DESCRIPTION
           "The variable specifies the Time Stamp in milli  Seconds ."
 
           ::= { ncmE1PerformanceSnapShotEntry  6 }
 
 
 
        ncmE1SecInCurrInterval OBJECT-TYPE
            SYNTAX INTEGER
           ACCESS read-only
           STATUS mandatory
           DESCRIPTION
           "The variable specifies the Seconds in the Current Interval."
 
           ::= { ncmE1PerformanceSnapShotEntry  7 }

 
         ncmE1ResetPerfReg OBJECT-TYPE
             SYNTAX  INTEGER {
                         no(1),
                         yes(2)
                     }
             ACCESS  read-write
             STATUS  mandatory
             DESCRIPTION
                "Reset Performance Monitoring registers."
            ::= { ncmE1PerformanceSnapShotEntry 8 }
 
 
 	--    ncm   E1 Port Latched Status
 
 
         ncmE1PortLatchedStatusTable OBJECT-TYPE
          SYNTAX  SEQUENCE OF NcmE1PortLatchedStatusEntry
          ACCESS  not-accessible
          STATUS  mandatory
	  --DEFAULT test-function    acee1-test
          --DEFAULT next-function    acee1-next

          ::= { ncm-generic 1015 }
 
 
         ncmE1PortLatchedStatusEntry OBJECT-TYPE
          SYNTAX  NcmE1PortLatchedStatusEntry
          ACCESS  not-accessible
          STATUS  mandatory
          DESCRIPTION
          "An entry in the  ncm E1 Port Latched Status Table."
          INDEX   { ncmE1PortLatchedStatusNIDIndex, ncmE1PortLatchedStatusIndex }
          ::= { ncmE1PortLatchedStatusTable 1 }
 
        NcmE1PortLatchedStatusEntry ::=
         SEQUENCE {
           ncmE1PortLatchedStatusNIDIndex
                 INTEGER,
           ncmE1PortLatchedStatusIndex
                 INTEGER,
           ncmE1PortLatchedCRC4Error
                INTEGER,
           ncmE1PortLatchedFramingSlip
                INTEGER,
           ncmE1PortLatchedRAI
                INTEGER,
           ncmE1PortLatchedLOFA
                INTEGER,
           ncmE1PortLatchedAIS
                INTEGER,
           ncmE1PortLatchedLOS
                INTEGER,
           ncmE1PortLatchedBPVThresholdExceeded
                INTEGER
                } 
                  
 
         ncmE1PortLatchedStatusNIDIndex OBJECT-TYPE
             SYNTAX  INTEGER (1..'7fffffff'h)
             ACCESS  read-only
             STATUS  mandatory
             DESCRIPTION
                "The object specifies the node id index of the node."
          ::= { ncmE1PortLatchedStatusEntry 1 }
 
	 ncmE1PortLatchedStatusIndex OBJECT-TYPE
          SYNTAX  INTEGER (1..'7fffffff'h)
          ACCESS  read-only
          STATUS  mandatory
          DESCRIPTION
          "The index value which uniquely identifies  the
           interface  to which this entry is applicable."
 
          ::= { ncmE1PortLatchedStatusEntry 2 }
 
 
 
        ncmE1PortLatchedCRC4Error OBJECT-TYPE
            SYNTAX INTEGER {
                                no(1),
                                yes(2)
                           }
            ACCESS  read-only
            STATUS  mandatory
            DESCRIPTION
            "This variable indicates the occurance Latched status of    CRC4
                error."
            ::= { ncmE1PortLatchedStatusEntry 3 }
 
 
 
        ncmE1PortLatchedFramingSlip OBJECT-TYPE
            SYNTAX INTEGER {
                                no(1),
                                yes(2)
                           }
            ACCESS  read-only
            STATUS  mandatory
            DESCRIPTION
            "This variable indicates the occurance Latched
                status of framing slip error."
            ::= { ncmE1PortLatchedStatusEntry 4 }
 
	ncmE1PortLatchedRAI OBJECT-TYPE
            SYNTAX INTEGER {
                                no(1),
                                yes(2)
                           }
            ACCESS  read-only
            STATUS  mandatory
            DESCRIPTION
            "This variable indicates the occurance Latched status of
             RAI."
            ::= { ncmE1PortLatchedStatusEntry 5 }
 
 
        ncmE1PortLatchedLOFA OBJECT-TYPE
            SYNTAX INTEGER {
                                no(1),
                                yes(2)
                           }
            ACCESS  read-only
            STATUS  mandatory
            DESCRIPTION
            "This variable indicates the occurance Latched status of
                 LOFA."
            ::= { ncmE1PortLatchedStatusEntry 6 }
 
 
         ncmE1PortLatchedAIS OBJECT-TYPE
            SYNTAX INTEGER {
                                no(1),
                                yes(2)
                           }
            ACCESS  read-only
            STATUS  mandatory
            DESCRIPTION
            "This variable indicates the occurance Latched
                status of  AIS."
            ::= { ncmE1PortLatchedStatusEntry 7 }
 
 
        ncmE1PortLatchedLOS OBJECT-TYPE
            SYNTAX INTEGER {
                                no(1),
                                yes(2)
                           }
            ACCESS  read-only
            STATUS  mandatory
            DESCRIPTION
            "This variable indicates the occurance Latched Status of
                 LOS."
            ::= { ncmE1PortLatchedStatusEntry 8 }
 
 
         ncmE1PortLatchedBPVThresholdExceeded OBJECT-TYPE
            SYNTAX INTEGER {
                                no(1),
                                yes(2)
                           }
            ACCESS  read-only
            STATUS  mandatory
            DESCRIPTION
            "This variable indicates whether BPV threshold is exceeded
                or not in Latched state."
            ::= { ncmE1PortLatchedStatusEntry 9 }
	

--    ncm  E1 Threshold Status Table
 
 
        ncmE1ThresholdStatusTable OBJECT-TYPE
             SYNTAX  SEQUENCE OF NcmE1ThresholdStatusEntry
             ACCESS  not-accessible
             STATUS  mandatory
	   --DEFAULT test-function    acee1-test
           --DEFAULT next-function    acee1-next

            ::= { ncm-generic 1016 }
 
 
         ncmE1ThresholdStatusEntry OBJECT-TYPE
             SYNTAX  NcmE1ThresholdStatusEntry
             ACCESS  not-accessible
             STATUS  mandatory
             DESCRIPTION
                "An entry in the  E1 Threshold Status Table."
            INDEX   { ncmE1ThresholdStatusNIDIndex, ncmE1ThresholdStatusIndex }
            ::= { ncmE1ThresholdStatusTable 1 }
 
 
 
         NcmE1ThresholdStatusEntry ::=
         SEQUENCE {
           ncmE1ThresholdStatusNIDIndex
                 INTEGER,
           ncmE1ThresholdStatusIndex
                 INTEGER,
           ncmE1CRCThreshold
                 INTEGER,
           ncmE1CRCExceeded
                 INTEGER,
           ncmE1SESThreshold
                 INTEGER,
           ncmE1SESExceeded
                 INTEGER,
           ncmE1UASThreshold
                 INTEGER,
           ncmE1UASExceeded
                 INTEGER,
           ncmE1BPVThresholdst
                 INTEGER,
           ncmE1BPVExceeded
                 INTEGER,
           ncmE1BERThreshold
                 INTEGER,
           ncmE1BERExceeded
                 INTEGER,
           ncmE1RestoreState
                 INTEGER,
	   ncmE1LineRestoreSec
		 INTEGER
 
                }
	
	 ncmE1ThresholdStatusNIDIndex OBJECT-TYPE
            SYNTAX  INTEGER (1..'7fffffff'h)
             ACCESS  read-only
             STATUS  mandatory
             DESCRIPTION
                "The object specifies the node id index of the node."
                  
            ::= { ncmE1ThresholdStatusEntry 1 }
 
         
         ncmE1ThresholdStatusIndex OBJECT-TYPE
             SYNTAX  INTEGER (1..'7fffffff'h)
             ACCESS  read-only
             STATUS  mandatory
             DESCRIPTION
                "This object is the identifier of an Interface
                on a managed device.  If there is an ifEntry
                that is directly associated with this and
                only this DS1 interface, it should have the
                same value as ifIndex.  Otherwise, the value
                exceeds ifNumber, and is a unique identifier
                following this rule: inside interfaces (e.g.,
                equipment side) with even numbers and outside
                interfaces (e.g., network side) with odd
                numbers."
            ::= { ncmE1ThresholdStatusEntry 2 }
 
 
 
        ncmE1CRCThreshold OBJECT-TYPE
            SYNTAX INTEGER
            ACCESS  read-only
            STATUS  mandatory
            DESCRIPTION
                "This variable indicates the CRC Error Threshold value ."
                  
            ::= { ncmE1ThresholdStatusEntry 3 }
 
 
 
        ncmE1CRCExceeded OBJECT-TYPE
            SYNTAX INTEGER {
                                no(1),
                                yes(2)
                            }
            ACCESS  read-only
            STATUS  mandatory
            DESCRIPTION
            "This variable indicates whether the  CRC Error has exceeded
                 the Threshold value or not."
                  
            ::= { ncmE1ThresholdStatusEntry 4 }
 
 
         ncmE1SESThreshold OBJECT-TYPE
            SYNTAX INTEGER
            ACCESS  read-only
            STATUS  mandatory
            DESCRIPTION
            "This variable indicates the SES Error Threshold value ."
 
            ::= { ncmE1ThresholdStatusEntry 5 }


	 ncmE1SESExceeded OBJECT-TYPE
            SYNTAX INTEGER {
                                no(1),
                                yes(2)
                            }
            ACCESS  read-only
            STATUS  mandatory
            DESCRIPTION
            "This variable indicates whether the  SES Error has exceeded
                the Threshold value or not."
                  
            ::= { ncmE1ThresholdStatusEntry 6 }
 
 
         
         ncmE1UASThreshold OBJECT-TYPE
            SYNTAX INTEGER
            ACCESS  read-only
            STATUS  mandatory
            DESCRIPTION
            "This variable indicates the UAS Error Threshold value ."
 
            ::= { ncmE1ThresholdStatusEntry 7 }
 
 
         ncmE1UASExceeded OBJECT-TYPE
            SYNTAX INTEGER {
                                no(1),
                                yes(2)
                            }
            ACCESS  read-only
            STATUS  mandatory
            DESCRIPTION
            "This variable indicates whether the  UAS Error has exceeded
                 the Threshold value or not."
                  
            ::= { ncmE1ThresholdStatusEntry 8 }
 
 
 
 
         ncmE1BPVThresholdst OBJECT-TYPE
            SYNTAX INTEGER
            ACCESS  read-only
            STATUS  mandatory
            DESCRIPTION
            "This variable indicates the BPV Error Threshold value ."
 
            ::= { ncmE1ThresholdStatusEntry 9 }
 
 
 
         ncmE1BPVExceeded OBJECT-TYPE
            SYNTAX INTEGER {
                                no(1),
                                yes(2)
                            }
            ACCESS  read-only
            STATUS  mandatory
            DESCRIPTION
            "This variable indicates whether the  BPV Error has exceeded
                the Threshold value or not."
		
	 ::= { ncmE1ThresholdStatusEntry 10 }
 
 
         ncmE1BERThreshold OBJECT-TYPE
            SYNTAX INTEGER
            ACCESS  read-only
            STATUS  mandatory
            DESCRIPTION
            "This variable indicates the BPV Error Threshold value ."
 
            ::= { ncmE1ThresholdStatusEntry 11 }
 
 
 
         ncmE1BERExceeded OBJECT-TYPE
            SYNTAX INTEGER {
                                no(1),
                                yes(2)
                            }
            ACCESS  read-only
            STATUS  mandatory
            DESCRIPTION
           "This variable indicates whether the  BER Error has exceeded
                the Threshold value or not."
                  
            ::= { ncmE1ThresholdStatusEntry 12 }

 
          ncmE1RestoreState OBJECT-TYPE
             SYNTAX  INTEGER {
                         out-of-servcie(1),
                         in-servcie(2),
			 disabled(3)
                     }   
             ACCESS  read-only
             STATUS  mandatory
             DESCRIPTION
             "This variable indicates the Restore State of Threshold "
 
             ::= { ncmE1ThresholdStatusEntry 13 }


         ncmE1LineRestoreSec OBJECT-TYPE
            SYNTAX INTEGER
            ACCESS  read-only
            STATUS  mandatory
            DESCRIPTION
            "This variable indicates the number of seconds until 
		the line restores."
            ::= { ncmE1ThresholdStatusEntry 14  }

 

	--   ncm T1 Port Configuration Table

 
       ncmT1ConfigTable OBJECT-TYPE
             SYNTAX  SEQUENCE OF NcmT1ConfigEntry
             ACCESS  not-accessible
             STATUS  mandatory
	     --DEFAULT test-function    ace-test
             --DEFAULT next-function    ace-next


            ::= { ncm-generic 1017 }


       ncmT1ConfigEntry OBJECT-TYPE
             SYNTAX  NcmT1ConfigEntry
             ACCESS  not-accessible
             STATUS  mandatory
             DESCRIPTION
                "An entry in the  ncm T1 Configuration table."
            INDEX   { ncmT1ConfigNIDIndex, ncmT1LineIndex }
            ::= { ncmT1ConfigTable 1 }


       NcmT1ConfigEntry ::=
         SEQUENCE {

	   ncmT1ConfigNIDIndex
		INTEGER,
           ncmT1LineIndex
                 INTEGER,
           ncmT1CRC6
                 INTEGER,
           ncmT1FramingFormat
                 INTEGER,
           ncmT1LineCoding
                 INTEGER,
	   ncmT1FramingType
		 INTEGER,
           ncmT1FDL
                 INTEGER,
           ncmT1InbandISDNEnableDisable
                 INTEGER,
           ncmT1EnableNetLoopback
                 INTEGER,
           ncmT1EnableNetOnesDensity
                INTEGER,
           ncmT1DensityPattern
                 INTEGER,
           ncmT1EnableRepeaterLpbkTimeout
                 INTEGER,
           ncmT1RepeaterLoopbackTimeout
                 INTEGER,
           ncmT1UserAlarmDeclareTime
                 INTEGER,
           ncmT1State
                 INTEGER,
           ncmT1NetworkLBOEQLIZ 
                 INTEGER,
           ncmT1TimeSlot
                DisplayString,
           ncmT1TimeSlotSelect
			INTEGER
		}

	ncmT1ConfigNIDIndex OBJECT-TYPE
             SYNTAX  INTEGER (1..'7fffffff'h)
             ACCESS  read-only
             STATUS  mandatory
             DESCRIPTION
                "This object is the identifier of the node id index."
            ::= { ncmT1ConfigEntry 1 }
 

	
 
        ncmT1LineIndex OBJECT-TYPE
             SYNTAX  INTEGER (1..'7fffffff'h)
             ACCESS  read-only
             STATUS  mandatory
             DESCRIPTION
                "This object is the identifier of an Interface
                on a managed device.  If there is an ifEntry
                that is directly associated with this and
                only this DS1 interface, it should have the
                same value as ifIndex.  Otherwise, the value
                exceeds ifNumber, and is a unique identifier
                following this rule: inside interfaces (e.g.,
                equipment side) with even numbers and outside
                interfaces (e.g., network side) with odd
                numbers."
            ::= { ncmT1ConfigEntry 2 }
 
 
         
         ncmT1CRC6  OBJECT-TYPE
             SYNTAX  INTEGER {
                         disabled(1),
                         enabled(2)
                     }
             ACCESS  read-write
             STATUS  mandatory
             DESCRIPTION
             "This variable indicates Whether CRC6 is enabled or not"
             ::= { ncmT1ConfigEntry 3 }
        
 
        ncmT1FramingFormat OBJECT-TYPE
             SYNTAX  INTEGER {
                         sF(1),
                         eSF(2)
                          }
             ACCESS  read-write
             STATUS  mandatory
             DESCRIPTION
                "This variable indicates  the  variety  of
                Line  implementing  this  circuit.  The type of
                circuit affects the number of bits  per  second
                that  the circuit can reasonably carry, as well
                as the interpretation of the  usage  and  error
                statistics.  The values, in sequence, describe:
 
                TITLE:          SPECIFICATION:
                ESF             Extended SuperFrame DS1
                SF              Super Frame"
 
         ::= { ncmT1ConfigEntry 4 }
	
	 ncmT1LineCoding OBJECT-TYPE
             SYNTAX  INTEGER {
        
                         aMI (1),
                         b8ZS (2)
                     }
             ACCESS  read-write
             STATUS  mandatory
             DESCRIPTION
                "This variable describes the  variety  of  Zero
                Code  Suppression  used  on  the link, which in
                turn affects a number of its characteristics.
 
                B8ZS refers to the use of a specified  pat-
                tern  of  normal  bits  and  bipolar violations
                which are used to replace a  sequence  of  eight
                zero bits.
 
                AMI refers to a mode wherein no  zero  code
                suppression  is  present  and the line encoding
                does not solve the problem directly.   In  this
                application, the higher layer must provide data
                which meets or exceeds the  pulse  density  re-
                quirements, such as inverting HDLC data."
 
            ::= { ncmT1ConfigEntry 5 }

 
          ncmT1FramingType OBJECT-TYPE
            SYNTAX INTEGER {
                          cAS-BR(1),
                          cAS-CC(2),
                          cCS(3)
                          }   

            ACCESS  read-write
            STATUS  mandatory
            DESCRIPTION
            "This variable indicates the framing type in this
		 T1 port, i.e., CAS-BR, CAS-CC, CCS"
            ::= { ncmT1ConfigEntry 6 }

        
         ncmT1FDL OBJECT-TYPE
             SYNTAX  INTEGER {
             disabled(1),
             enabled(2)
                     }
             ACCESS  read-write
             STATUS  mandatory
             DESCRIPTION
          "The variable specifies the Disable/Enable of the fdl State."
            ::= { ncmT1ConfigEntry 7 }
 
 
 
         ncmT1InbandISDNEnableDisable OBJECT-TYPE
             SYNTAX  INTEGER {
             	disablebothinbandisdn(1),
             	enableinband(2),
             	enableisdn(3)
                             }
             ACCESS  read-write
             STATUS  mandatory
             DESCRIPTION
             "This variable indicates the Inband, ISDN enable and disable options."
            ::= { ncmT1ConfigEntry 8 }
 
 
        ncmT1EnableNetLoopback OBJECT-TYPE
             SYNTAX  INTEGER {
                        disabled(1),
                        enabled(2)
                     }
             ACCESS  read-write
             STATUS  mandatory
             DESCRIPTION
          "The variable specifies the Disable/Enable of the Network
               intiated Loopback."

	::= { ncmT1ConfigEntry 9 }
 
 
 
 
        ncmT1EnableNetOnesDensity OBJECT-TYPE
             SYNTAX  INTEGER {
                        disabled(1),
                        enabled(2)
                     }
             ACCESS  read-write
             STATUS  mandatory
             DESCRIPTION
          "The variable specifies the Disable/Enable of the Network
               One's Density."
            ::= { ncmT1ConfigEntry 10 }
 
 
         ncmT1DensityPattern OBJECT-TYPE
            SYNTAX  INTEGER {
        
                             d80Zeros(1),
                             d15Zeros(2),
                             d12d5c80Zero(3),
                             tR-62411(4)
         
                              }
            ACCESS  read-write
            STATUS  mandatory
            DESCRIPTION
           "This variable indicates what type of density network is
            being sent on the port or line by the device. It only has
	    significance only when object ncmT1EnableNetOnesDensity is
	    enabled. The values mean :
           'D80Zeros' refers to send a request for network one's density
            of 80 zeroes density pattern.
 
           'D15Zeros' refers to send a request for network one's density
                of 15 zeroes density pattern.
 
          'D12d5c80Zero'refers to send a request for 12.5% and 80 zeroes
           network one's density pattern.
 
           'TR-62411' refers to sending a request for TR6241
            network density pattern."
           ::= { ncmT1ConfigEntry 11 }

 
	ncmT1EnableRepeaterLpbkTimeout OBJECT-TYPE
             SYNTAX  INTEGER {
                        disable(1),
                        enable(2)
                              }
             ACCESS  read-write
             STATUS  mandatory
             DESCRIPTION
             "The variable specifies whether repeater loopback is
                 enabled or not."
            ::= { ncmT1ConfigEntry 12 }
 
 
        ncmT1RepeaterLoopbackTimeout OBJECT-TYPE
             SYNTAX  INTEGER
             ACCESS  read-write
             STATUS  mandatory
             DESCRIPTION
             "The variable specifies the timeout value in seconds for
                 repeater loopback."
            ::= { ncmT1ConfigEntry 13 }
 
 
 
        ncmT1UserAlarmDeclareTime OBJECT-TYPE
             SYNTAX  INTEGER
             ACCESS  read-write
             STATUS  mandatory
             DESCRIPTION
            "The variable specifies the User ncmAlarm declaration Time in
                 seconds."
            ::= { ncmT1ConfigEntry 14 }
 
         ncmT1State  OBJECT-TYPE
             SYNTAX  INTEGER {
                        out-of-service(1),
                        in-service(2)
                              }
             ACCESS  read-write
             STATUS  mandatory
             DESCRIPTION
          "The variable specifies whether port state is in service or
               not."
            ::= { ncmT1ConfigEntry 15 }
 
         
          ncmT1NetworkLBOEQLIZ OBJECT-TYPE
            SYNTAX INTEGER {
                        bldLn-0db-FT-0-133(1),
                        bldLnNeg7d5db-FT-133-266(2),
                        bldLnNeg15db-FT-266-399(3),
                        bldLnNeg22d5-FT-399-533(4),
                	fT-533-655(5)
 
                        }
            ACCESS  read-write
            STATUS  mandatory
            DESCRIPTION
            "This variable indicates either
		(1) for long haul -- the db rate at which the line or port
                    using, i.e., is 0 , -7.5db, -15db or -22.5db.[pvt];
		or (2) for short haul -- the equalization at which the line 
		    or port using, i.e., is 0~133, 133~266, 266~399, 399~533
		    533~655 ft., which is only applicable in port 3 & 4 of 
		    dual csu card."
            ::= { ncmT1ConfigEntry 16 }


	   ncmT1TimeSlot  OBJECT-TYPE
             SYNTAX  DisplayString
             ACCESS  read-only
             STATUS  mandatory
             DESCRIPTION
             "This variable represents the timeslots used for the given
                  port directly from the hardware crosspoint switch for
                  example 1-10 if slot 1 to 10 are selected and 1,3,5 if 1,3
                  and 5 are selected."
 
             ::= { ncmT1ConfigEntry 17 }
 
        ncmT1TimeSlotSelect OBJECT-TYPE
            SYNTAX INTEGER
            ACCESS  read-write
            STATUS  mandatory
            DESCRIPTION
            "This variable indicates the number which is choosed for the inband/isdn timeslot."
            ::= { ncmT1ConfigEntry 18  }
 
 
--      ncm T1 Port Status Table
 
        ncmT1PortStatusTable OBJECT-TYPE
        SYNTAX  SEQUENCE OF NcmT1PortStatusEntry
        ACCESS  not-accessible
        STATUS  mandatory
	--DEFAULT test-function      ace-test
        --DEFAULT next-function      ace-next

         ::= { ncm-generic 1018  }
         
 
         ncmT1PortStatusEntry OBJECT-TYPE
        SYNTAX  NcmT1PortStatusEntry
        ACCESS  not-accessible
        STATUS  mandatory
        DESCRIPTION
        "An entry in the ncm T1 Port Status Table."
         INDEX   { ncmT1PortStatusNIDIndex, ncmT1PortStatusIndex }
         ::= { ncmT1PortStatusTable 1 }
         
 
         NcmT1PortStatusEntry ::=
         SEQUENCE {
	
	   ncmT1PortStatusNIDIndex
		  INTEGER,
           ncmT1PortStatusIndex
                 INTEGER,
           ncmT1PortCRC6Error
                INTEGER,
           ncmT1PortFramingSlip
                INTEGER,
           ncmT1PortRAI
                INTEGER,
           ncmT1PortLOF
                INTEGER,
           ncmT1PortAIS
                INTEGER,
           ncmT1PortLOS
                INTEGER,
           ncmT1PortBPVThresholdExceeded
                INTEGER,
           ncmT1BlockErrorCounter
                Gauge,
           ncmT1BERExceeded
                INTEGER,
           ncmT1PortSendRAI
                INTEGER,
           ncmT1PortSendAIS
                INTEGER,
           ncmT1PortCGA
                INTEGER,
           ncmT1PortLLB
                INTEGER,
           ncmT1PortPLB
                INTEGER,
           ncmT1PortLOC
                INTEGER,
           ncmT1PortTestPattern
                INTEGER
 
                }

	ncmT1PortStatusNIDIndex OBJECT-TYPE
        SYNTAX  INTEGER (1..'7fffffff'h)
        ACCESS  read-only
        STATUS  mandatory
        DESCRIPTION
        "This object identifies the node id index."
	 ::= { ncmT1PortStatusEntry 1 }


 
 
         ncmT1PortStatusIndex OBJECT-TYPE
        SYNTAX  INTEGER (1..'7fffffff'h)
        ACCESS  read-only
        STATUS  mandatory
        DESCRIPTION
        "The index value which uniquely identifies  the
        interface to which this entry is applicable."
        ::= { ncmT1PortStatusEntry 2 }
 
 
        ncmT1PortCRC6Error OBJECT-TYPE
            SYNTAX INTEGER {
                                no(1),
                                yes(2)
                           }
            ACCESS  read-only
            STATUS  mandatory
            DESCRIPTION
                "This variable indicates the occurance of CRC6 error."
            ::= { ncmT1PortStatusEntry 3 }
 
        ncmT1PortFramingSlip OBJECT-TYPE
            SYNTAX INTEGER {
                                no(1),
                                yes(2)
                           }
            ACCESS  read-only
            STATUS  mandatory
            DESCRIPTION
            "This variable indicates the occurance of framing slip error."
            ::= { ncmT1PortStatusEntry 4 }
 
 
     
         ncmT1PortRAI OBJECT-TYPE
            SYNTAX INTEGER {
                                no(1),
                                yes(2)
                                }
            ACCESS  read-only
            STATUS  mandatory
            DESCRIPTION
                "This variable indicates the occurance of RAI."
            ::= { ncmT1PortStatusEntry 5 }
 
	 ncmT1PortLOF OBJECT-TYPE
            SYNTAX INTEGER {
                                no(1),
                                yes(2)
                           }
            ACCESS  read-only
            STATUS  mandatory
            DESCRIPTION
                "This variable indicates the occurance of LOF."
            ::= { ncmT1PortStatusEntry 6 }
 
        ncmT1PortAIS OBJECT-TYPE
            SYNTAX INTEGER {
                                no(1),
                                yes(2)
                           }
            ACCESS  read-only
            STATUS  mandatory
            DESCRIPTION
                "This variable indicates the occurance of AIS."
            ::= { ncmT1PortStatusEntry 7 }
 
 
         ncmT1PortLOS OBJECT-TYPE
            SYNTAX INTEGER {
                                no(1),
                                yes(2)
                           }
            ACCESS  read-only
            STATUS  mandatory
            DESCRIPTION
                "This variable indicates the occurance of LOS."
            ::= { ncmT1PortStatusEntry 8 }
 
         
 
         ncmT1PortBPVThresholdExceeded OBJECT-TYPE
            SYNTAX INTEGER {
                                no(1),
                                yes(2)
                                }
            ACCESS  read-only
            STATUS  mandatory
            DESCRIPTION
           "This variable indicates whether BPV threshold is exceeded or
                not."
            ::= { ncmT1PortStatusEntry 9 }
 


	 ncmT1BlockErrorCounter OBJECT-TYPE
            SYNTAX Gauge
            ACCESS  read-only
            STATUS  mandatory
            DESCRIPTION
                "This variable indicates the Block Error Counter  ."
 
            ::= { ncmT1PortStatusEntry 10 }


        ncmT1BERExceeded  OBJECT-TYPE
             SYNTAX  INTEGER {
                         no(1),
                         yes(2)
                     }   
             ACCESS  read-only
             STATUS  mandatory
             DESCRIPTION
             "This variable indicates BER excceded or not   "
 
             ::= { ncmT1PortStatusEntry 11 }                         

        ncmT1PortSendRAI  OBJECT-TYPE
             SYNTAX  INTEGER {
                         no(1),
                         yes(2)
                     }
             ACCESS  read-only
             STATUS  mandatory
             DESCRIPTION
             "This variable indicates whether send RAI is on or off   "
 
             ::= { ncmT1PortStatusEntry 12 }

        ncmT1PortSendAIS  OBJECT-TYPE
             SYNTAX  INTEGER {
                         no(1),
                         yes(2)
                     }
             ACCESS  read-only
             STATUS  mandatory
             DESCRIPTION
             "This variable indicates whether send AIS is on or off   "
 
             ::= { ncmT1PortStatusEntry 13 }

        ncmT1PortCGA  OBJECT-TYPE
             SYNTAX  INTEGER {
                         no(1),
                         yes(2)
                     }
             ACCESS  read-only
             STATUS  mandatory
             DESCRIPTION
             "This variable indicates whether CGA is on or off   "
 
             ::= { ncmT1PortStatusEntry 14 }

        ncmT1PortLLB  OBJECT-TYPE
             SYNTAX  INTEGER {
                         no(1),
                         yes(2)
                     }
             ACCESS  read-only
             STATUS  mandatory
             DESCRIPTION
             "This variable indicates whether LLB is on or off   "
 
             ::= { ncmT1PortStatusEntry 15 }

        ncmT1PortPLB  OBJECT-TYPE
             SYNTAX  INTEGER {
                         no(1),
                         yes(2)
                     }
             ACCESS  read-only
             STATUS  mandatory
             DESCRIPTION
             "This variable indicates whether PLB is on or off   "
 
             ::= { ncmT1PortStatusEntry 16 }

        ncmT1PortLOC  OBJECT-TYPE
             SYNTAX  INTEGER {
                         no(1),
                         yes(2)
                     }
             ACCESS  read-only
             STATUS  mandatory
             DESCRIPTION
             "This variable indicates whether LOC is on or off   "
 
             ::= { ncmT1PortStatusEntry 17 }

        ncmT1PortTestPattern  OBJECT-TYPE
             SYNTAX  INTEGER {
                         none(1),
                         three-24(2),
                         qRSS(3),
                         two-n-20-1(4),
                         one-in-8(5),
                         two-n-15-1(6),
                         all-zeros(7),
                         fifty-octets(8),
                         all-ones(9)
                     }
             ACCESS  read-only
             STATUS  mandatory
             DESCRIPTION
             "This variable indicates the test patern in progress:
              1 = none
              2 = 3/24
              3 = QRSS
              4 = 2n20-1
              5 = 1 in 8
              6 = 2N15 - 1
              7 = All Zeros
              8 = 55 Octets
              9 = all ones  "
 
             ::= { ncmT1PortStatusEntry 18 }


 


--   ncm T1 Current Table


       ncmT1CurrentTable OBJECT-TYPE
             SYNTAX  SEQUENCE OF NcmT1CurrentEntry
             ACCESS  not-accessible
             STATUS  mandatory
	     --DEFAULT test-function      ace-test
             --DEFAULT next-function      ace-next


            ::= { ncm-generic 1019 }


       ncmT1CurrentEntry OBJECT-TYPE
             SYNTAX  NcmT1CurrentEntry
             ACCESS  not-accessible
             STATUS  mandatory
             DESCRIPTION
                "An entry in the ncm T1 Current table."
            INDEX   { ncmT1CurrentNIDIndex, ncmT1CurrentIndex, ncmT1CurrentEndType}
            ::= { ncmT1CurrentTable 1 }


         NcmT1CurrentEntry ::=
         SEQUENCE {

	    ncmT1CurrentNIDIndex
		 INTEGER,
           ncmT1CurrentIndex
                 INTEGER,
	   ncmT1CurrentEndType
                 INTEGER,
           ncmT1Timestamp
                 INTEGER,
           ncmT1Timestamp1
                INTEGER,
           ncmT1CurrentIntervalSec
                INTEGER,
           ncmT1CurrentASs
                 Gauge,
           ncmT1CurrentUASs
                 Gauge,
           ncmT1CurrentESs
                 Gauge,
           ncmT1CurrentBESs
                 Gauge,
           ncmT1CurrentSESs
                 Gauge,
           ncmT1CurrentSEFs
                 Gauge,
           ncmT1CurrentLOSs
                 Gauge,
           ncmT1CurrentAISs
                 Gauge,
           ncmT1CurrentLOFs
                Gauge,
           ncmT1CurrentOOFs
                Gauge,
           ncmT1CurrentESsTypeA
                 Gauge,
           ncmT1CurrentSASs
                 Gauge,
           ncmT1CurrentCSSs
                 Gauge,
	   ncmT1CurrentLOFC
                 Gauge,
       	   ncmT1CurrentFrameErrCount
		 Gauge, 
	   ncmT1CurrentErrorFreeSec
		 Gauge,
	   ncmT1CurrentDegradedMin
		 Gauge

                }


	 ncmT1CurrentNIDIndex OBJECT-TYPE
             SYNTAX  INTEGER (1..'7fffffff'h)
             ACCESS  read-only
             STATUS  mandatory
             DESCRIPTION
                "This object identifies the node id of the node."
            ::= { ncmT1CurrentEntry 1 }

 
        ncmT1CurrentIndex OBJECT-TYPE
             SYNTAX  INTEGER (1..'7fffffff'h)
             ACCESS  read-only
             STATUS  mandatory
             DESCRIPTION
                "The index value which uniquely identifies  the
                interf  to which this entry is applicable.
                The interface identified by a  particular
                value  of  this  index is the same interface as
                identified by the same value as a LineIndex
                object instance."
            ::= { ncmT1CurrentEntry 2 }
 
 
        ncmT1CurrentEndType OBJECT-TYPE
            SYNTAX INTEGER {
 
                       near-End(1),
                       far-End(2)
 
                        }
           ACCESS read-only
           STATUS mandatory
           DESCRIPTION
           "The variable specifies the End Type   ."
 
            ::= { ncmT1CurrentEntry 3 }
 
 
 
 
         ncmT1Timestamp OBJECT-TYPE
           SYNTAX INTEGER
           ACCESS read-only
           STATUS mandatory
           DESCRIPTION
           "The variable specifies the Timestamp in seconds  ."
             ::= { ncmT1CurrentEntry 4 }
 
 
 
         ncmT1Timestamp1 OBJECT-TYPE
           SYNTAX INTEGER
           ACCESS read-only
           STATUS mandatory
           DESCRIPTION
           "The variable specifies the Timestamp in millieseconds  ."
 
            ::= { ncmT1CurrentEntry 5 }


	
        ncmT1CurrentIntervalSec OBJECT-TYPE
           SYNTAX INTEGER
           ACCESS read-only
           STATUS mandatory
           DESCRIPTION
           "The variable specifies the Current Interval seconds  ."
 
            ::= { ncmT1CurrentEntry 6 }
 
 
         
        
        ncmT1CurrentASs OBJECT-TYPE
             SYNTAX  Gauge
             ACCESS  read-only
             STATUS  mandatory
             DESCRIPTION
                "The number of Availabe Seconds, encountered  by
                a DS1 interface in the current 15 minute inter-
                val."
            ::= { ncmT1CurrentEntry 7 }
        
 
         ncmT1CurrentUASs OBJECT-TYPE
             SYNTAX  Gauge
             ACCESS  read-only
             STATUS  mandatory
             DESCRIPTION
                "The number of Out of Unavailable Seconds  encountered
                by a DS1 interface in the current 15 minute in-
                terval."
            ::= { ncmT1CurrentEntry 8 }
 
 
         ncmT1CurrentESs OBJECT-TYPE
             SYNTAX  Gauge
             ACCESS  read-only
             STATUS  mandatory
             DESCRIPTION
                "The number of Errored Seconds  encountered
                by a DS1 interface in the current 15 minute in-
                terval."
            ::= { ncmT1CurrentEntry 9 }
 
 
 
         ncmT1CurrentBESs OBJECT-TYPE
             SYNTAX  Gauge
             ACCESS  read-only
             STATUS  mandatory
             DESCRIPTION
                "The number of Bursty Errored Seconds  encountered
                by a DS1 interface in the current 15 minute in-
                terval."
            ::= { ncmT1CurrentEntry 10 }



	
        ncmT1CurrentSESs OBJECT-TYPE
             SYNTAX  Gauge
             ACCESS  read-only
             STATUS  mandatory
             DESCRIPTION
                "The number of Severely Errored Seconds  encountered
                by a DS1 interface in the current 15 minute in-
                terval."
            ::= { ncmT1CurrentEntry 11 }
 
 
        ncmT1CurrentSEFs OBJECT-TYPE
             SYNTAX  Gauge
             ACCESS  read-only
             STATUS  mandatory
             DESCRIPTION
             "The number of Severely Errored Framing Seconds encountered
              by a DS1 interface in the current 15 minute in-terval."
            ::= { ncmT1CurrentEntry 12 }
 
 
        ncmT1CurrentLOSs OBJECT-TYPE
             SYNTAX  Gauge
             ACCESS  read-only
             STATUS  mandatory
             DESCRIPTION
                "The number of Loss of Signal Seconds encountered
                by a DS1 interface in the current 15 minute in-
                terval."
            ::= { ncmT1CurrentEntry 13 }
 
 
        ncmT1CurrentAISs OBJECT-TYPE
             SYNTAX  Gauge
             ACCESS  read-only
             STATUS  mandatory
             DESCRIPTION
             "The number of ncmAlarm Indication Signal Seconds encountered
              by a DS1 interface in the current 15 minute in-terval."
            ::= { ncmT1CurrentEntry 14 }
 
 
        ncmT1CurrentLOFs OBJECT-TYPE
             SYNTAX  Gauge
             ACCESS  read-only
             STATUS  mandatory
             DESCRIPTION
                "The number of Loss Of Frame Seconds encountered
                by a DS1 interface in the current 15 minute in-
                terval."
            ::= { ncmT1CurrentEntry 15  }
 
 

	ncmT1CurrentOOFs OBJECT-TYPE
             SYNTAX  Gauge
             ACCESS  read-only
             STATUS  mandatory
             DESCRIPTION
                "The number of Out Of Frame Seconds encountered
                by a DS1 interface in the current 15 minute in-
                terval."
            ::= { ncmT1CurrentEntry 16 }
 
         
         ncmT1CurrentESsTypeA OBJECT-TYPE
             SYNTAX  Gauge
             ACCESS  read-only
             STATUS  mandatory
             DESCRIPTION
                "The number of Errored seconds of type A encountered
                by a DS1 interface in the current 15 minute in-
                terval."
             ::= { ncmT1CurrentEntry 17 }
 
 
 
         ncmT1CurrentSASs OBJECT-TYPE
             SYNTAX  Gauge
             ACCESS  read-only
             STATUS  mandatory
             DESCRIPTION
                "The number of SEF/AIS encountered
                by a DS1 interface in the current 15 minute in-
                terval."
            ::= { ncmT1CurrentEntry 18 }
 
 
 
         ncmT1CurrentCSSs OBJECT-TYPE
             SYNTAX  Gauge
             ACCESS  read-only
             STATUS  mandatory
             DESCRIPTION
                "The number of controlled slip seconds encountered
                by a DS1 interface in the current 15 minute in-
                terval."
            ::= { ncmT1CurrentEntry 19 }
 
 
 
 
        ncmT1CurrentLOFC OBJECT-TYPE
             SYNTAX  Gauge
             ACCESS  read-only
             STATUS  mandatory
             DESCRIPTION
                "The number of Loss of frame counts encountered
                by a DS1 interface in the current 15 minute in-
                terval."
            ::= { ncmT1CurrentEntry 20 }


	ncmT1CurrentFrameErrCount  OBJECT-TYPE
             SYNTAX  Gauge
             ACCESS  read-only
             STATUS  mandatory
             DESCRIPTION
                "The number of Framing Error Count encountered
                by a DS1 interface in the current 15 minute in-
                terval."
            ::= { ncmT1CurrentEntry 21 }


        ncmT1CurrentErrorFreeSec  OBJECT-TYPE   
             SYNTAX  Gauge 
             ACCESS  read-only 
             STATUS  mandatory 
             DESCRIPTION 
                "The number of Error Free Seconds encountered 
                by a DS1 interface in the current 15 minute in- 
                terval." 
            ::= { ncmT1CurrentEntry 22 } 


        ncmT1CurrentDegradedMin  OBJECT-TYPE   
             SYNTAX  Gauge
             ACCESS  read-only
             STATUS  mandatory
             DESCRIPTION
                "The number of Degraded Minutes encountered
                by a DS1 interface in the current 15 minute in-
                terval."
            ::= { ncmT1CurrentEntry 23 }

	
--    ncm  T1 Interval Group


        ncmT1IntervalTable OBJECT-TYPE
             SYNTAX  SEQUENCE OF NcmT1IntervalEntry
             ACCESS  not-accessible
             STATUS  mandatory
	     --DEFAULT test-function    aceinterval-test
             --DEFAULT next-function    aceinterval-next

            ::= { ncm-generic 1020 }


          ncmT1IntervalEntry OBJECT-TYPE
             SYNTAX  NcmT1IntervalEntry
             ACCESS  not-accessible
             STATUS  mandatory
             DESCRIPTION
                "An entry in the ncm T1 Interval table."
            INDEX   {ncmT1IntervalNIDIndex, ncmT1IntervalIndex, ncmT1IntervalEndType, ncmT1IntervalNumber }
            ::= { ncmT1IntervalTable 1 }

          NcmT1IntervalEntry ::=
          SEQUENCE {

	   ncmT1IntervalNIDIndex
		  INTEGER,
           ncmT1IntervalIndex
                 INTEGER,
	   ncmT1IntervalEndType
                 INTEGER,
           ncmT1IntervalNumber
                 INTEGER,
           ncmT1IntervalASs
                 Gauge,
           ncmT1IntervalUASs
                 Gauge,
           ncmT1IntervalESs
                 Gauge,
           ncmT1IntervalBESs
                Gauge,
           ncmT1IntervalSESs
                 Gauge,
           ncmT1IntervalSEFs
                 Gauge,
           ncmT1IntervalLOSs
                 Gauge,
           ncmT1IntervalAISs
                 Gauge,
           ncmT1IntervalLOFs
                 Gauge,
           ncmT1IntervalOOFs
                 Gauge,
           ncmT1IntervalESsTypeA
                 Gauge,
           ncmT1IntervalSASs
                 Gauge,
           ncmT1IntervalCSSs
                 Gauge,
           ncmT1IntervalLOFC
                Gauge,
	   ncmT1IntervalFrameErr
		 Gauge, 
	   ncmT1IntervalErrFreeSec
		 Gauge,
	   ncmT1IntervalDegradMin
		 Gauge

         
         }
 

	ncmT1IntervalNIDIndex OBJECT-TYPE
             SYNTAX  INTEGER (1..'7fffffff'h)
             ACCESS  read-only
             STATUS  mandatory
             DESCRIPTION
                "The object specifies the node id index."
            ::= { ncmT1IntervalEntry 1 }


	 ncmT1IntervalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a LineIndex
                object instance."
            ::= { ncmT1IntervalEntry 2 }
         
         
        ncmT1IntervalEndType OBJECT-TYPE
            SYNTAX INTEGER {

                       near-End(1),
                       far-End(2)
                        }
           ACCESS read-only
           STATUS mandatory
           DESCRIPTION
           "The variable specifies the End Type   ."

            ::= { ncmT1IntervalEntry 3 }


         ncmT1IntervalNumber OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { ncmT1IntervalEntry 4 }
 
 
         ncmT1IntervalASs OBJECT-TYPE
             SYNTAX  Gauge
             ACCESS  read-only
             STATUS  mandatory
             DESCRIPTION
                "The number of Available Seconds encountered by a
                DS1  interface in one of the previous 96, indi-
                vidual 15 minute, intervals."
            ::= { ncmT1IntervalEntry 5 }
         
         
 
         ncmT1IntervalUASs OBJECT-TYPE
             SYNTAX  Gauge
             ACCESS  read-only
             STATUS  mandatory
             DESCRIPTION
                "The number of Unavailable Seconds  encoun-
                tered by a DS1 interface in one of the previous
                96, individual 15 minute, intervals."
            ::= { ncmT1IntervalEntry 6 }

	
          ncmT1IntervalESs OBJECT-TYPE
             SYNTAX  Gauge
             ACCESS  read-only
             STATUS  mandatory
             DESCRIPTION
                "The number of Error Seconds  encoun-
                tered by a DS1 interface in one of the previous
                96, individual 15 minute, intervals."
            ::= { ncmT1IntervalEntry 7 }
         
 
 
          ncmT1IntervalBESs OBJECT-TYPE
             SYNTAX  Gauge
             ACCESS  read-only
             STATUS  mandatory
             DESCRIPTION
                "The number of Bursty Error Seconds  encoun-
                tered by a DS1 interface in one of the previous
                96, individual 15 minute, intervals."
            ::= { ncmT1IntervalEntry 8 }
         
 
        ncmT1IntervalSESs OBJECT-TYPE
             SYNTAX  Gauge
             ACCESS  read-only
             STATUS  mandatory
             DESCRIPTION
                "The number of Severe Error Seconds  encoun-
                tered by a DS1 interface in one of the previous
                96, individual 15 minute, intervals."
            ::= { ncmT1IntervalEntry 9 }
         
 
         ncmT1IntervalSEFs OBJECT-TYPE
             SYNTAX  Gauge
             ACCESS  read-only
             STATUS  mandatory
             DESCRIPTION
                "The number of Severely Errored Framing Seconds
               encountered by a DS1 interface in one of the previous
                96, individual 15 minute, intervals."
            ::= { ncmT1IntervalEntry 10 }
         
 
        ncmT1IntervalLOSs OBJECT-TYPE
             SYNTAX  Gauge
             ACCESS  read-only
             STATUS  mandatory
             DESCRIPTION
                "The number of Loss of Signal Seconds encoun-
                tered by a DS1 interface in one of the previous
                96, individual 15 minute, intervals."
            ::= { ncmT1IntervalEntry 11 }


	 ncmT1IntervalAISs OBJECT-TYPE
             SYNTAX  Gauge
             ACCESS  read-only
             STATUS  mandatory
             DESCRIPTION
                "The number of ncmAlarm Indication Signal Seconds encoun-
                tered by a DS1 interface in one of the previous
                96, individual 15 minute, intervals."
            ::= { ncmT1IntervalEntry 12 }
         
 
 
        ncmT1IntervalLOFs OBJECT-TYPE
             SYNTAX  Gauge
             ACCESS  read-only
             STATUS  mandatory
             DESCRIPTION
                "The number of Loss Of Frame  Seconds encoun-
                tered by a DS1 interface in one of the previous
                96, individual 15 minute, intervals."
            ::= { ncmT1IntervalEntry 13 }
         
 
 
         ncmT1IntervalOOFs OBJECT-TYPE
             SYNTAX  Gauge
             ACCESS  read-only
             STATUS  mandatory
             DESCRIPTION
                "The number of Out Of Frame Seconds encoun-
                tered by a DS1 interface in one of the previous
                96, individual 15 minute, intervals."
            ::= { ncmT1IntervalEntry 14 }
         
         
        
         ncmT1IntervalESsTypeA OBJECT-TYPE
             SYNTAX  Gauge
             ACCESS  read-only
             STATUS  mandatory
             DESCRIPTION
                "The number of Errored seconds of type A encountered
                by a DS1 interface in one of the previous 96,
                        individual 15 minute interval."
             ::= { ncmT1IntervalEntry 15 }
 
 
 
         ncmT1IntervalSASs OBJECT-TYPE
             SYNTAX  Gauge
             ACCESS  read-only
             STATUS  mandatory
             DESCRIPTION
                "The number of SEF/AIS encountered
                by a DS1 interface in one of the previous 96,
                        individual 15 minute interval."
             ::= { ncmT1IntervalEntry 16 }
 


	ncmT1IntervalCSSs OBJECT-TYPE
             SYNTAX  Gauge
             ACCESS  read-only
             STATUS  mandatory
             DESCRIPTION
                "The number of controlled slip seconds encountered
                by a DS1 interface in one of the previous 96,
                        individual 15 minute interval."
             ::= { ncmT1IntervalEntry 17 }
 
 
 
        ncmT1IntervalLOFC OBJECT-TYPE
             SYNTAX  Gauge
             ACCESS  read-only
             STATUS  mandatory
             DESCRIPTION
                "The number of Loss of frame counts encountered
                by a DS1 interface in one of the previous 96,
                        individual 15 minute interval."
            ::= { ncmT1IntervalEntry 18 }


	ncmT1IntervalFrameErr  OBJECT-TYPE
             SYNTAX  Gauge
             ACCESS  read-only
             STATUS  mandatory
             DESCRIPTION
                "The number of Framing Error Count encountered
                by a DS1 interface in one of the previous 96,
                individual 15 minute interval."
            ::= { ncmT1IntervalEntry 19 }


        ncmT1IntervalErrFreeSec  OBJECT-TYPE   
             SYNTAX  Gauge 
             ACCESS  read-only 
             STATUS  mandatory 
             DESCRIPTION 
                "The number of Error Free Seconds encountered 
                by a DS1 interface in one of the previous 96,
                individual 15 minute interval." 
            ::= { ncmT1IntervalEntry 20 } 


        ncmT1IntervalDegradMin  OBJECT-TYPE   
             SYNTAX  Gauge
             ACCESS  read-only
             STATUS  mandatory
             DESCRIPTION
                "The number of Degraded Minutes encountered
                by a DS1 interface in one of the previous 96,
                individual 15 minute interval."
            ::= { ncmT1IntervalEntry 21 }


 


--      ncm T1 Total Group 24 Hour


      ncmT1TotalTable OBJECT-TYPE
             SYNTAX  SEQUENCE OF NcmT1TotalEntry
             ACCESS  not-accessible
             STATUS  mandatory
	     --DEFAULT test-function    ace-test
             --DEFAULT next-function    ace-next


            ::= { ncm-generic  1021 }


       ncmT1TotalEntry OBJECT-TYPE
             SYNTAX  NcmT1TotalEntry
             ACCESS  not-accessible
             STATUS  mandatory
             DESCRIPTION
                "An entry in the DS1 Total Loss table."
            INDEX   { ncmT1TotalNIDIndex,  ncmT1TotalIndex, ncmT1TotalEndType }
            ::= { ncmT1TotalTable 1 }

      NcmT1TotalEntry ::=
         SEQUENCE {
	   ncmT1TotalNIDIndex
		INTEGER,
           ncmT1TotalIndex
                 INTEGER,
	   ncmT1TotalEndType
                 INTEGER,
           ncmT1NumberOfValidIntervals
                INTEGER,
           ncmT1TotalASs
                 Gauge,
           ncmT1TotalUASs
                 Gauge,
           ncmT1TotalESs
                 Gauge,
           ncmT1TotalBESs
                 Gauge,
           ncmT1TotalSESs
                 Gauge,
           ncmT1TotalSEFs
                Gauge,
           ncmT1TotalLOSs
                Gauge,
           ncmT1TotalAISs
                Gauge,
           ncmT1TotalLOFs
                Gauge,
           ncmT1TotalOOFs
                Gauge,
           ncmT1TotalESsTypeA
                 Gauge,
           ncmT1TotalSASs
                 Gauge,
           ncmT1TotalCSSs
                Gauge,
           ncmT1TotalLOFC
                 Gauge,
           ncmT1TotalFrameErrCount
                 Gauge,
           ncmT1TotalErrorFreeSec
                 Gauge,
           ncmT1TotalDegradedMin
                 Gauge
 
                  }


	ncmT1TotalNIDIndex OBJECT-TYPE
             SYNTAX  INTEGER (1..'7fffffff'h)
             ACCESS  read-only
             STATUS  mandatory
             DESCRIPTION
                "The object specifies the node id index of the node."
            ::= { ncmT1TotalEntry 1 }
 

	  ncmT1TotalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a LineIndex
                object instance."
            ::= { ncmT1TotalEntry 2 }
 
        
        ncmT1TotalEndType OBJECT-TYPE
            SYNTAX INTEGER {
 
                       near-End(1),
                       far-End(2)
 
                        }
           ACCESS read-only
           STATUS mandatory
           DESCRIPTION
           "The variable specifies the End Type   ."
 
            ::= { ncmT1TotalEntry 3 }
 

        ncmT1NumberOfValidIntervals OBJECT-TYPE
           SYNTAX INTEGER
           ACCESS read-only
           STATUS mandatory
           DESCRIPTION
                "The number of  previous  intervals  for  which
                valid data was collected.  The value will be 96
                unless the interface was brought on-line within
                the last 24 hours, in which case the value will
                be the number of complete 15  minute  intervals
               the since interface has been online."

            ::= { ncmT1TotalEntry 4 }

 
         ncmT1TotalASs OBJECT-TYPE
             SYNTAX  Gauge
             ACCESS  read-only
             STATUS  mandatory
             DESCRIPTION
                "The number of Available Seconds encountered by a
                DS1 interface in the previous 24 hour interval."
 
            ::= { ncmT1TotalEntry 5 }
 
 
 
        ncmT1TotalUASs OBJECT-TYPE
             SYNTAX  Gauge
             ACCESS  read-only
             STATUS  mandatory
             DESCRIPTION
                "The number of Unavailable Seconds  encoun-
                tered  by  a  DS1  interface in the previous 24
                hour interval."
            ::= { ncmT1TotalEntry 6 }
 
 
 
        ncmT1TotalESs OBJECT-TYPE
             SYNTAX  Gauge
             ACCESS  read-only
             STATUS  mandatory
             DESCRIPTION
                "The number of Unavailable Seconds  encoun-
                tered  by  a  DS1  interface in the previous 24
                hour interval."
            ::= { ncmT1TotalEntry 7 }
 
         
         ncmT1TotalBESs OBJECT-TYPE
             SYNTAX  Gauge
             ACCESS  read-only
             STATUS  mandatory
             DESCRIPTION
                "The number of Unavailable Seconds  encoun-
                tered  by  a  DS1  interface in the previous 24
                hour interval."
            ::= { ncmT1TotalEntry 8 }

	
 	 ncmT1TotalSESs OBJECT-TYPE
             SYNTAX  Gauge
             ACCESS  read-only
             STATUS  mandatory
             DESCRIPTION
                "The number of Severly errored Seconds  encoun-
                tered  by  a  DS1  interface in the previous 24
                hour interval."
            ::= { ncmT1TotalEntry 9 }
 
         
         ncmT1TotalSEFs OBJECT-TYPE
             SYNTAX  Gauge
             ACCESS  read-only
             STATUS  mandatory
             DESCRIPTION
                "The number of Severly Errored frame Seconds  encoun-
                tered  by  a  DS1  interface in the previous 24
                hour interval."
            ::= { ncmT1TotalEntry 10 }
 
 
          ncmT1TotalLOSs OBJECT-TYPE
             SYNTAX  Gauge
             ACCESS  read-only
             STATUS  mandatory
             DESCRIPTION
                "The number of Loss Of Signal Errors  encoun-
                tered  by  a  DS1  interface in the previous 24
                hour interval."
            ::= { ncmT1TotalEntry 11 }
 
 
         ncmT1TotalAISs OBJECT-TYPE
             SYNTAX  Gauge
             ACCESS  read-only
             STATUS  mandatory
             DESCRIPTION
                "The number of ncmAlarm Indication Signal Seconds encoun-
                tered  by  a  DS1  interface in the previous 24
                hour interval."
            ::= { ncmT1TotalEntry 12 }
 
 
        ncmT1TotalLOFs OBJECT-TYPE
             SYNTAX  Gauge
             ACCESS  read-only
             STATUS  mandatory
             DESCRIPTION
                "The number of Loss Of Frame Seconds encoun-
                tered  by  a  DS1  interface in the previous 24
                hour interval."
            ::= { ncmT1TotalEntry 13 }
 
	 ncmT1TotalOOFs     OBJECT-TYPE
             SYNTAX  Gauge
             ACCESS  read-only
             STATUS  mandatory
             DESCRIPTION
                "The number of Out Of Frame Seconds encoun-
                tered  by  a  DS1  interface in the previous 24
                hour interval."
            ::= { ncmT1TotalEntry 14 }
 
 
 
        ncmT1TotalESsTypeA OBJECT-TYPE
             SYNTAX  Gauge
             ACCESS  read-only
             STATUS  mandatory
             DESCRIPTION
                "The number of Errored seconds of type A encountered
                by a DS1 interface in the previous 24 hour in
                terval."
             ::= { ncmT1TotalEntry 15 }
 
 
 
         ncmT1TotalSASs OBJECT-TYPE
             SYNTAX  Gauge
             ACCESS  read-only
             STATUS  mandatory
             DESCRIPTION
                "The number of SEF/AIS encountered
                by a DS1 interface in the previous 24 hour in-
                terval."
             ::= { ncmT1TotalEntry 16 }
 
 
 
         ncmT1TotalCSSs OBJECT-TYPE
             SYNTAX  Gauge
             ACCESS  read-only
             STATUS  mandatory
             DESCRIPTION
                "The number of controlled slip seconds encountered
                by a DS1 interface in the previous 24 hour in-
                terval."
             ::= { ncmT1TotalEntry 17 }
 
 
         ncmT1TotalLOFC OBJECT-TYPE
             SYNTAX  Gauge
             ACCESS  read-only
             STATUS  mandatory
             DESCRIPTION
                "The number of Loss of frame counts encountered
                by a DS1 interface in the previous 24 hour in-
                terval."
            ::= { ncmT1TotalEntry 18 }


         ncmT1TotalFrameErrCount  OBJECT-TYPE
             SYNTAX  Gauge
             ACCESS  read-only
             STATUS  mandatory
             DESCRIPTION
                "The number of Framing Error Count encountered
                by a DS1 interface in the previous 24 hour in-
                terval."
            ::= { ncmT1TotalEntry 19 }


         ncmT1TotalErrorFreeSec  OBJECT-TYPE
             SYNTAX  Gauge
             ACCESS  read-only
             STATUS  mandatory
             DESCRIPTION
                "The number of Error free seconds encountered
                by a DS1 interface in the previous 24 hour in-
                terval."
            ::= { ncmT1TotalEntry 20 }
 
                                        
         ncmT1TotalDegradedMin  OBJECT-TYPE
             SYNTAX  Gauge
             ACCESS  read-only
             STATUS  mandatory
             DESCRIPTION
                "The number of Degraded Minutes encountered
                by a DS1 interface in the previous 24 hour in-
                terval."
            ::= { ncmT1TotalEntry  21 }


--    ncm  T1 Prev  Total Group 24 Hour
 
 
         ncmT1PrevTotalTable OBJECT-TYPE
             SYNTAX  SEQUENCE OF NcmT1PrevTotalEntry
             ACCESS  not-accessible
             STATUS  mandatory
	     --DEFAULT test-function    ace-test
             --DEFAULT next-function    ace-next

            ::= { ncm-generic  1022 }
 
 
          ncmT1PrevTotalEntry OBJECT-TYPE
             SYNTAX  NcmT1PrevTotalEntry
             ACCESS  not-accessible
             STATUS  mandatory
             DESCRIPTION
                "An entry in the DS1 Total Loss table."
            INDEX   { ncmT1PrevTotalNIDIndex, ncmT1PrevTotalIndex, ncmT1PrevTotalEndType }
            ::= { ncmT1PrevTotalTable 1 }
 
         NcmT1PrevTotalEntry ::=
         SEQUENCE {

	   ncmT1PrevTotalNIDIndex
		 INTEGER,
           ncmT1PrevTotalIndex
                 INTEGER,
	   ncmT1PrevTotalEndType
                 INTEGER,
           ncmT1PrevTotalASs
                 Gauge,
           ncmT1PrevTotalUASs
                 Gauge,
           ncmT1PrevTotalESs
                 Gauge,
           ncmT1PrevTotalBESs
                 Gauge,
           ncmT1PrevTotalSESs
                 Gauge,
           ncmT1PrevTotalSEFs
                Gauge,
           ncmT1PrevTotalLOSs
                Gauge,
           ncmT1PrevTotalAISs
                Gauge,
           ncmT1PrevTotalLOFs
                Gauge,
           ncmT1PrevTotalOOFs
                Gauge,
           ncmT1PrevTotalESsTypeA
                 Gauge,
           ncmT1PrevTotalSASs
                 Gauge,
           ncmT1PrevTotalCSSs
                Gauge,
           ncmT1PrevTotalLOFC
                Gauge,
           ncmT1PrevTotalFrameErrCount
                 Gauge,
           ncmT1PrevTotalErrorFreeSec
                 Gauge,
           ncmT1PrevTotalDegradedMin
                 Gauge

 
             }

	 ncmT1PrevTotalNIDIndex OBJECT-TYPE
             SYNTAX  INTEGER (1..'7fffffff'h)
             ACCESS  read-only
             STATUS  mandatory
             DESCRIPTION
                "The object specifies the node id index of the node."
            ::= { ncmT1PrevTotalEntry 1 }



	 ncmT1PrevTotalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a LineIndex
                object instance."
            ::= { ncmT1PrevTotalEntry 2 }
       
      
        ncmT1PrevTotalEndType OBJECT-TYPE
            SYNTAX INTEGER {

                       near-End(1),
                       far-End(2)

                        }         
           ACCESS read-only
           STATUS mandatory
           DESCRIPTION
           "The variable specifies the End Type   ."

            ::= { ncmT1PrevTotalEntry 3 }                   

 
         ncmT1PrevTotalASs OBJECT-TYPE
             SYNTAX  Gauge
             ACCESS  read-only
             STATUS  mandatory
             DESCRIPTION
                "The number of Available Seconds encountered by a
                DS1 interface in the previous 24 hour interval."
 
            ::= { ncmT1PrevTotalEntry 4 }
 
 
 
         ncmT1PrevTotalUASs OBJECT-TYPE
             SYNTAX  Gauge
             ACCESS  read-only
             STATUS  mandatory
             DESCRIPTION
                "The number of Unavailable Seconds  encoun-
                tered  by  a  DS1  interface in the previous 24
                hour interval."
            ::= { ncmT1PrevTotalEntry 5 }
       
 
         ncmT1PrevTotalESs OBJECT-TYPE
             SYNTAX  Gauge
             ACCESS  read-only
             STATUS  mandatory
             DESCRIPTION
                "The number of Unavailable Seconds  encoun-
                tered  by  a  DS1  interface in the previous 24
                hour interval."
            ::= { ncmT1PrevTotalEntry 6 }
       
 
         ncmT1PrevTotalBESs OBJECT-TYPE
             SYNTAX  Gauge
             ACCESS  read-only
             STATUS  mandatory
             DESCRIPTION
                "The number of Unavailable Seconds  encoun-
                tered  by  a  DS1  interface in the previous 24
                hour interval."
            ::= { ncmT1PrevTotalEntry 7 }



	ncmT1PrevTotalSESs OBJECT-TYPE
             SYNTAX  Gauge
             ACCESS  read-only
             STATUS  mandatory
             DESCRIPTION
                "The number of Severly Errored Seconds  encoun-
                tered  by  a  DS1  interface in the previous 24
                hour interval."
            ::= { ncmT1PrevTotalEntry 8 }
       
 
         ncmT1PrevTotalSEFs OBJECT-TYPE
             SYNTAX  Gauge
             ACCESS  read-only
             STATUS  mandatory
             DESCRIPTION
                "The number of Severly Errored frame Seconds  encoun-
                tered  by  a  DS1  interface in the previous 24
                hour interval."
            ::= { ncmT1PrevTotalEntry 9 }
       
 
 
 
 
          ncmT1PrevTotalLOSs OBJECT-TYPE
             SYNTAX  Gauge
             ACCESS  read-only
             STATUS  mandatory
             DESCRIPTION
                "The number of Loss Of Signal Errors  encoun-
                tered  by  a  DS1  interface in the previous 24
                hour interval."
            ::= { ncmT1PrevTotalEntry 10 }
       
 
         ncmT1PrevTotalAISs OBJECT-TYPE
             SYNTAX  Gauge
             ACCESS  read-only
             STATUS  mandatory
             DESCRIPTION
                "The number of ncmAlarm Indication Signal Seconds encoun-
                tered  by  a  DS1  interface in the previous 24
                hour interval."
            ::= { ncmT1PrevTotalEntry 11 }
       
 
        ncmT1PrevTotalLOFs OBJECT-TYPE
             SYNTAX  Gauge
             ACCESS  read-only
             STATUS  mandatory
             DESCRIPTION
                "The number of Loss Of Frame Seconds encoun-
                tered  by  a  DS1  interface in the previous 24
                hour interval."
            ::= { ncmT1PrevTotalEntry 12 }



	
        ncmT1PrevTotalOOFs OBJECT-TYPE
             SYNTAX  Gauge
             ACCESS  read-only
             STATUS  mandatory
             DESCRIPTION
                "The number of Out Of Frame Seconds encoun-
                 tered  by  a  DS1  interface in the previous 24
                 hour interval."
            ::= { ncmT1PrevTotalEntry 13 }
 
 
        ncmT1PrevTotalESsTypeA OBJECT-TYPE
             SYNTAX  Gauge
             ACCESS  read-only
             STATUS  mandatory
             DESCRIPTION
                "The number of Errored seconds of type A encountered
                by a DS1 interface in the previous 24 hour in-
                terval."
             ::= { ncmT1PrevTotalEntry 14 }
       
 
 
         ncmT1PrevTotalSASs OBJECT-TYPE
             SYNTAX  Gauge
             ACCESS  read-only
             STATUS  mandatory
             DESCRIPTION
                "The number of SEF/AIS encountered
                by a DS1 interface in the previous 24 hour in-
                terval."
             ::= { ncmT1PrevTotalEntry 15 }
       
 
        ncmT1PrevTotalCSSs OBJECT-TYPE
             SYNTAX  Gauge
             ACCESS  read-only
             STATUS  mandatory
             DESCRIPTION
                "The number of controlled slip seconds encountered
                by a DS1 interface in the previous in-
                terval."
             ::= { ncmT1PrevTotalEntry 16 }
       
 
         ncmT1PrevTotalLOFC OBJECT-TYPE
             SYNTAX  Gauge
             ACCESS  read-only
             STATUS  mandatory
               DESCRIPTION
                "The number of Loss of frame counts encountered
                by a DS1 interface in the previous in-
                terval."
            ::= { ncmT1PrevTotalEntry 17 }
 
         ncmT1PrevTotalFrameErrCount  OBJECT-TYPE
             SYNTAX  Gauge
             ACCESS  read-only
             STATUS  mandatory
             DESCRIPTION
                "The number of Framing Error Count encountered
                by a DS1 interface in the previous in-
                terval."
            ::= { ncmT1PrevTotalEntry 18 }
 
 
         ncmT1PrevTotalErrorFreeSec  OBJECT-TYPE
             SYNTAX  Gauge
             ACCESS  read-only
             STATUS  mandatory
             DESCRIPTION
                "The number of Error free seconds encountered
                by a DS1 interface in the previous in-
                terval."
            ::= { ncmT1PrevTotalEntry 19 }
 
                 
         ncmT1PrevTotalDegradedMin  OBJECT-TYPE
             SYNTAX  Gauge
             ACCESS  read-only
             STATUS  mandatory
             DESCRIPTION
                "The number of Degraded Minutes encountered
                by a DS1 interface in the previous in-
                terval."
            ::= { ncmT1PrevTotalEntry  20 }
 


--               T1 24 Hour Performance Snap Shot
       
       
         ncmT1PreformanceSnapShotTable OBJECT-TYPE
             SYNTAX  SEQUENCE OF NcmT1PreformanceSnapShotEntry
             ACCESS  not-accessible
             STATUS  mandatory
	     --DEFAULT test-function    ace-test
             --DEFAULT next-function    ace-next

 
            ::= { ncm-generic 1023  }
 
 
         ncmT1PreformanceSnapShotEntry OBJECT-TYPE
             SYNTAX  NcmT1PreformanceSnapShotEntry
             ACCESS  not-accessible
             STATUS  mandatory
             DESCRIPTION
             "An entry in the  T1 Performance Snap Shot Entry
              table."
            INDEX   { ncmT1SnapShotNIDIndex, ncmT1SnapShotIndex, ncmT1SnapShotEndType }
            ::= { ncmT1PreformanceSnapShotTable 1 }
 
 
        NcmT1PreformanceSnapShotEntry ::=
         SEQUENCE {
	
	   ncmT1SnapShotNIDIndex
		INTEGER,
           ncmT1SnapShotIndex
                 INTEGER,
	   ncmT1SnapShotEndType
                 INTEGER,
           ncmT1SnapShot
                INTEGER,
           ncmT1TimeStampSec
                INTEGER,
           ncmT1TimeStampMilliSec
                 INTEGER,
           ncmT1CurrIntervalSec
                INTEGER,
           ncmT1ResetPerfReg
                 INTEGER
 
                }


	
	ncmT1SnapShotNIDIndex OBJECT-TYPE
             SYNTAX  INTEGER (1..'7fffffff'h)
             ACCESS  read-only
             STATUS  mandatory
             DESCRIPTION
                "The object specifies the node id index of the node."
 
 
            ::= { ncmT1PreformanceSnapShotEntry 1 }

       
 
          ncmT1SnapShotIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a LineIndex
                object instance."
 
 
            ::= { ncmT1PreformanceSnapShotEntry 2 }


        ncmT1SnapShotEndType OBJECT-TYPE
            SYNTAX INTEGER {

                       near-End(1),
                       far-End(2)

                        }
           ACCESS read-only
           STATUS mandatory
           DESCRIPTION
           "The variable specifies the End Type   ."

            ::= { ncmT1PreformanceSnapShotEntry 3 }

 
	ncmT1SnapShot OBJECT-TYPE
            SYNTAX INTEGER {
 
                                no(1),
                                yes(2)
                       }
           ACCESS read-write
           STATUS mandatory
           DESCRIPTION
           "The variable specifies the option to intiate snap shot
               command."
       
            ::= { ncmT1PreformanceSnapShotEntry 4 }
 
 
 
        ncmT1TimeStampSec OBJECT-TYPE
            SYNTAX INTEGER
           ACCESS read-only
           STATUS mandatory
           DESCRIPTION
           "The variable specifies the Time Stamp in Seconds ."
 
           ::= { ncmT1PreformanceSnapShotEntry 5 }
 
         ncmT1TimeStampMilliSec OBJECT-TYPE
            SYNTAX INTEGER
           ACCESS read-only
           STATUS mandatory
           DESCRIPTION
           "The variable specifies the Time Stamp in milli  Seconds ."
 
           ::= { ncmT1PreformanceSnapShotEntry  6 }
 
 
         ncmT1CurrIntervalSec OBJECT-TYPE
           SYNTAX INTEGER
           ACCESS read-only
           STATUS mandatory
           DESCRIPTION
           "The variable specifies the current interval in Seconds ."
 
           ::= { ncmT1PreformanceSnapShotEntry  7 }


         ncmT1ResetPerfReg OBJECT-TYPE
             SYNTAX  INTEGER {
                         no(1),
                         yes(2)
                     }
             ACCESS  read-write
             STATUS  mandatory
             DESCRIPTION
                "Reset Performance Monitoring registers."
            ::= { ncmT1PreformanceSnapShotEntry 8 }



--      ncm Advanced T1 Port Configuration Table

         ncmAdvancedT1ConfigTable OBJECT-TYPE
        SYNTAX  SEQUENCE OF NcmAdvancedT1ConfigEntry
        ACCESS  not-accessible
        STATUS  mandatory
	--DEFAULT test-function    ace-test
        --DEFAULT next-function    ace-next


         ::= { ncm-generic 1024  }


         ncmAdvancedT1ConfigEntry OBJECT-TYPE
        SYNTAX  NcmAdvancedT1ConfigEntry
        ACCESS  not-accessible
        STATUS  mandatory
        DESCRIPTION
        "An entry in the Advanced T1 Configuration table  ."
         INDEX   { ncmAdvancedT1NIDIndex, ncmAdvancedT1LineIndex }
         ::= { ncmAdvancedT1ConfigTable 1 }


         NcmAdvancedT1ConfigEntry ::=
         SEQUENCE {
	
	   ncmAdvancedT1NIDIndex
		 INTEGER,
           ncmAdvancedT1LineIndex
                 INTEGER,
           ncmadvfdlMode
                 INTEGER,
           ncmadvfdlStandard
                INTEGER,
           ncmadvfdlPerformanceReport
                INTEGER,
           ncmadvfdlLBEnable
                INTEGER,
           ncmadvfdlLLBT1BOPMsg
                INTEGER,
           ncmadvfdlPLBT1BOPMsg
                INTEGER,
           ncmadvfdlIdlePattern
                INTEGER,
           ncmadvfdlMonitoringCsuType
                INTEGER
                }


	 ncmAdvancedT1NIDIndex OBJECT-TYPE
          SYNTAX  INTEGER (1..'7fffffff'h)
          ACCESS  read-only
          STATUS  mandatory
          DESCRIPTION
         "The object specifies the node id of the node."
           
          ::= { ncmAdvancedT1ConfigEntry 1 }



	 ncmAdvancedT1LineIndex OBJECT-TYPE
          SYNTAX  INTEGER (1..'7fffffff'h)
          ACCESS  read-only
          STATUS  mandatory
          DESCRIPTION
         "The index value which uniquely identifies  the
          interface to which this entry is applicable."
           
          ::= { ncmAdvancedT1ConfigEntry 2 }
 
 
         ncmadvfdlMode OBJECT-TYPE
          SYNTAX INTEGER {
           
                       terminated(1),
                       pass(2)
 
               } 
          ACCESS read-write
          STATUS mandatory
          DESCRIPTION
          "The variable specifies the fdl mode which is bit 0 of  fdl
           Parameter1."
 
          ::= { ncmAdvancedT1ConfigEntry 3 }
 
 
         ncmadvfdlStandard OBJECT-TYPE
          SYNTAX INTEGER {
           
                       type-54016(1),
                       type-T1-403(2),
                       type-both(3)
 
               } 
          ACCESS read-write
          STATUS mandatory
          DESCRIPTION
          "The variable specifies the fdl standard which is bits 1
          and bit 2 of fdl Parameter1."
            
          ::= { ncmAdvancedT1ConfigEntry 4 }
 


	ncmadvfdlPerformanceReport OBJECT-TYPE
          SYNTAX INTEGER {
           
                       disable(1),
                       user(2),
                       telco(3)
        
               } 
          ACCESS read-write
          STATUS mandatory
          DESCRIPTION
          "The variable specifies the fdl standard which is bits 3
          and bit 4 of fdl Parameter1."
          ::= { ncmAdvancedT1ConfigEntry 5 }
 
 
 
         ncmadvfdlLBEnable OBJECT-TYPE
          SYNTAX INTEGER {
           
                       disable(1),
                       enable(2)
 
               } 
          ACCESS read-write
          STATUS mandatory
          DESCRIPTION
          "The variable specifies the Disable/Enable of the fdl Loopback
           which is bit 0 of the fdl-loop"
           ::= { ncmAdvancedT1ConfigEntry 6 }
 
 
	 ncmadvfdlLLBT1BOPMsg OBJECT-TYPE
          SYNTAX INTEGER {
           
                       disable(1),
                       enable(2)
 
               } 
          ACCESS read-write
          STATUS mandatory
          DESCRIPTION
          "The variable specifies the Disable/Enable of the send/receive
              of the LLB T1.403 BOP Messages. It is the bit 1 of the
          fdl-loop."
             
              ::= { ncmAdvancedT1ConfigEntry 7 }
 
 
         ncmadvfdlPLBT1BOPMsg OBJECT-TYPE
          SYNTAX INTEGER {
           
                        disable(1),
                        enable(2)
 
               } 
          ACCESS read-write
          STATUS mandatory
          DESCRIPTION
          "The variable specifies the Disable/Enable of the send/receive
               of the PLB T1.403 BOP Messages. It is the bit 2 of the
               fdl-loop"
           ::= { ncmAdvancedT1ConfigEntry 8 }
 
	ncmadvfdlIdlePattern OBJECT-TYPE
          SYNTAX INTEGER {
           
                       all-ones(1),
                       flags(2)
 
               } 
          ACCESS read-write
          STATUS mandatory
          DESCRIPTION
          "The variable specifies the fdl idle pattern which is bit 0 of
              fdl Parameter2."
 
          ::= { ncmAdvancedT1ConfigEntry 9 }
 
 
         ncmadvfdlMonitoringCsuType OBJECT-TYPE
          SYNTAX INTEGER {
           
                       polling(1),
                       no-polling(2),
                       unsolicited-messages(3)
 
               } 
          ACCESS read-write
          STATUS mandatory
          DESCRIPTION
          "The variable specifies the fdl standard which is bits 1
          and bit 2 of fdl Parameter2."
             
        ::= { ncmAdvancedT1ConfigEntry 10 }
 

--	 ncmT1PortLatchedStatus

         ncmT1LatchedStatusTable OBJECT-TYPE
             SYNTAX  SEQUENCE OF NcmT1LatchedStatusEntry
             ACCESS  not-accessible
             STATUS  mandatory
	     --DEFAULT test-function    ace-test
             --DEFAULT next-function    ace-next

            ::= { ncm-generic  1025 }
 
         ncmT1LatchedStatusEntry OBJECT-TYPE
             SYNTAX  NcmT1LatchedStatusEntry
             ACCESS  not-accessible
             STATUS  mandatory
             DESCRIPTION
                "An entry in the DS1 Port Latched Status Table."
            INDEX   { ncmT1LatchedStatusNIDIndex, ncmT1LatchedStatusIndex, ncmT1LatchedStatusEndType }
            ::= { ncmT1LatchedStatusTable 1 }
 
         NcmT1LatchedStatusEntry ::=
         SEQUENCE {

           ncmT1LatchedStatusNIDIndex
                 INTEGER,
           ncmT1LatchedStatusIndex
                 INTEGER,
           ncmT1LatchedStatusEndType
                 INTEGER,
           ncmT1LatchedStatusCRC6Error
                 INTEGER,
           ncmT1LatchedStatusFramingSlip
                 INTEGER,
           ncmT1LatchedStatusRAI
                 INTEGER,
           ncmT1LatchedStatusLOF
                 INTEGER,
           ncmT1LatchedStatusAIS
           	 INTEGER,      
           ncmT1LatchedStatusLOS
                 INTEGER,
           ncmT1LatchedStatusBPVThreExcd
                Gauge,
           ncmT1LatchedStatusBERExceeded
                Gauge

             }

                  
         ncmT1LatchedStatusNIDIndex  OBJECT-TYPE
          SYNTAX  INTEGER (1..'7fffffff'h)
          ACCESS  read-only
          STATUS  mandatory
          DESCRIPTION
         "The object specifies the node id of the node."

          ::= { ncmT1LatchedStatusEntry 1 }                  
 
 
         ncmT1LatchedStatusIndex  OBJECT-TYPE
          SYNTAX  INTEGER (1..'7fffffff'h)
          ACCESS  read-only
          STATUS  mandatory
          DESCRIPTION
         "The index value which uniquely identifies  the
          interface to which this entry is applicable."

          ::= { ncmT1LatchedStatusEntry 2 }                 


        ncmT1LatchedStatusEndType  OBJECT-TYPE
            SYNTAX INTEGER {
 
                       near-End(1),
                       far-End(2)
 
                        }
           ACCESS read-only
           STATUS mandatory
           DESCRIPTION
           "The variable specifies the End Type   ."
 
            ::= { ncmT1LatchedStatusEntry  3 }


        ncmT1LatchedStatusCRC6Error  OBJECT-TYPE
            SYNTAX INTEGER {
                                no(1),
                                yes(2)
                           }
            ACCESS  read-only
            STATUS  mandatory
            DESCRIPTION
                "This variable indicates the occurance of CRC6 error
			of the port latched status."
            ::= { ncmT1LatchedStatusEntry  4 }


        ncmT1LatchedStatusFramingSlip  OBJECT-TYPE
            SYNTAX INTEGER {
                                no(1),
                                yes(2)
                           }
            ACCESS  read-only
            STATUS  mandatory
            DESCRIPTION
            "This variable indicates the occurance of framing slip error
			of the port latched status."
            ::= { ncmT1LatchedStatusEntry  5 }


        ncmT1LatchedStatusRAI  OBJECT-TYPE
            SYNTAX INTEGER {
                                no(1),
                                yes(2)
                           }
            ACCESS  read-only
            STATUS  mandatory
            DESCRIPTION
            "This variable indicates the occurance Latched status of
             		RAI for T1 port."
            ::= { ncmT1LatchedStatusEntry  6 }


        ncmT1LatchedStatusLOF  OBJECT-TYPE
            SYNTAX INTEGER {
                                no(1),
                                yes(2)
                           }
            ACCESS  read-only
            STATUS  mandatory
            DESCRIPTION
            "This variable indicates the occurance Latched status of
                 LOF of T1 port."
            ::= { ncmT1LatchedStatusEntry  7 }


         ncmT1LatchedStatusAIS  OBJECT-TYPE
            SYNTAX INTEGER {
                                no(1),
                                yes(2)
                           }
            ACCESS  read-only
            STATUS  mandatory
            DESCRIPTION
            "This variable indicates the occurance T1 port Latched
                status of  AIS."
            ::= { ncmT1LatchedStatusEntry  8 }


        ncmT1LatchedStatusLOS  OBJECT-TYPE
            SYNTAX INTEGER {
                                no(1),
                                yes(2)
                           }
            ACCESS  read-only
            STATUS  mandatory
            DESCRIPTION
            "This variable indicates the occurance Latched Status of
                 LOS for T1 port."
            ::= { ncmT1LatchedStatusEntry  9 }


        ncmT1LatchedStatusBPVThreExcd  OBJECT-TYPE
             SYNTAX  Gauge
             ACCESS  read-only
             STATUS  mandatory
             DESCRIPTION
                "This variable indicates the BPV Threshold Exceeded
			of T1 port Latched Status."
            ::= { ncmT1LatchedStatusEntry  10 }
 

        ncmT1LatchedStatusBERExceeded  OBJECT-TYPE
             SYNTAX  Gauge
             ACCESS  read-only
             STATUS  mandatory
             DESCRIPTION
                "This variable indicates the BER Exceeded
                        of T1 port Latched Status."
            ::= { ncmT1LatchedStatusEntry  11 }

 
-- 	 ncmT1ThresholdStatus

         ncmT1ThresholdStatusTable OBJECT-TYPE
             SYNTAX  SEQUENCE OF NcmT1ThresholdStatusEntry
             ACCESS  not-accessible
             STATUS  mandatory
	         --DEFAULT test-function    ace-test
             --DEFAULT next-function    ace-next
            ::= { ncm-generic  1026 }

         ncmT1ThresholdStatusEntry OBJECT-TYPE
             SYNTAX  NcmT1ThresholdStatusEntry
             ACCESS  not-accessible
             STATUS  mandatory
             DESCRIPTION
                "An entry in the DS1 Port Threshold Status Table."
            INDEX   { ncmT1ThresholdStatusNIDIndex, ncmT1ThresholdStatusIndex, ncmT1ThresholdStatusEndType }
            ::= { ncmT1ThresholdStatusTable 1 }

         NcmT1ThresholdStatusEntry ::=
         SEQUENCE {
 
           ncmT1ThresholdStatusNIDIndex
                 INTEGER,
           ncmT1ThresholdStatusIndex
                 INTEGER,
           ncmT1ThresholdStatusEndType
                 INTEGER,
           ncmT1ThresholdRestoreState
                 INTEGER,
           ncmT1ThresholdSecLineRestore
                 Gauge,
           ncmT1ThresholdBERExceeded
                 INTEGER,
           ncmT1ThresholdBERCount
                 Gauge,
           ncmT1ThresholdSESExceeded
                 INTEGER,
           ncmT1ThresholdSESCount
                 Gauge,
           ncmT1ThresholdUASExceeded
                 INTEGER,
           ncmT1ThresholdUASCount
                 Gauge,
           ncmT1ThresholdCRCExceeded
                 INTEGER,
           ncmT1ThresholdCRCCount
                 Gauge,
           ncmT1ThresholdBPVExceeded
                 INTEGER,
           ncmT1ThresholdBPVCount
                 Gauge
 
             }
 
                  
         ncmT1ThresholdStatusNIDIndex  OBJECT-TYPE
          SYNTAX  INTEGER (1..'7fffffff'h)
          ACCESS  read-only
          STATUS  mandatory
          DESCRIPTION
         "The object specifies the node id of the node."

          ::= { ncmT1ThresholdStatusEntry  1 }                  
 
 
 
         ncmT1ThresholdStatusIndex  OBJECT-TYPE
          SYNTAX  INTEGER (1..'7fffffff'h)
          ACCESS  read-only
          STATUS  mandatory
          DESCRIPTION
         "The index value which uniquely identifies  the
          interface to which this entry is applicable."

          ::= { ncmT1ThresholdStatusEntry  2 }                 


        ncmT1ThresholdStatusEndType  OBJECT-TYPE
            SYNTAX INTEGER {
 
                       near-End(1),
                       far-End(2)
 
                        }
           ACCESS read-only
           STATUS mandatory
           DESCRIPTION
           "The variable specifies the End Type   ."
 
            ::= { ncmT1ThresholdStatusEntry  3 }


        ncmT1ThresholdRestoreState  OBJECT-TYPE
            SYNTAX INTEGER {
                                out-of-service(1),
                                in-service(2),
				disabled(3)
                           }
            ACCESS  read-only
            STATUS  mandatory
            DESCRIPTION
            "This variable indicates the restore state of
                 T1 port threshold status."
            ::= { ncmT1ThresholdStatusEntry  4 }


        ncmT1ThresholdSecLineRestore  OBJECT-TYPE
             SYNTAX  Gauge
             ACCESS  read-only
             STATUS  mandatory
             DESCRIPTION
             "This variable indicates the number of second until line
             restores(if restore mode is AUTO) of T1 port threshold Status."
            ::= { ncmT1ThresholdStatusEntry  5 }


        ncmT1ThresholdBERExceeded  OBJECT-TYPE
             SYNTAX  INTEGER {
                         no(1),
                         yes(2)
                     }
             ACCESS  read-only
             STATUS  mandatory
             DESCRIPTION
             "This variable indicates BER exceeded or not 
		of T1 Threshold Status."
             ::= { ncmT1ThresholdStatusEntry  6 }


        ncmT1ThresholdBERCount  OBJECT-TYPE
             SYNTAX  Gauge
             ACCESS  read-only
             STATUS  mandatory
             DESCRIPTION
             "This variable indicates the BER Count(reserved -
             	always 0) of T1 port threshold Status."
            ::= { ncmT1ThresholdStatusEntry  7 }

 
        ncmT1ThresholdSESExceeded  OBJECT-TYPE
             SYNTAX  INTEGER {
                         no(1),
                         yes(2)
                     }   
             ACCESS  read-only
             STATUS  mandatory
             DESCRIPTION
             "This variable indicates SES exceeded or not
                of T1 Threshold Status."
             ::= { ncmT1ThresholdStatusEntry  8 }
 

        ncmT1ThresholdSESCount  OBJECT-TYPE 
             SYNTAX  Gauge
             ACCESS  read-only
             STATUS  mandatory
             DESCRIPTION
             "This variable indicates the SES Count
                	of T1 port threshold Status."
            ::= { ncmT1ThresholdStatusEntry  9 }
 

        ncmT1ThresholdUASExceeded  OBJECT-TYPE
             SYNTAX  INTEGER {
                         no(1),
                         yes(2)
                     }   
             ACCESS  read-only
             STATUS  mandatory
             DESCRIPTION
             "This variable indicates UAS exceeded or not
                of T1 Threshold Status."
             ::= { ncmT1ThresholdStatusEntry  10 }
 
 
        ncmT1ThresholdUASCount  OBJECT-TYPE 
             SYNTAX  Gauge
             ACCESS  read-only
             STATUS  mandatory
             DESCRIPTION
             "This variable indicates the UAS Count
                        of T1 port threshold Status."
            ::= { ncmT1ThresholdStatusEntry  11 }
 

        ncmT1ThresholdCRCExceeded  OBJECT-TYPE
             SYNTAX  INTEGER {
                         no(1),
                         yes(2)
                     }
             ACCESS  read-only
             STATUS  mandatory
             DESCRIPTION
             "This variable indicates CRC exceeded or not
                of T1 Threshold Status."
             ::= { ncmT1ThresholdStatusEntry  12 }
         
         
        ncmT1ThresholdCRCCount  OBJECT-TYPE 
             SYNTAX  Gauge
             ACCESS  read-only
             STATUS  mandatory
             DESCRIPTION
             "This variable indicates the CRC Count
                        of T1 port threshold Status."
            ::= { ncmT1ThresholdStatusEntry  13 }
 

        ncmT1ThresholdBPVExceeded  OBJECT-TYPE
             SYNTAX  INTEGER {
                         no(1),
                         yes(2)
                     }
             ACCESS  read-only
             STATUS  mandatory
             DESCRIPTION
             "This variable indicates BPV exceeded or not
                of T1 Threshold Status."
             ::= { ncmT1ThresholdStatusEntry  14 }

 
        ncmT1ThresholdBPVCount  OBJECT-TYPE 
             SYNTAX  Gauge
             ACCESS  read-only
             STATUS  mandatory
             DESCRIPTION
             "This variable indicates the BPV Count
                        of T1 port threshold Status."
            ::= { ncmT1ThresholdStatusEntry  15 }


--               T1 Performance Counters

         ncmT1PerformanceCountersTable OBJECT-TYPE
             SYNTAX  SEQUENCE OF NcmT1PerformanceCountersEntry
             ACCESS  not-accessible
             STATUS  mandatory
		--DEFAULT test-function    ace-test
                --DEFAULT next-function    ace-next


            ::= { ncm-generic 1027  }

         ncmT1PerformanceCountersEntry OBJECT-TYPE
             SYNTAX  NcmT1PerformanceCountersEntry
             ACCESS  not-accessible
             STATUS  mandatory
             DESCRIPTION
             "An entry in the ncm T1 Performance Counters Entry
              table."
            INDEX   { ncmT1PerfCountNIDIndex, ncmT1PerfCountIndex, ncmT1PerfCountEndType }
            ::= { ncmT1PerformanceCountersTable 1 }
 
        NcmT1PerformanceCountersEntry ::=
         SEQUENCE {
         
           ncmT1PerfCountNIDIndex
                INTEGER,
           ncmT1PerfCountIndex
                 INTEGER,
           ncmT1PerfCountEndType
                 INTEGER,
           ncmT1PerfCountFrameMode
                INTEGER,
           ncmT1PerfCountCurESFErrEvt
                Gauge,
           ncmT1PerfCountCurBPVErrCnt
                 Gauge,
           ncmT1PerfCountCurFrameErrCnt
                Gauge,
           ncmT1PerfCountCurCRC6Error
                Gauge,
           ncmT1ResetPerfCount
		INTEGER

                }
 
         
        ncmT1PerfCountNIDIndex OBJECT-TYPE
             SYNTAX  INTEGER (1..'7fffffff'h)
             ACCESS  read-only
             STATUS  mandatory
             DESCRIPTION
                "The object specifies the node id index of the node."
            ::= { ncmT1PerformanceCountersEntry  1 }
 

         ncmT1PerfCountIndex  OBJECT-TYPE
          SYNTAX  INTEGER (1..'7fffffff'h)
          ACCESS  read-only
          STATUS  mandatory
          DESCRIPTION
         "The index value which uniquely identifies  the
          interface to which this entry is applicable."
          ::= { ncmT1PerformanceCountersEntry  2 }

 
        ncmT1PerfCountEndType  OBJECT-TYPE
            SYNTAX INTEGER {
                       near-End(1),
                       far-End(2)
                        }         
           ACCESS read-only
           STATUS mandatory
           DESCRIPTION
           "The variable specifies the End Type of
		T1 Performance Counter."
            ::= { ncmT1PerformanceCountersEntry  3 }        
 

        ncmT1PerfCountFrameMode  OBJECT-TYPE
            SYNTAX INTEGER {
                       d4(1),
                       esf(2)
                        }
           ACCESS read-only
           STATUS mandatory
           DESCRIPTION
           "The variable specifies the Framing Mode of
		T1 Performance Counter."
            ::= { ncmT1PerformanceCountersEntry  4 }


        ncmT1PerfCountCurESFErrEvt  OBJECT-TYPE
             SYNTAX  Gauge
             ACCESS  read-only
             STATUS  mandatory
             DESCRIPTION
             "This variable specifies the Current ESF
              events of T1 Performance Counter.
	      This object has no significance for QUAD cards."
            ::= { ncmT1PerformanceCountersEntry  5 }
 

        ncmT1PerfCountCurBPVErrCnt  OBJECT-TYPE
             SYNTAX  Gauge
             ACCESS  read-only
             STATUS  mandatory
             DESCRIPTION
             "This variable specifies the Current BPV
              counts of T1 Performance Counter.
	      This object has no significance for QUAD cards."
            ::= { ncmT1PerformanceCountersEntry  6 }


        ncmT1PerfCountCurFrameErrCnt  OBJECT-TYPE
             SYNTAX  Gauge
             ACCESS  read-only
             STATUS  mandatory
             DESCRIPTION
             "This variable specifies the Current Frame 
              Error counts of T1 Performance Counter.
	      This object has no significance for QUAD cards."
            ::= { ncmT1PerformanceCountersEntry  7 }


        ncmT1PerfCountCurCRC6Error  OBJECT-TYPE
             SYNTAX  Gauge
             ACCESS  read-only
             STATUS  mandatory
             DESCRIPTION
             "This variable specifies the Current CRC-6
              errors of T1 Performance Counter.
	      This object has no significance for QUAD cards."
            ::= { ncmT1PerformanceCountersEntry  8 }


         ncmT1ResetPerfCount  OBJECT-TYPE
             SYNTAX  INTEGER {
                         no(1),
                         yes(2)
                     }
             ACCESS  read-write
             STATUS  mandatory
             DESCRIPTION
                "Reset ncm T1 Performance Counters."
            ::= { ncmT1PerformanceCountersEntry  9 } 

 
--         ncmDataPort Configuration 

       
         ncmDataPortConfigTable OBJECT-TYPE
             SYNTAX  SEQUENCE OF NcmDataPortConfigEntry
             ACCESS  not-accessible
             STATUS  mandatory
	     --DEFAULT test-function    diu-test
             --DEFAULT next-function    diu-next



            ::= { ncm-generic 1028  }


         ncmDataPortConfigEntry OBJECT-TYPE
             SYNTAX  NcmDataPortConfigEntry
             ACCESS  not-accessible
             STATUS  mandatory
             DESCRIPTION
             "An entry in the  ncmData Port Configuration Entry
              table."
            INDEX   { ncmDataPortConfigNIDIndex, ncmDataPortConfigIndex }
            ::= { ncmDataPortConfigTable 1 }


        NcmDataPortConfigEntry ::=
         SEQUENCE {
           ncmDataPortConfigNIDIndex
                INTEGER,
           ncmDataPortConfigIndex
                 INTEGER,
           ncmDataPortConfigMode
                INTEGER,
           ncmDataPortConfigLineIndicate
                INTEGER,
           ncmDataPortLineStatusCDCC
                 INTEGER,
           ncmDataPortLineStatusCACB
                 INTEGER,
           ncmDataPortLineStatusLLCJ
                 INTEGER,
           ncmDataPortLineStatusRLTM
                 INTEGER,
           ncmDataPortConfigLOS
                INTEGER,
           ncmDataPortConfigServiceState
                INTEGER,
           ncmDataPortConfigClkOpt
                 INTEGER
 
                }
 

         ncmDataPortConfigNIDIndex OBJECT-TYPE
          SYNTAX  INTEGER (1..'7fffffff'h)
          ACCESS  read-only
          STATUS  mandatory
          DESCRIPTION
         "The object specifies the node id of the node."
          
          ::= { ncmDataPortConfigEntry 1 }



         ncmDataPortConfigIndex OBJECT-TYPE
          SYNTAX  INTEGER (1..'7fffffff'h)
          ACCESS  read-only
          STATUS  mandatory
          DESCRIPTION
         "The index value which uniquely identifies  the
          interface to which this entry is applicable."
           
          ::= { ncmDataPortConfigEntry 2 }
 
 
         ncmDataPortConfigMode OBJECT-TYPE
          SYNTAX INTEGER {
           
                       dce(1),
                       dte(2)
 
               } 
          ACCESS read-write
          STATUS mandatory
          DESCRIPTION
          "The variable specifies the data port mode whether it is 
           configured as DTE/DCE."
 
          ::= { ncmDataPortConfigEntry 3 }

 
        ncmDataPortConfigLineIndicate OBJECT-TYPE
          SYNTAX INTEGER {
           
                       active-low(1),
                       active-high(2)

               } 
          ACCESS read-write
          STATUS mandatory
          DESCRIPTION
          "The variable specifies the control line indicator for X.21 only,
              set to 0 if line is low while set to 1 if line is high."
 
          ::= { ncmDataPortConfigEntry 4 }

  
        ncmDataPortLineStatusCDCC OBJECT-TYPE
          SYNTAX INTEGER {
           
                       low(1),
                       high(2)
               } 
          ACCESS read-write
          STATUS mandatory
          DESCRIPTION
          "The variable specifies the bit 0 status of control line;
             where 0=low, 1=high; Status is CD/DTR if Mode = DTE while is CC/DSR if Mode = DCE" 
 
          ::= { ncmDataPortConfigEntry 5 }


        ncmDataPortLineStatusCACB OBJECT-TYPE 
          SYNTAX INTEGER {
 
                       low(1),
                       high(2)
               } 
          ACCESS read-write
          STATUS mandatory
          DESCRIPTION
          "The variable specifies the bit 1 status of control line;
             where 0=low, 1=high; Status is CA/RTS if Mode = DTE while is CB/CTS if Mode = DCE"
 
          ::= { ncmDataPortConfigEntry 6 }
 

        ncmDataPortLineStatusLLCJ OBJECT-TYPE
          SYNTAX INTEGER { 
 
                       low(1),
                       high(2)
               }  
          ACCESS read-write 
          STATUS mandatory 
          DESCRIPTION 
          "The variable specifies the bit 2 status of control line;
             where 0=low, 1=high; Status is LL if Mode = DTE while is CJ/DCD if Mode = DCE" 
  
          ::= { ncmDataPortConfigEntry 7 } 


        ncmDataPortLineStatusRLTM OBJECT-TYPE
          SYNTAX INTEGER {
 
                       low(1),
                       high(2)
               }
          ACCESS read-write
          STATUS mandatory
          DESCRIPTION
          "The variable specifies the bit 2 status of control line;
             where 0=low, 1=high; Status is RL if Mode = DTE while is TM if Mode = DCE"
 
          ::= { ncmDataPortConfigEntry 8 }


        ncmDataPortConfigLOS OBJECT-TYPE
          SYNTAX INTEGER {
 
                       disable(1),
                       enable(2)
               }
          ACCESS read-write
          STATUS mandatory
          DESCRIPTION
          "The variable specifies the bit 7 status of control line;
             where 0=disable, 1=enable; Status is LOS Mode"
 
          ::= { ncmDataPortConfigEntry 9 }                                                 
 

        ncmDataPortConfigServiceState OBJECT-TYPE
          SYNTAX INTEGER {

                       not-in-service(1),
                       in-service(2)
               } 
          ACCESS read-write
          STATUS mandatory
          DESCRIPTION
          "The variable specifies the  service state of this data port."

          ::= { ncmDataPortConfigEntry 10 }


        ncmDataPortConfigClkOpt OBJECT-TYPE
          SYNTAX INTEGER {
 
                       st(1),
                       invertedst(2),
		       tt(3)
               }  
          ACCESS read-write 
          STATUS mandatory 
          DESCRIPTION 
          "The variable specifies the clocking option of this data port."
 
          ::= { ncmDataPortConfigEntry 11 } 
 
 
 
--         ncmDataPort  Status
 
         
         ncmDataPortStatusTable OBJECT-TYPE
             SYNTAX  SEQUENCE OF NcmDataPortStatusEntry
             ACCESS  not-accessible
             STATUS  mandatory
	     --DEFAULT test-function    diu-test
             --DEFAULT next-function    diu-next


 
            ::= { ncm-generic 1029  }
 
 
         ncmDataPortStatusEntry OBJECT-TYPE
             SYNTAX  NcmDataPortStatusEntry
             ACCESS  not-accessible
             STATUS  mandatory
             DESCRIPTION
             "An entry in the  ncmData Port Status Entry
              table."
            INDEX   { ncmDataPortStatusNIDIndex, ncmDataPortStatusIndex }
            ::= { ncmDataPortStatusTable 1 }
 
 
        NcmDataPortStatusEntry ::=
         SEQUENCE {
         
           ncmDataPortStatusNIDIndex
                INTEGER,
           ncmDataPortStatusIndex
                 INTEGER,
           ncmDataPortStatusMode
                INTEGER,
           ncmDataPortStatusLineIndicate
                INTEGER,
           ncmDataPortStatusLineCDCC
                 INTEGER,
           ncmDataPortStatusLineCACB
                 INTEGER,
           ncmDataPortStatusLineLLCJ
                 INTEGER,
           ncmDataPortStatusLineRLTM
                 INTEGER,
	   ncmDataPortStatusLineLOS
		 INTEGER,
           ncmDataPortStatusServiceState
                INTEGER,
           ncmDataPortStatusCimType
                 INTEGER,
	   ncmDataPortStatusLoopback
		 INTEGER,
	   ncmDataPortTestPattern
		 INTEGER,
	   ncmDataPortTstPatErrCount
		 Gauge
 
                }

         ncmDataPortStatusNIDIndex OBJECT-TYPE
          SYNTAX  INTEGER (1..'7fffffff'h)
          ACCESS  read-only
          STATUS  mandatory
          DESCRIPTION
         "The object specifies the node id of the node."

          ::= { ncmDataPortStatusEntry 1}


         ncmDataPortStatusIndex OBJECT-TYPE
          SYNTAX  INTEGER (1..'7fffffff'h)
          ACCESS  read-only
          STATUS  mandatory
          DESCRIPTION
         "The index value which uniquely identifies  the
          interface to which this entry is applicable."

          ::= { ncmDataPortStatusEntry 2 }


         ncmDataPortStatusMode OBJECT-TYPE
          SYNTAX INTEGER {

                       dce(1),
                       dte(2)
 
               } 
          ACCESS read-only
          STATUS mandatory
          DESCRIPTION
          "The variable specifies the data port mode whether it is
           configured as DCE/DCE."
 
          ::= { ncmDataPortStatusEntry 3 }
 
 
        ncmDataPortStatusLineIndicate OBJECT-TYPE
          SYNTAX INTEGER {
           
                       active-low(1),
                       active-high(2)
 
               } 
          ACCESS read-only
          STATUS mandatory
          DESCRIPTION
          "The variable specifies the control line indicator for X.21 only,
              set to 0 if line is low while set to 1 if line is high."
 
          ::= { ncmDataPortStatusEntry 4 }
 
 
        ncmDataPortStatusLineCDCC OBJECT-TYPE
          SYNTAX INTEGER {
           
                       low(1),
                       high(2)
               }
          ACCESS read-only
          STATUS mandatory
          DESCRIPTION
          "The variable specifies the bit 0 status of control line;
             where 0=low, 1=high; Status is CD/DTR if Mode = DTE while is CC/DSR if Mode = DCE"
 
          ::= { ncmDataPortStatusEntry 5 }
 
 
        ncmDataPortStatusLineCACB OBJECT-TYPE
          SYNTAX INTEGER {
 
                       low(1),
                       high(2)
               }
          ACCESS read-only
          STATUS mandatory
          DESCRIPTION
          "The variable specifies the bit 1 status of control line;
             where 0=low, 1=high; Status is CA/RTS if Mode = DTE while is CB/CTS if Mode = DCE"
 
          ::= { ncmDataPortStatusEntry 6 }
 
 
        ncmDataPortStatusLineLLCJ OBJECT-TYPE
          SYNTAX INTEGER {
 
                       low(1),
                       high(2)
               }
          ACCESS read-only
          STATUS mandatory
          DESCRIPTION
          "The variable specifies the bit 2 status of control line;
             where 0=low, 1=high; Status is LL if Mode = DTE while is CJ/DCD if Mode = DCE"
 
          ::= { ncmDataPortStatusEntry 7 }
 
  
        ncmDataPortStatusLineRLTM OBJECT-TYPE
          SYNTAX INTEGER {
 
                       low(1),
                       high(2)
               }
          ACCESS read-only
          STATUS mandatory
          DESCRIPTION
          "The variable specifies the bit 3 status of control line;
             where 0=low, 1=high; Status is RL if Mode = DTE while is TM if Mode = DCE"
 
          ::= { ncmDataPortStatusEntry 8 }
 

        ncmDataPortStatusLineLOS OBJECT-TYPE
          SYNTAX INTEGER {
 
                       disable(1), 
                       enable(2)
               } 
          ACCESS read-only
          STATUS mandatory 
          DESCRIPTION 
          "The variable specifies the bit 7 status of control line; 
             where 0=disable, 1=enable; Status is LOS Mode"
  
          ::= { ncmDataPortStatusEntry 9 }                                                  
 
 
        ncmDataPortStatusServiceState OBJECT-TYPE
          SYNTAX INTEGER {
 
                       not-in-service(1),
                       in-service(2)
               }
          ACCESS read-only
          STATUS mandatory
          DESCRIPTION
          "The variable specifies the  service state of this data port."
 
          ::= { ncmDataPortStatusEntry 10 }
 
 
        ncmDataPortStatusCimType OBJECT-TYPE
          SYNTAX INTEGER {
 
                           cim-2000-E1(16),
                           cim-2002-E1(17),
                           cim-2003-E1(18),
                           cim-2004-E1(19),
                           cim-2005-E1(20),
                           cim-2006-E1(21),
                           cim-2101-T1(32),
                           cim-2102-T1(33),
                           cim-2164-T1(34),
                           cim-2061-E1(56),
                           cim-UNINSTALLED(255)
               }
          ACCESS read-only
          STATUS mandatory
          DESCRIPTION
          "The variable specifies the connector interface module type of this data port."
 
          ::= { ncmDataPortStatusEntry 11 }
 

        ncmDataPortStatusLoopback OBJECT-TYPE
          SYNTAX INTEGER {
 
                       disable(1),
                       enable(2)
               }
          ACCESS read-only
          STATUS mandatory
          DESCRIPTION
          "The variable specifies the loopback diagnostic status of this data port."
 
          ::= { ncmDataPortStatusEntry 12 }
 
 
        ncmDataPortTestPattern OBJECT-TYPE
          SYNTAX INTEGER { 
  
                       none(1),
                       d3-in-D24(2),
		       qrss(3)
               } 
          ACCESS read-only 
          STATUS mandatory 
          DESCRIPTION 
          "The variable specifies the test pattern in progress of this data port." 
  
          ::= { ncmDataPortStatusEntry 13 } 

 
        ncmDataPortTstPatErrCount OBJECT-TYPE 
            SYNTAX Gauge
            ACCESS  read-only
            STATUS  mandatory
            DESCRIPTION
                "This variable indicates the Test Pattern Error Count."
   
          ::= { ncmDataPortStatusEntry 14 }  



 
 
--      ncmAlarmConfig Group
        
 
        ncmALARMConfigTable OBJECT-TYPE
             SYNTAX   SEQUENCE OF NcmALARMConfigEntry
             ACCESS   not-accessible
             STATUS   mandatory
	     --DEFAULT test-function    almcfg-card-test
             --DEFAULT next-function    almcfg-card-next

 
             ::= { ncm-generic  1030 }
 
 
        ncmALARMConfigEntry OBJECT-TYPE
             SYNTAX   NcmALARMConfigEntry
             ACCESS   not-accessible
             STATUS   mandatory
             DESCRIPTION
                "An entry in the ncmAlarm Configure table."
             INDEX   { ncmAlarmConfigNIDIndex, ncmAlarmConfigIndex }
            ::= { ncmALARMConfigTable 1 }
             
  
        NcmALARMConfigEntry ::=
             SEQUENCE {
	     ncmAlarmConfigNIDIndex
		 INTEGER,
             ncmAlarmConfigIndex
                 INTEGER,
             ncmAlmCfgDomain
                 INTEGER,
             ncmAlmCfgSrcAddr
                 DisplayString,
             ncmAlmCfgCard
                 INTEGER,
             ncmAlmCfgShelf
                 INTEGER,
             ncmAlmCfgE1T1Port1EnableAlmRpt
                 INTEGER,
             ncmAlmCfgE1T1Port2EnableAlmRpt
                 INTEGER,
             ncmAlmCfgE1T1Port3EnableAlmRpt
                 INTEGER,
             ncmAlmCfgE1T1Port4EnableAlmRpt
                 INTEGER,
             ncmAlmCfgDataPort1EnableAlmRpt
		 INTEGER,
             ncmAlmCfgDataPort2EnableAlmRpt
		 INTEGER,
  	     ncmAlmCfgEnableCardAlmRpt
		 INTEGER,
	     ncmAlmCfgDeclareTime
		 INTEGER 

	     }


         ncmAlarmConfigNIDIndex OBJECT-TYPE
          SYNTAX  INTEGER (1..'7fffffff'h)
          ACCESS  read-only
          STATUS  mandatory
          DESCRIPTION
         "The object specifies the node id of the node."
 
          ::= { ncmALARMConfigEntry 1}
 
 
         ncmAlarmConfigIndex OBJECT-TYPE
          SYNTAX  INTEGER (1..'7fffffff'h)
          ACCESS  read-only
          STATUS  mandatory
          DESCRIPTION
         "The index value which uniquely identifies  the
          interface to which this entry is applicable."
 
          ::= { ncmALARMConfigEntry 2 }

 
         ncmAlmCfgDomain OBJECT-TYPE
          SYNTAX  INTEGER
          ACCESS  read-write
          STATUS mandatory
          DESCRIPTION
          "The variable specifies the Domain the alarm came from."
 
          ::= { ncmALARMConfigEntry 3 }


        ncmAlmCfgSrcAddr OBJECT-TYPE
           SYNTAX  DisplayString 
           ACCESS  read-write
           STATUS  mandatory
           DESCRIPTION
           "The variable specifies the Address where the alarm
               came from."
          ::= { ncmALARMConfigEntry 4 }
  

         ncmAlmCfgCard OBJECT-TYPE
          SYNTAX  INTEGER
          ACCESS  read-write
          STATUS mandatory
          DESCRIPTION
          "The variable specifies the card in a specified shelf."
 
          ::= { ncmALARMConfigEntry 5 }                               
 

         ncmAlmCfgShelf OBJECT-TYPE
          SYNTAX  INTEGER
          ACCESS  read-write
          STATUS mandatory
          DESCRIPTION
          "The variable specifies the particular shelf."
 
          ::= { ncmALARMConfigEntry 6 }


        ncmAlmCfgE1T1Port1EnableAlmRpt OBJECT-TYPE
          SYNTAX INTEGER {
 
                       disable(1),
                       enable(2)
               } 
          ACCESS read-write
          STATUS mandatory
          DESCRIPTION
          "The variable Enable/Disable the alarm reporting of the 
	   Port #1 for E1/T1 by specifying the bit 0; 1=yes, 0=no."
          ::= { ncmALARMConfigEntry 7 }
  

        ncmAlmCfgE1T1Port2EnableAlmRpt OBJECT-TYPE
          SYNTAX INTEGER {
 
                       disable(1),
                       enable(2)
               } 
          ACCESS read-write
          STATUS mandatory
          DESCRIPTION
          "The variable Enable/Disable the alarm reporting of the 
	   Port #2 for E1/T1 by specifying the bit 1; 1=yes, 0=no."
          ::= { ncmALARMConfigEntry 8 }                                     
 

        ncmAlmCfgE1T1Port3EnableAlmRpt OBJECT-TYPE
          SYNTAX INTEGER {
 
                       disable(1),
                       enable(2)
               } 
          ACCESS read-write
          STATUS mandatory
          DESCRIPTION
          "The variable Enable/Disable the alarm reporting of the
           Port #3 for E1/T1 by specifying the bit 0; 1=yes, 0=no."
          ::= { ncmALARMConfigEntry 9 }
 
                                     
        ncmAlmCfgE1T1Port4EnableAlmRpt OBJECT-TYPE
          SYNTAX INTEGER {
 
                       disable(1),
                       enable(2)
               }
          ACCESS read-write
          STATUS mandatory
          DESCRIPTION
          "The variable Enable/Disable the alarm reporting of the
           Port #4 for E1/T1 by specifying the bit 1; 1=yes, 0=no."
          ::= { ncmALARMConfigEntry 10 }

        ncmAlmCfgDataPort1EnableAlmRpt OBJECT-TYPE 
          SYNTAX INTEGER {
  
                       disable(1), 
                       enable(2), 
		       not-applicable(3)	
               }  
          ACCESS read-write 
          STATUS mandatory 
          DESCRIPTION 
          "The variable Enable/Disable the alarm reporting of the 
	   Port #1 for ncmData by specifying the bit 0; 1=yes, 0=no.
	   This object has no significance in QUAD cards." 
          ::= { ncmALARMConfigEntry 11 }                                      


        ncmAlmCfgDataPort2EnableAlmRpt OBJECT-TYPE
          SYNTAX INTEGER {
 
                       disable(1),
                       enable(2),
		       not-applicable(3)	
               }  
          ACCESS read-write
          STATUS mandatory
          DESCRIPTION 
          "The variable Enable/Disable the alarm reporting of the 
           Port #2 for ncmData by specifying the bit 1; 1=yes, 0=no.
	   This object has no significance in QUAD cards." 
          ::= { ncmALARMConfigEntry 12 }
  

        ncmAlmCfgEnableCardAlmRpt OBJECT-TYPE 
          SYNTAX INTEGER { 
 
                       disable(1), 
                       enable(2) 
               }   
          ACCESS read-write 
          STATUS mandatory 
          DESCRIPTION  
          "The variable Enable/Disable the alarm reporting for this card."  

          ::= { ncmALARMConfigEntry 13 } 

        ncmAlmCfgDeclareTime OBJECT-TYPE
          SYNTAX  INTEGER
          ACCESS  read-write
          STATUS mandatory
          DESCRIPTION
          "The variable specifies the alarm declaration time (in seconds)."

          ::= { ncmALARMConfigEntry 14 }



--      ncmAlarmCurrentMsg Group


        ncmCURRENTAlarmMsgTable OBJECT-TYPE
             SYNTAX   SEQUENCE OF NcmCURRENTAlarmMsgEntry
             ACCESS   not-accessible
             STATUS   mandatory
	      --DEFAULT test-function   curralm-test
             --DEFAULT next-function    curralm-next



             ::= { ncm-generic  1031 }


        ncmCURRENTAlarmMsgEntry OBJECT-TYPE
             SYNTAX   NcmCURRENTAlarmMsgEntry
             ACCESS   not-accessible
             STATUS   mandatory
             DESCRIPTION
                "An entry in the Current ncm Alarm Message table."
             INDEX   { ncmCurrAlarmMsgNIDIndex, ncmCurrAlarmMsgIndex }
            ::= { ncmCURRENTAlarmMsgTable 1 }


        NcmCURRENTAlarmMsgEntry ::=
          SEQUENCE {

           ncmCurrAlarmMsgNIDIndex
                  INTEGER,
           ncmCurrAlarmMsgIndex
                 INTEGER,
           ncmCurrAlarmMsgNumber
                 INTEGER,
           ncmCurrAlarmMsgEquipID
                 INTEGER

	   }


          ncmCurrAlarmMsgNIDIndex OBJECT-TYPE
          SYNTAX  INTEGER (1..'7fffffff'h)
          ACCESS  read-only
          STATUS  mandatory
          DESCRIPTION
         "The object specifies the node id of the node."
          
          ::= { ncmCURRENTAlarmMsgEntry 1 }
 
 
         ncmCurrAlarmMsgIndex OBJECT-TYPE
          SYNTAX  INTEGER (1..'7fffffff'h)
          ACCESS  read-only
          STATUS  mandatory
          DESCRIPTION
         "The index value which uniquely identifies  the
          interface to which this entry is applicable."
 
          ::= { ncmCURRENTAlarmMsgEntry 2 }
 
 
         ncmCurrAlarmMsgNumber OBJECT-TYPE
             SYNTAX  INTEGER (1..15)
             ACCESS  read-only
             STATUS  mandatory
             DESCRIPTION
                "A number between 1 and 15, where 1 is the latest
                alarm and 15 is the most recent alarm captured
                inside the data base."
            ::= { ncmCURRENTAlarmMsgEntry 3 }
 

         ncmCurrAlarmMsgEquipID OBJECT-TYPE
             SYNTAX  INTEGER
             ACCESS  read-only
             STATUS  mandatory
             DESCRIPTION
             "The object specifies the Equipment ID of the card."
 
            ::= { ncmCURRENTAlarmMsgEntry 4 }                           

 
 
--    	ncmAlarmMessage Group


        ncmPrevAlarmMsgTable OBJECT-TYPE
             SYNTAX   SEQUENCE OF NcmPrevAlarmMsgEntry
             ACCESS   not-accessible
             STATUS   mandatory
	      --DEFAULT test-function   prevalm-test
             --DEFAULT next-function    prevalm-next


 
             ::= { ncm-generic  1032 }
 
 
        ncmPrevAlarmMsgEntry OBJECT-TYPE
             SYNTAX   NcmPrevAlarmMsgEntry
             ACCESS   not-accessible
             STATUS   mandatory
             DESCRIPTION
                "An entry in the Enhanced ncmAlarm Configure table."
             INDEX   { ncmPrevAlarmMsgNIDIndex, ncmPrevAlarmMsgIndex, ncmPrevAlarmMsgNumber }
            ::= { ncmPrevAlarmMsgTable 1 }
 
 
        NcmPrevAlarmMsgEntry ::=
          SEQUENCE {

           ncmPrevAlarmMsgNIDIndex
                  INTEGER,
           ncmPrevAlarmMsgIndex
                 INTEGER,
           ncmPrevAlarmMsgNumber
                 INTEGER,
           ncmPrevAlarmMsgTimeStampSec
                 INTEGER,
           ncmPrevAlarmMsgTimeStampms
                 INTEGER,
           ncmPrevAlarmMsgAlarmCode
                 INTEGER,
           ncmPrevAlarmMsgAlarmInstance
                 INTEGER,
           ncmPrevAlarmMsgObjType
                 INTEGER,
           ncmPrevAlarmMsgSeverity
                 INTEGER

	   }


          ncmPrevAlarmMsgNIDIndex OBJECT-TYPE
          SYNTAX  INTEGER (1..'7fffffff'h)
          ACCESS  read-only
          STATUS  mandatory
          DESCRIPTION
         "The object specifies the node id of the node."
          
          ::= { ncmPrevAlarmMsgEntry 1 }
 
 
         ncmPrevAlarmMsgIndex OBJECT-TYPE
          SYNTAX  INTEGER (1..'7fffffff'h)
          ACCESS  read-only
          STATUS  mandatory
          DESCRIPTION
         "The index value which uniquely identifies  the
          interface to which this entry is applicable."
 
          ::= { ncmPrevAlarmMsgEntry 2 }

 
         ncmPrevAlarmMsgNumber OBJECT-TYPE
             SYNTAX  INTEGER (1..15)
             ACCESS  read-only
             STATUS  mandatory
             DESCRIPTION
                "A number between 1 and 15, where 1 is the latest
                alarm and 15 is the most recent alarm captured
                inside the data base."
            ::= { ncmPrevAlarmMsgEntry 3 }


        ncmPrevAlarmMsgTimeStampSec OBJECT-TYPE
           SYNTAX INTEGER
           ACCESS read-only
           STATUS mandatory
           DESCRIPTION
           "The variable specifies the Time Stamp in Seconds."

           ::= { ncmPrevAlarmMsgEntry 4 }


        ncmPrevAlarmMsgTimeStampms OBJECT-TYPE
           SYNTAX INTEGER
           ACCESS read-only
           STATUS mandatory
           DESCRIPTION
           "The variable specifies the Time Stamp in milli Seconds."

           ::= {  ncmPrevAlarmMsgEntry 5 }


         ncmPrevAlarmMsgAlarmCode OBJECT-TYPE
           SYNTAX INTEGER
           ACCESS read-only
           STATUS mandatory
           DESCRIPTION
           "The variable specifies the ncm Alarm Code of the card."
 
           ::= {  ncmPrevAlarmMsgEntry 6 }

 
         ncmPrevAlarmMsgAlarmInstance OBJECT-TYPE
           SYNTAX INTEGER (1..'ffffffff'h)
           ACCESS read-only 
           STATUS mandatory 
           DESCRIPTION 
           "The object specifies the ncm Alarm Instance."
  
           ::= {  ncmPrevAlarmMsgEntry 7 }
  

          ncmPrevAlarmMsgObjType OBJECT-TYPE
          SYNTAX INTEGER {
 
                       e1-PortID(1),
                       dataPort(2),
                       circuit(3),
                       power(4),
                       clkRef(5),
                       timeBus(6),
                       refBus(7),
		       notUsed(8),
		       software(9),
		       equipment(10),
		       t1-PortID(11),
		       dS3-Port(16),
		       hssi-Port(17)
               }
          ACCESS  read-only
          STATUS mandatory
          DESCRIPTION
          "The variable specifies the Object Type of the ncmAlarm refer."
 
          ::= {  ncmPrevAlarmMsgEntry 8 }                                   


         ncmPrevAlarmMsgSeverity OBJECT-TYPE
          SYNTAX INTEGER {
 
                       cleared(1),
                       informational(2),
                       warning(3),
                       minor(4),
                       major(5),
                       critical(6)
               }
          ACCESS  read-only
          STATUS mandatory
          DESCRIPTION
          "The variable specifies the severity of the ncm Alarm."
 
          ::= {  ncmPrevAlarmMsgEntry 9 }                                  
 

 
--       ncmEnhancedAlarmConfig Group


         ncmEnhanAlmCfgTable OBJECT-TYPE
             SYNTAX   SEQUENCE OF  NcmEnhanAlmCfgEntry
             ACCESS   not-accessible
             STATUS   mandatory
	         --DEFAULT test-function    enhalm-test
             --DEFAULT next-function    enhalm-next
             ::= { ncm-generic  1033 }

         ncmEnhanAlmCfgEntry OBJECT-TYPE
             SYNTAX    NcmEnhanAlmCfgEntry
             ACCESS   not-accessible
             STATUS   mandatory
             DESCRIPTION
                "An entry in the Enhanced ncm Alarm Configure table."
             INDEX   {  ncmEnhanAlmCfgNIDIndex,  ncmEnhanAlmCfgIndex }
            ::= {  ncmEnhanAlmCfgTable 1 }
 
         NcmEnhanAlmCfgEntry ::=
             SEQUENCE {
              ncmEnhanAlmCfgNIDIndex
                 INTEGER,
              ncmEnhanAlmCfgIndex
                 INTEGER,
              ncmEnhanAlmCfgCRCThreshold
                 INTEGER,
              ncmEnhanAlmCfgSESThreshold
                 INTEGER,
              ncmEnhanAlmCfgUASThreshold
                 INTEGER,
              ncmEnhanAlmCfgBERThreshold
                 INTEGER,
              ncmEnhanAlmCfgBPVThreshold
                 INTEGER,
              ncmEnhanAlmCfgLineRestoral
                 INTEGER,
              ncmEnhanAlmCfgTODHour
                 INTEGER,
              ncmEnhanAlmCfgTODMinute
                 INTEGER,
              ncmEnhanAlmCfgLinRestEvalPer
                 INTEGER
             }

          ncmEnhanAlmCfgNIDIndex OBJECT-TYPE
          SYNTAX  INTEGER (1..'7fffffff'h)
          ACCESS  read-only
          STATUS  mandatory
          DESCRIPTION
         "The object specifies the node id of the node."
          ::= {  ncmEnhanAlmCfgEntry 1}


          ncmEnhanAlmCfgIndex OBJECT-TYPE
          SYNTAX  INTEGER (1..'7fffffff'h)
          ACCESS  read-only
          STATUS  mandatory
          DESCRIPTION
         "The index value which uniquely identifies  the
          interface to which this entry is applicable."
          ::= {  ncmEnhanAlmCfgEntry 2 }
 
          ncmEnhanAlmCfgCRCThreshold OBJECT-TYPE
          SYNTAX  INTEGER
          ACCESS  read-write
          STATUS mandatory
          DESCRIPTION
          "The variable specifies the consecutive CRC error threshold
	       of the port; 0 is to disable this error threshold and 1~31 is
	       to enable also specify a particular value for this threshold."
          ::= {  ncmEnhanAlmCfgEntry 3 }

          ncmEnhanAlmCfgSESThreshold OBJECT-TYPE
          SYNTAX  INTEGER
          ACCESS  read-write
          STATUS mandatory
          DESCRIPTION
          "The variable specifies the severly errored seconds threshold
           of the port; 0 is to disable this error threshold and 1~100 is
           to enable also specify a particular value for this threshold."
          ::= {  ncmEnhanAlmCfgEntry 4 }

          ncmEnhanAlmCfgUASThreshold OBJECT-TYPE
          SYNTAX  INTEGER
          ACCESS  read-write
          STATUS mandatory
          DESCRIPTION
          "The variable specifies the unavailable seconds threshold
           of the port; 0 is to disable this error threshold and 1~100 is
           to enable also specify a particular value for this threshold."
          ::= {  ncmEnhanAlmCfgEntry 5 }                                      
 
          ncmEnhanAlmCfgBERThreshold OBJECT-TYPE
          SYNTAX INTEGER {

                       disable(1),
                       d10E-4(2),
                       d10E-5(3),
                       d10E-6(4),
                       d10E-7(5),
                       d10E-8(6),
                       d10E-9(7)
               } 
          ACCESS  read-write
          STATUS mandatory
          DESCRIPTION
          "The variable specifies the bit error rate threshold of the 
               port; the value = 10 Exponential to the power minus n."
          ::= {  ncmEnhanAlmCfgEntry 6 }
 

          ncmEnhanAlmCfgBPVThreshold OBJECT-TYPE
          SYNTAX  INTEGER (1..'7fffffff'h)
          ACCESS  read-write
          STATUS  mandatory
          DESCRIPTION
         "The object specifies the BPV threshold the port."
          ::= {  ncmEnhanAlmCfgEntry 7 }

          ncmEnhanAlmCfgLineRestoral OBJECT-TYPE
          SYNTAX INTEGER {
                       disable(1),
                       automatic(2),
                       manual(3),
                       time-of-day(4)
               } 
          ACCESS  read-write
          STATUS mandatory
          DESCRIPTION
          "The variable specifies the Line Restoral mode of the port."
          ::= {  ncmEnhanAlmCfgEntry 8 }
 

          ncmEnhanAlmCfgTODHour OBJECT-TYPE
          SYNTAX  INTEGER 
          ACCESS  read-write
          STATUS  mandatory
          DESCRIPTION
         "The object specifies the Time of day hour the port;
		  this is the hours to restore line if line restore is TOD."
          ::= {  ncmEnhanAlmCfgEntry 9 }


          ncmEnhanAlmCfgTODMinute OBJECT-TYPE
          SYNTAX  INTEGER 
          ACCESS  read-write
          STATUS  mandatory
          DESCRIPTION
         "The object specifies the Time of day minute the port;
                this is the minutes to restore line if line restore is TOD."
          ::= {  ncmEnhanAlmCfgEntry 10 }

          ncmEnhanAlmCfgLinRestEvalPer OBJECT-TYPE
          SYNTAX  INTEGER (0..'ffff'h)
          ACCESS  read-write
          STATUS  mandatory
          DESCRIPTION
         "The object specifies the Line Restoral evaulation period (seconds)
         	of the port." 
          ::= {  ncmEnhanAlmCfgEntry 11 }

  
--	 ncm Diagnostic  supergroup

--       ncm Loopback Group 

     	 ncmLoopbackTable OBJECT-TYPE
	  SYNTAX  SEQUENCE OF NcmLoopbackEntry
	  ACCESS  not-accessible
	  STATUS  mandatory
	  
             --DEFAULT test-function    diagnose-test
             --DEFAULT next-function    diagnose-next

	  ::= { ncm-generic 1034  }


      	 ncmLoopbackEntry OBJECT-TYPE
	  SYNTAX   NcmLoopbackEntry
	  ACCESS  not-accessible
	  STATUS  mandatory
	  DESCRIPTION
	  "An entry in the  Loopback Table."
	  INDEX   {  ncmLpbkNIDIndex,  ncmLpbkLineIndex }
	  ::= {  ncmLoopbackTable 1 }

      	 NcmLoopbackEntry ::=
	 SEQUENCE {
	     ncmLpbkNIDIndex
		 INTEGER,
	     ncmLpbkLineIndex
		 INTEGER,
	     ncmSetAllOnes
		INTEGER,
	     ncmTimeoutLOCSec
		INTEGER,
             ncmRemoteLB
                INTEGER,
	     ncmActivateDeactLBType
		INTEGER
	     }


          ncmLpbkNIDIndex OBJECT-TYPE
          SYNTAX  INTEGER (1..'7fffffff'h)
          ACCESS  read-only
          STATUS  mandatory
          DESCRIPTION
         "The object specifies the node id of the node."
          ::= {  ncmLoopbackEntry 1}


	 ncmLpbkLineIndex OBJECT-TYPE
	  SYNTAX  INTEGER (1..'7fffffff'h)
	  ACCESS  read-only
	  STATUS  mandatory
	  DESCRIPTION
	  "The index value which uniquely identifies  the
	  interface  to which this entry is applicable."
	::= {  ncmLoopbackEntry 2 }


        ncmSetAllOnes OBJECT-TYPE
          SYNTAX INTEGER {

                       disable(1),
                       enable(2)
               } 
          ACCESS read-write
          STATUS mandatory
          DESCRIPTION
          "The variable Enable/Disable the set all ones loopback option."

          ::= {  ncmLoopbackEntry 3 }


          ncmTimeoutLOCSec OBJECT-TYPE
          SYNTAX  INTEGER (0..'ffff'h)
          ACCESS  read-write
          STATUS  mandatory
          DESCRIPTION
         "The object specifies the  number of seconds to loop for
                LOC.  0 for infinite."
 
          ::= {  ncmLoopbackEntry 4 }


          ncmRemoteLB OBJECT-TYPE
             SYNTAX  INTEGER {
                         no(1),
                         yes(2)
                     }
             ACCESS  read-write
             STATUS  mandatory
             DESCRIPTION
             "This object specify whether the loopback is remote
                or local."
            ::= {  ncmLoopbackEntry 5 }


          ncmActivateDeactLBType OBJECT-TYPE
             SYNTAX  INTEGER {
                       deactivate(10000),
                       lineLoop(1),
                       payloadLoop(2),
                       localLoopbk(4),
                       dPLoop(8),
                       act-LLBBOP(16),
                       act-PLBBOP(32),
		       aCT-SIX-TWO-FOUR-ONE-ONE-INBAND(64),
		       aCT-FT1-LOOP-CODE(128),
		       deact-LLBBOP(10016),
		       deact-PLBBOP(10032),
		       deact-SIX-TWO-FOUR-ONE-ONE-INBAND(10064),
		       deact-FT1-LOOP-CODE(10128)

                     }
             ACCESS  read-write
             STATUS  mandatory
             DESCRIPTION
                "This variable represents the  loopback  confi-
                guration of the DS1 interface.  Agents support-
                ing read/write access should return badValue in
                response to a requested loopback state that the
                interface does not support.  The values mean:
 
              PayloadLoop
                     The received signal at this  interf  is
                     looped  through  the device. Typically the
                     received signal is  looped  back  for  re-
                     transmission  after  it has passed through
                     the device's framing function.

              LineLoop
                     The received signal at this interface does
                     not  go  through the device (minimum pene-
                     tration) but is looped back out.

              LocalLoopbk
                     This variable indicates whether the
                     local loopback is enabled or disabled on
                     the port or line by the device.

              DPLoop
                     This variable indicates whether the
                     ncmData Port loopback is enabled or disabled
                     by the device.
		     Remark: Only ACE-T1/ACE-E1 cards use this loopbk
			     type for port# 3 & 4; while the QUAD-T1/
			     QUAD-E1 don't support this loopback type.

              Act-LLBBOP
                     This variable indicates to activate the LLBBOP.
 
              Act-PLBBOP
                     This variable indicates to activate the PLBBOP.

              Deact-LLBBOP
                     This variable indicates to deactivate the LLBBOP.
 
              Deact-PLBBOP
                     This variable indicates to deactivate the PLBBOP.

	      Deact-SIX-TWO-FOUR-ONE-ONE-INBAND
		      This variable indicates to deactivate 62411 Inband

	      Deact-FT1-LOOP-CODE
		      This variable indicates to deactivate FT1 Loop Code

              When one of this object is chosen and received by the agent, this loopback 
		type is send to the target platform to activate the loopback action;
                while the object value = 0 is received the loopback action will be deactivated
		by the loopback type stored inside the port status."
            ::= { ncmLoopbackEntry 6 }

        

--	ncm Test Pattern Group


        ncmTestPatternTable OBJECT-TYPE
          SYNTAX  SEQUENCE OF NcmTestPatternEntry
          ACCESS  not-accessible
          STATUS  mandatory
	  --DEFAULT test-function    diagnose-test
          --DEFAULT next-function    diagnose-next


          ::= { ncm-generic  1035  }
 
 
        
          ncmTestPatternEntry OBJECT-TYPE
	  SYNTAX  NcmTestPatternEntry
          ACCESS  not-accessible
          STATUS  mandatory
          DESCRIPTION
          "An entry in the  Test Pattern Table."
          INDEX   { ncmTstpattNIDIndex, ncmTstpattLineIndex }
          ::= { ncmTestPatternTable 1 }
 
       
         NcmTestPatternEntry ::=
	  SEQUENCE {
            ncmTstpattNIDIndex
                 INTEGER,
            ncmTstpattLineIndex
                 INTEGER,
	    ncmTstpattTestPeriod
		INTEGER,
	    ncmStartStopTestPattern
		INTEGER,
            ncmResetTestCounter
                INTEGER

             }   
 
 
         ncmTstpattNIDIndex OBJECT-TYPE
          SYNTAX  INTEGER (1..'7fffffff'h)
          ACCESS  read-only
          STATUS  mandatory
          DESCRIPTION
         "The object specifies the node id of the node."
          ::= { ncmTestPatternEntry 1}
 
 
        ncmTstpattLineIndex OBJECT-TYPE
          SYNTAX  INTEGER (1..'7fffffff'h)
          ACCESS  read-only
          STATUS  mandatory
          DESCRIPTION
          "The index value which uniquely identifies  the
          interface  to which this entry is applicable."
        ::= { ncmTestPatternEntry 2 }
          

         ncmTstpattTestPeriod OBJECT-TYPE
          SYNTAX  INTEGER (0..'ffff'h)
          ACCESS  read-write
          STATUS  mandatory
          DESCRIPTION
         "The object specifies the  number of seconds to test;
                0 for infinite."

          ::= { ncmTestPatternEntry 3 }


          ncmStartStopTestPattern OBJECT-TYPE 
             SYNTAX  INTEGER {
                         stop(100),
                         three-In-Twentyfour(1),
                         qrss(2),
                         two-N-Twenty-One(3),
                         one-In-Eight(4),
                         two-N-Fifteen-One(5),
                         all-Zeroes(6),
                         fiftyfive-Octets(7),
                         all-Ones(8)
                     }   
             ACCESS  read-write
             STATUS  mandatory
             DESCRIPTION
              "When one of this object is chosen and received by the agent, this test 
		pattern is send to the target platform to start the diagnostic action;
                while object value = 0, it will stop the test pattern by the pattern
		  is stored inside the port status.
		Remark: Only ACE-T1/ACE-E1 cards use the QRSS test pattern 
			for data port# 3 & 4; while the QUAD-T1/QUAD-E1 don't 
			support this test pattern."
            ::= { ncmTestPatternEntry 4 }
 

         ncmResetTestCounter OBJECT-TYPE
             SYNTAX  INTEGER {
                         reset(1)
                     }
             ACCESS  read-write
             STATUS  mandatory
             DESCRIPTION
             "This object reset the test counter in the diagnostic."
            ::= { ncmTestPatternEntry 5 }



--      Add/Edit/Delete/Activate/Deactivate/Get Detail Information ncmCircuit Group
         
        ncmCircuitInfoTable OBJECT-TYPE
             SYNTAX   SEQUENCE OF NcmCircuitInfoEntry
             ACCESS   not-accessible
             STATUS   mandatory
	      --DEFAULT test-function   ccb-test
             --DEFAULT next-function    ccb-next

 
             ::= { ncm-generic 1036 }
 
 
        ncmCircuitInfoEntry  OBJECT-TYPE
             SYNTAX   NcmCircuitInfoEntry
             ACCESS   not-accessible
             STATUS   mandatory
             DESCRIPTION
                "An entry in the circuitBuilder Table for adding, editing, deleting,
		 activate, deactivate and get the detail information of a particular circuit."
             INDEX   { ncmCircuitInfoNIDIndex }
            ::= { ncmCircuitInfoTable 1 }
             
 
        NcmCircuitInfoEntry ::=
             SEQUENCE {
             ncmCircuitInfoNIDIndex
                 INTEGER,
             ncmCircuitInfoCircName
                 DisplayString,
             ncmCircuitInfoCircPriority
                 INTEGER,
             ncmCircuitInfoCircType
                 INTEGER,
             ncmCircuitInfoCircMode
                 INTEGER,
             ncmCircuitInfoSrcPortSite
                 INTEGER,
             ncmCircuitInfoSrcCardEquipID
                 INTEGER,
             ncmCircuitInfoSrcPortID
                 INTEGER,
             ncmCircuitInfoSrcTimeslotmap
                 INTEGER,
             ncmCircuitInfoDstPortSite
                 INTEGER,
             ncmCircuitInfoDstCardEquipID
                 INTEGER,
             ncmCircuitInfoDstPortID
                 INTEGER,
             ncmCircuitInfoDstTimeslotmap
                 INTEGER,
             ncmCircuitInfoBackPlaneBusID
                 INTEGER,
             ncmCircuitInfoAssoCircName
                 DisplayString,
             ncmCircuitInfoAction
                 INTEGER,
	     ncmAddEditActDeactCircuitStatus
	   	 INTEGER,
	     ncmDeleteCircuitStatus
	   	 INTEGER,
	     ncmGetDetailCircuitStatus
	   	 INTEGER
 
                }
 
 
        ncmCircuitInfoNIDIndex  OBJECT-TYPE
             SYNTAX  INTEGER (1..'7fffffff'h)
             ACCESS  read-only
             STATUS  mandatory
             DESCRIPTION
                "This variable indicates the node id
                 value of the node."
               ::= { ncmCircuitInfoEntry 1 }
  
 
        ncmCircuitInfoCircName OBJECT-TYPE
            SYNTAX DisplayString (SIZE (0..12))
            ACCESS  read-write
            STATUS  mandatory
            DESCRIPTION
            "This object allocates & indicates the circuit name for sending the 
	     add/edit/delete/activate/deactivate/get detail info circuit 
	     request to the circuitbuilder."
            ::= { ncmCircuitInfoEntry 2 }


        ncmCircuitInfoCircPriority  OBJECT-TYPE
             SYNTAX  INTEGER {
                ccb-CPRIO-LOW(1),
                ccb-CPRIO-NRML(2),
                ccb-CPRIO-HIGH(3),
                ccb-CPRIO-CRIT(4)

                        }         
             ACCESS  read-write
             STATUS  mandatory
             DESCRIPTION
             "This object allocates & indicates the circuit priority for sending 
	     the add/edit/get detail info circuit request to the circuitbuilder."
             ::= { ncmCircuitInfoEntry 3 }
               
                                           
        ncmCircuitInfoCircType  OBJECT-TYPE
             SYNTAX  INTEGER {
                 ccb-CTYPE-RESERVED(1),
                 ccb-CTYPE-PERMANENT(2),
                 ccb-CTYPE-SWITCHED(3),
                 ccb-CTYPE-PRIMARY(4),
                 ccb-CTYPE-BACKUP(5),
                 ccb-CTYPE-BACKUP-ND(6)
 
                        }
             ACCESS  read-write
             STATUS  mandatory
             DESCRIPTION
             "This object allocates & indicates the circuit type for sending 
	     the add/edit/get detail info circuit request to the circuitbuilder."
             ::= { ncmCircuitInfoEntry 4 }
                
 
        ncmCircuitInfoCircMode  OBJECT-TYPE
             SYNTAX  INTEGER {
                 ccb-CMODE-NX56-DATA(1),
                 ccb-CMODE-NX64-DATA(2),
                 ccb-CMODE-SIG-VOICE(3),
                 ccb-CMODE-NSIG-VOICE(4),
                 ccb-CMODE-RESERVED(5)
 
                        }
             ACCESS  read-write
             STATUS  mandatory
             DESCRIPTION
             "This object allocates & indicates the circuit mode for sending 
	     the add/edit/get detail info circuit request to the circuitbuilder."
             ::= { ncmCircuitInfoEntry 5 }
                
 
        ncmCircuitInfoSrcPortSite  OBJECT-TYPE
             SYNTAX  INTEGER
             ACCESS  read-write
             STATUS  mandatory
             DESCRIPTION
             "This object allocates & indicates the shelf and slot combination of the
	      source port for sending the add/edit/get detail info circuit request to 
	      the circuitbuilder."
             ::= { ncmCircuitInfoEntry 6 }
  

        ncmCircuitInfoSrcCardEquipID  OBJECT-TYPE
             SYNTAX  INTEGER {
                        card-SIGMA-VCU(77), 
                        ace-FW-E1(80),     
                        ace-FW-T1(81),    
                        ace-FW-QUAD-T1(82),
                        ace-FW-QUAD-E1(83),
                        ace-Reserved(84), 
                        tabs-IMUX(85),   
                        ace-FW-DUAL-T1(86),
                        ace-FW-DUAL-E1(87),
                        fw-DS3-CDSU(88),  
                        fw-DS3-CDSU-CHANNEL(89),
                        ace-FW-ISDN-T1(112),    
                        ace-FW-ISDN-E1(113),
			fw-DS3-DUDS3(116),   
                        fw-NCM(96) 

                        }
             ACCESS  read-write
             STATUS  mandatory
             DESCRIPTION
             "This object allocates & indicates the card equipment id of the source port 
	      for sending the add/edit/get detail info circuit request to the circuitbuilder."
             ::= { ncmCircuitInfoEntry 7 }
                
                                         
        ncmCircuitInfoSrcPortID  OBJECT-TYPE
             SYNTAX  INTEGER {
                        ccb-NET-PORT-1(1),
                        ccb-NET-PORT-2(2),
                        ccb-NET-PORT-3(3),
                        ccb-NET-PORT-4(4),
                        ccb-DATA-PORT-1(5),
                        ccb-DATA-PORT-2(6),
                        ccb-TAC-NET-PORT(7),
                        ccb-TAC-EQP-PORT(8),
                        ccb-UNKNOWN-PORT(9)
 
                        }
             ACCESS  read-write
             STATUS  mandatory
             DESCRIPTION
             "This object allocates & indicates the port identity of the source port 
	      for sending the add/edit/get detail info circuit request to the circuitbuilder."
             ::= { ncmCircuitInfoEntry 8 }
                
 
        ncmCircuitInfoSrcTimeslotmap  OBJECT-TYPE
             SYNTAX  INTEGER
             ACCESS  read-write
             STATUS  mandatory
             DESCRIPTION
             "This object allocates & indicates the timeslot map allocated for the source 
	      port for sending the add/edit/get detail info circuit request to the circuitbuilder."
          ::= { ncmCircuitInfoEntry 9 }


        ncmCircuitInfoDstPortSite  OBJECT-TYPE
             SYNTAX  INTEGER
             ACCESS  read-write
             STATUS  mandatory
             DESCRIPTION
             "This object allocates & indicates the shelf and slot combination of the
	      destination port for sending the add/edit/get detail info circuit request 
	      to the circuitbuilder."
             ::= { ncmCircuitInfoEntry 10 }
 
 
        ncmCircuitInfoDstCardEquipID  OBJECT-TYPE
             SYNTAX  INTEGER {
                        card-SIGMA-VCU(77), 
                        ace-FW-E1(80),     
                        ace-FW-T1(81),    
                        ace-FW-QUAD-T1(82),
                        ace-FW-QUAD-E1(83),
                        ace-Reserved(84), 
                        tabs-IMUX(85),   
                        ace-FW-DUAL-T1(86),
                        ace-FW-DUAL-E1(87),
                        fw-DS3-CDSU(88),  
                        fw-DS3-CDSU-CHANNEL(89),
                        ace-FW-ISDN-T1(112),    
                        ace-FW-ISDN-E1(113),
			fw-DS3-DUDS3(116),
                        fw-NCM(96) 

                        }
             ACCESS  read-write
             STATUS  mandatory
             DESCRIPTION
             "This object allocates & indicates the card equipment id of the destination port 
	      for sending the add/edit/get detail info circuit request to the circuitbuilder."
             ::= { ncmCircuitInfoEntry 11 }
                
 
        ncmCircuitInfoDstPortID  OBJECT-TYPE
             SYNTAX  INTEGER {
                        ccb-NET-PORT-1(1),
                        ccb-NET-PORT-2(2),
                        ccb-NET-PORT-3(3),
                        ccb-NET-PORT-4(4),
                        ccb-DATA-PORT-1(5),
                        ccb-DATA-PORT-2(6),
                        ccb-TAC-NET-PORT(7),
                        ccb-TAC-EQP-PORT(8),
                        ccb-UNKNOWN-PORT(9)
 
                        }
             ACCESS  read-write
             STATUS  mandatory
             DESCRIPTION
             "This object allocates & indicates the port identity of the destination port 
	      for sending the add/edit/get detail info circuit request to the circuitbuilder."
             ::= { ncmCircuitInfoEntry 12 }
                
 
        ncmCircuitInfoDstTimeslotmap  OBJECT-TYPE
             SYNTAX  INTEGER
             ACCESS  read-write
             STATUS  mandatory
             DESCRIPTION
             "This object allocates & indicates the timeslot map allocated for the destination 
	      port for sending the add/edit/get detail info circuit request to the circuitbuilder."
          ::= { ncmCircuitInfoEntry 13 }
        
     
        ncmCircuitInfoBackPlaneBusID  OBJECT-TYPE
             SYNTAX  INTEGER {
                        ccb-BKPL-BUS-A1(1),
                        ccb-BKPL-BUS-A2(2),
                        ccb-BKPL-BUS-A3(3),
                        ccb-BKPL-BUS-A4(4),
                        ccb-BKPL-BUS-A5(5),
                        ccb-BKPL-BUS-A6(6),
                        ccb-BKPL-BUS-A7(7),
                        ccb-BKPL-BUS-A8(8),
                        ccb-BKPL-BUS-B(9),
                        ccb-BKPL-BUS-C(10),
                        ccb-BKPL-BUS-NONE(11),
                        ccb-BKPL-BUS-AUTO(12)
                     }
             ACCESS  read-write
             STATUS  mandatory
             DESCRIPTION
             "This object allocates & indicates the backplane bus ID for sending the 
	      add/edit/get detail info circuit request to the circuitbuilder."
           ::= { ncmCircuitInfoEntry 14 }
             
 
        ncmCircuitInfoAssoCircName  OBJECT-TYPE
            SYNTAX DisplayString (SIZE (0..12))
            ACCESS  read-write
            STATUS  mandatory
            DESCRIPTION
             "This object allocates & indicates the Assoicate circuit name for sending the 
	      add/edit/get detail info circuit request to the circuitbuilder."
            ::= { ncmCircuitInfoEntry 15 }
 
 
        ncmCircuitInfoAction  OBJECT-TYPE
             SYNTAX  INTEGER {
                add(1),
		edit(2),
		delete(3),
		activate(4),
		deactivate(5),
		getdetailinfo(6)
                }
             ACCESS  read-write
             STATUS  mandatory
             DESCRIPTION
                "The object send the corresponding acp command to execute the specified
		 circuit action with all necessary parameters setup properly."
            ::= { ncmCircuitInfoEntry 16 }


        ncmAddEditActDeactCircuitStatus  OBJECT-TYPE
             SYNTAX  INTEGER {
                ccb-BUILD-SUCCESS(1),
                ccb-BUILD-NO-PORT-BW(2),
                ccb-BUILD-CKT-EXIST(3),
                ccb-BUILD-INVALID-DATA(4),
                ccb-BUILD-PROM-FAILURE(5),
                ccb-BUILD-NO-BUS-BW(6),
                ccb-BUILD-NO-PEER-CARD(7),
                ccb-BUILD-PEER-NO-PORT-BW(8),
                ccb-BUILD-PEER-CKT-EXIST(9),
                ccb-BUILD-PEER-INVALID-DATA(10),
                ccb-BUILD-PEER-PROM-FAILURE(11),
                ccb-BUILD-PEER-NO-BUS-BW(12),
                ccb-BUILD-CIRCDBASE-OVRFLOW(13),
                ccb-BUILD-CKT-NOT-EXIST(14),
                ccb-BUILD-PORT-SETUP-FAIL(15),
                ccb-BUILD-CKT-INACTIVE(16),
                ccb-BUILD-NOT-ACT-CIRC(17),
                ccb-BUILD-SCHECK-OK(21),
                ccb-BUILD-SCHECK-BAD-CARD(22),
                ccb-BUILD-SCHECK-BAD-CTYPE(23),
                ccb-BUILD-SCHECK-BAD-CMODE(24),
                ccb-BUILD-SCHECK-DIFF-ncmSHELF(25),
                ccb-BUILD-SCHECK-DIFF-TSNUM(26),
                ccb-BUILD-SCHECK-BAD-BUS(27),
                ccb-BUILD-DCHECK-OK(31),
                ccb-BUILD-DCHECK-MISSCARD(32),
                ccb-BUILD-DCHECK-DIFFCARD(33),
                ccb-BUILD-DCHECK-BUS-TS-CNFL(34),
                ccb-BUILD-DCHECK-BUS-DRV-CNFL(35),
                ccb-BUILD-DCHECK-PORT-CNFL(36),
                ccb-BUILD-DBKCHECK-NO-PRICIRC(41),
                ccb-BUILD-DBKCHECK-NO-BKPCIRC(42),
                ccb-BUILD-DBKCHECK-NO-SHRPORT(43),
                ccb-BUILD-DBKCHECK-NO-PRIPORT(44)
 
                        }
             ACCESS  read-only
             STATUS  mandatory
             DESCRIPTION
                "This variable indicates the status as the result
                        of add/edit/Activate/Deactivate circuit."
             ::= { ncmCircuitInfoEntry 17 }


        ncmDeleteCircuitStatus  OBJECT-TYPE
             SYNTAX  INTEGER {
                ccb-DELETE-SUCCESS(1),
                ccb-DELETE-PROM-FAILURE(2),
                ccb-DELETE-CANT-FIND(3),
                ccb-DELETE-NO-PEER-CARD(4),
                ccb-DELETE-PEER-PROM-FAILURE(5),
                ccb-DELETE-PEER-CANT-FIND(6),
                ccb-DELETE-CKT-NOT-EXIST(7)
 
                }                           
             ACCESS  read-only
             STATUS  mandatory
             DESCRIPTION
                "This variable indicates the status as the result
                        of delete circuit."
             ::= { ncmCircuitInfoEntry 18 }
 

        ncmGetDetailCircuitStatus  OBJECT-TYPE
             SYNTAX  INTEGER {
                ccb-CSTAT-SPARE(1),
                ccb-CSTAT-EDITING(2),
                ccb-CSTAT-ACTIVE(3),
                ccb-CSTAT-INACTIVE(4),
                ccb-CSTAT-PREEMPTED(5),
                ccb-CSTAT-BROKEN(6),
                ccb-CSTAT-LINE-ERR(7),
                ccb-CSTAT-BACKUPPED(8)

                        }              
             ACCESS  read-only
             STATUS  mandatory
             DESCRIPTION
                "This variable indicates the status of the get circuit detail information."
             ::= { ncmCircuitInfoEntry 19 }
 
 

--     Port Bus Timeslot Allocation Group

        ncmPortTimeslotAllocTable OBJECT-TYPE
             SYNTAX   SEQUENCE OF NcmPortTimeslotAllocEntry
             ACCESS   not-accessible
             STATUS   mandatory
	     --DEFAULT test-function    ccb-test
             --DEFAULT next-function    ccb-next



             ::= {  ncm-generic 1037 }



        ncmPortTimeslotAllocEntry OBJECT-TYPE
             SYNTAX   NcmPortTimeslotAllocEntry
             ACCESS   not-accessible
             STATUS   mandatory
             DESCRIPTION
                "An entry in the Port Timeslot Allocation table for ncmCircuit Build."
             INDEX   { ncmPortTimeslotAllocNIDIndex }
            ::= { ncmPortTimeslotAllocTable 1 }


        NcmPortTimeslotAllocEntry ::=
             SEQUENCE {
             ncmPortTimeslotAllocNIDIndex
                 INTEGER,
             ncmPortTimeslotCardSite
                 INTEGER,
             ncmPortTimeslotCardEquipID
                 INTEGER,
             ncmPortTimeslotPortID
                 INTEGER,
             ncmPortAllocTimeSlotMap
                 INTEGER

                }

        ncmPortTimeslotAllocNIDIndex OBJECT-TYPE
             SYNTAX  INTEGER (1..'7fffffff'h)
             ACCESS  read-only
             STATUS  mandatory
             DESCRIPTION
                "This variable indicates the node id
                 value of the node."
               ::= { ncmPortTimeslotAllocEntry 1 }


        ncmPortTimeslotCardSite  OBJECT-TYPE
             SYNTAX  INTEGER
             ACCESS  read-write
             STATUS  mandatory
             DESCRIPTION
                "This variable indicates the shelf and slot combination number of the device."
             ::= { ncmPortTimeslotAllocEntry 2 }


        ncmPortTimeslotCardEquipID  OBJECT-TYPE
             SYNTAX  INTEGER {
        		card-SIGMA-VCU(77), 
        		ace-FW-E1(80),     
        		ace-FW-T1(81),    
        		ace-FW-QUAD-T1(82),
        		ace-FW-QUAD-E1(83),
        		ace-Reserved(84), 
        		tabs-IMUX(85),   
        		ace-FW-DUAL-T1(86),
        		ace-FW-DUAL-E1(87),
        		fw-DS3-CDSU(88),  
        		fw-DS3-CDSU-CHANNEL(89),
        		ace-FW-ISDN-T1(112),    
        		ace-FW-ISDN-E1(113),
			fw-DS3-DUDS3(116),
        		fw-NCM(96)           

                        }
             ACCESS  read-write
             STATUS  mandatory
             DESCRIPTION
                "This variable indicates the card equipment id of the target."
             ::= { ncmPortTimeslotAllocEntry 3 }
                
 
        ncmPortTimeslotPortID  OBJECT-TYPE
             SYNTAX  INTEGER {
        		ccb-NET-PORT-1(1),
        		ccb-NET-PORT-2(2), 
        		ccb-NET-PORT-3(3), 
        		ccb-NET-PORT-4(4), 
        		ccb-DATA-PORT-1(5), 
        		ccb-DATA-PORT-2(6), 
        		ccb-TAC-NET-PORT(7),
        		ccb-TAC-EQP-PORT(8), 
			ccb-UNKNOWN-PORT(9)

			} 
             ACCESS  read-write
             STATUS  mandatory
             DESCRIPTION
                "This variable indicates the port identity of the interface."
             ::= { ncmPortTimeslotAllocEntry 4 }


        ncmPortAllocTimeSlotMap  OBJECT-TYPE
             SYNTAX  INTEGER
             ACCESS  read-only
             STATUS  mandatory
             DESCRIPTION
             "The variable indicates the timeslot map allocated for the port by
                sending the corresponding acp command to execute the Get Action."
          ::= { ncmPortTimeslotAllocEntry 5 }

 

--    Dial-Backup Group

        ncmDialBkUpInfoTable OBJECT-TYPE
             SYNTAX   SEQUENCE OF NcmDialBkUpInfoEntry
             ACCESS   not-accessible
             STATUS   mandatory
	     --DEFAULT test-function    ccb-test
             --DEFAULT next-function    ccb-next


             ::= { ncm-generic 1038 }


        ncmDialBkUpInfoEntry OBJECT-TYPE
             SYNTAX   NcmDialBkUpInfoEntry
             ACCESS   not-accessible
             STATUS   mandatory
             DESCRIPTION
                "An entry in the retrieval of dial-backup parameter table for ncmCircuit Build."
             INDEX   { ncmDialBkUpInfoNIDIndex }
            ::= { ncmDialBkUpInfoTable 1 }


        NcmDialBkUpInfoEntry ::=
             SEQUENCE {
             ncmDialBkUpInfoNIDIndex
                 INTEGER,
             ncmDialBkUpReqCircName
                 DisplayString,
             ncmPrimaryCircName
                 DisplayString,
             ncmBackupCircName
                 DisplayString,
             ncmCallReferenceNumber
                 INTEGER,
             ncmCirSrcPortErrsetupMask
                 INTEGER,
             ncmCirDstPortErrsetupMask
                 INTEGER,
             ncmCirErrClearanceMask
                 INTEGER,
             ncmDialBkUpTimeout
                 INTEGER,
	     ncmDialBkUpAction
		 INTEGER,
	     ncmDialBkUpSetupStatus
		 INTEGER

                }


        ncmDialBkUpInfoNIDIndex OBJECT-TYPE
             SYNTAX  INTEGER (1..'7fffffff'h)
             ACCESS  read-only
             STATUS  mandatory
             DESCRIPTION
                "This variable indicates the node id
                 value of the node."
               ::= { ncmDialBkUpInfoEntry 1 }


        ncmDialBkUpReqCircName OBJECT-TYPE
            SYNTAX DisplayString (SIZE (0..12))
            ACCESS  read-write
            STATUS  mandatory
            DESCRIPTION
            "This variable indicates the circuit name for request dial-backup
		parameter and retrieve from the circuitbuilder."
            ::= { ncmDialBkUpInfoEntry 2 }


        ncmPrimaryCircName  OBJECT-TYPE
            SYNTAX DisplayString (SIZE (0..12))       
            ACCESS  read-write
            STATUS  mandatory  
            DESCRIPTION
            "This variable indicates the primary circuit name for request 
		and retrieve from the circuitbuilder as a parameter of dial-backup."
            ::= { ncmDialBkUpInfoEntry 3 }
 

        ncmBackupCircName  OBJECT-TYPE
            SYNTAX DisplayString (SIZE (0..12))       
            ACCESS  read-write
            STATUS  mandatory  
            DESCRIPTION
            "This variable indicates the backup circuit name for request and 
		retrieve from the circuitbuilder as a parameter of dial-backup."
            ::= { ncmDialBkUpInfoEntry 4 }
 
 
        ncmCallReferenceNumber  OBJECT-TYPE
             SYNTAX  INTEGER
             ACCESS  read-write
             STATUS  mandatory
             DESCRIPTION
             "The variable indicates the call reference number of the dial-backup."
          ::= { ncmDialBkUpInfoEntry 5 }


        ncmCirSrcPortErrsetupMask  OBJECT-TYPE
             SYNTAX  INTEGER {
        		ccb-DBKP-ALM-AIS-CTS(1),
        		ccb-DBKP-ALM-YEL-DSR(2),
        		ccb-DBKP-ALM-LOS-DCD(4),
        		ccb-DBKP-ALM-LOF(8),
        		ccb-DBKP-ALM-UAS(16),
        		ccb-DBKP-ALM-SES(32)

		}
             ACCESS  read-write
             STATUS  mandatory
             DESCRIPTION
             "The variable indicates the bitmap to setup the mask for circuit 
		source port error of the dial-backup; ncmAlarm Mask ALM-AIS, ALM-YEL
		and ALM-LOS are defined for t1 port; whilst ALM-CTS, ALM-DSR and
		ALM-DCD are defined for data port."
          ::= { ncmDialBkUpInfoEntry 6 }
 

        ncmCirDstPortErrsetupMask  OBJECT-TYPE
             SYNTAX  INTEGER {
        		ccb-DBKP-ALM-AIS-CTS(1),
        		ccb-DBKP-ALM-YEL-DSR(2),
        		ccb-DBKP-ALM-LOS-DCD(4),
                        ccb-DBKP-ALM-LOF(8),
                        ccb-DBKP-ALM-UAS(16),
                        ccb-DBKP-ALM-SES(32)
 
                }
             ACCESS  read-write
             STATUS  mandatory
             DESCRIPTION
             "The variable indicates the bitmap to setup the mask for circuit
                destination port error of the dial-backup; ncmAlarm Mask ALM-AIS, 
		ALM-YEL and ALM-LOS are defined for t1 port; whilst ALM-CTS, 
		ALM-DSR and ALM-DCD are defined for data port."
          ::= { ncmDialBkUpInfoEntry 7 }


        ncmCirErrClearanceMask  OBJECT-TYPE
             SYNTAX  INTEGER {
        		ccb-DBKP-ALM-AIS-CTS(1),
        		ccb-DBKP-ALM-YEL-DSR(2),
        		ccb-DBKP-ALM-LOS-DCD(4),
                        ccb-DBKP-ALM-LOF(8),
                        ccb-DBKP-ALM-UAS(16),
                        ccb-DBKP-ALM-SES(32)
 
                }
             ACCESS  read-write
             STATUS  mandatory
             DESCRIPTION
             "The variable indicates the bitmap to setup the mask for circuit
                error clearance of the dial-backup; ncmAlarm Mask ALM-AIS, 
                ALM-YEL and ALM-LOS are defined for t1 port; whilst ALM-CTS, 
                ALM-DSR and ALM-DCD are defined for data port."
          ::= { ncmDialBkUpInfoEntry 8 }


        ncmDialBkUpTimeout  OBJECT-TYPE
             SYNTAX  INTEGER
             ACCESS  read-write
             STATUS  mandatory
             DESCRIPTION
             "The variable indicates the dial-backup timeout."
          ::= { ncmDialBkUpInfoEntry 9 }


        ncmDialBkUpAction  OBJECT-TYPE
             SYNTAX  INTEGER {
                set(1)
                }
             ACCESS  read-write
             STATUS  mandatory
             DESCRIPTION
                "The object send the corresponding acp command to
                   execute the dial-backup set action."
            ::= { ncmDialBkUpInfoEntry 10 }


        ncmDialBkUpSetupStatus  OBJECT-TYPE
             SYNTAX  INTEGER {
                ccb-BUILD-SUCCESS(1),
                ccb-BUILD-NO-PORT-BW(2),
                ccb-BUILD-CKT-EXIST(3),
                ccb-BUILD-INVALID-DATA(4),
                ccb-BUILD-PROM-FAILURE(5),
                ccb-BUILD-NO-BUS-BW(6),
                ccb-BUILD-NO-PEER-CARD(7),
                ccb-BUILD-PEER-NO-PORT-BW(8),
                ccb-BUILD-PEER-CKT-EXIST(9),
                ccb-BUILD-PEER-INVALID-DATA(10),
                ccb-BUILD-PEER-PROM-FAILURE(11),
                ccb-BUILD-PEER-NO-BUS-BW(12),
                ccb-BUILD-CIRCDBASE-OVRFLOW(13),
                ccb-BUILD-CKT-NOT-EXIST(14),
                ccb-BUILD-PORT-SETUP-FAIL(15),
                ccb-BUILD-CKT-INACTIVE(16),
                ccb-BUILD-NOT-ACT-CIRC(17),
                ccb-BUILD-SCHECK-OK(21),
                ccb-BUILD-SCHECK-BAD-CARD(22),
                ccb-BUILD-SCHECK-BAD-CTYPE(23),
                ccb-BUILD-SCHECK-BAD-CMODE(24),
                ccb-BUILD-SCHECK-DIFF-ncmSHELF(25),
                ccb-BUILD-SCHECK-DIFF-TSNUM(26),
                ccb-BUILD-SCHECK-BAD-BUS(27),
                ccb-BUILD-DCHECK-OK(31),
                ccb-BUILD-DCHECK-MISSCARD(32),
                ccb-BUILD-DCHECK-DIFFCARD(33),
                ccb-BUILD-DCHECK-BUS-TS-CNFL(34),
                ccb-BUILD-DCHECK-BUS-DRV-CNFL(35),
                ccb-BUILD-DCHECK-PORT-CNFL(36),
                ccb-BUILD-DBKCHECK-NO-PRICIRC(41),
                ccb-BUILD-DBKCHECK-NO-BKPCIRC(42),
                ccb-BUILD-DBKCHECK-NO-SHRPORT(43),
                ccb-BUILD-DBKCHECK-NO-PRIPORT(44)

                        }
             ACCESS  read-only
             STATUS  mandatory
             DESCRIPTION
                "This variable indicates the setup status as the result
			of set dial-backup parameters."
             ::= { ncmDialBkUpInfoEntry 11 }



--      Clear Circuit(In Group)  Group

        ncmClearCircuitGrpTable OBJECT-TYPE
             SYNTAX   SEQUENCE OF NcmClearCircuitGrpEntry
             ACCESS   not-accessible
             STATUS   mandatory
   	     --DEFAULT test-function    ccb-test
             --DEFAULT next-function    ccb-next


             ::= { ncm-generic 1039 }
 

        ncmClearCircuitGrpEntry  OBJECT-TYPE
             SYNTAX   NcmClearCircuitGrpEntry
             ACCESS   not-accessible
             STATUS   mandatory
             DESCRIPTION
                "An entry in the circuitBuilder Table for clearing any circuit group."
             INDEX   { ncmClearCircuitGrpNIDIndex }
            ::= { ncmClearCircuitGrpTable 1 }


        NcmClearCircuitGrpEntry ::=
             SEQUENCE {
             ncmClearCircuitGrpNIDIndex
                 INTEGER,
             ncmClearCircuitGrpName
                 INTEGER,
             ncmClearCircuitGrpSite
                 INTEGER,
             ncmClearCircuitCardEquipID
                 INTEGER,
             ncmClearCircuitPortID
                 INTEGER,
	     ncmClearCircuitAction
		 INTEGER

		}


        ncmClearCircuitGrpNIDIndex  OBJECT-TYPE
             SYNTAX  INTEGER (1..'7fffffff'h)
             ACCESS  read-only
             STATUS  mandatory
             DESCRIPTION
                "This variable indicates the node id
                 value of the node."
               ::= { ncmClearCircuitGrpEntry 1 }

                                         
        ncmClearCircuitGrpName  OBJECT-TYPE
             SYNTAX  INTEGER {
		ccb-CDEL-ALL(1),
		ccb-CDEL-INACTIVE(2),
		ccb-CDEL-CARD-CKT(3),
		ccb-CDEL-PORT-CKT(4),
		ccb-CDEL-BUS-CKT(5)

                        }
             ACCESS  read-write
             STATUS  mandatory
             DESCRIPTION
                "This object allocates the circuit group site for the request."
             ::= { ncmClearCircuitGrpEntry 2 }


        ncmClearCircuitGrpSite  OBJECT-TYPE
             SYNTAX  INTEGER 
             ACCESS  read-write
             STATUS  mandatory
             DESCRIPTION
                "This object allocates the shelf and slot combination
                        of the port for the request."
             ::= { ncmClearCircuitGrpEntry 3 }

 
        ncmClearCircuitCardEquipID  OBJECT-TYPE
             SYNTAX  INTEGER {
                        card-SIGMA-VCU(77), 
                        ace-FW-E1(80),     
                        ace-FW-T1(81),    
                        ace-FW-QUAD-T1(82),
                        ace-FW-QUAD-E1(83),
                        ace-Reserved(84), 
                        tabs-IMUX(85),   
                        ace-FW-DUAL-T1(86),
                        ace-FW-DUAL-E1(87),
                        fw-DS3-CDSU(88),  
                        fw-DS3-CDSU-CHANNEL(89),
                        ace-FW-ISDN-T1(112),    
                        ace-FW-ISDN-E1(113),
			fw-DS3-DUDS3(116),   
                        fw-NCM(96) 

                        }
             ACCESS  read-write
             STATUS  mandatory
             DESCRIPTION
                "This object allocate the card equipment id for the request."
             ::= { ncmClearCircuitGrpEntry 4 }
  

        ncmClearCircuitPortID  OBJECT-TYPE
             SYNTAX  INTEGER {
                        ccb-NET-PORT-1(1),
                        ccb-NET-PORT-2(2),
                        ccb-NET-PORT-3(3),
                        ccb-NET-PORT-4(4),
                        ccb-DATA-PORT-1(5),
                        ccb-DATA-PORT-2(6),
                        ccb-TAC-NET-PORT(7),
                        ccb-TAC-EQP-PORT(8),
                        ccb-UNKNOWN-PORT(9)
 
                        }
             ACCESS  read-write
             STATUS  mandatory
             DESCRIPTION
                "This object allocates the port identity for the request."
             ::= { ncmClearCircuitGrpEntry 5 }


        ncmClearCircuitAction  OBJECT-TYPE
             SYNTAX  INTEGER {
                clear(1)
                }
             ACCESS  read-write
             STATUS  mandatory
             DESCRIPTION
                "The object send the corresponding acp command to
                   execute the clear circuit action."
            ::= { ncmClearCircuitGrpEntry 6 }
 


--      Get Message Number CCB
 
        ncmListGetMsgNumTable OBJECT-TYPE
             SYNTAX   SEQUENCE OF NcmListGetMsgNumEntry
             ACCESS   not-accessible
             STATUS   mandatory
	     --DEFAULT test-function    ccb-test
             --DEFAULT next-function    ccb-next


 
             ::= { ncm-generic 1040 }
 
 
        ncmListGetMsgNumEntry OBJECT-TYPE
             SYNTAX   NcmListGetMsgNumEntry
             ACCESS   not-accessible
             STATUS   mandatory
             DESCRIPTION
                "An entry to retrieve circuit list in a particular page of 
			the central ncmCircuit Build ncmDatabase."
             INDEX   { ncmListMsgNumNIDIndex }   
            ::= { ncmListGetMsgNumTable 1 }
 
 
        NcmListGetMsgNumEntry ::=
             SEQUENCE {
             ncmListMsgNumNIDIndex
                 INTEGER,
             ncmListMsgNumCircuitGroup
                 INTEGER,
             ncmListMsgNumPageNumber
                 INTEGER,
             ncmListMsgNumCardSite
                 INTEGER,
             ncmListMsgNumCardEquipID
                 INTEGER,
             ncmListMsgNumPortID
                 INTEGER,
             ncmNumofGetListMessage
                 INTEGER,
             ncmTotalCircDatabase
                 INTEGER

		}


        ncmListMsgNumNIDIndex  OBJECT-TYPE
             SYNTAX  INTEGER (1..'7fffffff'h)
             ACCESS  read-only
             STATUS  mandatory
             DESCRIPTION
                "This variable indicates the node id
                 value of the node."
               ::= { ncmListGetMsgNumEntry 1 }
 
 
        ncmListMsgNumCircuitGroup  OBJECT-TYPE
             SYNTAX  INTEGER {
                        ccb-CLIST-ALL(1),
                        ccb-CLIST-ACTIVE(2),
                        ccb-CLIST-PORT-CKT(3),
                        ccb-CLIST-CARD-CKT(4)
 
                }
             ACCESS  read-write
             STATUS  mandatory
             DESCRIPTION
             "ccb-CLIST-ALL: List all circuits in the central circuit database.
              ccb-CLIST-ACTIVE: List all active circuits in the circuit database.
              ccb-CLIST-PORT-CKT: List circuits associated with a port.
              ccb-CLIST-CARD-CKT: List circuits associated with a card.
 
                The variable indicates the constant for request to list
                which circuit group should be listed from the response."
          ::= { ncmListGetMsgNumEntry 2 }
 
 
        ncmListMsgNumPageNumber  OBJECT-TYPE
             SYNTAX  INTEGER
             ACCESS  read-write
             STATUS  mandatory
             DESCRIPTION
             "The object allocates the page number for the retrival
                                        of ncmCircuit List request."
          ::= { ncmListGetMsgNumEntry 3 }


        ncmListMsgNumCardSite  OBJECT-TYPE
             SYNTAX  INTEGER
             ACCESS  read-write
             STATUS  mandatory
             DESCRIPTION
                "This object allocates the shelf and slot combination
                        for the retrival of ncmCircuit List request."
             ::= { ncmListGetMsgNumEntry 4 }

                                        
        ncmListMsgNumCardEquipID  OBJECT-TYPE
             SYNTAX  INTEGER {
                        card-SIGMA-VCU(77), 
                        ace-FW-E1(80),     
                        ace-FW-T1(81),    
                        ace-FW-QUAD-T1(82),
                        ace-FW-QUAD-E1(83),
                        ace-Reserved(84), 
                        tabs-IMUX(85),   
                        ace-FW-DUAL-T1(86),
                        ace-FW-DUAL-E1(87),
                        fw-DS3-CDSU(88),  
                        fw-DS3-CDSU-CHANNEL(89),
                        ace-FW-ISDN-T1(112),    
                        ace-FW-ISDN-E1(113),
			fw-DS3-DUDS3(116),   
                        fw-NCM(96) 

                        }
             ACCESS  read-write
             STATUS  mandatory
             DESCRIPTION
                "This object defines the card equipment id of the target."
             ::= { ncmListGetMsgNumEntry 5 }
                
 
        ncmListMsgNumPortID OBJECT-TYPE
             SYNTAX  INTEGER {
                        ccb-NET-PORT-1(1),
                        ccb-NET-PORT-2(2),
                        ccb-NET-PORT-3(3),
                        ccb-NET-PORT-4(4),
                        ccb-DATA-PORT-1(5),
                        ccb-DATA-PORT-2(6),
                        ccb-TAC-NET-PORT(7),
                        ccb-TAC-EQP-PORT(8),
                        ccb-UNKNOWN-PORT(9)
 
                        }
             ACCESS  read-write
             STATUS  mandatory
             DESCRIPTION
                "This object defines the port identity of the interface."
             ::= { ncmListGetMsgNumEntry 6 }


        ncmNumofGetListMessage  OBJECT-TYPE
             SYNTAX  INTEGER
             ACCESS  read-only
             STATUS  mandatory
             DESCRIPTION
                "This variable indicates number of circuits listed in this message."
             ::= { ncmListGetMsgNumEntry 7 }
 

        ncmTotalCircDatabase  OBJECT-TYPE
             SYNTAX  INTEGER
             ACCESS  read-only
             STATUS  mandatory
             DESCRIPTION
                "This variable indicates total number of circuits in circuit database."
             ::= { ncmListGetMsgNumEntry 8 }

 
--      ncm Circuit List ccb Information Group
 
        ncmCircListccbTable OBJECT-TYPE
             SYNTAX   SEQUENCE OF NcmCircListccbEntry
             ACCESS   not-accessible
             STATUS   mandatory
   	     --DEFAULT test-function    ccbinterval-test
             --DEFAULT next-function    ccbinterval-next

 
             ::= { ncm-generic 1041 }
 
 
        ncmCircListccbEntry  OBJECT-TYPE
             SYNTAX   NcmCircListccbEntry
             ACCESS   not-accessible
             STATUS   mandatory
             DESCRIPTION
                "An entry to retrieve the specified circuit detail information as listed 
			out in the Get List Message Number MIB Group."
             INDEX   { ncmListccbNIDIndex, ncmNumofCircListMessage }
            ::= { ncmCircListccbTable 1 }
 
 
        NcmCircListccbEntry ::=
             SEQUENCE {
             ncmListccbNIDIndex
                 INTEGER,
	     ncmNumofCircListMessage
		 INTEGER,
             ncmListccbCircName
                 DisplayString,
	     ncmListccbCircPriority
		 INTEGER,
	     ncmListccbCircType
		 INTEGER,
	     ncmListccbCircMode
		 INTEGER,
             ncmSrcPortSite
                 INTEGER,
             ncmSrcCardEquipID
                 INTEGER,
             ncmSrcPortIdentifier
                 INTEGER,
             ncmSrcTimeslotmap
                 INTEGER,
             ncmDstPortSite
                 INTEGER,
             ncmDstCardEquipID
                 INTEGER,
             ncmDstPortIdentifier
                 INTEGER,
             ncmDstTimeslotmap
                 INTEGER,
	     ncmListccbBackPlaneBusID
		 INTEGER,
	     ncmListccbCircStatus
		 INTEGER 
                }
 
 
        ncmListccbNIDIndex OBJECT-TYPE
             SYNTAX  INTEGER (1..'7fffffff'h)
             ACCESS  read-only
             STATUS  mandatory
             DESCRIPTION
                "This variable indicates the node id
                 value of the node."
               ::= { ncmCircListccbEntry 1 }


        ncmNumofCircListMessage  OBJECT-TYPE
             SYNTAX  INTEGER
             ACCESS  read-only
             STATUS  mandatory
             DESCRIPTION
                "This variable indicates the number of circuit listed in this page."
             ::= { ncmCircListccbEntry 2 }
 

        ncmListccbCircName  OBJECT-TYPE
            SYNTAX DisplayString (SIZE (0..12))
            ACCESS  read-only
            STATUS  mandatory
            DESCRIPTION
            "This variable indicates the circuit name response from
                the circuitbuilder as the circuit identity of the object."
            ::= { ncmCircListccbEntry 3 }


        ncmListccbCircPriority  OBJECT-TYPE
             SYNTAX  INTEGER {
		ccb-CPRIO-LOW(1),
		ccb-CPRIO-NRML(2),
		ccb-CPRIO-HIGH(3),
		ccb-CPRIO-CRIT(4)
 
                        }
             ACCESS  read-only
             STATUS  mandatory
             DESCRIPTION
                "This variable indicates circuit priority of this circuit."
             ::= { ncmCircListccbEntry 4 }
 

       ncmListccbCircType  OBJECT-TYPE
             SYNTAX  INTEGER {
		ccb-CTYPE-RESERVED(1),
		ccb-CTYPE-PERMANENT(2),
		ccb-CTYPE-SWITCHED(3),
		ccb-CTYPE-PRIMARY(4),
		ccb-CTYPE-BACKUP(5)
 
                        }
             ACCESS  read-only
             STATUS  mandatory
             DESCRIPTION
                "This variable indicates circuit type of this circuit."
             ::= { ncmCircListccbEntry 5 }
 

           ncmListccbCircMode  OBJECT-TYPE
             SYNTAX  INTEGER {   
		ccb-CMODE-NX56-DATA(1),
		ccb-CMODE-NX64-DATA(2),
		ccb-CMODE-SIG-VOICE(3),
		ccb-CMODE-NSIG-VOICE(4),
		ccb-CMODE-RESERVED(5)

                        }
             ACCESS  read-only
             STATUS  mandatory
             DESCRIPTION
                "This variable indicates circuit mode of this circuit."
             ::= { ncmCircListccbEntry 6 }


         ncmSrcPortSite  OBJECT-TYPE
             SYNTAX  INTEGER
             ACCESS  read-only
             STATUS  mandatory
             DESCRIPTION
                "This variable indicates the shelf and slot combination
                     of the source port."
             ::= { ncmCircListccbEntry 7 }

                                        
         ncmSrcCardEquipID  OBJECT-TYPE
             SYNTAX  INTEGER {
                        card-SIGMA-VCU(77), 
                        ace-FW-E1(80),     
                        ace-FW-T1(81),    
                        ace-FW-QUAD-T1(82),
                        ace-FW-QUAD-E1(83),
                        ace-Reserved(84), 
                        tabs-IMUX(85),   
                        ace-FW-DUAL-T1(86),
                        ace-FW-DUAL-E1(87),
                        fw-DS3-CDSU(88),  
                        fw-DS3-CDSU-CHANNEL(89),
                        ace-FW-ISDN-T1(112),    
                        ace-FW-ISDN-E1(113),
			fw-DS3-DUDS3(116),   
                        fw-NCM(96) 

                        }          
             ACCESS  read-only
             STATUS  mandatory
             DESCRIPTION
                "This variable indicates the card equipment id of the source port."
             ::= { ncmCircListccbEntry 8 }
              
                                        
         ncmSrcPortIdentifier  OBJECT-TYPE
             SYNTAX  INTEGER {
                        ccb-NET-PORT-1(1),
                        ccb-NET-PORT-2(2),
                        ccb-NET-PORT-3(3),
                        ccb-NET-PORT-4(4),
                        ccb-DATA-PORT-1(5),
                        ccb-DATA-PORT-2(6),
                        ccb-TAC-NET-PORT(7),
                        ccb-TAC-EQP-PORT(8),
                        cb-UNKNOWN-PORT(9)

                        }                  
             ACCESS  read-only
             STATUS  mandatory
             DESCRIPTION
                "This variable indicates the port identity of the source port."
             ::= { ncmCircListccbEntry 9 }


         ncmSrcTimeslotmap  OBJECT-TYPE
             SYNTAX  INTEGER
             ACCESS  read-only
             STATUS  mandatory
             DESCRIPTION
             "The variable indicates the timeslot map allocated for the source port."
          ::= { ncmCircListccbEntry 10 }


         ncmDstPortSite  OBJECT-TYPE
             SYNTAX  INTEGER
             ACCESS  read-only
             STATUS  mandatory
             DESCRIPTION
                "This variable indicates the shelf and slot combination
                        of the destination port."
             ::= { ncmCircListccbEntry 11 }


         ncmDstCardEquipID  OBJECT-TYPE
             SYNTAX  INTEGER {
                        card-SIGMA-VCU(77), 
                        ace-FW-E1(80),     
                        ace-FW-T1(81),    
                        ace-FW-QUAD-T1(82),
                        ace-FW-QUAD-E1(83),
                        ace-Reserved(84), 
                        tabs-IMUX(85),   
                        ace-FW-DUAL-T1(86),
                        ace-FW-DUAL-E1(87),
                        fw-DS3-CDSU(88),  
                        fw-DS3-CDSU-CHANNEL(89),
                        ace-FW-ISDN-T1(112),    
                        ace-FW-ISDN-E1(113),
			fw-DS3-DUDS3(116),   
                        fw-NCM(96) 

                        }
             ACCESS  read-only
             STATUS  mandatory
             DESCRIPTION
                "This variable indicates the card equipment id of the destination port."
             ::= { ncmCircListccbEntry 12 }
              
                                         
         ncmDstPortIdentifier  OBJECT-TYPE
             SYNTAX  INTEGER {
                        ccb-NET-PORT-1(1),
                        ccb-NET-PORT-2(2),
                        ccb-NET-PORT-3(3),
                        ccb-NET-PORT-4(4),
                        ccb-DATA-PORT-1(5),
                        ccb-DATA-PORT-2(6),
                        ccb-TAC-NET-PORT(7),
                        ccb-TAC-EQP-PORT(8),
                        cb-UNKNOWN-PORT(9)
 
                        }
             ACCESS  read-only
             STATUS  mandatory
             DESCRIPTION
                "This variable indicates the port identity of the destination port."
             ::= { ncmCircListccbEntry 13 }


         ncmDstTimeslotmap  OBJECT-TYPE
             SYNTAX  INTEGER
             ACCESS  read-only
             STATUS  mandatory
             DESCRIPTION
             "The variable indicates the timeslot map allocated for the destination port."
          ::= { ncmCircListccbEntry 14 }


         ncmListccbBackPlaneBusID  OBJECT-TYPE
             SYNTAX  INTEGER {
                        ccb-BKPL-BUS-A1(1),
                        ccb-BKPL-BUS-A2(2),
                        ccb-BKPL-BUS-A3(3),
                        ccb-BKPL-BUS-A4(4),
                        ccb-BKPL-BUS-A5(5),
                        ccb-BKPL-BUS-A6(6),
                        ccb-BKPL-BUS-A7(7),
                        ccb-BKPL-BUS-A8(8),
                        ccb-BKPL-BUS-B(9),
                        ccb-BKPL-BUS-C(10),
                        ccb-BKPL-BUS-NONE(11),
                        ccb-BKPL-BUS-AUTO(12)
                     }
             ACCESS  read-only
             STATUS  mandatory
             DESCRIPTION
             "The variable indicates the backplane bus ID of the device."
           ::= { ncmCircListccbEntry 15 }


         ncmListccbCircStatus  OBJECT-TYPE
             SYNTAX  INTEGER {
		ccb-CSTAT-SPARE(1),
		ccb-CSTAT-EDITING(2),
		ccb-CSTAT-ACTIVE(3),
		ccb-CSTAT-INACTIVE(4),
		ccb-CSTAT-PREEMPTED(5),
		ccb-CSTAT-BROKEN(6),
		ccb-CSTAT-LINE-ERR(7),
		ccb-CSTAT-BACKUPPED(8)
 
                        }
             ACCESS  read-only
             STATUS  mandatory
             DESCRIPTION
                "This variable indicates the status of the List circuit ccb."
             ::= { ncmCircListccbEntry 16 }





	  -- The  Equipment ID  table
 
 
 
        ncmEquipmentIDTable OBJECT-TYPE
        SYNTAX SEQUENCE OF  NcmEquipmentIDEntry
        ACCESS not-accessible
        STATUS mandatory
	--DEFAULT test-function tabs-test
        --DEFAULT next-function tabs-next


 
                  ::= { ncm-generic 1042 }
 

        ncmEquipmentIDEntry OBJECT-TYPE
        SYNTAX  NcmEquipmentIDEntry
        ACCESS not-accessible
        STATUS mandatory
        DESCRIPTION
               "An entry in the Equipment ID table."
        INDEX   { ncmEquipmentIDNIDIndex, ncmEquipmentIDLineIndex }
        ::= { ncmEquipmentIDTable 1 }
 

         NcmEquipmentIDEntry ::=
        SEQUENCE {
 
             ncmEquipmentIDNIDIndex
                  INTEGER,
             ncmEquipmentIDLineIndex
                 INTEGER,
             ncmFirmwareVersion
                 INTEGER,
             ncmFirmwareRevision
                INTEGER,
             ncmEquipmentType
                INTEGER,
             ncmHardwareVersion
                INTEGER,
             ncmHardwareRevision
                INTEGER,
             ncmLocationID
                 INTEGER


                }
 
 
        ncmEquipmentIDNIDIndex OBJECT-TYPE
        SYNTAX  INTEGER
        ACCESS  read-only
        STATUS  mandatory
        DESCRIPTION
        "This variable specifies the node id."
        ::= { ncmEquipmentIDEntry 1 }
 
	
        ncmEquipmentIDLineIndex OBJECT-TYPE
        SYNTAX  INTEGER
        ACCESS  read-only
        STATUS  mandatory
        DESCRIPTION
        "This variable specifies the line index value."
        ::= { ncmEquipmentIDEntry 2 }
 
         ncmFirmwareVersion OBJECT-TYPE
        SYNTAX INTEGER
        ACCESS read-only
        STATUS mandatory
        DESCRIPTION
               "The variable specifies the firmware version."
 
        ::= { ncmEquipmentIDEntry 3 }
 
 
         ncmFirmwareRevision OBJECT-TYPE
        SYNTAX INTEGER
        ACCESS read-only
        STATUS mandatory
        DESCRIPTION
               "The variable specifies the firmware revision."
 
        ::= { ncmEquipmentIDEntry 4 }
 
 
         ncmEquipmentType OBJECT-TYPE
        SYNTAX INTEGER
        ACCESS read-only
        STATUS mandatory
        DESCRIPTION
               "The variable specifies the Equipment Type."
 
        ::= { ncmEquipmentIDEntry 5 }
 
 
         ncmHardwareVersion OBJECT-TYPE
        SYNTAX INTEGER
        ACCESS read-only
        STATUS mandatory
        DESCRIPTION
               "The variable specifies the hardware version."
 
        ::= { ncmEquipmentIDEntry 6 }
 
 
         ncmHardwareRevision OBJECT-TYPE
        SYNTAX INTEGER
        ACCESS read-only
        STATUS mandatory
        DESCRIPTION
               "The variable specifies the hardwareware revision."
 
        ::= { ncmEquipmentIDEntry 7 }
	
       
 	
         ncmLocationID OBJECT-TYPE
        SYNTAX INTEGER
        ACCESS read-only
        STATUS mandatory
        DESCRIPTION
               "The variable specifies the Location ID."
 
        ::= { ncmEquipmentIDEntry 8 }



	 --      E1AlarmThresholdConfig Group


        ncmE1AlarmThresholdConfigTable OBJECT-TYPE
             SYNTAX   SEQUENCE OF NcmE1AlarmThresholdConfigEntry
             ACCESS   not-accessible
             STATUS   mandatory
	     --DEFAULT test-function    acee1-test
             --DEFAULT next-function    acee1-next


 
 
             ::= { ncm-generic  1043 }


        ncmE1AlarmThresholdConfigEntry OBJECT-TYPE
             SYNTAX   NcmE1AlarmThresholdConfigEntry
             ACCESS   not-accessible
             STATUS   mandatory
             DESCRIPTION
                "An entry in the E1 ncmAlarm Threshold Configure table."
             INDEX   { ncmE1AlarmThresholdConfigNIDIndex, ncmE1AlarmThresholdConfigIndex }
            ::= { ncmE1AlarmThresholdConfigTable 1 }


        NcmE1AlarmThresholdConfigEntry ::=
             SEQUENCE {
             ncmE1AlarmThresholdConfigNIDIndex
                 INTEGER,
             ncmE1AlarmThresholdConfigIndex
                 INTEGER,
             ncmE1LOFThreshold
                INTEGER,
             ncmE1LOFTimeInterval
                INTEGER,
             ncmE1LOSThreshold
                INTEGER,
             ncmE1LOSTimeInterval
                INTEGER,
             ncmE1RAIThreshold
                INTEGER,
             ncmE1RAITimeInterval
                INTEGER,
             ncmE1AISThreshold
                INTEGER,
             ncmE1AISTimeInterval
                INTEGER,
             ncmE1BPVThreshold
                INTEGER,
             ncmE1BPVTimeInterval
                INTEGER,
             ncmE1ES15MINThreshold
                INTEGER,
             ncmE1ES24HRThreshold
                INTEGER,
             ncmE1SES15MINThreshold
                INTEGER,
             ncmE1SES24HRThreshold
                INTEGER,
             ncmCVP15MINThreshold
                INTEGER,
             ncmCVP24HRThreshold
                INTEGER,
             ncmCVL15MINThreshold
                INTEGER,
             ncmCVL24HRThreshold
                INTEGER,
	     ncmESL15MINThreshold
                INTEGER,
             ncmESL24HRThreshold
                INTEGER,
             ncmSESL15MINThreshold
                INTEGER,
             ncmSESL24HRThreshold
                INTEGER,
             ncmUASP15MINThreshold
                INTEGER,
             ncmUASP24HRThreshold
                INTEGER
 
 
 
        }
 
 
 
 
        ncmE1AlarmThresholdConfigNIDIndex OBJECT-TYPE
          SYNTAX  INTEGER (1..'7fffffff'h)
          ACCESS  read-only
          STATUS  mandatory
          DESCRIPTION
         "The object specifies the node id of the node."
 
          ::= { ncmE1AlarmThresholdConfigEntry 1}
 
 
        ncmE1AlarmThresholdConfigIndex OBJECT-TYPE
          SYNTAX  INTEGER
          ACCESS  read-only
          STATUS  mandatory
          DESCRIPTION
         "The index value which uniquely identifies  the
          interface to which this entry is applicable."
 
          ::= { ncmE1AlarmThresholdConfigEntry 2 }
 
 
         ncmE1LOFThreshold OBJECT-TYPE
          SYNTAX  INTEGER
          ACCESS  read-write
          STATUS  mandatory
          DESCRIPTION
          "This variable specifies the LOF Threshold count in secs." 
          ::= { ncmE1AlarmThresholdConfigEntry 3 }
 
         
        ncmE1LOFTimeInterval OBJECT-TYPE
          SYNTAX  INTEGER
          ACCESS  read-write
          STATUS  mandatory
          DESCRIPTION
          "This variable specifies the LOF Time Interval in secs." 
          ::= { ncmE1AlarmThresholdConfigEntry 4 }


	    ncmE1LOSThreshold OBJECT-TYPE
          SYNTAX  INTEGER
          ACCESS  read-write
          STATUS  mandatory
          DESCRIPTION
          "This variable specifies the LOS Threshold count in secs." 
          ::= { ncmE1AlarmThresholdConfigEntry 5 }
 
         
        ncmE1LOSTimeInterval OBJECT-TYPE
          SYNTAX  INTEGER
          ACCESS  read-write
          STATUS  mandatory
          DESCRIPTION
          "This variable specifies the LOS Time Interval in secs." 
          ::= { ncmE1AlarmThresholdConfigEntry 6 }
 
 
        ncmE1RAIThreshold OBJECT-TYPE
          SYNTAX  INTEGER
          ACCESS  read-write
          STATUS  mandatory
          DESCRIPTION
          "This variable specifies the RAI Threshold count in secs." 
          ::= { ncmE1AlarmThresholdConfigEntry 7 }
 
         
        ncmE1RAITimeInterval OBJECT-TYPE
          SYNTAX  INTEGER
          ACCESS  read-write
          STATUS  mandatory
          DESCRIPTION
          "This variable specifies the RAI Time Interval in secs." 
 
          ::= { ncmE1AlarmThresholdConfigEntry 8 }
 
 
        ncmE1AISThreshold OBJECT-TYPE
          SYNTAX  INTEGER
          ACCESS  read-write
          STATUS  mandatory
          DESCRIPTION
          "This variable specifies the AIS Threshold count in secs." 
          ::= { ncmE1AlarmThresholdConfigEntry 9 }
 
        ncmE1AISTimeInterval OBJECT-TYPE
          SYNTAX  INTEGER
          ACCESS  read-write
          STATUS  mandatory
          DESCRIPTION
          "This variable specifies the AIS Time Interval in secs." 
 
          ::= { ncmE1AlarmThresholdConfigEntry 10 }


	   ncmE1BPVThreshold OBJECT-TYPE
          SYNTAX  INTEGER
          ACCESS  read-write
          STATUS  mandatory
          DESCRIPTION
          "This variable specifies the BPV Threshold count in secs." 
          ::= { ncmE1AlarmThresholdConfigEntry 11 }
 
         
        ncmE1BPVTimeInterval OBJECT-TYPE
          SYNTAX  INTEGER
          ACCESS  read-write
          STATUS  mandatory
          DESCRIPTION
          "This variable specifies the BPV Time Interval in secs." 
          ::= { ncmE1AlarmThresholdConfigEntry 12 }
 
        ncmE1ES15MINThreshold OBJECT-TYPE
          SYNTAX  INTEGER
          ACCESS  read-write
          STATUS  mandatory
          DESCRIPTION
          "This variable specifies the ES 15 minute Threshold count in secs." 
          ::= { ncmE1AlarmThresholdConfigEntry 13 }
         
        ncmE1ES24HRThreshold OBJECT-TYPE
          SYNTAX  INTEGER
          ACCESS  read-write
          STATUS  mandatory
          DESCRIPTION
          "This variable specifies the ES 24 hour Threshold count in secs." 
          ::= { ncmE1AlarmThresholdConfigEntry 14 }
 
        ncmE1SES15MINThreshold OBJECT-TYPE
          SYNTAX  INTEGER
          ACCESS  read-write
          STATUS  mandatory
          DESCRIPTION
          "This variable specifies the SES 15 minute Threshold count in secs."
          ::= { ncmE1AlarmThresholdConfigEntry 15 }
 
         
       ncmE1SES24HRThreshold OBJECT-TYPE
          SYNTAX  INTEGER
          ACCESS  read-write
          STATUS  mandatory
          DESCRIPTION
          "This variable specifies the SES 24 hour Threshold count in secs." 
          ::= { ncmE1AlarmThresholdConfigEntry 16 }

	   ncmCVP15MINThreshold OBJECT-TYPE
          SYNTAX  INTEGER
          ACCESS  read-write
          STATUS  mandatory
          DESCRIPTION
          "This variable specifies the CVP 15 minute Threshold count in secs."
          ::= { ncmE1AlarmThresholdConfigEntry 17 }
 
        ncmCVP24HRThreshold OBJECT-TYPE
          SYNTAX  INTEGER
          ACCESS  read-write
          STATUS  mandatory
          DESCRIPTION
          "This variable specifies the CVP 24 hour Threshold count in secs."
          ::= { ncmE1AlarmThresholdConfigEntry 18 }
 
        ncmCVL15MINThreshold OBJECT-TYPE
          SYNTAX  INTEGER
          ACCESS  read-write
          STATUS  mandatory
          DESCRIPTION
          "This variable specifies the CVL 15 minute Threshold count in secs."
          ::= { ncmE1AlarmThresholdConfigEntry 19 }
         
        ncmCVL24HRThreshold OBJECT-TYPE
          SYNTAX  INTEGER
          ACCESS  read-write
          STATUS  mandatory
          DESCRIPTION
          "This variable specifies the CVL 24 hour Threshold count in secs." 
          ::= { ncmE1AlarmThresholdConfigEntry 20 }
 
        ncmESL15MINThreshold OBJECT-TYPE
          SYNTAX  INTEGER
          ACCESS  read-write
          STATUS  mandatory
          DESCRIPTION
          "This variable specifies the ESL 15 minute Threshold count in secs."
          ::= { ncmE1AlarmThresholdConfigEntry 21 }
         
        ncmESL24HRThreshold OBJECT-TYPE
          SYNTAX  INTEGER
          ACCESS  read-write
          STATUS  mandatory
          DESCRIPTION
          "This variable specifies the CVL 24 hour Threshold count in secs." 
	      ::= { ncmE1AlarmThresholdConfigEntry 22 }
 
        ncmSESL15MINThreshold OBJECT-TYPE
          SYNTAX  INTEGER
          ACCESS  read-write
          STATUS  mandatory
          DESCRIPTION
          "This variable specifies the SESL 15 minute Threshold count in secs."
          ::= { ncmE1AlarmThresholdConfigEntry 23 }
         
        ncmSESL24HRThreshold OBJECT-TYPE
          SYNTAX  INTEGER
          ACCESS  read-write
          STATUS  mandatory
          DESCRIPTION
          "This variable specifies the SESL 24 hour Threshold count in secs." 
          ::= { ncmE1AlarmThresholdConfigEntry 24 }
 
        ncmUASP15MINThreshold OBJECT-TYPE
          SYNTAX  INTEGER
          ACCESS  read-write
          STATUS  mandatory
          DESCRIPTION
          "This variable specifies the UASP 15 minute Threshold count in secs." 
          ::= { ncmE1AlarmThresholdConfigEntry 25 }
 
         
        ncmUASP24HRThreshold OBJECT-TYPE
          SYNTAX  INTEGER
          ACCESS  read-write
          STATUS  mandatory
          DESCRIPTION
          "This variable specifies the UASP 24 hour Threshold count in secs." 
          ::= { ncmE1AlarmThresholdConfigEntry 26 }

	 -- ncm E1AlarmThresholdStatus Table
         
         ncmE1AlarmThresholdStatusTable OBJECT-TYPE
             SYNTAX   SEQUENCE OF  NcmE1AlarmThresholdStatusEntry
             ACCESS   not-accessible
             STATUS   mandatory
	      --DEFAULT test-function    acee1-test
             --DEFAULT next-function     acee1-next
             ::= { ncm-generic  1044 }
 
 
        ncmE1AlarmThresholdStatusEntry OBJECT-TYPE
             SYNTAX    NcmE1AlarmThresholdStatusEntry
             ACCESS   not-accessible
             STATUS   mandatory
             DESCRIPTION
                "An entry in the E1 ncmAlarm Threshold Status table."
             INDEX   { ncmE1AlarmThresholdStatusNIDIndex, ncmE1AlarmThresholdStatusIndex }
            ::= { ncmE1AlarmThresholdStatusTable 1 }
 
 
         NcmE1AlarmThresholdStatusEntry ::=
             SEQUENCE {
             ncmE1AlarmThresholdStatusNIDIndex
                 INTEGER,
             ncmE1AlarmThresholdStatusIndex
                 INTEGER,
             ncmLOFExceededE1
                INTEGER,
             ncmLOSExceededE1
                INTEGER,
             ncmRAIExceededE1
                INTEGER,
             ncmAISExceededE1
                INTEGER,
             ncmBPVExceededE1
                INTEGER,
             ncmES15MINExceeded
                INTEGER,
             ncmES24HRExceeded
                INTEGER,
              ncmSES15MINExceeded
                INTEGER,
              ncmSES24HRExceeded
                INTEGER,
              ncmCVP15MINExceeded
                INTEGER,
             ncmCVP24HRExceeded
                INTEGER,
              ncmCVL15MINExceeded
                INTEGER,
              ncmCVL24HRExceeded
                INTEGER,
              ncmESL15MINExceeded
                INTEGER,
              ncmESL24HRExceeded
                INTEGER,
              ncmSESL15MINExceeded
                INTEGER,
              ncmSESL24HRExceeded
                INTEGER,
              ncmUASP15MINExceeded
                INTEGER,
              ncmUASP24HRExceeded
                INTEGER,
	      ncmLOFThresholdCount
		INTEGER,
	      ncmLOFTimeIntervals
		INTEGER,
	      ncmLOSThresholdCount
		INTEGER,
	      ncmLOSTimeIntervals
		INTEGER,
	      ncmRAIThresholdCount
		INTEGER,
	      ncmRAITimeIntervals
		INTEGER,
	      ncmAISThresholdCount
		INTEGER,
	      ncmAISTimeIntervals
		INTEGER,
	      ncmBPVThresholdCount
		INTEGER,
	      ncmBPVTimeIntervals
		INTEGER,
	     ncmES15MINThresholdCount
		INTEGER,
	      ncmES24HRThresholdCount
		INTEGER,
	      ncmSES15MINThresholdCount
		INTEGER,
	      ncmSES24HRThresholdCount
		INTEGER,
	      ncmCVP15MINThresholdCount
		INTEGER,
	      ncmCVP24HRThresholdCount
		INTEGER,
	      ncmCVL15MINThresholdCount
		INTEGER,
	      ncmCVL24HRThresholdCount
		INTEGER,
	      ncmESL15MINThresholdCount
		INTEGER,
	      ncmESL24HRThresholdCount
		INTEGER,
	      ncmSESL15MINThresholdCount
		INTEGER,
	      ncmSESL24HRThresholdCount
		INTEGER,
	      ncmUASP15MINThresholdCount
		INTEGER,
	      ncmUASP24HRThresholdCount
		INTEGER





	}
 
 
 
        ncmE1AlarmThresholdStatusNIDIndex OBJECT-TYPE
          SYNTAX  INTEGER (1..'7fffffff'h)
          ACCESS  read-only
          STATUS  mandatory
          DESCRIPTION
         "The object specifies the node id of the node."
 
          ::= { ncmE1AlarmThresholdStatusEntry 1}
 
 
        ncmE1AlarmThresholdStatusIndex OBJECT-TYPE
          SYNTAX  INTEGER
          ACCESS  read-only
          STATUS  mandatory
          DESCRIPTION
         "The index value which uniquely identifies  the
          interface to which this entry is applicable."
 
          ::= { ncmE1AlarmThresholdStatusEntry 2 }
 
 
 
          ncmLOFExceededE1 OBJECT-TYPE
          SYNTAX  INTEGER {
 
                        no(1),
                        yes(2)
 
                        }
          ACCESS  read-only
          STATUS  mandatory
          DESCRIPTION
         "This variable specifies if LOF exceeded or not."
 
          ::= { ncmE1AlarmThresholdStatusEntry 3 }
 
 
         ncmLOSExceededE1 OBJECT-TYPE
          SYNTAX  INTEGER {
 
                        no(1),
                        yes(2)
 
                        }
          ACCESS  read-only
          STATUS  mandatory
          DESCRIPTION
         "This variable specifies if LOS exceeded or not."
 
          ::= { ncmE1AlarmThresholdStatusEntry 4 }


	 ncmRAIExceededE1 OBJECT-TYPE
          SYNTAX  INTEGER {
 
                        no(1),
                        yes(2)
 
                        }
          ACCESS  read-only
          STATUS  mandatory
          DESCRIPTION
         "This variable specifies if RAI exceeded or not."
 
          ::= { ncmE1AlarmThresholdStatusEntry 5 }
 
 
         ncmAISExceededE1 OBJECT-TYPE
          SYNTAX  INTEGER {
 
                        no(1),
                        yes(2)
 
                        }
          ACCESS  read-only
          STATUS  mandatory
          DESCRIPTION
         "This variable specifies if AIS exceeded or not."
 
          ::= { ncmE1AlarmThresholdStatusEntry 6 }
 
 
         ncmBPVExceededE1 OBJECT-TYPE
          SYNTAX  INTEGER {
 
                        no(1),
                        yes(2)
 
                        }
          ACCESS  read-only
          STATUS  mandatory
          DESCRIPTION
         "This variable specifies if BPV exceeded or not."
 
          ::= { ncmE1AlarmThresholdStatusEntry 7 }
 
 
 
         ncmES15MINExceeded OBJECT-TYPE
          SYNTAX  INTEGER {
 
                        no(1),
                        yes(2)
 
                        }
          ACCESS  read-only
          STATUS  mandatory
          DESCRIPTION
         "This variable specifies if ES 15 minute exceeded or not."
 
          ::= { ncmE1AlarmThresholdStatusEntry 8 }


	 
	  ncmES24HRExceeded OBJECT-TYPE
          SYNTAX  INTEGER {
 
                        no(1),
                        yes(2)
 
                        }
          ACCESS  read-only
          STATUS  mandatory
          DESCRIPTION
         "This variable specifies if ES 24 Hour exceeded or not."
 
          ::= { ncmE1AlarmThresholdStatusEntry 9 }

 
        
 
        
 
 
         ncmSES15MINExceeded OBJECT-TYPE
          SYNTAX  INTEGER {
 
                        no(1),
                        yes(2)
 
                        }
          ACCESS  read-only
          STATUS  mandatory
          DESCRIPTION
         "This variable specifies if SES 15 minute exceeded or not."
 
          ::= { ncmE1AlarmThresholdStatusEntry 10 }


	 ncmSES24HRExceeded OBJECT-TYPE
          SYNTAX  INTEGER {
 
                        no(1),
                        yes(2)
 
                        }
          ACCESS  read-only
          STATUS  mandatory
          DESCRIPTION
         "This variable specifies if SES 24 Hour exceeded or not."
 
          ::= { ncmE1AlarmThresholdStatusEntry 11 }


	 ncmCVP15MINExceeded OBJECT-TYPE
          SYNTAX  INTEGER {
 
                        no(1),
                        yes(2)
 
                        }
          ACCESS  read-only
          STATUS  mandatory
          DESCRIPTION
         "This variable specifies if CVP 15 minute exceeded or not."
 
          ::= { ncmE1AlarmThresholdStatusEntry 12 }




	  ncmCVP24HRExceeded OBJECT-TYPE
          SYNTAX  INTEGER {
 
                        no(1),
                        yes(2)
 
                        }
          ACCESS  read-only
          STATUS  mandatory
          DESCRIPTION
         "This variable specifies if CVP 24 Hour exceeded or not."
 
          ::= { ncmE1AlarmThresholdStatusEntry 13 }
 
 
         ncmCVL15MINExceeded OBJECT-TYPE
          SYNTAX  INTEGER {
 
                        no(1),
                        yes(2)
 
                        }
          ACCESS  read-only
          STATUS  mandatory
          DESCRIPTION
         "This variable specifies if CVL 15 minute exceeded or not."
 
          ::= { ncmE1AlarmThresholdStatusEntry 14 }
 
 
        ncmCVL24HRExceeded OBJECT-TYPE
          SYNTAX  INTEGER {
 
                        no(1),
                        yes(2)
 
                        }
          ACCESS  read-only
          STATUS  mandatory
          DESCRIPTION
         "This variable specifies if CVL 24 Hour exceeded or not."
 
          ::= { ncmE1AlarmThresholdStatusEntry 15 }
 
 
         ncmESL15MINExceeded OBJECT-TYPE
          SYNTAX  INTEGER {
 
                        no(1),
                        yes(2)
 
                        }
          ACCESS  read-only
          STATUS  mandatory
          DESCRIPTION
         "This variable specifies if ESL 15 minute exceeded or not."
 
          ::= { ncmE1AlarmThresholdStatusEntry 16 }


	 ncmESL24HRExceeded OBJECT-TYPE
          SYNTAX  INTEGER {
 
                        no(1),
                        yes(2)
 
                        }
          ACCESS  read-only
          STATUS  mandatory
          DESCRIPTION
         "This variable specifies if ESL 24 Hour exceeded or not."
 
          ::= { ncmE1AlarmThresholdStatusEntry 17 }
 
 
 
        ncmSESL15MINExceeded OBJECT-TYPE
          SYNTAX  INTEGER {
 
                        no(1),
                        yes(2)
 
                        }
          ACCESS  read-only
          STATUS  mandatory
          DESCRIPTION
         "This variable specifies if SESL 15 minute exceeded or not."
 
          ::= { ncmE1AlarmThresholdStatusEntry 18 }
 
 
        ncmSESL24HRExceeded OBJECT-TYPE
          SYNTAX  INTEGER {
 
                        no(1),
                        yes(2)
 
                        }
          ACCESS  read-only
          STATUS  mandatory
          DESCRIPTION
         "This variable specifies if SESL 24 Hour exceeded or not."
 
          ::= { ncmE1AlarmThresholdStatusEntry 19 }
 
 
        ncmUASP15MINExceeded OBJECT-TYPE
          SYNTAX  INTEGER {
 
                        no(1),
                        yes(2)
 
                        }
          ACCESS  read-only
          STATUS  mandatory
          DESCRIPTION
         "This variable specifies if UASP 15 minute exceeded or not."
 
          ::= { ncmE1AlarmThresholdStatusEntry 20 }


	  ncmUASP24HRExceeded OBJECT-TYPE
          SYNTAX  INTEGER {
 
                        no(1),
                        yes(2)
 
                        }
          ACCESS  read-only
          STATUS  mandatory
          DESCRIPTION
         "This variable specifies if UASP 24 Hour exceeded or not."
 
          ::= { ncmE1AlarmThresholdStatusEntry 21 }


	ncmLOFThresholdCount OBJECT-TYPE
          SYNTAX  INTEGER                         
          ACCESS  read-only
          STATUS  mandatory
          DESCRIPTION
         "This variable specifies the LOF Threshold Count in seconds."
 
          ::= { ncmE1AlarmThresholdStatusEntry 22 }


	ncmLOFTimeIntervals OBJECT-TYPE
          SYNTAX  INTEGER                         
          ACCESS  read-only
          STATUS  mandatory
          DESCRIPTION
         "This variable specifies the LOF Time Intervals in seconds."
 
          ::= { ncmE1AlarmThresholdStatusEntry 23 }



	ncmLOSThresholdCount OBJECT-TYPE
          SYNTAX  INTEGER                         
          ACCESS  read-only
          STATUS  mandatory
          DESCRIPTION
         "This variable specifies the LOS Threshold Count in seconds."
 
          ::= { ncmE1AlarmThresholdStatusEntry 24 }


	ncmLOSTimeIntervals OBJECT-TYPE
          SYNTAX  INTEGER                         
          ACCESS  read-only
          STATUS  mandatory
          DESCRIPTION
         "This variable specifies the LOS Time Intervals in seconds."
 
          ::= { ncmE1AlarmThresholdStatusEntry 25 }



	ncmRAIThresholdCount OBJECT-TYPE
          SYNTAX  INTEGER                         
          ACCESS  read-only
          STATUS  mandatory
          DESCRIPTION
         "This variable specifies the RAI Threshold Count in seconds."
 
          ::= { ncmE1AlarmThresholdStatusEntry 26 }


	ncmRAITimeIntervals OBJECT-TYPE
          SYNTAX  INTEGER                         
          ACCESS  read-only
          STATUS  mandatory
          DESCRIPTION
         "This variable specifies the RAI Time Intervals in seconds."
 
          ::= { ncmE1AlarmThresholdStatusEntry 27 }



	ncmAISThresholdCount OBJECT-TYPE
          SYNTAX  INTEGER                         
          ACCESS  read-only
          STATUS  mandatory
          DESCRIPTION
         "This variable specifies the AIS Threshold Count in seconds."
 
          ::= { ncmE1AlarmThresholdStatusEntry 28 }


	ncmAISTimeIntervals OBJECT-TYPE
          SYNTAX  INTEGER                         
          ACCESS  read-only
          STATUS  mandatory
          DESCRIPTION
         "This variable specifies the AIS Time Intervals in seconds."
 
          ::= { ncmE1AlarmThresholdStatusEntry 29 }


	ncmBPVThresholdCount OBJECT-TYPE
          SYNTAX  INTEGER                         
          ACCESS  read-only
          STATUS  mandatory
          DESCRIPTION
         "This variable specifies the BPV Threshold Count in seconds."
 
          ::= { ncmE1AlarmThresholdStatusEntry 30 }


	ncmBPVTimeIntervals OBJECT-TYPE
          SYNTAX  INTEGER                         
          ACCESS  read-only
          STATUS  mandatory
          DESCRIPTION
         "This variable specifies the BPV Time Intervals in seconds."
 
          ::= { ncmE1AlarmThresholdStatusEntry 31 }



	ncmES15MINThresholdCount OBJECT-TYPE
          SYNTAX  INTEGER                         
          ACCESS  read-only
          STATUS  mandatory
          DESCRIPTION
         "This variable specifies the ES 15MIN Threshold Count in seconds."
 
          ::= { ncmE1AlarmThresholdStatusEntry 32 }


	ncmES24HRThresholdCount OBJECT-TYPE
          SYNTAX  INTEGER                         
          ACCESS  read-only
          STATUS  mandatory
          DESCRIPTION
         "This variable specifies the ES 24HR Threshold Count in seconds."
 
          ::= { ncmE1AlarmThresholdStatusEntry 33 }


	ncmSES15MINThresholdCount OBJECT-TYPE
          SYNTAX  INTEGER                         
          ACCESS  read-only
          STATUS  mandatory
          DESCRIPTION
         "This variable specifies the SES 15MIN Threshold Count in seconds."
 
          ::= { ncmE1AlarmThresholdStatusEntry 34 }


	ncmSES24HRThresholdCount OBJECT-TYPE
          SYNTAX  INTEGER                         
          ACCESS  read-only
          STATUS  mandatory
          DESCRIPTION
         "This variable specifies the SES 24 HR Threshold Count in seconds."
 
          ::= { ncmE1AlarmThresholdStatusEntry 35 }



 	ncmCVP15MINThresholdCount OBJECT-TYPE
          SYNTAX  INTEGER                         
          ACCESS  read-only
          STATUS  mandatory
          DESCRIPTION
         "This variable specifies the CVP 15MIN Threshold Count in seconds."
 
          ::= { ncmE1AlarmThresholdStatusEntry 36 }


	ncmCVP24HRThresholdCount OBJECT-TYPE
          SYNTAX  INTEGER                         
          ACCESS  read-only
          STATUS  mandatory
          DESCRIPTION
         "This variable specifies the CVP 24 HR Threshold Count in seconds."
 
          ::= { ncmE1AlarmThresholdStatusEntry 37 }


	ncmCVL15MINThresholdCount OBJECT-TYPE
          SYNTAX  INTEGER                         
          ACCESS  read-only
          STATUS  mandatory
          DESCRIPTION
         "This variable specifies the CVL 15MIN Threshold Count in seconds."
 
          ::= { ncmE1AlarmThresholdStatusEntry 38 }


	ncmCVL24HRThresholdCount OBJECT-TYPE
          SYNTAX  INTEGER                         
          ACCESS  read-only
          STATUS  mandatory
          DESCRIPTION
         "This variable specifies the CVL 24 HR Threshold Count in seconds."
 
          ::= { ncmE1AlarmThresholdStatusEntry 39 }


	ncmESL15MINThresholdCount OBJECT-TYPE
          SYNTAX  INTEGER                         
          ACCESS  read-only
          STATUS  mandatory
          DESCRIPTION
         "This variable specifies the ESL 15MIN Threshold Count in seconds."
 
          ::= { ncmE1AlarmThresholdStatusEntry 40 }


	 ncmESL24HRThresholdCount OBJECT-TYPE
          SYNTAX  INTEGER                         
          ACCESS  read-only
          STATUS  mandatory
          DESCRIPTION
         "This variable specifies the ESL 24 HR Threshold Count in seconds."
 
          ::= { ncmE1AlarmThresholdStatusEntry 41 }


	ncmSESL15MINThresholdCount OBJECT-TYPE
          SYNTAX  INTEGER                         
          ACCESS  read-only
          STATUS  mandatory
          DESCRIPTION
         "This variable specifies the SESL 15MIN Threshold Count in seconds."
 
          ::= { ncmE1AlarmThresholdStatusEntry 42 }


	ncmSESL24HRThresholdCount OBJECT-TYPE
          SYNTAX  INTEGER                         
          ACCESS  read-only
          STATUS  mandatory
          DESCRIPTION
         "This variable specifies the SESL 24 HR Threshold Count in seconds."
 
          ::= { ncmE1AlarmThresholdStatusEntry 43 }


	ncmUASP15MINThresholdCount OBJECT-TYPE
          SYNTAX  INTEGER                         
          ACCESS  read-only
          STATUS  mandatory
          DESCRIPTION
         "This variable specifies the UASP 15MIN Threshold Count in seconds."
 
          ::= { ncmE1AlarmThresholdStatusEntry 44 }


	ncmUASP24HRThresholdCount OBJECT-TYPE
          SYNTAX  INTEGER                         
          ACCESS  read-only
          STATUS  mandatory
          DESCRIPTION
         "This variable specifies the UASP 24 HR Threshold Count in seconds."
 
          ::= { ncmE1AlarmThresholdStatusEntry 45 }



		-- 	The additional groups for Qualcomm


	 	--      ncmAlarmThresholdConfig Group


        ncmAlarmThresholdConfigTable OBJECT-TYPE
             SYNTAX   SEQUENCE OF NcmAlarmThresholdConfigEntry
             ACCESS   not-accessible
             STATUS   mandatory
	     --DEFAULT test-function    almcfg-test
             --DEFAULT next-function    almcfg-next


	  
 
 
             ::= { ncm-generic  1045 }


        ncmAlarmThresholdConfigEntry OBJECT-TYPE
             SYNTAX   NcmAlarmThresholdConfigEntry
             ACCESS   not-accessible
             STATUS   mandatory
             DESCRIPTION
                "An entry in the  ncmAlarm Threshold Configure table."
             INDEX   { ncmAlarmThresholdConfigNIDIndex, ncmAlarmThresholdConfigIndex }
            ::= { ncmAlarmThresholdConfigTable 1 }


       	NcmAlarmThresholdConfigEntry ::=
             SEQUENCE {
             ncmAlarmThresholdConfigNIDIndex
                 INTEGER,
             ncmAlarmThresholdConfigIndex
                 INTEGER,
             ncmLOFThreshold
                INTEGER,
             ncmLOFTimeInterval
                INTEGER,
             ncmLOSThreshold
                INTEGER,
             ncmLOSTimeInterval
                INTEGER,
	     ncmRAIThreshold
                INTEGER,
             ncmRAITimeInterval
                INTEGER,
             ncmAISThreshold
                INTEGER,
             ncmAISTimeInterval
                INTEGER,
             ncmBPVThreshold
                INTEGER,
             ncmBPVTimeInterval
                INTEGER,
             ncmES15MINThreshold
                INTEGER,
             ncmES24HRThreshold
                INTEGER,
             ncmSES15MINThreshold
                INTEGER,
             ncmSES24HRThreshold
                INTEGER


	}




	 ncmAlarmThresholdConfigNIDIndex OBJECT-TYPE
          SYNTAX  INTEGER (1..'7fffffff'h)
          ACCESS  read-only
          STATUS  mandatory
          DESCRIPTION
         "The object specifies the node id of the node."
 
          ::= { ncmAlarmThresholdConfigEntry 1}
 
 
         ncmAlarmThresholdConfigIndex OBJECT-TYPE
          SYNTAX  INTEGER
          ACCESS  read-only
          STATUS  mandatory
          DESCRIPTION
         "The index value which uniquely identifies  the
          interface to which this entry is applicable."
 
          ::= { ncmAlarmThresholdConfigEntry 2 }
 
 
         ncmLOFThreshold OBJECT-TYPE
          SYNTAX  INTEGER
          ACCESS  read-write
          STATUS  mandatory
          DESCRIPTION
          "This variable the LOF Threshold count is seconds (1-86,400)." 
          ::= { ncmAlarmThresholdConfigEntry 3 }
 
         
        ncmLOFTimeInterval OBJECT-TYPE
          SYNTAX  INTEGER
          ACCESS  read-write
          STATUS  mandatory
          DESCRIPTION
          "This variable specifies the LOF Time Interval is seconds (1-86,400)."
 
          ::= { ncmAlarmThresholdConfigEntry 4 }

	
	
	ncmLOSThreshold OBJECT-TYPE
          SYNTAX  INTEGER
          ACCESS  read-write
          STATUS  mandatory
          DESCRIPTION
          "This variable specifies the LOS Threshold count is seconds (1-86,400)." 
          ::= { ncmAlarmThresholdConfigEntry 5 }
 
         
        ncmLOSTimeInterval OBJECT-TYPE
          SYNTAX  INTEGER
          ACCESS  read-write
          STATUS  mandatory
          DESCRIPTION
          "This variable specifies the LOS Time Interval is seconds (1-86,400)."
 
          ::= { ncmAlarmThresholdConfigEntry 6 }



	ncmRAIThreshold OBJECT-TYPE
          SYNTAX  INTEGER
          ACCESS  read-write
          STATUS  mandatory
          DESCRIPTION
          "This variable specifies the RAI Threshold count is seconds (1-86,400)." 
          ::= { ncmAlarmThresholdConfigEntry 7 }
 
         
        ncmRAITimeInterval OBJECT-TYPE
          SYNTAX  INTEGER
          ACCESS  read-write
          STATUS  mandatory
          DESCRIPTION
          "This variable specifies the RAI Time Interval is seconds (1-86,400)."
 
          ::= { ncmAlarmThresholdConfigEntry 8 }


	ncmAISThreshold OBJECT-TYPE
          SYNTAX  INTEGER
          ACCESS  read-write
          STATUS  mandatory
          DESCRIPTION
          "This variable specifies the AIS Threshold count is seconds (1-86,400)." 
          ::= { ncmAlarmThresholdConfigEntry 9 }
 
         
      	 ncmAISTimeInterval OBJECT-TYPE
          SYNTAX  INTEGER
          ACCESS  read-write
          STATUS  mandatory
          DESCRIPTION
          "This variable specifies the AIS Time Interval is seconds (1-86,400)."
 
          ::= { ncmAlarmThresholdConfigEntry 10 }



	ncmBPVThreshold OBJECT-TYPE
          SYNTAX  INTEGER
          ACCESS  read-write
          STATUS  mandatory
          DESCRIPTION
          "This variable specifies the BPV Threshold count is seconds (1-86,400)." 
          ::= { ncmAlarmThresholdConfigEntry 11 }
 
         
        ncmBPVTimeInterval OBJECT-TYPE
          SYNTAX  INTEGER
          ACCESS  read-write
          STATUS  mandatory
          DESCRIPTION
          "This variable specifies the BPV Time Interval is seconds (1-86,400)."
 
          ::= { ncmAlarmThresholdConfigEntry 12 }


	ncmES15MINThreshold OBJECT-TYPE
          SYNTAX  INTEGER
          ACCESS  read-write
          STATUS  mandatory
          DESCRIPTION
          "This variable specifies the ES 15 minute Threshold count is seconds (1-86,400)." 
          ::= { ncmAlarmThresholdConfigEntry 13 }
 
         
        ncmES24HRThreshold OBJECT-TYPE
          SYNTAX  INTEGER
          ACCESS  read-write
          STATUS  mandatory
          DESCRIPTION
          "This variable specifies the ES 24 hour Threshold count in seconds (1-86,400)."
 
          ::= { ncmAlarmThresholdConfigEntry 14 }



	ncmSES15MINThreshold OBJECT-TYPE
          SYNTAX  INTEGER
          ACCESS  read-write
          STATUS  mandatory
          DESCRIPTION
          "This variable specifies the SES 15 minute Threshold count is seconds (1-86,400)." 
          ::= { ncmAlarmThresholdConfigEntry 15 }
 
         
        ncmSES24HRThreshold OBJECT-TYPE
          SYNTAX  INTEGER
          ACCESS  read-write
          STATUS  mandatory
          DESCRIPTION
          "This variable specifies the SES 24 hour Threshold count in seconds (1-86,400)."
 
          ::= { ncmAlarmThresholdConfigEntry 16 }





	 --  ncmAlarmThresholdStatus Table
 
         
         ncmAlarmThresholdStatusTable OBJECT-TYPE
             SYNTAX   SEQUENCE OF NcmAlarmThresholdStatusEntry
             ACCESS   not-accessible
             STATUS   mandatory
		 --DEFAULT test-function  almcfg-test
             --DEFAULT next-function    	almcfg-next



 
 
             ::= { ncm-generic  1046 }
 
 
        ncmAlarmThresholdStatusEntry OBJECT-TYPE
             SYNTAX   NcmAlarmThresholdStatusEntry
             ACCESS   not-accessible
             STATUS   mandatory
             DESCRIPTION
                "An entry in the  ncmAlarm Threshold Status table."
             INDEX   { ncmAlarmThresholdStatusNIDIndex, ncmAlarmThresholdStatusIndex }
            ::= { ncmAlarmThresholdStatusTable 1 }
 
 
        NcmAlarmThresholdStatusEntry ::=
             SEQUENCE {
             ncmAlarmThresholdStatusNIDIndex
                 INTEGER,
             ncmAlarmThresholdStatusIndex
                 INTEGER,
             ncmLOFExceeded
                INTEGER,
             ncmLOSExceeded
                INTEGER,
	     ncmAISExceeded
                INTEGER,
             ncmRAIExceeded
                INTEGER,
             ncmBPVExceeded
                INTEGER,
             ncmESExceeded
                INTEGER,
	     ncmSESExceeded
                INTEGER,
	     ncmLOFThresholdCountst
		INTEGER,
	     ncmLOFTimeIntervalst
		INTEGER,
	      ncmLOSThresholdCountst
		INTEGER,
	      ncmLOSTimeIntervalst
		INTEGER,
	      ncmRAIThresholdCountst
		INTEGER,
	      ncmRAITimeIntervalst
		INTEGER,
	      ncmAISThresholdCountst
		INTEGER,
	      ncmAISTimeIntervalst
		INTEGER,
	     ncmBPVThresholdCountst
		INTEGER,
	     ncmBPVTimeIntervalst
		INTEGER,
	    ncmES15MINThresholdCountst
		INTEGER,
	    ncmES24HRThresholdCountst
		INTEGER,
	     ncmSES15MINThresholdCountst
		INTEGER,
	     ncmSES24HRThresholdCountst
		INTEGER,
	     ncmResetAlmThresholdCount
		INTEGER

	}

	     

	ncmAlarmThresholdStatusNIDIndex OBJECT-TYPE
          SYNTAX  INTEGER (1..'7fffffff'h)
          ACCESS  read-only
          STATUS  mandatory
          DESCRIPTION
         "The object specifies the node id of the node."
 
          ::= { ncmAlarmThresholdStatusEntry 1}
 
 
        ncmAlarmThresholdStatusIndex OBJECT-TYPE
          SYNTAX  INTEGER
          ACCESS  read-only
          STATUS  mandatory
          DESCRIPTION
         "The index value which uniquely identifies  the
          interface to which this entry is applicable."
 
          ::= { ncmAlarmThresholdStatusEntry 2 }
 
 
 
          ncmLOFExceeded OBJECT-TYPE
          SYNTAX  INTEGER {
 
                        no(1),
                        yes(2)
 
                        }
          ACCESS  read-only
          STATUS  mandatory
          DESCRIPTION
         "This variable specifies if LOF exceeded or not."
 
          ::= { ncmAlarmThresholdStatusEntry 3 }


	ncmLOSExceeded OBJECT-TYPE
          SYNTAX  INTEGER {
 
                        no(1),
                        yes(2)
 
                        }
          ACCESS  read-only
          STATUS  mandatory
          DESCRIPTION
         "This variable specifies if LOS exceeded or not."
 
          ::= { ncmAlarmThresholdStatusEntry 4 }

        ncmAISExceeded OBJECT-TYPE
          SYNTAX  INTEGER {
 
                        no(1),
                        yes(2)
 
                        }
          ACCESS  read-only
          STATUS  mandatory
          DESCRIPTION
         "This variable specifies if AIS exceeded or not."
 
          ::= { ncmAlarmThresholdStatusEntry 5 }


	ncmRAIExceeded OBJECT-TYPE
          SYNTAX  INTEGER {
 
                        no(1),
                        yes(2)
 
                        }
          ACCESS  read-only
          STATUS  mandatory
          DESCRIPTION
         "This variable specifies if RAI exceeded or not."
 
          ::= { ncmAlarmThresholdStatusEntry 6 }


	ncmBPVExceeded OBJECT-TYPE
          SYNTAX  INTEGER {
 
                        no(1),
                        yes(2)
 
                        }
          ACCESS  read-only
          STATUS  mandatory
          DESCRIPTION
         "This variable specifies if BPV exceeded or not."
 
          ::= { ncmAlarmThresholdStatusEntry 7 }



	ncmESExceeded OBJECT-TYPE
          SYNTAX  INTEGER {
 
                        no(1),
                        yes(2)
 
                        }
          ACCESS  read-only
          STATUS  mandatory
          DESCRIPTION
         "This variable specifies if ES exceeded or not."
 
          ::= { ncmAlarmThresholdStatusEntry 8 }


	ncmSESExceeded OBJECT-TYPE
          SYNTAX  INTEGER {
 
                        no(1),
                        yes(2)
 
                        }
          ACCESS  read-only
          STATUS  mandatory
          DESCRIPTION
         "This variable specifies if SES exceeded or not."
 
          ::= { ncmAlarmThresholdStatusEntry 9 }


	

	ncmLOFThresholdCountst OBJECT-TYPE
          SYNTAX  INTEGER                         
          ACCESS  read-only
          STATUS  mandatory
          DESCRIPTION
         "This variable specifies the LOF Threshold Count in seconds."
 
          ::= { ncmAlarmThresholdStatusEntry 10 }


	ncmLOFTimeIntervalst OBJECT-TYPE
          SYNTAX  INTEGER                         
          ACCESS  read-only
          STATUS  mandatory
          DESCRIPTION
         "This variable specifies the LOF Time Intervals in seconds."
 
          ::= { ncmAlarmThresholdStatusEntry 11 }



	ncmLOSThresholdCountst OBJECT-TYPE
          SYNTAX  INTEGER                         
          ACCESS  read-only
          STATUS  mandatory
          DESCRIPTION
         "This variable specifies the LOS Threshold Count in seconds."
 
          ::= { ncmAlarmThresholdStatusEntry 12 }


	ncmLOSTimeIntervalst OBJECT-TYPE
          SYNTAX  INTEGER                         
          ACCESS  read-only
          STATUS  mandatory
          DESCRIPTION
         "This variable specifies the LOS Time Intervals in seconds."
 
          ::= { ncmAlarmThresholdStatusEntry 13 }


	ncmRAIThresholdCountst OBJECT-TYPE
          SYNTAX  INTEGER                         
          ACCESS  read-only
          STATUS  mandatory
          DESCRIPTION
         "This variable specifies the RAI Threshold Count in seconds."
 
          ::= { ncmAlarmThresholdStatusEntry 14 }


	ncmRAITimeIntervalst OBJECT-TYPE
          SYNTAX  INTEGER                         
          ACCESS  read-only
          STATUS  mandatory
          DESCRIPTION
         "This variable specifies the RAI Time Intervals in seconds."
 
          ::= { ncmAlarmThresholdStatusEntry 15 }



	ncmAISThresholdCountst  OBJECT-TYPE
          SYNTAX  INTEGER                         
          ACCESS  read-only
          STATUS  mandatory
          DESCRIPTION
         "This variable specifies the AIS Threshold Count in seconds."
 
          ::= { ncmAlarmThresholdStatusEntry 16 }


	ncmAISTimeIntervalst OBJECT-TYPE
          SYNTAX  INTEGER                         
          ACCESS  read-only
          STATUS  mandatory
          DESCRIPTION
         "This variable specifies the AIS Time Intervals in seconds."
 
          ::= { ncmAlarmThresholdStatusEntry 17 }


	
	ncmBPVThresholdCountst OBJECT-TYPE
          SYNTAX  INTEGER                         
          ACCESS  read-only
          STATUS  mandatory
          DESCRIPTION
         "This variable specifies the BPV Threshold Count in seconds."
 
          ::= { ncmAlarmThresholdStatusEntry 18 }


	ncmBPVTimeIntervalst OBJECT-TYPE
          SYNTAX  INTEGER                         
          ACCESS  read-only
          STATUS  mandatory
          DESCRIPTION
         "This variable specifies the BPV Time Intervals in seconds."
 
          ::= { ncmAlarmThresholdStatusEntry 19 }



	ncmES15MINThresholdCountst OBJECT-TYPE
          SYNTAX  INTEGER                         
          ACCESS  read-only
          STATUS  mandatory
          DESCRIPTION
         "This variable specifies the ES 15 minute Threshold Count in seconds."
 
          ::= { ncmAlarmThresholdStatusEntry 20 }


	ncmES24HRThresholdCountst OBJECT-TYPE
          SYNTAX  INTEGER                         
          ACCESS  read-only
          STATUS  mandatory
          DESCRIPTION
         "This variable specifies the ES 24 Hour Count in seconds."
 
          ::= { ncmAlarmThresholdStatusEntry 21 }


	ncmSES15MINThresholdCountst OBJECT-TYPE
          SYNTAX  INTEGER                         
          ACCESS  read-only
          STATUS  mandatory
          DESCRIPTION
         "This variable specifies the SES 15 minute Threshold Count in seconds."
 
          ::= { ncmAlarmThresholdStatusEntry 22 }


	 ncmSES24HRThresholdCountst OBJECT-TYPE
          SYNTAX  INTEGER                         
          ACCESS  read-only
          STATUS  mandatory
          DESCRIPTION
         "This variable specifies the SES 24 hour Count in seconds."
 
          ::= { ncmAlarmThresholdStatusEntry 23 }


        ncmResetAlmThresholdCount OBJECT-TYPE
             SYNTAX  INTEGER {
                         reset(1)
                     }
             ACCESS  read-write
             STATUS  mandatory
             DESCRIPTION
             "This object reset the alarm threshold counter."
            ::= { ncmAlarmThresholdStatusEntry 24 }

        --
        --
        -- ncm-generic 1047-1049 being used by Node Manager.
        -- 
        --

	--      ncm Shelf Sync Source Segment Table

 
         ncmShelfSyncSourceSegTable OBJECT-TYPE
             SYNTAX  SEQUENCE OF NcmShelfSyncSourceSegEntry
             ACCESS  not-accessible
             STATUS  mandatory
	     --DEFAULT test-function    acesyncseg-test
             --DEFAULT next-function    acesyncseg-next
 
            ::= { ncm-generic  1050 }


        ncmShelfSyncSourceSegEntry OBJECT-TYPE
             SYNTAX NcmShelfSyncSourceSegEntry
             ACCESS  not-accessible
             STATUS  mandatory
             DESCRIPTION
                "An entry in the ncm Shelf Sync Source Segment Time table."
            INDEX   { ncmShelfSyncSegNIDIndex, ncmShelfSyncSourceSegIndex, ncmShelfSyncSourceSegNum }
            ::= { ncmShelfSyncSourceSegTable 1 }


        NcmShelfSyncSourceSegEntry ::=
         SEQUENCE {
           ncmShelfSyncSegNIDIndex
                INTEGER,
           ncmShelfSyncSourceSegIndex
                INTEGER,
	   ncmShelfSyncSourceSegNum
                INTEGER,
           ncmShelfTypeSeg
                INTEGER,
	   ncmRefBusSeg
                INTEGER,
           ncmSourceSegOneShelfNum
                INTEGER,
           ncmSourceSegOneCardNum
                INTEGER,
           ncmSourceSegOneClockRef
                INTEGER,
           ncmSourceSegAutoRestore1
                INTEGER,
           ncmSourceSegTwoShelfNum
                INTEGER,
           ncmSourceSegTwoCardNum
                INTEGER,
           ncmSourceSegTwoClockRef
                INTEGER,
           ncmSourceSegAutoRestore2
                INTEGER,
           ncmSourceSegThreeShelfNum
                INTEGER,
           ncmSourceSegThreeCardNum
                INTEGER,
           ncmSourceSegThreeClockRef
                INTEGER,
           ncmSourceSegAutoRestore3
                INTEGER,
           ncmShelfCurrentSyncSourceSeg
                INTEGER

                }

        ncmShelfSyncSegNIDIndex OBJECT-TYPE
             SYNTAX  INTEGER (1..'7fffffff'h)
             ACCESS  read-only
             STATUS  mandatory
             DESCRIPTION
                "This variable indicates the node id
	         value of the node."  
            ::= { ncmShelfSyncSourceSegEntry 1 }


         ncmShelfSyncSourceSegIndex OBJECT-TYPE
             SYNTAX  INTEGER (1..'7fffffff'h)
             ACCESS  read-only
             STATUS  mandatory
	      DESCRIPTION
                "This object is the identifier of an Interface
                on a managed device.  If there is an ifEntry
                that is directly associated with this and
                only this DS1 interface, it should have the
                same value as ifIndex.  Otherwise, the value
                exceeds ifNumber, and is a unique identifier
                following this rule: inside interfaces (e.g.,
                equipment side) with even numbers and outside
                interfaces (e.g., network side) with odd
                numbers."
            ::= { ncmShelfSyncSourceSegEntry 2 }
 
 
	   ncmShelfSyncSourceSegNum OBJECT-TYPE
             SYNTAX  INTEGER (1..'7fffffff'h)
             ACCESS  read-only
             STATUS  mandatory
             DESCRIPTION
                "This variable indicates the segment index."
            ::= { ncmShelfSyncSourceSegEntry 3 }

	     
           ncmShelfTypeSeg OBJECT-TYPE
             SYNTAX  INTEGER {
                         uninstalled(1),
                         dualLineShelf(2),
                         multiLineShelf(3),
                         nb-2200LineShelf(4),
                         nb-2200-4ILineShelf(10),
                         nb-2200QLineShelf(52),
                         nb-2200-4IQLineShelf(54)
                     }
             ACCESS  read-only
             STATUS  mandatory
             DESCRIPTION
                "This variable indicates the shelf hardware type."
            ::= { ncmShelfSyncSourceSegEntry 4 }


	   ncmRefBusSeg OBJECT-TYPE
             SYNTAX  INTEGER {
                         c(1),
                         a(2)
                     }
             ACCESS  read-write
             STATUS  mandatory
             DESCRIPTION
                "This variable indicates the reference bus of the segment."
            ::= { ncmShelfSyncSourceSegEntry 5 }

         
        ncmSourceSegOneShelfNum OBJECT-TYPE
            SYNTAX INTEGER
            ACCESS read-write
            STATUS mandatory
            DESCRIPTION
                "This variable indicates the source one shelf number of
                 the segment."
            ::= { ncmShelfSyncSourceSegEntry 6 }
 
         
         ncmSourceSegOneCardNum OBJECT-TYPE
            SYNTAX INTEGER
            ACCESS  read-write
            STATUS  mandatory
            DESCRIPTION
                "This variable indicates the source one card number of the
                 segment."
            ::= {ncmShelfSyncSourceSegEntry 7 }
  
 
        ncmSourceSegOneClockRef OBJECT-TYPE
            SYNTAX INTEGER {
                        e1-t1port1(5),
                        e1-t1port2(6),
                        external-timing(7),
                        internal-timing(8),
                        quad-t1-port3(11),
                        quad-t1-port4(12)
                           }
            ACCESS  read-write
            STATUS  mandatory 
         DESCRIPTION
            "This variable indicates the source one clock reference of
             the segment."
            ::= {ncmShelfSyncSourceSegEntry 8 }
 
 
         ncmSourceSegAutoRestore1 OBJECT-TYPE
            SYNTAX INTEGER {
                        disable(1),
			enable(2)        
                    }
            ACCESS  read-write
            STATUS  mandatory
            DESCRIPTION
            "This variable indicates the source one auto restore of the
             segment."
            ::= {ncmShelfSyncSourceSegEntry 9 }
 
 
         ncmSourceSegTwoShelfNum OBJECT-TYPE
            SYNTAX INTEGER
            ACCESS  read-write
            STATUS  mandatory
            DESCRIPTION
            "This variable indicates the source two shelf number of the
             segment."
            ::= { ncmShelfSyncSourceSegEntry 10 }
 
         
        ncmSourceSegTwoCardNum OBJECT-TYPE
            SYNTAX INTEGER
            ACCESS  read-write
            STATUS  mandatory
            DESCRIPTION
            "This variable indicates the source two card number of the
             segment."
            ::= { ncmShelfSyncSourceSegEntry 11 }
 
         
        ncmSourceSegTwoClockRef OBJECT-TYPE
            SYNTAX INTEGER {
                        e1-t1port1(5),
                        e1-t1port2(6),
                        external-timing(7),
                        internal-timing(8),
                        quad-t1-port3(11),
                        quad-t1-port4(12)
                           }
            ACCESS  read-write
            STATUS  mandatory
            DESCRIPTION
            "This variable indicates the source two clock reference of the
             segment."
            ::= { ncmShelfSyncSourceSegEntry 12 }
 
         
        ncmSourceSegAutoRestore2 OBJECT-TYPE
            SYNTAX INTEGER {
                        disable(1),
                        enable(2)        
                    }
            ACCESS  read-write
            STATUS  mandatory
            DESCRIPTION
                "This variable indicates the source two auto restore of
                 the segment."
            ::= { ncmShelfSyncSourceSegEntry 13 }


	ncmSourceSegThreeShelfNum OBJECT-TYPE
            SYNTAX INTEGER
            ACCESS  read-write
            STATUS  mandatory
            DESCRIPTION
                "This variable indicates the source three shelf number of
                the segment."
            ::= { ncmShelfSyncSourceSegEntry 14 }
 
 
        ncmSourceSegThreeCardNum OBJECT-TYPE
            SYNTAX INTEGER
            ACCESS  read-write
            STATUS  mandatory
            DESCRIPTION
                "This variable indicates the source three card number of
                the segment."
            ::= { ncmShelfSyncSourceSegEntry 15 }
 
 
        ncmSourceSegThreeClockRef OBJECT-TYPE
            SYNTAX INTEGER {
                        e1-t1port1(5),
                        e1-t1port2(6),
                        external-timing(7),
                        internal-timing(8),
                        quad-t1-port3(11),
                        quad-t1-port4(12)
                           }
            ACCESS  read-write
            STATUS  mandatory
            DESCRIPTION
            "This variable indicates the source three clock reference of 
             the segment."
            ::= { ncmShelfSyncSourceSegEntry 16 }
 
 
         ncmSourceSegAutoRestore3 OBJECT-TYPE
            SYNTAX INTEGER {
                        disable(1),
                        enable(2)       
                    }
            ACCESS  read-write
            STATUS  mandatory
            DESCRIPTION
                "This variable indicates the source three auto restore of
                 the segment."
            ::= { ncmShelfSyncSourceSegEntry 17 }
  
 
         ncmShelfCurrentSyncSourceSeg OBJECT-TYPE
            SYNTAX INTEGER {
                        source1(1),
                        source2(2),
                        source3(3)    
                    }

		ACCESS  read-write
            	STATUS  mandatory
            	DESCRIPTION
                "This variable indicates the current sync source of the segment."
            ::= { ncmShelfSyncSourceSegEntry 18 }
	 
END
