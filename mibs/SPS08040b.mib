FOUNDRY-SN-ROOT-MIB DEFINITIONS ::= BEGIN

IMPORTS
  MODULE-IDENTITY,enterprises
	FROM	SNMPv2-SMI;	
	

foundry MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"            
	REVISION     "200909300000Z" -- September 30, 2009
	DESCRIPTION
			"convert from SMIv1 to SMIv2"
	::= { enterprises 1991}

snTraps         OBJECT IDENTIFIER ::= { foundry 0 }
products        OBJECT IDENTIFIER ::= { foundry 1 }
vendors         OBJECT IDENTIFIER ::= { foundry 2 }

  switch		OBJECT IDENTIFIER ::= { products 1 }
  snChassis		OBJECT IDENTIFIER ::= { switch 1 }
  snAgentSys	OBJECT IDENTIFIER ::= { switch 2 }
  snSwitch		OBJECT IDENTIFIER ::= { switch 3 }
  snL4			OBJECT IDENTIFIER ::= { switch 4 }
  snStack		OBJECT IDENTIFIER ::= { switch 5 }
  snSci			OBJECT IDENTIFIER ::= { switch 6 }
  fdrySntp	    OBJECT IDENTIFIER ::= { switch 7 }
  fdryRadius	OBJECT IDENTIFIER ::= { switch 8 }
  fdryTacacs	OBJECT IDENTIFIER ::= { switch 9 }
  fdryTrap	    OBJECT IDENTIFIER ::= { switch 10 }
  brcdSysLog    OBJECT IDENTIFIER ::= { switch 11 }
  brcdMct    OBJECT IDENTIFIER ::= { switch 12 }
  brcdFabric    OBJECT IDENTIFIER ::= { switch 13 }

router 		OBJECT IDENTIFIER ::= { products 2 }
  snIpx			OBJECT IDENTIFIER ::= { router 1 }
  snIp			OBJECT IDENTIFIER ::= { router 2 }
  snRip			OBJECT IDENTIFIER ::= { router 3 }
  snOspf		OBJECT IDENTIFIER ::= { router 4 }
  snDvmrp		OBJECT IDENTIFIER ::= { router 5 }
  snIgmp		OBJECT IDENTIFIER ::= { router 6 }
  snFsrp		OBJECT IDENTIFIER ::= { router 7 }
  snGblRt		OBJECT IDENTIFIER ::= { router 8 }
  snPim			OBJECT IDENTIFIER ::= { router 9 }
  snAppleTalk	OBJECT IDENTIFIER ::= { router 10 }
  snBgp4		OBJECT IDENTIFIER ::= { router 11 }
  snVrrp		OBJECT IDENTIFIER ::= { router 12 }
  snLoopbackIf 	OBJECT IDENTIFIER ::= { router 13 }
  snPOS 		OBJECT IDENTIFIER ::= { router 14 }
  snMpls		OBJECT IDENTIFIER ::= { router 15 }
  fdryAcl	    OBJECT IDENTIFIER ::= { router 16 }
  fdryIpv6		OBJECT IDENTIFIER ::= { router 17 }  

registration	OBJECT IDENTIFIER ::= { products 3 } -- sysObjectID values

  snFastIron        OBJECT IDENTIFIER ::= { registration 1 }   -- Stackable FastIron family
  snFIWGSwitch      OBJECT IDENTIFIER ::= { snFastIron 1 }     -- Stackable FastIron workgroup switch
  snFIBBSwitch      OBJECT IDENTIFIER ::= { snFastIron 2 }     -- Stackable FastIron backbone switch

  snNetIron         OBJECT IDENTIFIER ::= { registration 2 }   -- Stackable NetIron family
  snNIRouter        OBJECT IDENTIFIER ::= { snNetIron 1 }      -- Stackable NetIron router

  snServerIron      OBJECT IDENTIFIER ::= { registration 3 }   -- Stackable ServerIron family
  snSI              OBJECT IDENTIFIER ::= { snServerIron 1 }   -- Stackable ServerIron
  snSIXL            OBJECT IDENTIFIER ::= { snServerIron 2 }   -- Stackable ServerIronXL
  snSIXLTCS         OBJECT IDENTIFIER ::= { snServerIron 3 }   -- Stackable ServerIronXL TCS

  snTurboIron       OBJECT IDENTIFIER ::= { registration 4 }   -- Stackable TurboIron family
  snTISwitch        OBJECT IDENTIFIER ::= { snTurboIron 1 }    -- Stackable TurboIron switch
  snTIRouter        OBJECT IDENTIFIER ::= { snTurboIron 2 }    -- Stackable TurboIron router

  snTurboIron8      OBJECT IDENTIFIER ::= { registration 5 }   -- Stackable TurboIron 8 family
  snT8Switch        OBJECT IDENTIFIER ::= { snTurboIron8 1 }   -- Stackable TurboIron 8 switch
  snT8Router        OBJECT IDENTIFIER ::= { snTurboIron8 2 }   -- Stackable TurboIron 8 router
  snT8SI            OBJECT IDENTIFIER ::= { snTurboIron8 3 }
  snT8SIXLG         OBJECT IDENTIFIER ::= { snTurboIron8 4 }   -- Stackable ServerIronXLG

  snBigIron4000     OBJECT IDENTIFIER ::= { registration 6 }   -- BigIron 4000 family
  snBI4000Switch    OBJECT IDENTIFIER ::= { snBigIron4000 1 }  -- BigIron 4000 switch
  snBI4000Router    OBJECT IDENTIFIER ::= { snBigIron4000 2 }  -- BigIron 4000 router
  snBI4000SI        OBJECT IDENTIFIER ::= { snBigIron4000 3 }  -- BigServerIron

  snBigIron8000     OBJECT IDENTIFIER ::= { registration 7 }   -- BigIron 8000 family
  snBI8000Switch    OBJECT IDENTIFIER ::= { snBigIron8000 1 }  -- BigIron 8000 switch
  snBI8000Router    OBJECT IDENTIFIER ::= { snBigIron8000 2 }  -- BigIron 8000 router
  snBI8000SI        OBJECT IDENTIFIER ::= { snBigIron8000 3 }  -- BigServerIron

  snFastIron2       OBJECT IDENTIFIER ::= { registration 8 }   -- FastIron II family
  snFI2Switch       OBJECT IDENTIFIER ::= { snFastIron2 1 }    -- FastIron II switch
  snFI2Router       OBJECT IDENTIFIER ::= { snFastIron2 2 }    -- FastIron II router

  snFastIron2Plus   OBJECT IDENTIFIER ::= { registration 9 }     -- FastIron II Plus family
  snFI2PlusSwitch   OBJECT IDENTIFIER ::= { snFastIron2Plus 1 }  -- FastIron II Plus switch
  snFI2PlusRouter   OBJECT IDENTIFIER ::= { snFastIron2Plus 2 }  -- FastIron II Plus router

  snNetIron400      OBJECT IDENTIFIER ::= { registration 10 }  -- NetIron 400 family
  snNI400Router     OBJECT IDENTIFIER ::= { snNetIron400 1 }   -- NetIron 400 router

  snNetIron800      OBJECT IDENTIFIER ::= { registration 11 }  -- NetIron 800 family
  snNI800Router     OBJECT IDENTIFIER ::= { snNetIron800 1 }   -- NetIron 800 router

  snFastIron2GC     OBJECT IDENTIFIER ::= { registration 12 }  -- FastIron II GC family
  snFI2GCSwitch     OBJECT IDENTIFIER ::= { snFastIron2GC 1 }  -- FastIron II GC switch
  snFI2GCRouter     OBJECT IDENTIFIER ::= { snFastIron2GC 2 }  -- FastIron II GC router

  snFastIron2PlusGC OBJECT IDENTIFIER ::= { registration 13 }     -- FastIron II Plus GC family
  snFI2PlusGCSwitch OBJECT IDENTIFIER ::= { snFastIron2PlusGC 1 } -- FastIron II Plus GC switch
  snFI2PlusGCRouter OBJECT IDENTIFIER ::= { snFastIron2PlusGC 2 } -- FastIron II Plus GC router

  snBigIron15000    OBJECT IDENTIFIER ::= { registration 14 }   -- BigIron 15000 family
  snBI15000Switch   OBJECT IDENTIFIER ::= { snBigIron15000 1 }  -- BigIron 15000 switch
  snBI15000Router   OBJECT IDENTIFIER ::= { snBigIron15000 2 }  -- BigIron 15000 router
  snBI15000SI       OBJECT IDENTIFIER ::= { snBigIron15000 3 }

  snNetIron1500     OBJECT IDENTIFIER ::= { registration 15 }   -- NetIron 1500 family
  snNI1500Router    OBJECT IDENTIFIER ::= { snNetIron1500 1 }   -- NetIron 1500 router

  snFastIron3       OBJECT IDENTIFIER ::= { registration 16 }   -- FastIron III family
  snFI3Switch       OBJECT IDENTIFIER ::= { snFastIron3 1 }     -- FastIron III switch
  snFI3Router       OBJECT IDENTIFIER ::= { snFastIron3 2 }     -- FastIron III router

  snFastIron3GC     OBJECT IDENTIFIER ::= { registration 17 }   -- FastIron III GC family
  snFI3GCSwitch     OBJECT IDENTIFIER ::= { snFastIron3GC 1 }   -- FastIron III GC switch
  snFI3GCRouter     OBJECT IDENTIFIER ::= { snFastIron3GC 2 }   -- FastIron III GC router

  snServerIron400   OBJECT IDENTIFIER ::= { registration 18 }   -- ServerIron 400 family
  snSI400Switch     OBJECT IDENTIFIER ::= { snServerIron400 1 } -- ServerIron 400 switch
  snSI400Router     OBJECT IDENTIFIER ::= { snServerIron400 2 } -- ServerIron 400 router

  snServerIron800   OBJECT IDENTIFIER ::= { registration 19 }   -- ServerIron 800 family
  snSI800Switch     OBJECT IDENTIFIER ::= { snServerIron800 1 } -- ServerIron800 switch
  snSI800Router     OBJECT IDENTIFIER ::= { snServerIron800 2 } -- ServerIron800 router

  snServerIron1500  OBJECT IDENTIFIER ::= { registration 20 }    -- ServerIron 1500 family
  snSI1500Switch    OBJECT IDENTIFIER ::= { snServerIron1500 1 } -- ServerIron1500 switch
  snSI1500Router    OBJECT IDENTIFIER ::= { snServerIron1500 2 } -- ServerIron1500 router

  sn4802            OBJECT IDENTIFIER ::= { registration 21 }  -- Stackable 4802 family
  sn4802Switch      OBJECT IDENTIFIER ::= { sn4802 1 }         -- Stackable 4802 switch
  sn4802Router      OBJECT IDENTIFIER ::= { sn4802 2 }         -- Stackable 4802 router
  sn4802SI          OBJECT IDENTIFIER ::= { sn4802 3 }         -- Stackable 4802 ServerIron

  snFastIron400     OBJECT IDENTIFIER ::= { registration 22 } -- FastIron 400 family
  snFI400Switch     OBJECT IDENTIFIER ::= { snFastIron400 1 } -- FastIron 400 switch
  snFI400Router     OBJECT IDENTIFIER ::= { snFastIron400 2 } -- FastIron 400 router

  snFastIron800     OBJECT IDENTIFIER ::= { registration 23 } -- FastIron 800 family
  snFI800Switch     OBJECT IDENTIFIER ::= { snFastIron800 1 } -- FastIron800 switch
  snFI800Router     OBJECT IDENTIFIER ::= { snFastIron800 2 } -- FastIron800 router

  snFastIron1500    OBJECT IDENTIFIER ::= { registration 24 }  -- FastIron 1500 family
  snFI1500Switch    OBJECT IDENTIFIER ::= { snFastIron1500 1 } -- FastIron1500 switch
  snFI1500Router    OBJECT IDENTIFIER ::= { snFastIron1500 2 } -- FastIron1500 router

  snFES2402         OBJECT IDENTIFIER ::= { registration 25 } -- FastIron Edge Switch(FES) 2402
  snFES2402Switch   OBJECT IDENTIFIER ::= { snFES2402 1 }     -- FES2402 switch
  snFES2402Router   OBJECT IDENTIFIER ::= { snFES2402 2 }     -- FES2402 router

  snFES4802         OBJECT IDENTIFIER ::= { registration 26 } -- FastIron Edge Switch(FES) 4802
  snFES4802Switch   OBJECT IDENTIFIER ::= { snFES4802 1 }     -- FES4802 switch
  snFES4802Router   OBJECT IDENTIFIER ::= { snFES4802 2 }     -- FES4802 router

  snFES9604         OBJECT IDENTIFIER ::= { registration 27 } -- FastIron Edge Switch(FES) 9604
  snFES9604Switch   OBJECT IDENTIFIER ::= { snFES9604 1 }     -- FES9604 switch
  snFES9604Router   OBJECT IDENTIFIER ::= { snFES9604 2 }     -- FES9604 router

  snFES12GCF        OBJECT IDENTIFIER ::= { registration 28 }  -- FastIron Edge Switch(FES) 12GCF 
  snFES12GCFSwitch  OBJECT IDENTIFIER ::= { snFES12GCF 1 }  -- snFES12GCF switch 
  snFES12GCFRouter  OBJECT IDENTIFIER ::= { snFES12GCF 2 }  -- snFES12GCF router

  snFES2402POE        OBJECT IDENTIFIER ::= { registration 29 }   -- FastIron Edge Switch(FES) 2402 POE 
  snFES2402POESwitch  OBJECT IDENTIFIER ::= { snFES2402POE 1 }  -- snFES2402POE switch 
  snFES2402POERouter  OBJECT IDENTIFIER ::= { snFES2402POE 2 }  -- snFES2402POE router

  snFES4802POE        OBJECT IDENTIFIER ::= { registration 30 }   -- FastIron Edge Switch (FES) 4802 POE 
  snFES4802POESwitch  OBJECT IDENTIFIER ::= { snFES4802POE 1 } -- snFES4802POE switch 
  snFES4802POERouter  OBJECT IDENTIFIER ::= { snFES4802POE 2 } -- snFES4802POE router

  snNetIron4802     OBJECT IDENTIFIER ::= { registration 31 }     -- NetIron 4802 family 
  snNI4802Switch    OBJECT IDENTIFIER ::= { snNetIron4802 1 }   -- NetIron 4802 switch
  snNI4802Router    OBJECT IDENTIFIER ::= { snNetIron4802 2 }   -- NetIron 4802 router

  snBigIronMG8      OBJECT IDENTIFIER ::= { registration 32 }   -- BigIron MG8 family
  snBIMG8Switch     OBJECT IDENTIFIER ::= { snBigIronMG8 1 }    -- BigIron MG8 switch
  snBIMG8Router     OBJECT IDENTIFIER ::= { snBigIronMG8 2 }    -- BigIron MG8 router

  snNetIron40G      OBJECT IDENTIFIER ::= { registration 33 }   -- NetIron 40G family
  snNI40GRouter     OBJECT IDENTIFIER ::= { snNetIron40G 2 }    -- NetIron 40G router

  snFESXFamily      OBJECT IDENTIFIER ::= { registration 34 }

  snFESX424Family   OBJECT IDENTIFIER ::= { snFESXFamily 1 }

  snFESX424BaseFamily   OBJECT IDENTIFIER ::= { snFESX424Family 1 }
  snFESX424             OBJECT IDENTIFIER ::= { snFESX424BaseFamily 1 }  -- FastIron Edge Switch(FES) 24G
  snFESX424Switch       OBJECT IDENTIFIER ::= { snFESX424 1 }            -- FESX424 switch
  snFESX424Router       OBJECT IDENTIFIER ::= { snFESX424 2 }            -- FESX424 router
  snFESX424Prem         OBJECT IDENTIFIER ::= { snFESX424BaseFamily 2 }  -- FastIron Edge Switch(FES) 24G-PREM
  snFESX424PremSwitch   OBJECT IDENTIFIER ::= { snFESX424Prem 1 }        -- FESX424-PREM switch
  snFESX424PremRouter   OBJECT IDENTIFIER ::= { snFESX424Prem 2 }        -- FESX424-PREM router

  snFESX424Plus1XGFamily     OBJECT IDENTIFIER ::= { snFESX424Family 2 }
  snFESX424Plus1XG           OBJECT IDENTIFIER ::= { snFESX424Plus1XGFamily 1 } -- FastIron Edge Switch(FES) 24G + 1 10G
  snFESX424Plus1XGSwitch     OBJECT IDENTIFIER ::= { snFESX424Plus1XG 1 }     -- FESX424+1XG switch
  snFESX424Plus1XGRouter     OBJECT IDENTIFIER ::= { snFESX424Plus1XG 2 }     -- FESX424+1XG router
  snFESX424Plus1XGPrem       OBJECT IDENTIFIER ::= { snFESX424Plus1XGFamily 2 } -- FastIron Edge Switch(FES) 24G + 1 10G-PREM
  snFESX424Plus1XGPremSwitch OBJECT IDENTIFIER ::= { snFESX424Plus1XGPrem 1 } -- FESX424+1XG-PREM switch
  snFESX424Plus1XGPremRouter OBJECT IDENTIFIER ::= { snFESX424Plus1XGPrem 2 } -- FESX424+1XG-PREM router

  snFESX424Plus2XGFamily     OBJECT IDENTIFIER ::= { snFESX424Family 3 }
  snFESX424Plus2XG           OBJECT IDENTIFIER ::= { snFESX424Plus2XGFamily 1 } -- FastIron Edge Switch(FES) 24G + 2 10G
  snFESX424Plus2XGSwitch     OBJECT IDENTIFIER ::= { snFESX424Plus2XG 1 }     -- FESX424+2XG switch
  snFESX424Plus2XGRouter     OBJECT IDENTIFIER ::= { snFESX424Plus2XG 2 }     -- FESX424+2XG router
  snFESX424Plus2XGPrem       OBJECT IDENTIFIER ::= { snFESX424Plus2XGFamily 2 } -- FastIron Edge Switch(FES) 24G + 2 10G-PREM
  snFESX424Plus2XGPremSwitch OBJECT IDENTIFIER ::= { snFESX424Plus2XGPrem 1 } -- FESX424+2XG-PREM switch
  snFESX424Plus2XGPremRouter OBJECT IDENTIFIER ::= { snFESX424Plus2XGPrem 2 } -- FESX424+2XG-PREM router

  snFESX448Family         OBJECT IDENTIFIER ::= { snFESXFamily 2 }

  snFESX448BaseFamily     OBJECT IDENTIFIER ::= { snFESX448Family 1 }
  snFESX448               OBJECT IDENTIFIER ::= { snFESX448BaseFamily 1 }    -- FastIron Edge Switch(FES) 48G
  snFESX448Switch         OBJECT IDENTIFIER ::= { snFESX448 1 }            -- FESX448 switch
  snFESX448Router         OBJECT IDENTIFIER ::= { snFESX448 2 }            -- FESX448 router
  snFESX448Prem           OBJECT IDENTIFIER ::= { snFESX448BaseFamily 2 }    -- FastIron Edge Switch(FES) 48G-PREM
  snFESX448PremSwitch     OBJECT IDENTIFIER ::= { snFESX448Prem 1 }        -- FESX448-PREM switch
  snFESX448PremRouter     OBJECT IDENTIFIER ::= { snFESX448Prem 2 }        -- FESX448-PREM router

  snFESX448Plus1XGFamily     OBJECT IDENTIFIER ::= { snFESX448Family 2 }
  snFESX448Plus1XG           OBJECT IDENTIFIER ::= { snFESX448Plus1XGFamily 1 } -- FastIron Edge Switch(FES) 48G + 1 10G
  snFESX448Plus1XGSwitch     OBJECT IDENTIFIER ::= { snFESX448Plus1XG 1 }     -- FESX448+1XG switch
  snFESX448Plus1XGRouter     OBJECT IDENTIFIER ::= { snFESX448Plus1XG 2 }     -- FESX448+1XG router
  snFESX448Plus1XGPrem       OBJECT IDENTIFIER ::= { snFESX448Plus1XGFamily 2 } -- FastIron Edge Switch(FES) 48G + 1 10G-PREM
  snFESX448Plus1XGPremSwitch OBJECT IDENTIFIER ::= { snFESX448Plus1XGPrem 1 } -- FESX448+1XG-PREM switch
  snFESX448Plus1XGPremRouter OBJECT IDENTIFIER ::= { snFESX448Plus1XGPrem 2 } -- FESX448+1XG-PREM router

  snFESX448Plus2XGFamily     OBJECT IDENTIFIER ::= { snFESX448Family 3 }
  snFESX448Plus2XG           OBJECT IDENTIFIER ::= { snFESX448Plus2XGFamily 1 } -- FastIron Edge Switch(FES) 48G + 2 10G
  snFESX448Plus2XGSwitch     OBJECT IDENTIFIER ::= { snFESX448Plus2XG 1 }     -- FESX448+2XG switch
  snFESX448Plus2XGRouter     OBJECT IDENTIFIER ::= { snFESX448Plus2XG 2 }     -- FESX448+2XG router
  snFESX448Plus2XGPrem       OBJECT IDENTIFIER ::= { snFESX448Plus2XGFamily 2 } -- FastIron Edge Switch(FES) 48G + 2 10G-PREM
  snFESX448Plus2XGPremSwitch OBJECT IDENTIFIER ::= { snFESX448Plus2XGPrem 1 } -- FESX448+2XG-PREM switch
  snFESX448Plus2XGPremRouter OBJECT IDENTIFIER ::= { snFESX448Plus2XGPrem 2 } -- FESX448+2XG-PREM router

  snFESX424FiberFamily       OBJECT IDENTIFIER ::= { snFESXFamily 3 }

  snFESX424FiberBaseFamily     OBJECT IDENTIFIER ::= { snFESX424FiberFamily 1 }
  snFESX424Fiber                 OBJECT IDENTIFIER ::= { snFESX424FiberBaseFamily 1 }    -- FastIron Edge Switch(FES)Fiber 24G
  snFESX424FiberSwitch             OBJECT IDENTIFIER ::= { snFESX424Fiber 1 }            -- FESX424Fiber switch
  snFESX424FiberRouter             OBJECT IDENTIFIER ::= { snFESX424Fiber 2 }            -- FESX424Fiber router
  snFESX424FiberPrem             OBJECT IDENTIFIER ::= { snFESX424FiberBaseFamily 2 }    -- FastIron Edge Switch(FES)Fiber 24G-PREM
  snFESX424FiberPremSwitch         OBJECT IDENTIFIER ::= { snFESX424FiberPrem 1 }        -- FESX424Fiber-PREM switch
  snFESX424FiberPremRouter         OBJECT IDENTIFIER ::= { snFESX424FiberPrem 2 }        -- FESX424Fiber-PREM router

  snFESX424FiberPlus1XGFamily  OBJECT IDENTIFIER ::= { snFESX424FiberFamily 2 }
  snFESX424FiberPlus1XG          OBJECT IDENTIFIER ::= { snFESX424FiberPlus1XGFamily 1 } -- FastIron Edge Switch(FES)Fiber 24G + 1 10G
  snFESX424FiberPlus1XGSwitch      OBJECT IDENTIFIER ::= { snFESX424FiberPlus1XG 1 }     -- FESX424Fiber+1XG switch
  snFESX424FiberPlus1XGRouter      OBJECT IDENTIFIER ::= { snFESX424FiberPlus1XG 2 }     -- FESX424Fiber+1XG router
  snFESX424FiberPlus1XGPrem      OBJECT IDENTIFIER ::= { snFESX424FiberPlus1XGFamily 2 } -- FastIron Edge Switch(FES)Fiber 24G + 1 10G-PREM
  snFESX424FiberPlus1XGPremSwitch  OBJECT IDENTIFIER ::= { snFESX424FiberPlus1XGPrem 1 } -- FESX424Fiber+1XG-PREM switch
  snFESX424FiberPlus1XGPremRouter  OBJECT IDENTIFIER ::= { snFESX424FiberPlus1XGPrem 2 } -- FESX424Fiber+1XG-PREM router

  snFESX424FiberPlus2XGFamily  OBJECT IDENTIFIER ::= { snFESX424FiberFamily 3 }
  snFESX424FiberPlus2XG          OBJECT IDENTIFIER ::= { snFESX424FiberPlus2XGFamily 1 } -- FastIron Edge Switch(FES)Fiber 24G + 2 10G
  snFESX424FiberPlus2XGSwitch      OBJECT IDENTIFIER ::= { snFESX424FiberPlus2XG 1 }     -- FESX424Fiber+2XG switch
  snFESX424FiberPlus2XGRouter      OBJECT IDENTIFIER ::= { snFESX424FiberPlus2XG 2 }     -- FESX424Fiber+2XG router
  snFESX424FiberPlus2XGPrem      OBJECT IDENTIFIER ::= { snFESX424FiberPlus2XGFamily 2 } -- FastIron Edge Switch(FES)Fiber 24G + 2 10G-PREM
  snFESX424FiberPlus2XGPremSwitch  OBJECT IDENTIFIER ::= { snFESX424FiberPlus2XGPrem 1 } -- FESX424Fiber+2XG-PREM switch
  snFESX424FiberPlus2XGPremRouter  OBJECT IDENTIFIER ::= { snFESX424FiberPlus2XGPrem 2 } -- FESX424Fiber+2XG-PREM router

  snFESX448FiberFamily       OBJECT IDENTIFIER ::= { snFESXFamily 4 }

  snFESX448FiberBaseFamily     OBJECT IDENTIFIER ::= { snFESX448FiberFamily 1 }
  snFESX448Fiber                 OBJECT IDENTIFIER ::= { snFESX448FiberBaseFamily 1 }    -- FastIron Edge Switch(FES)Fiber 48G
  snFESX448FiberSwitch             OBJECT IDENTIFIER ::= { snFESX448Fiber 1 }            -- FESX448Fiber switch
  snFESX448FiberRouter             OBJECT IDENTIFIER ::= { snFESX448Fiber 2 }            -- FESX448Fiber router
  snFESX448FiberPrem             OBJECT IDENTIFIER ::= { snFESX448FiberBaseFamily 2 }    -- FastIron Edge Switch(FES)Fiber 48G-PREM
  snFESX448FiberPremSwitch         OBJECT IDENTIFIER ::= { snFESX448FiberPrem 1 }        -- FESX448Fiber-PREM switch
  snFESX448FiberPremRouter         OBJECT IDENTIFIER ::= { snFESX448FiberPrem 2 }        -- FESX448Fiber-PREM router

  snFESX448FiberPlus1XGFamily  OBJECT IDENTIFIER ::= { snFESX448FiberFamily 2 }
  snFESX448FiberPlus1XG          OBJECT IDENTIFIER ::= { snFESX448FiberPlus1XGFamily 1 } -- FastIron Edge Switch(FES)Fiber 48G + 1 10G
  snFESX448FiberPlus1XGSwitch      OBJECT IDENTIFIER ::= { snFESX448FiberPlus1XG 1 }     -- FESX448Fiber+1XG switch
  snFESX448FiberPlus1XGRouter      OBJECT IDENTIFIER ::= { snFESX448FiberPlus1XG 2 }     -- FESX448Fiber+1XG router
  snFESX448FiberPlus1XGPrem      OBJECT IDENTIFIER ::= { snFESX448FiberPlus1XGFamily 2 } -- FastIron Edge Switch(FES)Fiber 48G + 1 10G-PREM
  snFESX448FiberPlus1XGPremSwitch  OBJECT IDENTIFIER ::= { snFESX448FiberPlus1XGPrem 1 } -- FESX448Fiber+1XG-PREM switch
  snFESX448FiberPlus1XGPremRouter  OBJECT IDENTIFIER ::= { snFESX448FiberPlus1XGPrem 2 } -- FESX448Fiber+1XG-PREM router

  snFESX448FiberPlus2XGFamily  OBJECT IDENTIFIER ::= { snFESX448FiberFamily 3 }
  snFESX448FiberPlus2XG          OBJECT IDENTIFIER ::= { snFESX448FiberPlus2XGFamily 1 } -- FastIron Edge Switch(FES)Fiber 48G + 2 10G
  snFESX448FiberPlus2XGSwitch      OBJECT IDENTIFIER ::= { snFESX448FiberPlus2XG 1 }     -- FESX448Fiber+2XG switch
  snFESX448FiberPlus2XGRouter      OBJECT IDENTIFIER ::= { snFESX448FiberPlus2XG 2 }     -- FESX448+2XG router
  snFESX448FiberPlus2XGPrem      OBJECT IDENTIFIER ::= { snFESX448FiberPlus2XGFamily 2 } -- FastIron Edge Switch(FES)Fiber 48G + 2 10G-PREM
  snFESX448FiberPlus2XGPremSwitch  OBJECT IDENTIFIER ::= { snFESX448FiberPlus2XGPrem 1 } -- FESX448Fiber+2XG-PREM switch
  snFESX448FiberPlus2XGPremRouter  OBJECT IDENTIFIER ::= { snFESX448FiberPlus2XGPrem 2 } -- FESX448Fiber+2XG-PREM router

  snFESX424POEFamily       OBJECT IDENTIFIER ::= { snFESXFamily 5 }

  snFESX424POEBaseFamily    OBJECT IDENTIFIER ::= { snFESX424POEFamily 1 }
  snFESX424POE                 OBJECT IDENTIFIER ::= { snFESX424POEBaseFamily 1 }    -- FastIron Edge Switch(FES) 24G POE
  snFESX424POESwitch             OBJECT IDENTIFIER ::= { snFESX424POE 1 }            -- FESX424POE switch
  snFESX424POERouter             OBJECT IDENTIFIER ::= { snFESX424POE 2 }            -- FESX424POE router
  snFESX424POEPrem             OBJECT IDENTIFIER ::= { snFESX424POEBaseFamily 2 }    -- FastIron Edge Switch(FES) 24GPOE-PREM
  snFESX424POEPremSwitch         OBJECT IDENTIFIER ::= { snFESX424POEPrem 1 }        -- FESX424POE-PREM switch
  snFESX424POEPremRouter         OBJECT IDENTIFIER ::= { snFESX424POEPrem 2 }        -- FESX424POE-PREM router

  snFESX424POEPlus1XGFamily  OBJECT IDENTIFIER ::= { snFESX424POEFamily 2 }
  snFESX424POEPlus1XG          OBJECT IDENTIFIER ::= { snFESX424POEPlus1XGFamily 1 } -- FastIron Edge Switch(FES) 24GPOE + 1 10G
  snFESX424POEPlus1XGSwitch      OBJECT IDENTIFIER ::= { snFESX424POEPlus1XG 1 }     -- FESX424POE+1XG switch
  snFESX424POEPlus1XGRouter      OBJECT IDENTIFIER ::= { snFESX424POEPlus1XG 2 }     -- FESX424POE+1XG router
  snFESX424POEPlus1XGPrem      OBJECT IDENTIFIER ::= { snFESX424POEPlus1XGFamily 2 } -- FastIron Edge Switch(FES) 24GPOE + 1 10G-PREM
  snFESX424POEPlus1XGPremSwitch  OBJECT IDENTIFIER ::= { snFESX424POEPlus1XGPrem 1 } -- FESX424POE+1XG-PREM switch
  snFESX424POEPlus1XGPremRouter  OBJECT IDENTIFIER ::= { snFESX424POEPlus1XGPrem 2 } -- FESX424POE+1XG-PREM router

  snFESX424POEPlus2XGFamily  OBJECT IDENTIFIER ::= { snFESX424POEFamily 3 }
  snFESX424POEPlus2XG          OBJECT IDENTIFIER ::= { snFESX424POEPlus2XGFamily 1 } -- FastIron Edge Switch(FES) 24GPOE + 2 10G
  snFESX424POEPlus2XGSwitch      OBJECT IDENTIFIER ::= { snFESX424POEPlus2XG 1 }     -- FESX424POE+2XG switch
  snFESX424POEPlus2XGRouter      OBJECT IDENTIFIER ::= { snFESX424POEPlus2XG 2 }     -- FESX424POE+2XG router
  snFESX424POEPlus2XGPrem      OBJECT IDENTIFIER ::= { snFESX424POEPlus2XGFamily 2 } -- FastIron Edge Switch(FES) 24GPOE + 2 10G-PREM
  snFESX424POEPlus2XGPremSwitch  OBJECT IDENTIFIER ::= { snFESX424POEPlus2XGPrem 1 } -- FESX424POE+2XG-PREM switch
  snFESX424POEPlus2XGPremRouter  OBJECT IDENTIFIER ::= { snFESX424POEPlus2XGPrem 2 } -- FESX424POE+2XG-PREM router

  snFESX624Family   OBJECT IDENTIFIER ::= { snFESXFamily 6 }

  snFESX624BaseFamily       OBJECT IDENTIFIER ::= { snFESX624Family 1 }      -- FstIron edge V6 family
  snFESX624                 OBJECT IDENTIFIER ::= { snFESX624BaseFamily 1 }  -- FastIron Edge V6 Switch(FES) 24G
  snFESX624Switch           OBJECT IDENTIFIER ::= { snFESX624 1 }            -- FESX624 switch
  snFESX624Router           OBJECT IDENTIFIER ::= { snFESX624 2 }            -- FESX624 Ipv4 router
  snFESX624Prem             OBJECT IDENTIFIER ::= { snFESX624BaseFamily 2 }  -- FastIron Edge V6 Switch(FES) 24G-PREM
  snFESX624PremSwitch       OBJECT IDENTIFIER ::= { snFESX624Prem 1 }        -- FESX624-PREM switch
  snFESX624PremRouter       OBJECT IDENTIFIER ::= { snFESX624Prem 2 }        -- FESX624-PREM Ipv4 router
  snFESX624Prem6Router   OBJECT IDENTIFIER ::= { snFESX624Prem 3 }        -- FESX624-PREM Ipv6 router

  snFESX624Plus1XGFamily         OBJECT IDENTIFIER ::= { snFESX624Family 2 }     -- FstIron edge V6 family
  snFESX624Plus1XG               OBJECT IDENTIFIER ::= { snFESX624Plus1XGFamily 1 } -- FastIron Edge V6 Switch(FES) 24G + 1 10G
  snFESX624Plus1XGSwitch         OBJECT IDENTIFIER ::= { snFESX624Plus1XG 1 }     -- FESX624+1XG switch
  snFESX624Plus1XGRouter         OBJECT IDENTIFIER ::= { snFESX624Plus1XG 2 }     -- FESX624+1XG Ipv4 router
  snFESX624Plus1XGPrem           OBJECT IDENTIFIER ::= { snFESX624Plus1XGFamily 2 } -- FastIron Edge V6 Switch(FES) 24G + 1 10G-PREM
  snFESX624Plus1XGPremSwitch     OBJECT IDENTIFIER ::= { snFESX624Plus1XGPrem 1 } -- FESX624+1XG-PREM switch
  snFESX624Plus1XGPremRouter     OBJECT IDENTIFIER ::= { snFESX624Plus1XGPrem 2 } -- FESX624+1XG-PREM Ipv4 router
  snFESX624Plus1XGPrem6Router OBJECT IDENTIFIER ::= { snFESX624Plus1XGPrem 3 } -- FESX624+1XG-PREM Ipv6 router

  snFESX624Plus2XGFamily     OBJECT IDENTIFIER ::= { snFESX624Family 3 }  -- FstIron edge V6 family
  snFESX624Plus2XG           OBJECT IDENTIFIER ::= { snFESX624Plus2XGFamily 1 } -- FastIron Edge V6 Switch(FES) 24G + 2 10G
  snFESX624Plus2XGSwitch     OBJECT IDENTIFIER ::= { snFESX624Plus2XG 1 }     -- FESX624+2XG switch
  snFESX624Plus2XGRouter     OBJECT IDENTIFIER ::= { snFESX624Plus2XG 2 }     -- FESX624+2XG Ipv4 router
  snFESX624Plus2XGPrem       OBJECT IDENTIFIER ::= { snFESX624Plus2XGFamily 2 } -- FastIron Edge V6 Switch(FES) 24G + 2 10G-PREM
  snFESX624Plus2XGPremSwitch OBJECT IDENTIFIER ::= { snFESX624Plus2XGPrem 1 } -- FESX624+2XG-PREM switch
  snFESX624Plus2XGPremRouter OBJECT IDENTIFIER ::= { snFESX624Plus2XGPrem 2 } -- FESX624+2XG-PREM Ipv4 router
  snFESX624Plus2XGPrem6Router OBJECT IDENTIFIER ::= { snFESX624Plus2XGPrem 3 } -- FESX624+2XG-PREM Ipv6 router

  snFESX648Family         OBJECT IDENTIFIER ::= { snFESXFamily 7 }

  snFESX648BaseFamily     OBJECT IDENTIFIER ::= { snFESX648Family 1 }      -- FstIron edge V6 family
  snFESX648               OBJECT IDENTIFIER ::= { snFESX648BaseFamily 1 }  -- FastIron Edge V6 Switch(FES) 48G
  snFESX648Switch         OBJECT IDENTIFIER ::= { snFESX648 1 }            -- FESX648 switch
  snFESX648Router         OBJECT IDENTIFIER ::= { snFESX648 2 }            -- FESX648 Ipv4 router
  snFESX648Prem           OBJECT IDENTIFIER ::= { snFESX648BaseFamily 2 }    -- FastIron Edge V6 Switch(FES) 48G-PREM
  snFESX648PremSwitch     OBJECT IDENTIFIER ::= { snFESX648Prem 1 }        -- FESX648-PREM switch
  snFESX648PremRouter     OBJECT IDENTIFIER ::= { snFESX648Prem 2 }        -- FESX648-PREM Ipv4 router
  snFESX648Prem6Router OBJECT IDENTIFIER ::= { snFESX648Prem 3 }        -- FESX648-PREM Ipv6 router

  snFESX648Plus1XGFamily         OBJECT IDENTIFIER ::= { snFESX648Family 2 }      -- FstIron edge V6 family
  snFESX648Plus1XG               OBJECT IDENTIFIER ::= { snFESX648Plus1XGFamily 1 } -- FastIron Edge V6 Switch(FES) 48G + 1 10G
  snFESX648Plus1XGSwitch         OBJECT IDENTIFIER ::= { snFESX648Plus1XG 1 }     -- FESX648+1XG switch
  snFESX648Plus1XGRouter         OBJECT IDENTIFIER ::= { snFESX648Plus1XG 2 }     -- FESX648+1XG Ipv4 router
  snFESX648Plus1XGPrem           OBJECT IDENTIFIER ::= { snFESX648Plus1XGFamily 2 } -- FastIron Edge V6 Switch(FES) 48G + 1 10G-PREM
  snFESX648Plus1XGPremSwitch     OBJECT IDENTIFIER ::= { snFESX648Plus1XGPrem 1 } -- FESX648+1XG-PREM switch
  snFESX648Plus1XGPremRouter     OBJECT IDENTIFIER ::= { snFESX648Plus1XGPrem 2 } -- FESX648+1XG-PREM Ipv4 router
  snFESX648Plus1XGPrem6Router OBJECT IDENTIFIER ::= { snFESX648Plus1XGPrem 3 } -- FESX648+1XG-PREM Ipv6 router

  snFESX648Plus2XGFamily         OBJECT IDENTIFIER ::= { snFESX648Family 3 }      -- FstIron edge V6 family
  snFESX648Plus2XG               OBJECT IDENTIFIER ::= { snFESX648Plus2XGFamily 1 } -- FastIron Edge V6 Switch(FES) 48G + 2 10G
  snFESX648Plus2XGSwitch         OBJECT IDENTIFIER ::= { snFESX648Plus2XG 1 }     -- FESX648+2XG switch
  snFESX648Plus2XGRouter         OBJECT IDENTIFIER ::= { snFESX648Plus2XG 2 }     -- FESX648+2XG Ipv4 router
  snFESX648Plus2XGPrem           OBJECT IDENTIFIER ::= { snFESX648Plus2XGFamily 2 } -- FastIron Edge V6 Switch(FES) 48G + 2 10G-PREM
  snFESX648Plus2XGPremSwitch     OBJECT IDENTIFIER ::= { snFESX648Plus2XGPrem 1 } -- FESX648+2XG-PREM switch
  snFESX648Plus2XGPremRouter     OBJECT IDENTIFIER ::= { snFESX648Plus2XGPrem 2 } -- FESX648+2XG-PREM Ipv4 router
  snFESX648Plus2XGPrem6Router OBJECT IDENTIFIER ::= { snFESX648Plus2XGPrem 3 } -- FESX648+2XG-PREM Ipv6 router

  snFESX624FiberFamily       OBJECT IDENTIFIER ::= { snFESXFamily 8 }

  snFESX624FiberBaseFamily         OBJECT IDENTIFIER ::= { snFESX624FiberFamily 1 }          -- FstIron edge V6 family
  snFESX624Fiber                   OBJECT IDENTIFIER ::= { snFESX624FiberBaseFamily 1 }    -- FastIron V6 Edge Switch(FES)Fiber 24G
  snFESX624FiberSwitch             OBJECT IDENTIFIER ::= { snFESX624Fiber 1 }            -- FESX624Fiber switch
  snFESX624FiberRouter             OBJECT IDENTIFIER ::= { snFESX624Fiber 2 }            -- FESX624Fiber Ipv4 router
  snFESX624FiberPrem               OBJECT IDENTIFIER ::= { snFESX624FiberBaseFamily 2 }    -- FastIron Edge V6 Switch(FES)Fiber 24G-PREM
  snFESX624FiberPremSwitch         OBJECT IDENTIFIER ::= { snFESX624FiberPrem 1 }        -- FESX624Fiber-PREM switch
  snFESX624FiberPremRouter         OBJECT IDENTIFIER ::= { snFESX624FiberPrem 2 }        -- FESX624Fiber-PREM Ipv4 router
  snFESX624FiberPrem6Router     OBJECT IDENTIFIER ::= { snFESX624FiberPrem 3 }        -- FESX624Fiber-PREM Ipv6 router

  snFESX624FiberPlus1XGFamily          OBJECT IDENTIFIER ::= { snFESX624FiberFamily 2 }        -- FstIron edge V6 family
  snFESX624FiberPlus1XG                OBJECT IDENTIFIER ::= { snFESX624FiberPlus1XGFamily 1 } -- FastIron Edge V6 Switch(FES)Fiber 24G + 1 10G
  snFESX624FiberPlus1XGSwitch          OBJECT IDENTIFIER ::= { snFESX624FiberPlus1XG 1 }     -- FESX624Fiber+1XG switch
  snFESX624FiberPlus1XGRouter          OBJECT IDENTIFIER ::= { snFESX624FiberPlus1XG 2 }     -- FESX624Fiber+1XG Ipv4 router
  snFESX624FiberPlus1XGPrem            OBJECT IDENTIFIER ::= { snFESX624FiberPlus1XGFamily 2 } -- FastIron Edge V6 Switch(FES)Fiber 24G + 1 10G-PREM
  snFESX624FiberPlus1XGPremSwitch      OBJECT IDENTIFIER ::= { snFESX624FiberPlus1XGPrem 1 } -- FESX624Fiber+1XG-PREM switch
  snFESX624FiberPlus1XGPremRouter      OBJECT IDENTIFIER ::= { snFESX624FiberPlus1XGPrem 2 } -- FESX624Fiber+1XG-PREM Ipv4 router
  snFESX624FiberPlus1XGPrem6Router  OBJECT IDENTIFIER ::= { snFESX624FiberPlus1XGPrem 3 } -- FESX624Fiber+1XG-PREM Ipv6 router

  snFESX624FiberPlus2XGFamily          OBJECT IDENTIFIER ::= { snFESX624FiberFamily 3 }          -- FstIron edge V6 family
  snFESX624FiberPlus2XG                OBJECT IDENTIFIER ::= { snFESX624FiberPlus2XGFamily 1 } -- FastIron Edge V6 Switch(FES)Fiber 24G + 2 10G
  snFESX624FiberPlus2XGSwitch          OBJECT IDENTIFIER ::= { snFESX624FiberPlus2XG 1 }     -- FESX624Fiber+2XG switch
  snFESX624FiberPlus2XGRouter          OBJECT IDENTIFIER ::= { snFESX624FiberPlus2XG 2 }     -- FESX624Fiber+2XG Ipv4 router
  snFESX624FiberPlus2XGPrem            OBJECT IDENTIFIER ::= { snFESX624FiberPlus2XGFamily 2 } -- FastIron Edge V6 Switch(FES)Fiber 24G + 2 10G-PREM
  snFESX624FiberPlus2XGPremSwitch      OBJECT IDENTIFIER ::= { snFESX624FiberPlus2XGPrem 1 } -- FESX624Fiber+2XG-PREM switch
  snFESX624FiberPlus2XGPremRouter      OBJECT IDENTIFIER ::= { snFESX624FiberPlus2XGPrem 2 } -- FESX624Fiber+2XG-PREM Ipv4 router
  snFESX624FiberPlus2XGPrem6Router  OBJECT IDENTIFIER ::= { snFESX624FiberPlus2XGPrem 3 } -- FESX624Fiber+2XG-PREM Ipv6 router

  snFESX648FiberFamily       OBJECT IDENTIFIER ::= { snFESXFamily 9 }

  snFESX648FiberBaseFamily         OBJECT IDENTIFIER ::= { snFESX648FiberFamily 1 }        -- FstIron edge V6 family
  snFESX648Fiber                   OBJECT IDENTIFIER ::= { snFESX648FiberBaseFamily 1 }    -- FastIron Edge V6 Switch(FES)Fiber 48G
  snFESX648FiberSwitch             OBJECT IDENTIFIER ::= { snFESX648Fiber 1 }            -- FESX648Fiber switch
  snFESX648FiberRouter             OBJECT IDENTIFIER ::= { snFESX648Fiber 2 }            -- FESX648Fiber Ipv4 router
  snFESX648FiberPrem               OBJECT IDENTIFIER ::= { snFESX648FiberBaseFamily 2 }    -- FastIron Edge V6 Switch(FES)Fiber 48G-PREM
  snFESX648FiberPremSwitch         OBJECT IDENTIFIER ::= { snFESX648FiberPrem 1 }        -- FESX648Fiber-PREM switch
  snFESX648FiberPremRouter         OBJECT IDENTIFIER ::= { snFESX648FiberPrem 2 }        -- FESX648Fiber-PREM Ipv4 router
  snFESX648FiberPrem6Router         OBJECT IDENTIFIER ::= { snFESX648FiberPrem 3 }		 -- FESX648Fiber-PREM Ipv6 router

  snFESX648FiberPlus1XGFamily          OBJECT IDENTIFIER ::= { snFESX648FiberFamily 2 }          -- FstIron edge V6 family
  snFESX648FiberPlus1XG                OBJECT IDENTIFIER ::= { snFESX648FiberPlus1XGFamily 1 } -- FastIron Edge V6 Switch(FES)Fiber 48G + 1 10G
  snFESX648FiberPlus1XGSwitch          OBJECT IDENTIFIER ::= { snFESX648FiberPlus1XG 1 }     -- FESX648Fiber+1XG switch
  snFESX648FiberPlus1XGRouter          OBJECT IDENTIFIER ::= { snFESX648FiberPlus1XG 2 }     -- FESX648Fiber+1XG Ipv4 router
  snFESX648FiberPlus1XGPrem            OBJECT IDENTIFIER ::= { snFESX648FiberPlus1XGFamily 2 } -- FastIron Edge V6 Switch(FES)Fiber 48G + 1 10G-PREM
  snFESX648FiberPlus1XGPremSwitch      OBJECT IDENTIFIER ::= { snFESX648FiberPlus1XGPrem 1 } -- FESX648Fiber+1XG-PREM switch
  snFESX648FiberPlus1XGPremRouter      OBJECT IDENTIFIER ::= { snFESX648FiberPlus1XGPrem 2 } -- FESX648Fiber+1XG-PREM Ipv4 router
  snFESX648FiberPlus1XGPrem6Router  OBJECT IDENTIFIER ::= { snFESX648FiberPlus1XGPrem 3 } -- FESX648Fiber+1XG-PREM Ipv6 router

  snFESX648FiberPlus2XGFamily          OBJECT IDENTIFIER ::= { snFESX648FiberFamily 3 }          -- FstIron edge V6 family
  snFESX648FiberPlus2XG                OBJECT IDENTIFIER ::= { snFESX648FiberPlus2XGFamily 1 } -- FastIron Edge V6 Switch(FES)Fiber 48G + 2 10G
  snFESX648FiberPlus2XGSwitch          OBJECT IDENTIFIER ::= { snFESX648FiberPlus2XG 1 }     -- FESX648Fiber+2XG switch
  snFESX648FiberPlus2XGRouter          OBJECT IDENTIFIER ::= { snFESX648FiberPlus2XG 2 }     -- FESX648+2XG Ipv4 router
  snFESX648FiberPlus2XGPrem            OBJECT IDENTIFIER ::= { snFESX648FiberPlus2XGFamily 2 } -- FastIron Edge V6 Switch(FES)Fiber 48G + 2 10G-PREM
  snFESX648FiberPlus2XGPremSwitch      OBJECT IDENTIFIER ::= { snFESX648FiberPlus2XGPrem 1 } -- FESX648Fiber+2XG-PREM switch
  snFESX648FiberPlus2XGPremRouter      OBJECT IDENTIFIER ::= { snFESX648FiberPlus2XGPrem 2 } -- FESX648Fiber+2XG-PREM Ipv4 router
  snFESX648FiberPlus2XGPrem6Router  OBJECT IDENTIFIER ::= { snFESX648FiberPlus2XGPrem 3 } -- FESX648Fiber+2XG-PREM Ipv6 router

  snFESX624POEFamily       OBJECT IDENTIFIER ::= { snFESXFamily 10 }

  snFESX624POEBaseFamily         OBJECT IDENTIFIER ::= { snFESX624POEFamily 1 }           -- FstIron edge V6 family
  snFESX624POE                   OBJECT IDENTIFIER ::= { snFESX624POEBaseFamily 1 }    -- FastIron Edge V6 Switch(FES) 24G POE
  snFESX624POESwitch             OBJECT IDENTIFIER ::= { snFESX624POE 1 }            -- FESX624POE switch
  snFESX624POERouter             OBJECT IDENTIFIER ::= { snFESX624POE 2 }            -- FESX624POE Ipv4 router
  snFESX624POEPrem               OBJECT IDENTIFIER ::= { snFESX624POEBaseFamily 2 }    -- FastIron Edge V6 Switch(FES) 24GPOE-PREM
  snFESX624POEPremSwitch         OBJECT IDENTIFIER ::= { snFESX624POEPrem 1 }        -- FESX624POE-PREM switch
  snFESX624POEPremRouter         OBJECT IDENTIFIER ::= { snFESX624POEPrem 2 }        -- FESX624POE-PREM Ipv4 router
  snFESX624POEPrem6Router     OBJECT IDENTIFIER ::= { snFESX624POEPrem 3 }        -- FESX624POE-PREM Ipv6 router

  snFESX624POEPlus1XGFamily          OBJECT IDENTIFIER ::= { snFESX624POEFamily 2 }          -- FstIron edge V6 family
  snFESX624POEPlus1XG                OBJECT IDENTIFIER ::= { snFESX624POEPlus1XGFamily 1 } -- FastIron Edge V6 Switch(FES) 24GPOE + 1 10G
  snFESX624POEPlus1XGSwitch          OBJECT IDENTIFIER ::= { snFESX624POEPlus1XG 1 }     -- FESX624POE+1XG switch
  snFESX624POEPlus1XGRouter          OBJECT IDENTIFIER ::= { snFESX624POEPlus1XG 2 }     -- FESX624POE+1XG Ipv4 router
  snFESX624POEPlus1XGPrem            OBJECT IDENTIFIER ::= { snFESX624POEPlus1XGFamily 2 } -- FastIron Edge V6 Switch(FES) 24GPOE + 1 10G-PREM
  snFESX624POEPlus1XGPremSwitch      OBJECT IDENTIFIER ::= { snFESX624POEPlus1XGPrem 1 } -- FESX624POE+1XG-PREM switch
  snFESX624POEPlus1XGPremRouter      OBJECT IDENTIFIER ::= { snFESX624POEPlus1XGPrem 2 } -- FESX624POE+1XG-PREM Ipv4 router
  snFESX624POEPlus1XGPrem6Router  OBJECT IDENTIFIER ::= { snFESX624POEPlus1XGPrem 3 } -- FESX624POE+1XG-PREM Ipv6 router

  snFESX624POEPlus2XGFamily          OBJECT IDENTIFIER ::= { snFESX624POEFamily 3 }          -- FstIron edge V6 family
  snFESX624POEPlus2XG                OBJECT IDENTIFIER ::= { snFESX624POEPlus2XGFamily 1 } -- FastIron Edge V6 Switch(FES) 24GPOE + 2 10G
  snFESX624POEPlus2XGSwitch          OBJECT IDENTIFIER ::= { snFESX624POEPlus2XG 1 }     -- FESX624POE+2XG switch
  snFESX624POEPlus2XGRouter          OBJECT IDENTIFIER ::= { snFESX624POEPlus2XG 2 }     -- FESX624POE+2XG Ipv4 router
  snFESX624POEPlus2XGPrem            OBJECT IDENTIFIER ::= { snFESX624POEPlus2XGFamily 2 } -- FastIron Edge V6 Switch(FES) 24GPOE + 2 10G-PREM
  snFESX624POEPlus2XGPremSwitch      OBJECT IDENTIFIER ::= { snFESX624POEPlus2XGPrem 1 } -- FESX624POE+2XG-PREM switch
  snFESX624POEPlus2XGPremRouter      OBJECT IDENTIFIER ::= { snFESX624POEPlus2XGPrem 2 } -- FESX624POE+2XG-PREM Ipv4 router
  snFESX624POEPlus2XGPrem6Router  OBJECT IDENTIFIER ::= { snFESX624POEPlus2XGPrem 3 } -- FESX624POE+2XG-PREM Ipv6 router

  snFESX624EFamily   OBJECT IDENTIFIER ::= { snFESXFamily 11 }

  snFESX624EBaseFamily       OBJECT IDENTIFIER ::= { snFESX624EFamily 1 }      -- FstIron edge V6-E (Expanded)  family
  snFESX624E                 OBJECT IDENTIFIER ::= { snFESX624EBaseFamily 1 }  -- FastIron Edge V6 Switch(FES) 24G
  snFESX624ESwitch           OBJECT IDENTIFIER ::= { snFESX624E 1 }            -- FESX624 switch
  snFESX624ERouter           OBJECT IDENTIFIER ::= { snFESX624E 2 }            -- FESX624 Ipv4 router
  snFESX624EPrem             OBJECT IDENTIFIER ::= { snFESX624EBaseFamily 2 }  -- FastIron Edge V6 Switch(FES) 24G-PREM
  snFESX624EPremSwitch       OBJECT IDENTIFIER ::= { snFESX624EPrem 1 }        -- FESX624-PREM switch
  snFESX624EPremRouter       OBJECT IDENTIFIER ::= { snFESX624EPrem 2 }        -- FESX624-PREM Ipv4 router
  snFESX624EPrem6Router   OBJECT IDENTIFIER ::= { snFESX624EPrem 3 }        -- FESX624-PREM Ipv6 router

  snFESX624EPlus1XGFamily         OBJECT IDENTIFIER ::= { snFESX624EFamily 2 } -- FstIron edge V6 family
  snFESX624EPlus1XG               OBJECT IDENTIFIER ::= { snFESX624EPlus1XGFamily 1 } -- FastIron Edge V6 Switch(FES) 24G + 1 10G
  snFESX624EPlus1XGSwitch         OBJECT IDENTIFIER ::= { snFESX624EPlus1XG 1 }     -- FESX624+1XG switch
  snFESX624EPlus1XGRouter         OBJECT IDENTIFIER ::= { snFESX624EPlus1XG 2 }     -- FESX624+1XG Ipv4 router
  snFESX624EPlus1XGPrem           OBJECT IDENTIFIER ::= { snFESX624EPlus1XGFamily 2 } -- FastIron Edge V6 Switch(FES) 24G + 1 10G-PREM
  snFESX624EPlus1XGPremSwitch     OBJECT IDENTIFIER ::= { snFESX624EPlus1XGPrem 1 } -- FESX624+1XG-PREM switch
  snFESX624EPlus1XGPremRouter     OBJECT IDENTIFIER ::= { snFESX624EPlus1XGPrem 2 } -- FESX624+1XG-PREM Ipv4 router
  snFESX624EPlus1XGPrem6Router OBJECT IDENTIFIER ::= { snFESX624EPlus1XGPrem 3 } -- FESX624+1XG-PREM Ipv6 router

  snFESX624EPlus2XGFamily         OBJECT IDENTIFIER ::= { snFESX624EFamily 3 }  -- FstIron edge V6 family
  snFESX624EPlus2XG               OBJECT IDENTIFIER ::= { snFESX624EPlus2XGFamily 1 } -- FastIron Edge V6 Switch(FES) 24G + 2 10G
  snFESX624EPlus2XGSwitch         OBJECT IDENTIFIER ::= { snFESX624EPlus2XG 1 }     -- FESX624+2XG switch
  snFESX624EPlus2XGRouter         OBJECT IDENTIFIER ::= { snFESX624EPlus2XG 2 }     -- FESX624+2XG Ipv4 router
  snFESX624EPlus2XGPrem           OBJECT IDENTIFIER ::= { snFESX624EPlus2XGFamily 2 } -- FastIron Edge V6 Switch(FES) 24G + 2 10G-PREM
  snFESX624EPlus2XGPremSwitch     OBJECT IDENTIFIER ::= { snFESX624EPlus2XGPrem 1 } -- FESX624+2XG-PREM switch
  snFESX624EPlus2XGPremRouter     OBJECT IDENTIFIER ::= { snFESX624EPlus2XGPrem 2 } -- FESX624+2XG-PREM Ipv4 router
  snFESX624EPlus2XGPrem6Router OBJECT IDENTIFIER ::= { snFESX624EPlus2XGPrem 3 } -- FESX624+2XG-PREM Ipv6 router

  snFESX624EFiberFamily       OBJECT IDENTIFIER ::= { snFESXFamily 12 }

  snFESX624EFiberBaseFamily     OBJECT IDENTIFIER ::= { snFESX624EFiberFamily 1 }          -- FstIron edge V6-E(Expanded)  Fiber family
  snFESX624EFiber               OBJECT IDENTIFIER ::= { snFESX624EFiberBaseFamily 1 }    -- FastIron V6 Edge Switch(FES) Fiber 24G
  snFESX624EFiberSwitch         OBJECT IDENTIFIER ::= { snFESX624EFiber 1 }            -- FESX624Fiber switch
  snFESX624EFiberRouter         OBJECT IDENTIFIER ::= { snFESX624EFiber 2 }            -- FESX624Fiber Ipv4 router
  snFESX624EFiberPrem           OBJECT IDENTIFIER ::= { snFESX624EFiberBaseFamily 2 }    -- FastIron Edge V6 Switch(FES) Fiber 24G-PREM
  snFESX624EFiberPremSwitch     OBJECT IDENTIFIER ::= { snFESX624EFiberPrem 1 }        -- FESX624Fiber-PREM switch
  snFESX624EFiberPremRouter     OBJECT IDENTIFIER ::= { snFESX624EFiberPrem 2 }        -- FESX624Fiber-PREM Ipv4 router
  snFESX624EFiberPrem6Router OBJECT IDENTIFIER ::= { snFESX624EFiberPrem 3 }        -- FESX624Fiber-PREM Ipv6 router

  snFESX624EFiberPlus1XGFamily          OBJECT IDENTIFIER ::= { snFESX624EFiberFamily 2 }          -- FstIron edge V6 family
  snFESX624EFiberPlus1XG                OBJECT IDENTIFIER ::= { snFESX624EFiberPlus1XGFamily 1 } -- FastIron Edge V6 Switch(FES) Fiber 24G + 1 10G
  snFESX624EFiberPlus1XGSwitch          OBJECT IDENTIFIER ::= { snFESX624EFiberPlus1XG 1 }     -- FESX624Fiber+1XG switch
  snFESX624EFiberPlus1XGRouter          OBJECT IDENTIFIER ::= { snFESX624EFiberPlus1XG 2 }     -- FESX624Fiber+1XG Ipv4 router
  snFESX624EFiberPlus1XGPrem            OBJECT IDENTIFIER ::= { snFESX624EFiberPlus1XGFamily 2 } -- FastIron Edge V6 Switch(FES) Fiber 24G + 1 10G-PREM
  snFESX624EFiberPlus1XGPremSwitch      OBJECT IDENTIFIER ::= { snFESX624EFiberPlus1XGPrem 1 } -- FESX624Fiber+1XG-PREM switch
  snFESX624EFiberPlus1XGPremRouter      OBJECT IDENTIFIER ::= { snFESX624EFiberPlus1XGPrem 2 } -- FESX624Fiber+1XG-PREM Ipv4 router
  snFESX624EFiberPlus1XGPrem6Router  OBJECT IDENTIFIER ::= { snFESX624EFiberPlus1XGPrem 3 } -- FESX624Fiber+1XG-PREM Ipv6 router

  snFESX624EFiberPlus2XGFamily          OBJECT IDENTIFIER ::= { snFESX624EFiberFamily 3 }          -- FstIron edge V6 family
  snFESX624EFiberPlus2XG                OBJECT IDENTIFIER ::= { snFESX624EFiberPlus2XGFamily 1 } -- FastIron Edge V6 Switch(FES) Fiber 24G + 2 10G
  snFESX624EFiberPlus2XGSwitch          OBJECT IDENTIFIER ::= { snFESX624EFiberPlus2XG 1 }     -- FESX624Fiber+2XG switch
  snFESX624EFiberPlus2XGRouter          OBJECT IDENTIFIER ::= { snFESX624EFiberPlus2XG 2 }     -- FESX624Fiber+2XG Ipv4 router
  snFESX624EFiberPlus2XGPrem            OBJECT IDENTIFIER ::= { snFESX624EFiberPlus2XGFamily 2 } -- FastIron Edge V6 Switch(FES) Fiber 24G + 2 10G-PREM
  snFESX624EFiberPlus2XGPremSwitch      OBJECT IDENTIFIER ::= { snFESX624EFiberPlus2XGPrem 1 } -- FESX624Fiber+2XG-PREM switch
  snFESX624EFiberPlus2XGPremRouter      OBJECT IDENTIFIER ::= { snFESX624EFiberPlus2XGPrem 2 } -- FESX624Fiber+2XG-PREM Ipv4  router
  snFESX624EFiberPlus2XGPrem6Router  OBJECT IDENTIFIER ::= { snFESX624EFiberPlus2XGPrem 3 } -- FESX624Fiber+2XG-PREM Ipv6 router

  snFESX648EFamily         OBJECT IDENTIFIER ::= { snFESXFamily 13 }

  snFESX648EBaseFamily     OBJECT IDENTIFIER ::= { snFESX648EFamily 1 }      -- FstIron edge V6-E (Expanded)family
  snFESX648E               OBJECT IDENTIFIER ::= { snFESX648EBaseFamily 1 }  -- FastIron Edge V6 Switch(FES) 48G
  snFESX648ESwitch         OBJECT IDENTIFIER ::= { snFESX648E 1 }            -- FESX648 switch
  snFESX648ERouter         OBJECT IDENTIFIER ::= { snFESX648E 2 }            -- FESX648 Ipv4 router
  snFESX648EPrem           OBJECT IDENTIFIER ::= { snFESX648EBaseFamily 2 }    -- FastIron Edge V6 Switch(FES) 48G-PREM
  snFESX648EPremSwitch     OBJECT IDENTIFIER ::= { snFESX648EPrem 1 }        -- FESX648-PREM switch
  snFESX648EPremRouter     OBJECT IDENTIFIER ::= { snFESX648EPrem 2 }        -- FESX648-PREM Ipv4 router
  snFESX648EPrem6Router OBJECT IDENTIFIER ::= { snFESX648EPrem 3 }        -- FESX648-PREM Ipv6 router

  snFESX648EPlus1XGFamily         OBJECT IDENTIFIER ::= { snFESX648EFamily 2 }      -- FstIron edge V6 family
  snFESX648EPlus1XG               OBJECT IDENTIFIER ::= { snFESX648EPlus1XGFamily 1 } -- FastIron Edge V6 Switch(FES) 48G + 1 10G
  snFESX648EPlus1XGSwitch         OBJECT IDENTIFIER ::= { snFESX648EPlus1XG 1 }     -- FESX648+1XG switch
  snFESX648EPlus1XGRouter         OBJECT IDENTIFIER ::= { snFESX648EPlus1XG 2 }     -- FESX648+1XG Ipv4 router
  snFESX648EPlus1XGPrem           OBJECT IDENTIFIER ::= { snFESX648EPlus1XGFamily 2 } -- FastIron Edge V6 Switch(FES) 48G + 1 10G-PREM
  snFESX648EPlus1XGPremSwitch     OBJECT IDENTIFIER ::= { snFESX648EPlus1XGPrem 1 } -- FESX648+1XG-PREM switch
  snFESX648EPlus1XGPremRouter     OBJECT IDENTIFIER ::= { snFESX648EPlus1XGPrem 2 } -- FESX648+1XG-PREM Ipv4 router
  snFESX648EPlus1XGPrem6Router OBJECT IDENTIFIER ::= { snFESX648EPlus1XGPrem 3 } -- FESX648+1XG-PREM Ipv6 router

  snFESX648EPlus2XGFamily         OBJECT IDENTIFIER ::= { snFESX648EFamily 3 }      -- FstIron edge V6 family
  snFESX648EPlus2XG               OBJECT IDENTIFIER ::= { snFESX648EPlus2XGFamily 1 } -- FastIron Edge V6 Switch(FES) 48G + 2 10G
  snFESX648EPlus2XGSwitch         OBJECT IDENTIFIER ::= { snFESX648EPlus2XG 1 }     -- FESX648+2XG switch
  snFESX648EPlus2XGRouter         OBJECT IDENTIFIER ::= { snFESX648EPlus2XG 2 }     -- FESX648+2XG Ipv4 router
  snFESX648EPlus2XGPrem           OBJECT IDENTIFIER ::= { snFESX648EPlus2XGFamily 2 } -- FastIron Edge V6 Switch(FES) 48G + 2 10G-PREM
  snFESX648EPlus2XGPremSwitch     OBJECT IDENTIFIER ::= { snFESX648EPlus2XGPrem 1 } -- FESX648+2XG-PREM switch
  snFESX648EPlus2XGPremRouter     OBJECT IDENTIFIER ::= { snFESX648EPlus2XGPrem 2 } -- FESX648+2XG-PREM Ipv4 router
  snFESX648EPlus2XGPrem6Router OBJECT IDENTIFIER ::= { snFESX648EPlus2XGPrem 3 } -- FESX648+2XG-PREM Ipv6 router

  snFWSXFamily          OBJECT IDENTIFIER ::= { registration 35 }

  snFWSX424Family       OBJECT IDENTIFIER ::= { snFWSXFamily 1 }
  snFWSX424BaseFamily   OBJECT IDENTIFIER ::= { snFWSX424Family 1 }
  snFWSX424             OBJECT IDENTIFIER ::= { snFWSX424BaseFamily 1 }    -- FastIron WorkGroup Switch(FWS) 24G
  snFWSX424Switch       OBJECT IDENTIFIER ::= { snFWSX424 1 }            -- FWSX424 switch
  snFWSX424Router       OBJECT IDENTIFIER ::= { snFWSX424 2 }            -- FWSX424 router

  snFWSX424Plus1XGFamily   OBJECT IDENTIFIER ::= { snFWSX424Family 2 }
  snFWSX424Plus1XG         OBJECT IDENTIFIER ::= { snFWSX424Plus1XGFamily 1 } -- FastIron WorkGroup Switch(FWS) 24G + 1 10G
  snFWSX424Plus1XGSwitch   OBJECT IDENTIFIER ::= { snFWSX424Plus1XG 1 }     -- FWSX424+1XG switch
  snFWSX424Plus1XGRouter   OBJECT IDENTIFIER ::= { snFWSX424Plus1XG 2 }     -- FWSX424+1XG router

  snFWSX424Plus2XGFamily  OBJECT IDENTIFIER ::= { snFWSX424Family 3 }
  snFWSX424Plus2XG        OBJECT IDENTIFIER ::= { snFWSX424Plus2XGFamily 1 } -- FastIron WorkGroup Switch(FWS) 24G + 2 10G
  snFWSX424Plus2XGSwitch  OBJECT IDENTIFIER ::= { snFWSX424Plus2XG 1 }     -- FWSX424+2XG switch
  snFWSX424Plus2XGRouter  OBJECT IDENTIFIER ::= { snFWSX424Plus2XG 2 }     -- FWSX424+2XG router

  snFWSX448Family         OBJECT IDENTIFIER ::= { snFWSXFamily 2 }
  snFWSX448BaseFamily     OBJECT IDENTIFIER ::= { snFWSX448Family 1 }
  snFWSX448               OBJECT IDENTIFIER ::= { snFWSX448BaseFamily 1 }    -- FastIron WorkGroup Switch(FWS) 48G
  snFWSX448Switch         OBJECT IDENTIFIER ::= { snFWSX448 1 }            -- FWSX448 switch
  snFWSX448Router         OBJECT IDENTIFIER ::= { snFWSX448 2 }            -- FWSX448 router

  snFWSX448Plus1XGFamily  OBJECT IDENTIFIER ::= { snFWSX448Family 2 }
  snFWSX448Plus1XG        OBJECT IDENTIFIER ::= { snFWSX448Plus1XGFamily 1 } -- FastIron WorkGroup Switch(FWS) 48G + 1 10G
  snFWSX448Plus1XGSwitch  OBJECT IDENTIFIER ::= { snFWSX448Plus1XG 1 }     -- FWSX448+1XG switch
  snFWSX448Plus1XGRouter  OBJECT IDENTIFIER ::= { snFWSX448Plus1XG 2 }     -- FWSX448+1XG router

  snFWSX448Plus2XGFamily  OBJECT IDENTIFIER ::= { snFWSX448Family 3 }
  snFWSX448Plus2XG        OBJECT IDENTIFIER ::= { snFWSX448Plus2XGFamily 1 } -- FastIron WorkGroup Switch(FWS) 48G + 2 10G
  snFWSX448Plus2XGSwitch  OBJECT IDENTIFIER ::= { snFWSX448Plus2XG 1 }     -- FWSX448+2XG switch
  snFWSX448Plus2XGRouter  OBJECT IDENTIFIER ::= { snFWSX448Plus2XG 2 }     -- FWSX448+2XG router

-- Do not use { snFWSXFamily 3 } to { snFWSXFamily 4 }

  snFastIronSuperXFamily            OBJECT IDENTIFIER ::= { registration 36 }        -- FastIron SuperX Family
  snFastIronSuperX                  OBJECT IDENTIFIER ::= { snFastIronSuperXFamily 1 }    -- FastIron SuperX
  snFastIronSuperXSwitch            OBJECT IDENTIFIER ::= { snFastIronSuperX 1 }          -- FastIron SuperX Switch
  snFastIronSuperXRouter            OBJECT IDENTIFIER ::= { snFastIronSuperX 2 }          -- FastIron SuperX Router
  snFastIronSuperXBaseL3Switch      OBJECT IDENTIFIER ::= { snFastIronSuperX 3 }          -- FastIron SuperX Base L3 Switch
  snFastIronSuperXPrem              OBJECT IDENTIFIER ::= { snFastIronSuperXFamily 2 }    -- FastIron SuperX Premium
  snFastIronSuperXPremSwitch        OBJECT IDENTIFIER ::= { snFastIronSuperXPrem 1 }      -- FastIron SuperX Premium Switch
  snFastIronSuperXPremRouter        OBJECT IDENTIFIER ::= { snFastIronSuperXPrem 2 }      -- FastIron SuperX Premium Router
  snFastIronSuperXPremBaseL3Switch  OBJECT IDENTIFIER ::= { snFastIronSuperXPrem 3 }      -- FastIron SuperX Premium Base L3 Switch

  snFastIronSuperX800                  OBJECT IDENTIFIER ::= { snFastIronSuperXFamily 3 }    -- FastIron SuperX 800 
  snFastIronSuperX800Switch            OBJECT IDENTIFIER ::= { snFastIronSuperX800 1 }          -- FastIron SuperX 800 Switch
  snFastIronSuperX800Router            OBJECT IDENTIFIER ::= { snFastIronSuperX800 2 }          -- FastIron SuperX 800 Router
  snFastIronSuperX800BaseL3Switch      OBJECT IDENTIFIER ::= { snFastIronSuperX800 3 }          -- FastIron SuperX 800 Base L3 Switch
  snFastIronSuperX800Prem              OBJECT IDENTIFIER ::= { snFastIronSuperXFamily 4 }    -- FastIron SuperX 800 Premium
  snFastIronSuperX800PremSwitch        OBJECT IDENTIFIER ::= { snFastIronSuperX800Prem 1 }      -- FastIron SuperX 800 Premium Switch
  snFastIronSuperX800PremRouter        OBJECT IDENTIFIER ::= { snFastIronSuperX800Prem 2 }      -- FastIron SuperX 800 Premium Router
  snFastIronSuperX800PremBaseL3Switch  OBJECT IDENTIFIER ::= { snFastIronSuperX800Prem 3 }      -- FastIron SuperX 800 Premium Base L3 Switch

  snFastIronSuperX1600                  OBJECT IDENTIFIER ::= { snFastIronSuperXFamily 5 }    -- FastIron SuperX 1600 
  snFastIronSuperX1600Switch            OBJECT IDENTIFIER ::= { snFastIronSuperX1600 1 }          -- FastIron SuperX 1600 Switch
  snFastIronSuperX1600Router            OBJECT IDENTIFIER ::= { snFastIronSuperX1600 2 }          -- FastIron SuperX 1600 Router
  snFastIronSuperX1600BaseL3Switch      OBJECT IDENTIFIER ::= { snFastIronSuperX1600 3 }          -- FastIron SuperX 1600 Base L3 Switch
  snFastIronSuperX1600Prem              OBJECT IDENTIFIER ::= { snFastIronSuperXFamily 6 }    -- FastIron SuperX 1600 Premium
  snFastIronSuperX1600PremSwitch        OBJECT IDENTIFIER ::= { snFastIronSuperX1600Prem 1 }      -- FastIron SuperX 1600 Premium Switch
  snFastIronSuperX1600PremRouter        OBJECT IDENTIFIER ::= { snFastIronSuperX1600Prem 2 }      -- FastIron SuperX 1600 Premium Router
  snFastIronSuperX1600PremBaseL3Switch  OBJECT IDENTIFIER ::= { snFastIronSuperX1600Prem 3 }      -- FastIron SuperX 1600 Premium Base L3 Switch

  snFastIronSuperXV6                  OBJECT IDENTIFIER ::= { snFastIronSuperXFamily 7 }    -- FastIron SuperX V6 
  snFastIronSuperXV6Switch            OBJECT IDENTIFIER ::= { snFastIronSuperXV6 1 }          -- FastIron SuperX V6 Switch
  snFastIronSuperXV6Router            OBJECT IDENTIFIER ::= { snFastIronSuperXV6 2 }          -- FastIron SuperX V6- Ipv4 Router
  snFastIronSuperXV6BaseL3Switch      OBJECT IDENTIFIER ::= { snFastIronSuperXV6 3 }          -- FastIron SuperX V6 Base L3 Switch
  snFastIronSuperXV6Prem              OBJECT IDENTIFIER ::= { snFastIronSuperXFamily 8 }    -- FastIron SuperX V6 Premium
  snFastIronSuperXV6PremSwitch        OBJECT IDENTIFIER ::= { snFastIronSuperXV6Prem 1 }      -- FastIron SuperX V6 Premium Switch
  snFastIronSuperXV6PremRouter        OBJECT IDENTIFIER ::= { snFastIronSuperXV6Prem 2 }      -- FastIron SuperX V6 Premium Ipv4 Router
  snFastIronSuperXV6PremBaseL3Switch  OBJECT IDENTIFIER ::= { snFastIronSuperXV6Prem 3 }      -- FastIron SuperX V6 Premium Base L3 Switch
  snFastIronSuperXV6Prem6Router    OBJECT IDENTIFIER ::= { snFastIronSuperXV6Prem 4 }      -- FastIron SuperX V6 Premium Ipv6 Router

  snFastIronSuperX800V6                  OBJECT IDENTIFIER ::= { snFastIronSuperXFamily 9 }    -- FastIron SuperX 800 V6 
  snFastIronSuperX800V6Switch            OBJECT IDENTIFIER ::= { snFastIronSuperX800V6 1 }          -- FastIron SuperX 800 V6 Switch
  snFastIronSuperX800V6Router            OBJECT IDENTIFIER ::= { snFastIronSuperX800V6 2 }          -- FastIron SuperX 800 V6 - Ipv4 Router
  snFastIronSuperX800V6BaseL3Switch      OBJECT IDENTIFIER ::= { snFastIronSuperX800V6 3 }          -- FastIron SuperX 800 V6 Base L3 Switch
  snFastIronSuperX800V6Prem              OBJECT IDENTIFIER ::= { snFastIronSuperXFamily 10 }    -- FastIron SuperX 800 V6 Premium
  snFastIronSuperX800V6PremSwitch        OBJECT IDENTIFIER ::= {   snFastIronSuperX800V6Prem 1 }      -- FastIron SuperX 800 Premium V6 Switch
  snFastIronSuperX800V6PremRouter        OBJECT IDENTIFIER ::= {   snFastIronSuperX800V6Prem 2 }      -- FastIron SuperX 800 Premium V6 - Ipv4 Router
  snFastIronSuperX800V6PremBaseL3Switch  OBJECT IDENTIFIER ::= {   snFastIronSuperX800V6Prem 3 }      -- FastIron SuperX 800 Premium V6 Base L3 Switch
  snFastIronSuperX800V6Prem6Router    OBJECT IDENTIFIER ::= {   snFastIronSuperX800V6Prem 4 }      -- FastIron SuperX 800 Premium V6- Ipv6  Router

  snFastIronSuperX1600V6                  OBJECT IDENTIFIER ::= { snFastIronSuperXFamily 11 }    -- FastIron SuperX 1600 V6 
  snFastIronSuperX1600V6Switch            OBJECT IDENTIFIER ::= { snFastIronSuperX1600V6 1 }          -- FastIron SuperX 1600 V6 Switch
  snFastIronSuperX1600V6Router            OBJECT IDENTIFIER ::= { snFastIronSuperX1600V6 2 }          -- FastIron SuperX 1600 V6 - Ipv4 Router
  snFastIronSuperX1600V6BaseL3Switch      OBJECT IDENTIFIER ::= { snFastIronSuperX1600V6 3 }          -- FastIron SuperX 1600 V6 Base L3 Switch
  snFastIronSuperX1600V6Prem              OBJECT IDENTIFIER ::= { snFastIronSuperXFamily 12 }    -- FastIron SuperX 1600 Premium V6
  snFastIronSuperX1600V6PremSwitch        OBJECT IDENTIFIER ::= { snFastIronSuperX1600V6Prem 1 }      -- FastIron SuperX 1600 Premium V6 Switch
  snFastIronSuperX1600V6PremRouter        OBJECT IDENTIFIER ::= { snFastIronSuperX1600V6Prem 2 }      -- FastIron SuperX 1600 Premium V6- Ipv4 Router
  snFastIronSuperX1600V6PremBaseL3Switch  OBJECT IDENTIFIER ::= { snFastIronSuperX1600V6Prem 3 }      -- FastIron SuperX 1600 Premium V6 Base L3 Switch
  snFastIronSuperX1600V6Prem6Router    OBJECT IDENTIFIER ::= { snFastIronSuperX1600V6Prem 4 }      -- FastIron SuperX 1600 Premium V6- Ipv6 Router

  snBigIronSuperXFamily             OBJECT IDENTIFIER ::= { registration 37 }        -- BigIron SuperX Family
  snBigIronSuperX                   OBJECT IDENTIFIER ::= { snBigIronSuperXFamily 1 }    -- BigIron SuperX
  snBigIronSuperXSwitch             OBJECT IDENTIFIER ::= { snBigIronSuperX 1 }          -- BigIron SuperX Switch
  snBigIronSuperXRouter             OBJECT IDENTIFIER ::= { snBigIronSuperX 2 }          -- BigIron SuperX Router
  snBigIronSuperXBaseL3Switch       OBJECT IDENTIFIER ::= { snBigIronSuperX 3 }          -- BigIron SuperX Base L3 Switch

  snTurboIronSuperXFamily           OBJECT IDENTIFIER ::= { registration 38 }        -- TurboIron SuperX Family
  snTurboIronSuperX                 OBJECT IDENTIFIER ::= { snTurboIronSuperXFamily 1 }    -- TurboIron SuperX
  snTurboIronSuperXSwitch           OBJECT IDENTIFIER ::= { snTurboIronSuperX 1 }          -- TurboIron SuperX Switch
  snTurboIronSuperXRouter           OBJECT IDENTIFIER ::= { snTurboIronSuperX 2 }          -- TurboIron SuperX Router
  snTurboIronSuperXBaseL3Switch     OBJECT IDENTIFIER ::= { snTurboIronSuperX 3 }          -- TurboIron SuperX Base L3 Switch
  snTurboIronSuperXPrem             OBJECT IDENTIFIER ::= { snTurboIronSuperXFamily 2 }    -- TurboIron SuperX Premium
  snTurboIronSuperXPremSwitch       OBJECT IDENTIFIER ::= { snTurboIronSuperXPrem 1 }      -- TurboIron SuperX Premium Switch
  snTurboIronSuperXPremRouter       OBJECT IDENTIFIER ::= { snTurboIronSuperXPrem 2 }      -- TurboIron SuperX Premium Router
  snTurboIronSuperXPremBaseL3Switch OBJECT IDENTIFIER ::= { snTurboIronSuperXPrem 3 }      -- TurboIron SuperX Premium Base L3 Switch


  snIMRFamily       OBJECT IDENTIFIER ::= { registration 39 }
  snNetIronIMR      OBJECT IDENTIFIER ::= { snIMRFamily 1 }     -- NetIron IMR family
  snNIIMRRouter     OBJECT IDENTIFIER ::= { snNetIronIMR 2 }    -- NetIron IMR router

  snBigIronRXFamily OBJECT IDENTIFIER ::= { registration 40 }      -- BigIron RX family
  snBigIronRX16     OBJECT IDENTIFIER ::= { snBigIronRXFamily 1 }  -- BigIron RX16 family
  snBIRX16Switch    OBJECT IDENTIFIER ::= { snBigIronRX16 1 }      -- BigIron RX16 switch
  snBIRX16Router    OBJECT IDENTIFIER ::= { snBigIronRX16 2 }      -- BigIron RX16 router
  snBigIronRX8      OBJECT IDENTIFIER ::= { snBigIronRXFamily 2 }  -- BigIron RX8 family
  snBIRX8Switch     OBJECT IDENTIFIER ::= { snBigIronRX8 1 }       -- BigIron RX8 switch
  snBIRX8Router     OBJECT IDENTIFIER ::= { snBigIronRX8 2 }       -- BigIron RX8 router
  snBigIronRX4      OBJECT IDENTIFIER ::= { snBigIronRXFamily 3 }  -- BigIron RX4 family
  snBIRX4Switch     OBJECT IDENTIFIER ::= { snBigIronRX4 1 }       -- BigIron RX4 switch
  snBIRX4Router     OBJECT IDENTIFIER ::= { snBigIronRX4 2 }       -- BigIron RX4 router
  snBigIronRX32     OBJECT IDENTIFIER ::= { snBigIronRXFamily 4 }  -- BigIron RX32 family
  snBIRX32Switch    OBJECT IDENTIFIER ::= { snBigIronRX32 1 }      -- BigIron RX32 switch
  snBIRX32Router    OBJECT IDENTIFIER ::= { snBigIronRX32 2 }      -- BigIron RX32 router

  snNetIronXMRFamily OBJECT IDENTIFIER ::= { registration 41 }      -- NetIron XMR family
  snNetIronXMR16000     OBJECT IDENTIFIER ::= { snNetIronXMRFamily 1 }  -- NetIron XMR16000 family
  snNIXMR16000Router    OBJECT IDENTIFIER ::= { snNetIronXMR16000 2 }      -- NetIron XMR16000 router
  snNetIronXMR8000      OBJECT IDENTIFIER ::= { snNetIronXMRFamily 2 }  -- NetIron XMR8000 family
  snNIXMR8000Router     OBJECT IDENTIFIER ::= { snNetIronXMR8000 2 }       -- NetIron XMR8000 router
  snNetIronXMR4000      OBJECT IDENTIFIER ::= { snNetIronXMRFamily 3 }  -- NetIron XMR4000 family
  snNIXMR4000Router     OBJECT IDENTIFIER ::= { snNetIronXMR4000 2 }       -- NetIron XMR4000 router
  snNetIronXMR32000      OBJECT IDENTIFIER ::= { snNetIronXMRFamily 4 }  -- NetIron XMR32000 family
  snNIXMR32000Router     OBJECT IDENTIFIER ::= { snNetIronXMR32000 2 }       -- NetIron XMR32000 router

  snSecureIronFamily            OBJECT IDENTIFIER ::= {  registration 42 }    -- SecureIron family
-- Do not use { snSecureIronFamily 1 } to { snSecureIronFamily 8 }
  snSecureIronLSFamily          OBJECT IDENTIFIER ::= { snSecureIronFamily 9 }    -- SecureIron LS family
  snSecureIronLS100             OBJECT IDENTIFIER ::= { snSecureIronLSFamily 1 }  -- SecureIronLS 100
  snSecureIronLS100Switch       OBJECT IDENTIFIER ::= { snSecureIronLS100 1 }     -- SecureIronLS 100 Switch
  snSecureIronLS100Router       OBJECT IDENTIFIER ::= { snSecureIronLS100 2 }     -- SecureIronLS 100 Router
  snSecureIronLS300             OBJECT IDENTIFIER ::= { snSecureIronLSFamily 2 }  -- SecureIronLS 300
  snSecureIronLS300Switch       OBJECT IDENTIFIER ::= { snSecureIronLS300 1 }     -- SecureIronLS 300 Switch
  snSecureIronLS300Router       OBJECT IDENTIFIER ::= { snSecureIronLS300 2 }     -- SecureIronLS 300 Router
  snSecureIronTMFamily          OBJECT IDENTIFIER ::= { snSecureIronFamily 10 }   -- SecureIron TM family
  snSecureIronTM100             OBJECT IDENTIFIER ::= { snSecureIronTMFamily 1 }  -- SecureIronTM 100
  snSecureIronTM100Switch       OBJECT IDENTIFIER ::= { snSecureIronTM100 1 }     -- SecureIronTM 100 Switch
  snSecureIronTM100Router       OBJECT IDENTIFIER ::= { snSecureIronTM100 2 }     -- SecureIronTM 100 Router
  snSecureIronTM300             OBJECT IDENTIFIER ::= { snSecureIronTMFamily 2 }  -- SecureIronTM 300
  snSecureIronTM300Switch       OBJECT IDENTIFIER ::= { snSecureIronTM300 1 }     -- SecureIronTM 300 Switch
  snSecureIronTM300Router       OBJECT IDENTIFIER ::= { snSecureIronTM300 2 }     -- SecureIronTM 300 Router

-- Do not use { registration 43 }

  snNetIronMLXFamily OBJECT IDENTIFIER ::= { registration 44 }      -- NetIron MLX family
  snNetIronMLX16      OBJECT IDENTIFIER ::= { snNetIronMLXFamily 1 }  -- NetIron MLX-16 family
  snNetIronMLX16Router     OBJECT IDENTIFIER ::= { snNetIronMLX16 2 }       -- NetIron MLX-16 router
  snNetIronMLX8      OBJECT IDENTIFIER ::= { snNetIronMLXFamily 2 }  -- NetIron MLX-8 family
  snNetIronMLX8Router     OBJECT IDENTIFIER ::= { snNetIronMLX8 2 }       -- NetIron MLX-8 router
  snNetIronMLX4      OBJECT IDENTIFIER ::= { snNetIronMLXFamily 3 }  -- NetIron MLX-4 family
  snNetIronMLX4Router     OBJECT IDENTIFIER ::= { snNetIronMLX4 2 }       -- NetIron MLX-4 router
  snNetIronMLX32      OBJECT IDENTIFIER ::= { snNetIronMLXFamily 4 }  -- NetIron MLX-32 family
  snNetIronMLX32Router     OBJECT IDENTIFIER ::= { snNetIronMLX32 2 }       -- NetIron MLX-32 router


  snFGSFamily          OBJECT IDENTIFIER ::= { registration 45 }	-- FastIron GS series family
  snFGS624Family       OBJECT IDENTIFIER ::= { snFGSFamily 1 }

  snFGS624PBaseFamily  OBJECT IDENTIFIER ::= { snFGS624Family 1 }
  snFGS624P            OBJECT IDENTIFIER ::= { snFGS624PBaseFamily 1 }  -- FastIron GS Switch(FGS) 24-port 10/100/1000 POE Ready
  snFGS624PSwitch      OBJECT IDENTIFIER ::= { snFGS624P 1 }            -- FGS624P switch
  snFGS624PRouter      OBJECT IDENTIFIER ::= { snFGS624P 2 }            -- FGS624P router

  snFGS624XGPFamily    OBJECT IDENTIFIER ::= { snFGS624Family 2 }
  snFGS624XGP          OBJECT IDENTIFIER ::= { snFGS624XGPFamily 1 }    -- FastIron GS Switch(FGS) 24-port 10/100/1000 POE Ready + 1 10G
  snFGS624XGPSwitch    OBJECT IDENTIFIER ::= { snFGS624XGP 1 }          -- FGS624XGP switch
  snFGS624XGPRouter    OBJECT IDENTIFIER ::= { snFGS624XGP 2 }          -- FGS624XGP router

  snFGS624PPOEFamily   OBJECT IDENTIFIER ::= { snFGS624Family 3 }
  snFGS624PPOE         OBJECT IDENTIFIER ::= { snFGS624PPOEFamily 1 }   -- FastIron GS Switch(FGS) 24-port 10/100/1000 POE 
  snFGS624PPOESwitch   OBJECT IDENTIFIER ::= { snFGS624PPOE 1 }         -- snFGS624P-POE switch
  snFGS624PPOERouter   OBJECT IDENTIFIER ::= { snFGS624PPOE 2 }         -- snFGS624P-POE router

  snFGS624XGPPOEFamily OBJECT IDENTIFIER ::= { snFGS624Family 4 }
  snFGS624XGPPOE       OBJECT IDENTIFIER ::= { snFGS624XGPPOEFamily 1 } -- FastIron GS Switch(FGS) 24-port 10/100/1000 POE + 1 10G
  snFGS624XGPPOESwitch OBJECT IDENTIFIER ::= { snFGS624XGPPOE 1 }       -- FGS624XGP-POE switch
  snFGS624XGPPOERouter OBJECT IDENTIFIER ::= { snFGS624XGPPOE 2 }       -- FGS624XGP-POE router

  snFGS648Family       OBJECT IDENTIFIER ::= { snFGSFamily 2 }

  snFGS648PBaseFamily  OBJECT IDENTIFIER ::= { snFGS648Family 1 }
  snFGS648P            OBJECT IDENTIFIER ::= { snFGS648PBaseFamily 1 }  -- FastIron GS Switch(FGS) 48-port 10/100/1000 POE Ready
  snFGS648PSwitch      OBJECT IDENTIFIER ::= { snFGS648P 1 }            -- FGS648P switch
  snFGS648PRouter      OBJECT IDENTIFIER ::= { snFGS648P 2 }            -- FGS648P router

  snFGS648PPOEFamily   OBJECT IDENTIFIER ::= { snFGS648Family 2 }
  snFGS648PPOE         OBJECT IDENTIFIER ::= { snFGS648PPOEFamily 1 }   -- FastIron GS Switch(FGS) 48-port 10/100/1000 POE 
  snFGS648PPOESwitch   OBJECT IDENTIFIER ::= { snFGS648PPOE 1 }         -- snFGS648P-POE switch
  snFGS648PPOERouter   OBJECT IDENTIFIER ::= { snFGS648PPOE 2 }         -- snFGS648P-POE router


  snFLSFamily          OBJECT IDENTIFIER ::= { registration 46 }	-- FastIron LS series family
  snFLS624Family       OBJECT IDENTIFIER ::= { snFLSFamily 1 }

  snFLS624BaseFamily  OBJECT IDENTIFIER ::= { snFLS624Family 1 }
  snFLS624            OBJECT IDENTIFIER ::= { snFLS624BaseFamily 1 }  -- FastIron LS Switch(FLS) 24-port 10/100/1000 
  snFLS624Switch      OBJECT IDENTIFIER ::= { snFLS624 1 }                 -- FLS624 switch
  snFLS624Router      OBJECT IDENTIFIER ::= { snFLS624 2 }                 -- FLS624 router

  snFLS648Family       OBJECT IDENTIFIER ::= { snFLSFamily 2 }

  snFLS648BaseFamily  OBJECT IDENTIFIER ::= { snFLS648Family 1 }
  snFLS648            OBJECT IDENTIFIER ::= { snFLS648BaseFamily 1 }  -- FastIron LS Switch(FLS) 48-port 10/100/1000
  snFLS648Switch      OBJECT IDENTIFIER ::= { snFLS648 1 }               -- FLS648 switch
  snFLS648Router      OBJECT IDENTIFIER ::= { snFLS648 2 }               -- FLS648 router

  snSIFamily           OBJECT IDENTIFIER ::= { registration 47 }     -- ServerIron series family

  snSI100              OBJECT IDENTIFIER ::= { snSIFamily 1 }        -- ServerIron 100 series
  snSI100Switch        OBJECT IDENTIFIER ::= { snSI100 1 }           -- SI100 switch
  snSI100Router        OBJECT IDENTIFIER ::= { snSI100 2 }           -- SI100 router

  snSI350              OBJECT IDENTIFIER ::= { snSIFamily 2 }        -- ServerIron 350 series
  snSI350Switch        OBJECT IDENTIFIER ::= { snSI350 1 }           -- SI350 switch
  snSI350Router        OBJECT IDENTIFIER ::= { snSI350 2 }           -- SI350 router

  snSI450              OBJECT IDENTIFIER ::= { snSIFamily 3 }        -- ServerIron 450 series
  snSI450Switch        OBJECT IDENTIFIER ::= { snSI450 1 }           -- SI450 switch
  snSI450Router        OBJECT IDENTIFIER ::= { snSI450 2 }           -- SI450 router

  snSI850              OBJECT IDENTIFIER ::= { snSIFamily 4 }        -- ServerIron 850 series
  snSI850Switch        OBJECT IDENTIFIER ::= { snSI850 1 }           -- SI850 switch
  snSI850Router        OBJECT IDENTIFIER ::= { snSI850 2 }           -- SI850 router

  snSI350Plus          OBJECT IDENTIFIER ::= { snSIFamily 5 }        -- ServerIron 350 Plus series
  snSI350PlusSwitch    OBJECT IDENTIFIER ::= { snSI350Plus 1 }       -- SI350 Plus switch
  snSI350PlusRouter    OBJECT IDENTIFIER ::= { snSI350Plus 2 }       -- SI350 Plus router

  snSI450Plus          OBJECT IDENTIFIER ::= { snSIFamily 6 }        -- ServerIron 450 Plus series
  snSI450PlusSwitch    OBJECT IDENTIFIER ::= { snSI450Plus 1 }       -- SI450 Plus switch
  snSI450PlusRouter    OBJECT IDENTIFIER ::= { snSI450Plus 2 }       -- SI450 Plus router

  snSI850Plus          OBJECT IDENTIFIER ::= { snSIFamily 7 }        -- ServerIron 850 Plus series
  snSI850PlusSwitch    OBJECT IDENTIFIER ::= { snSI850Plus 1 }       -- SI850 Plus switch
  snSI850PlusRouter    OBJECT IDENTIFIER ::= { snSI850Plus 2 }       -- SI850 Plus router

  snServerIronGTc         OBJECT IDENTIFIER ::= { snSIFamily 8 }         -- ServerIronGT C series
  snServerIronGTcSwitch   OBJECT IDENTIFIER ::= { snServerIronGTc 1 }    -- ServerIronGT C switch
  snServerIronGTcRouter   OBJECT IDENTIFIER ::= { snServerIronGTc 2 }    -- ServerIronGT C router

  snServerIronGTe         OBJECT IDENTIFIER ::= { snSIFamily 9 }         -- ServerIronGT E series
  snServerIronGTeSwitch   OBJECT IDENTIFIER ::= { snServerIronGTe 1 }    -- ServerIronGT E switch
  snServerIronGTeRouter   OBJECT IDENTIFIER ::= { snServerIronGTe 2 }    -- ServerIronGT E router

  snServerIronGTePlus       OBJECT IDENTIFIER ::= { snSIFamily 10 }         -- ServerIronGT E Plus series
  snServerIronGTePlusSwitch OBJECT IDENTIFIER ::= { snServerIronGTePlus 1 } -- ServerIronGT E Plus switch
  snServerIronGTePlusRouter OBJECT IDENTIFIER ::= { snServerIronGTePlus 2 } -- ServerIronGT E Plus router

  snServerIron4G          OBJECT IDENTIFIER ::= { snSIFamily 11 }        -- ServerIron4G series
  snServerIron4GSwitch    OBJECT IDENTIFIER ::= { snServerIron4G 1 }     -- ServerIron4G switch
  snServerIron4GRouter    OBJECT IDENTIFIER ::= { snServerIron4G 2 }     -- ServerIron4G router

  serverIronAdx1000          OBJECT IDENTIFIER ::= { snSIFamily 12 }           -- ServerIron ADX 1000 series
  serverIronAdx1000Switch    OBJECT IDENTIFIER ::= { serverIronAdx1000 1 }     -- ServerIron ADX 1000 switch
  serverIronAdx1000Router    OBJECT IDENTIFIER ::= { serverIronAdx1000 2 }     -- ServerIron ADX 1000 router

  serverIronAdx1000Ssl          OBJECT IDENTIFIER ::= { snSIFamily 13 }           -- ServerIron ADX 1000 SSL series
  serverIronAdx1000SslSwitch    OBJECT IDENTIFIER ::= { serverIronAdx1000Ssl 1 }     -- ServerIron ADX 1000 SSL switch
  serverIronAdx1000SslRouter    OBJECT IDENTIFIER ::= { serverIronAdx1000Ssl 2 }     -- ServerIron ADX 1000 SSL router

  serverIronAdx4000          OBJECT IDENTIFIER ::= { snSIFamily 14 }           -- ServerIron ADX 4000 series
  serverIronAdx4000Switch    OBJECT IDENTIFIER ::= { serverIronAdx4000 1 }     -- ServerIron ADX 4000 switch
  serverIronAdx4000Router    OBJECT IDENTIFIER ::= { serverIronAdx4000 2 }     -- ServerIron ADX 4000 router

  serverIronAdx4000Ssl          OBJECT IDENTIFIER ::= { snSIFamily 15 }           -- ServerIron ADX 4000 SSL series
  serverIronAdx4000SslSwitch    OBJECT IDENTIFIER ::= { serverIronAdx4000Ssl 1 }  -- ServerIron ADX 4000 SSL switch
  serverIronAdx4000SslRouter    OBJECT IDENTIFIER ::= { serverIronAdx4000Ssl 2 }  -- ServerIron ADX 4000 SSL router

  serverIronAdx8000          OBJECT IDENTIFIER ::= { snSIFamily 16 }           -- ServerIron ADX 8000 series
  serverIronAdx8000Switch    OBJECT IDENTIFIER ::= { serverIronAdx8000 1 }     -- ServerIron ADX 8000 switch
  serverIronAdx8000Router    OBJECT IDENTIFIER ::= { serverIronAdx8000 2 }     -- ServerIron ADX 8000 router

  serverIronAdx8000Ssl          OBJECT IDENTIFIER ::= { snSIFamily 17 }           -- ServerIron ADX 8000 SSL series
  serverIronAdx8000SslSwitch    OBJECT IDENTIFIER ::= { serverIronAdx8000Ssl 1 }  -- ServerIron ADX 8000 SSL switch
  serverIronAdx8000SslRouter    OBJECT IDENTIFIER ::= { serverIronAdx8000Ssl 2 }  -- ServerIron ADX 8000 SSL router

  serverIronAdx10000          OBJECT IDENTIFIER ::= { snSIFamily 18 }           -- ServerIron ADX 10000 series
  serverIronAdx10000Switch    OBJECT IDENTIFIER ::= { serverIronAdx10000 1 }     -- ServerIron ADX 10000 switch
  serverIronAdx10000Router    OBJECT IDENTIFIER ::= { serverIronAdx10000 2 }     -- ServerIron ADX 10000 router

  serverIronAdx10000Ssl          OBJECT IDENTIFIER ::= { snSIFamily 19 }           -- ServerIron ADX 10000 SSL series
  serverIronAdx10000SslSwitch    OBJECT IDENTIFIER ::= { serverIronAdx10000Ssl 1 }     -- ServerIron ADX 10000 SSL switch
  serverIronAdx10000SslRouter    OBJECT IDENTIFIER ::= { serverIronAdx10000Ssl 2 }     -- ServerIron ADX 10000 SSL router


--FastIron GS/LS/CX (FGS/FLS/FCX/ICX) stacking family
  snFastIronStackFamily      OBJECT IDENTIFIER ::= { registration 48 }	-- FGS/FLS/FCX/ICX stacking family
  
  snFastIronStack               OBJECT IDENTIFIER ::= { snFastIronStackFamily 1 } 
  snFastIronStackSwitch      OBJECT IDENTIFIER ::= { snFastIronStack 1}           --FGS/FLS switch
  snFastIronStackRouter      OBJECT IDENTIFIER ::= { snFastIronStack 2}           --FGS/FLS router

  snFastIronStackFCX               OBJECT IDENTIFIER ::= { snFastIronStackFamily 2 } 
  snFastIronStackFCXSwitch      OBJECT IDENTIFIER ::= { snFastIronStackFCX 1}        -- FCX switch
  snFastIronStackFCXBaseL3Router      OBJECT IDENTIFIER ::= { snFastIronStackFCX 2}   --FCX Base L3 router
  snFastIronStackFCXRouter      OBJECT IDENTIFIER ::= { snFastIronStackFCX 3}           --FCX Premium Router
  snFastIronStackFCXAdvRouter      OBJECT IDENTIFIER ::= { snFastIronStackFCX 4}           --FCX Advanced Router (BGP)

  snFastIronStackICX6610               OBJECT IDENTIFIER ::= { snFastIronStackFamily 3 } 
  snFastIronStackICX6610Switch      OBJECT IDENTIFIER ::= { snFastIronStackICX6610 1}        -- ICX6610 switch
  snFastIronStackICX6610BaseL3Router      OBJECT IDENTIFIER ::= { snFastIronStackICX6610 2}   --ICX6610 Base L3 router
  snFastIronStackICX6610Router      OBJECT IDENTIFIER ::= { snFastIronStackICX6610 3}           --ICX6610 Base Router
  snFastIronStackICX6610PRouter      OBJECT IDENTIFIER ::= { snFastIronStackICX6610 4}           --ICX6610 Premium Router
  snFastIronStackICX6610ARouter      OBJECT IDENTIFIER ::= { snFastIronStackICX6610 5}           --ICX6610 Advanced Router

  snFastIronStackICX6430     OBJECT IDENTIFIER ::= { snFastIronStackFamily 4 }
  snFastIronStackICX6430Switch      OBJECT IDENTIFIER ::= { snFastIronStackICX6430 1}        -- ICX6430 switch

  snFastIronStackICX6450     OBJECT IDENTIFIER ::= { snFastIronStackFamily 5 }
  snFastIronStackICX6450Switch      OBJECT IDENTIFIER ::= { snFastIronStackICX6450 1}               -- ICX6450 switch
  snFastIronStackICX6450BaseL3Router      OBJECT IDENTIFIER ::= { snFastIronStackICX6450 2}    --ICX6450 Base L3 router
  snFastIronStackICX6450Router      OBJECT IDENTIFIER ::= { snFastIronStackICX6450 3}               -- ICX6450 Router
  snFastIronStackICX6450PRouter     OBJECT IDENTIFIER ::= { snFastIronStackICX6450 4}              -- ICX6450 Premium Router

  snFastIronStackMixedStack     OBJECT IDENTIFIER ::= { snFastIronStackFamily 6 }
  snFastIronStackMixedStackSwitch      OBJECT IDENTIFIER ::= { snFastIronStackMixedStack     1}               -- FastIron MixedStack switch
  snFastIronStackMixedStackBaseL3Router      OBJECT IDENTIFIER ::= { snFastIronStackMixedStack 2}    --FastIron MixedStack Base L3 router
  snFastIronStackMixedStackRouter      OBJECT IDENTIFIER ::= { snFastIronStackMixedStack 3}               -- FastIron MixedStack Router
  snFastIronStackMixedStackPRouter     OBJECT IDENTIFIER ::= { snFastIronStackMixedStack 4}              -- FastIron MixedStack Premium Router
  snFastIronStackMixedStackARouter      OBJECT IDENTIFIER ::= { snFastIronStackMixedStack 5}           --FastIronMixedStack Advanced Router

  snFastIronStackICX7750     OBJECT IDENTIFIER ::= { snFastIronStackFamily 7 }
  snFastIronStackICX7750Switch      OBJECT IDENTIFIER ::= { snFastIronStackICX7750 1}          -- ICX7750 switch
  snFastIronStackICX7750BaseL3Router      OBJECT IDENTIFIER ::= { snFastIronStackICX7750 2}    -- ICX7750 Base L3 router
  snFastIronStackICX7750Router      OBJECT IDENTIFIER ::= { snFastIronStackICX7750 3}          -- ICX7750 Router

  snFastIronStackICX7450     OBJECT IDENTIFIER ::= { snFastIronStackFamily 8 }
  snFastIronStackICX7450Switch      OBJECT IDENTIFIER ::= { snFastIronStackICX7450 1}          -- ICX7450 switch
  snFastIronStackICX7450BaseL3Router      OBJECT IDENTIFIER ::= { snFastIronStackICX7450 2}    -- ICX7450 Base L3 router
  snFastIronStackICX7450Router      OBJECT IDENTIFIER ::= { snFastIronStackICX7450 3}          -- ICX7450 Router

  snFastIronStackICX7250     OBJECT IDENTIFIER ::= { snFastIronStackFamily 9 }
  snFastIronStackICX7250Switch      OBJECT IDENTIFIER ::= { snFastIronStackICX7250 1}          -- ICX750 switch
  snFastIronStackICX7250BaseL3Router      OBJECT IDENTIFIER ::= { snFastIronStackICX7250 2}    -- ICX7250 Base L3 router
  snFastIronStackICX7250Router      OBJECT IDENTIFIER ::= { snFastIronStackICX7250 3}          -- ICX7250 Router

-- NetIron Carrier Ethernet Switch (CES) product line
snCes2000Family  OBJECT IDENTIFIER ::= { registration 49 }  

 snCes2024F OBJECT IDENTIFIER ::= { snCes2000Family  1 }   -- 24X1G fiber 
 snCes2024C OBJECT IDENTIFIER ::= { snCes2000Family  2 }  --  24X1G copper 
 snCes2048F OBJECT IDENTIFIER ::= { snCes2000Family  3 }  --  48X1G fiber 
 snCes2048C OBJECT IDENTIFIER ::= { snCes2000Family  4 }  -- 48X1G copper
 snCes2048FX OBJECT IDENTIFIER ::= { snCes2000Family  5 }  -- 48X1G fiber + 2X10G 
 snCes2048CX OBJECT IDENTIFIER ::= { snCes2000Family  6 }  -- 48X1G copper + 2X10G

  snFLSLCFamily          OBJECT IDENTIFIER ::= { registration 50 }       -- FastIron LSLC series family
  snFLSLC624Family       OBJECT IDENTIFIER ::= { snFLSLCFamily 1 }

  snFLSLC624BaseFamily  OBJECT IDENTIFIER ::= { snFLSLC624Family 1 }
  snFLSLC624            OBJECT IDENTIFIER ::= { snFLSLC624BaseFamily 1 }  -- FastIron LSLC Switch(FLSLC) 24-port 10/100/1000 POE Ready
  snFLSLC624Switch      OBJECT IDENTIFIER ::= { snFLSLC624 1 }            -- FLSLC624 switch
  snFLSLC624Router      OBJECT IDENTIFIER ::= { snFLSLC624 2 }            -- FLSLC624 router

  snFLSLC624POEFamily   OBJECT IDENTIFIER ::= { snFLSLC624Family 2 }
  snFLSLC624POE         OBJECT IDENTIFIER ::= { snFLSLC624POEFamily 1 }   -- FastIron LSLC Switch(FLSLC) 24-port 10/100/1000 POE 
  snFLSLC624POESwitch   OBJECT IDENTIFIER ::= { snFLSLC624POE 1 }         -- snFLSLC624-POE switch
  snFLSLC624POERouter   OBJECT IDENTIFIER ::= { snFLSLC624POE 2 }         -- snFLSLC624-POE router


  snFLSLC648Family       OBJECT IDENTIFIER ::= { snFLSLCFamily 2 }

  snFLSLC648BaseFamily  OBJECT IDENTIFIER ::= { snFLSLC648Family 1 }
  snFLSLC648            OBJECT IDENTIFIER ::= { snFLSLC648BaseFamily 1 }  -- FastIron LSLC Switch(FLSLC) 48-port 10/100/1000 POE Ready
  snFLSLC648Switch      OBJECT IDENTIFIER ::= { snFLSLC648 1 }            -- FLSLC648 switch
  snFLSLC648Router      OBJECT IDENTIFIER ::= { snFLSLC648 2 }            -- FLSLC648 router

  snFLSLC648POEFamily   OBJECT IDENTIFIER ::= { snFLSLC648Family 2 }
  snFLSLC648POE         OBJECT IDENTIFIER ::= { snFLSLC648POEFamily 1 }   -- FastIron LSLC Switch(FLSLC) 48-port 10/100/1000 POE 
  snFLSLC648POESwitch   OBJECT IDENTIFIER ::= { snFLSLC648POE 1 }         -- snFLSLC648-POE switch
  snFLSLC648POERouter   OBJECT IDENTIFIER ::= { snFLSLC648POE 2 }         -- snFLSLC648-POE router

-- NetIron Carrier Ethernet Router (CER) product line
snCer2000Family  OBJECT IDENTIFIER ::= { registration 51 }  

 snCer2024F OBJECT IDENTIFIER ::= { snCer2000Family  1 }   -- 24X1G fiber 
 snCer2024C OBJECT IDENTIFIER ::= { snCer2000Family  2 }  --  24X1G copper 
 snCer2048F OBJECT IDENTIFIER ::= { snCer2000Family  3 }  --  48X1G fiber 
 snCer2048C OBJECT IDENTIFIER ::= { snCer2000Family  4 }  -- 48X1G copper
 snCer2048FX OBJECT IDENTIFIER ::= { snCer2000Family  5 }  -- 48X1G fiber + 2X10G 
 snCer2048CX OBJECT IDENTIFIER ::= { snCer2000Family  6 }  -- 48X1G copper + 2X10G

  snFWSFamily          OBJECT IDENTIFIER ::= { registration 52 }	-- FastIron WS series family
  snFWS624Family       OBJECT IDENTIFIER ::= { snFWSFamily 1 }

  snFWS624BaseFamily  OBJECT IDENTIFIER ::= { snFWS624Family 1 }
  snFWS624            OBJECT IDENTIFIER ::= { snFWS624BaseFamily 1 }  -- FastIron WS Switch(FWS) 24-port 10/100 
  snFWS624Switch      OBJECT IDENTIFIER ::= { snFWS624 1 }            -- FWS624 switch
  snFWS624BaseL3Router      OBJECT IDENTIFIER ::= { snFWS624 2 }            -- FWS624 Base L3 router
  snFWS624EdgePremRouter      OBJECT IDENTIFIER ::= { snFWS624 3 }            -- FWS624 Edge Prem router

  snFWS624GFamily  OBJECT IDENTIFIER ::= { snFWS624Family 2 }
  snFWS624G            OBJECT IDENTIFIER ::= { snFWS624GFamily 1 }  -- FastIron WS Switch(FWS) 24-port 10/100/1000 
  snFWS624GSwitch      OBJECT IDENTIFIER ::= { snFWS624G 1 }            -- FWS624G switch
  snFWS624GBaseL3Router      OBJECT IDENTIFIER ::= { snFWS624G 2 }            -- FWS624G Base L3 router
  snFWS624GEdgePremRouter      OBJECT IDENTIFIER ::= { snFWS624G 3 }            -- FWS624G Edge Prem router

  snFWS624POEFamily  OBJECT IDENTIFIER ::= { snFWS624Family 3 }
  snFWS624POE            OBJECT IDENTIFIER ::= { snFWS624POEFamily 1 }  -- FastIron WS Switch(FWS) 24-port 10/100 POE 
  snFWS624POESwitch      OBJECT IDENTIFIER ::= { snFWS624POE 1 }            -- FWS624-POE switch 
  snFWS624POEBaseL3Router      OBJECT IDENTIFIER ::= { snFWS624POE 2 }            -- FWS624-POE Base L3 router
  snFWS624POEEdgePremRouter      OBJECT IDENTIFIER ::= { snFWS624POE 3 }            -- FWS624-POE Edge Prem router

  snFWS624GPOEFamily  OBJECT IDENTIFIER ::= { snFWS624Family 4 }
  snFWS624GPOE            OBJECT IDENTIFIER ::= { snFWS624GPOEFamily 1 }  -- FastIron WS Switch(FWS) 24-port 10/100/1000 POE 
  snFWS624GPOESwitch      OBJECT IDENTIFIER ::= { snFWS624GPOE 1 }            -- FWS624G-POE switch
  snFWS624GPOEBaseL3Router      OBJECT IDENTIFIER ::= { snFWS624GPOE 2 }            -- FWS624G-POE Base L3 router
  snFWS624GPOEEdgePremRouter      OBJECT IDENTIFIER ::= { snFWS624GPOE 3 }            -- FWS624G-POE Edge Prem router

  snFWS648Family       OBJECT IDENTIFIER ::= { snFWSFamily 2 }

  snFWS648BaseFamily  OBJECT IDENTIFIER ::= { snFWS648Family 1 }
  snFWS648            OBJECT IDENTIFIER ::= { snFWS648BaseFamily 1 }  -- FastIron WS Switch(FWS) 48-port 10/100 POE Ready
  snFWS648Switch      OBJECT IDENTIFIER ::= { snFWS648 1 }            -- FWS648 switch
  snFWS648BaseL3Router      OBJECT IDENTIFIER ::= { snFWS648 2 }            -- FWS648 Base L3 router
  snFWS648EdgePremRouter      OBJECT IDENTIFIER ::= { snFWS648 3 }            -- FWS648 Edge Prem router

  snFWS648GFamily  OBJECT IDENTIFIER ::= { snFWS648Family 2 }
  snFWS648G            OBJECT IDENTIFIER ::= { snFWS648GFamily 1 }  -- FastIron WS Switch(FWS) 48-port 10/100/1000 POE Ready
  snFWS648GSwitch      OBJECT IDENTIFIER ::= { snFWS648G 1 }            -- FWS648G switch
  snFWS648GBaseL3Router      OBJECT IDENTIFIER ::= { snFWS648G 2 }            -- FWS648G Base L3 router
  snFWS648GEdgePremRouter      OBJECT IDENTIFIER ::= { snFWS648G 3 }            -- FWS648G Edge Prem router

  snFWS648POEFamily  OBJECT IDENTIFIER ::= { snFWS648Family 3 }
  snFWS648POE            OBJECT IDENTIFIER ::= { snFWS648POEFamily 1 }  -- FastIron WS Switch(FWS) 48-port 10/100 POE
  snFWS648POESwitch      OBJECT IDENTIFIER ::= { snFWS648POE 1 }            -- FWS648-POE switch
  snFWS648POEBaseL3Router      OBJECT IDENTIFIER ::= { snFWS648POE 2 }            -- FWS648-POE Base L3 router
  snFWS648POEEdgePremRouter      OBJECT IDENTIFIER ::= { snFWS648POE 3 }            -- FWS648-POE Edge Prem router

  snFWS648GPOEFamily  OBJECT IDENTIFIER ::= { snFWS648Family 4 }
  snFWS648GPOE            OBJECT IDENTIFIER ::= { snFWS648GPOEFamily 1 }  -- FastIron WS Switch(FWS) 48-port 10/100/1000 POE 
  snFWS648GPOESwitch      OBJECT IDENTIFIER ::= { snFWS648GPOE 1 }            -- FWS648G-POE switch
  snFWS648GPOEBaseL3Router      OBJECT IDENTIFIER ::= { snFWS648GPOE 2 }            -- FWS648G-POE Base L3 router
  snFWS648GPOEEdgePremRouter      OBJECT IDENTIFIER ::= { snFWS648GPOE 3 }            -- FWS648G-POE Edge Prem router

  snTurboIron2    OBJECT IDENTIFIER ::= { registration 53 }    -- TurboIron(TOR) family
  snTI2X24Family  OBJECT IDENTIFIER ::= { snTurboIron2 1}      --TOR 24X
  snTI2X24Switch  OBJECT IDENTIFIER ::= { snTI2X24Family 1}    --TOR 24X switch
  snTI2X24Router  OBJECT IDENTIFIER ::= { snTI2X24Family 2}    --TOR 24X router
  snTI2X48Family  OBJECT IDENTIFIER ::= { snTurboIron2 2}      --TOR 48X
  snTI2X48Switch  OBJECT IDENTIFIER ::= { snTI2X48Family 1}    --TOR 48X switch
  snTI2X48Router  OBJECT IDENTIFIER ::= { snTI2X48Family 2}    --TOR 48X router


--FastIron CX (FCX) family
  snFCXFamily          OBJECT IDENTIFIER ::= { registration 54 }	-- FastIron CX series family
  snFCX624Family       OBJECT IDENTIFIER ::= { snFCXFamily 1 }

  snFCX624SBaseFamily  OBJECT IDENTIFIER ::= { snFCX624Family 1 }
  snFCX624S            OBJECT IDENTIFIER ::= { snFCX624SBaseFamily 1 }  -- FastIron CX Switch(FCX-S) 24-port 10/100/1000 
  snFCX624SSwitch      OBJECT IDENTIFIER ::= { snFCX624S 1 }            -- FCX624S switch
  snFCX624SBaseL3Router      OBJECT IDENTIFIER ::= { snFCX624S 2 }            -- FCX624S Base L3 router
  snFCX624SRouter      OBJECT IDENTIFIER ::= { snFCX624S 3 }            -- FCX624S Premium Router
  snFCX624SAdvRouter      OBJECT IDENTIFIER ::= { snFCX624S 4 }            -- FCX624S Advanced Premium Router (BGP)  

  snFCX624SHPOEFamily  OBJECT IDENTIFIER ::= { snFCX624Family 2 }
  snFCX624SHPOE            OBJECT IDENTIFIER ::= { snFCX624SHPOEFamily 1 }  -- FastIron CX Switch(FCX-S) 24-port 10/100/1000 HPOE 
  snFCX624SHPOESwitch      OBJECT IDENTIFIER ::= { snFCX624SHPOE 1 }            -- FCX624S-HPOE switch 
  snFCX624SHPOEBaseL3Router      OBJECT IDENTIFIER ::= { snFCX624SHPOE 2 }            -- FCX624S-HPOE Base L3 router
  snFCX624SHPOERouter      OBJECT IDENTIFIER ::= { snFCX624SHPOE 3 }            -- FCX624S-HPOE Premium Router
  snFCX624SHPOEAdvRouter      OBJECT IDENTIFIER ::= { snFCX624SHPOE 4 }            -- FCX624S-HPOE Advanced Premium Router (BGP)

  snFCX624SFFamily  OBJECT IDENTIFIER ::= { snFCX624Family 3 }
  snFCX624SF            OBJECT IDENTIFIER ::= { snFCX624SFFamily 1 }  -- FastIron CX Switch(FCX-SF) 24-port 10/100/1000 
  snFCX624SFSwitch      OBJECT IDENTIFIER ::= { snFCX624SF 1 }            -- FCX624SF switch 
  snFCX624SFBaseL3Router      OBJECT IDENTIFIER ::= { snFCX624SF 2 }            -- FCX624SF Base L3 router
  snFCX624SFRouter      OBJECT IDENTIFIER ::= { snFCX624SF 3 }            -- FCX624SF Premium Router
  snFCX624SFAdvRouter      OBJECT IDENTIFIER ::= { snFCX624SF 4 }      -- FCX624SF Advanced Premium Router (BGP)  

  snFCX624BaseFamily  OBJECT IDENTIFIER ::= { snFCX624Family 4 }
  snFCX624            OBJECT IDENTIFIER ::= { snFCX624BaseFamily 1 }  -- FastIron CX Switch(FCX) 24-port 10/100/1000 
  snFCX624Switch      OBJECT IDENTIFIER ::= { snFCX624 1 }            -- FCX624 switch
  snFCX624BaseL3Router      OBJECT IDENTIFIER ::= { snFCX624 2 }            -- FCX624 Base L3 router
  snFCX624Router      OBJECT IDENTIFIER ::= { snFCX624 3 }            -- FCX624 Premium Router
  snFCX624AdvRouter      OBJECT IDENTIFIER ::= { snFCX624 4 }            -- FCX624 Advanced Premium Router (BGP)  

  snFCX648Family       OBJECT IDENTIFIER ::= { snFCXFamily 2 }

  snFCX648SBaseFamily  OBJECT IDENTIFIER ::= { snFCX648Family 1 }
  snFCX648S            OBJECT IDENTIFIER ::= { snFCX648SBaseFamily 1 }  -- FastIron CX Switch(FCX-S) 48-port 10/100/1000 
  snFCX648SSwitch      OBJECT IDENTIFIER ::= { snFCX648S 1 }            -- FCX648S switch
  snFCX648SBaseL3Router      OBJECT IDENTIFIER ::= { snFCX648S 2 }            -- FCX648S Base L3 router
  snFCX648SRouter      OBJECT IDENTIFIER ::= { snFCX648S 3 }            -- FCX648S Premium Router
  snFCX648SAdvRouter      OBJECT IDENTIFIER ::= { snFCX648S 4 }            -- FCX648S Advanced Premium Router (BGP)

  snFCX648SHPOEFamily  OBJECT IDENTIFIER ::= { snFCX648Family 2 }
  snFCX648SHPOE            OBJECT IDENTIFIER ::= { snFCX648SHPOEFamily 1 }  -- FastIron CX Switch(FCX-S) 48-port 10/100/1000 HPOE
  snFCX648SHPOESwitch      OBJECT IDENTIFIER ::= { snFCX648SHPOE 1 }            -- FCX648S-HPOE switch
  snFCX648SHPOEBaseL3Router      OBJECT IDENTIFIER ::= { snFCX648SHPOE 2 }            -- FCX648S-HPOE Base L3 router
  snFCX648SHPOERouter      OBJECT IDENTIFIER ::= { snFCX648SHPOE 3 }            -- FCX648S-HPOE Premium Router
  snFCX648SHPOEAdvRouter      OBJECT IDENTIFIER ::= { snFCX648SHPOE 4 }            -- FCX648S-HPOE Advanced Premium Router (BGP)

-- snFCX648SFFamily  OBJECT IDENTIFIER ::= { snFCX648Family 3 }    reserve for FastIron CX Switch(FCX-SF) 48-port 10/100/1000 
  
  snFCX648BaseFamily  OBJECT IDENTIFIER ::= { snFCX648Family 4 }
  snFCX648            OBJECT IDENTIFIER ::= { snFCX648BaseFamily 1 }  -- FastIron CX Switch(FCX) 48-port 10/100/1000 
  snFCX648Switch      OBJECT IDENTIFIER ::= { snFCX648 1 }            -- FCX648 switch
  snFCX648BaseL3Router      OBJECT IDENTIFIER ::= { snFCX648 2 }            -- FCX648 Base L3 router
  snFCX648Router      OBJECT IDENTIFIER ::= { snFCX648 3 }            -- FCX648 Premium Router
  snFCX648AdvRouter      OBJECT IDENTIFIER ::= { snFCX648 4 }            -- FCX648 Advanced Premium Router (BGP)


--FastIron CX 6610 (ICX6610) family
  snICX6610Family          OBJECT IDENTIFIER ::= { registration 56}	-- FastIron CX 6610 series family

  snICX661024Family       OBJECT IDENTIFIER ::= { snICX6610Family 1 }

  snICX661024BaseFamily  OBJECT IDENTIFIER ::= { snICX661024Family 1 }
  snICX661024            OBJECT IDENTIFIER ::= { snICX661024BaseFamily 1 }  -- FastIron CX 6610 Switch(ICX6610) 24-port  
  snICX661024Switch      OBJECT IDENTIFIER ::= { snICX661024 1 }            -- ICX661024 switch
  snICX661024BaseL3Router      OBJECT IDENTIFIER ::= { snICX661024 2 }            -- ICX661024 Base L3 router
  snICX661024Router      OBJECT IDENTIFIER ::= { snICX661024 3 }            -- ICX661024 Base Router
  snICX661024PRouter      OBJECT IDENTIFIER ::= { snICX661024 4 }            -- ICX661024 Premium Router  
  snICX661024ARouter      OBJECT IDENTIFIER ::= { snICX661024 5 }            -- ICX661024 Advanced Router 

  snICX661024HPOEFamily  OBJECT IDENTIFIER ::= { snICX661024Family 2 }
  snICX661024HPOE            OBJECT IDENTIFIER ::= { snICX661024HPOEFamily 1 }  -- FastIron CX 6610 Switch(ICX6610) 24-port HPOE 
  snICX661024HPOESwitch      OBJECT IDENTIFIER ::= { snICX661024HPOE 1 }            -- ICX661024-HPOE switch 
  snICX661024HPOEBaseL3Router      OBJECT IDENTIFIER ::= { snICX661024HPOE 2 }            -- ICX661024-HPOE Base L3 router
  snICX661024HPOERouter      OBJECT IDENTIFIER ::= { snICX661024HPOE 3 }            -- ICX661024-HPOE Base Router
  snICX661024HPOEPRouter      OBJECT IDENTIFIER ::= { snICX661024HPOE 4 }            -- ICX661024-HPOE Premium Router 
  snICX661024HPOEARouter      OBJECT IDENTIFIER ::= { snICX661024HPOE 5 }            -- ICX661024-HPOE Advanced Router 

  snICX661024FFamily  OBJECT IDENTIFIER ::= { snICX661024Family 3 }
  snICX661024F            OBJECT IDENTIFIER ::= { snICX661024FFamily 1 }  -- FastIron CX Switch(ICX6610-F) 24-port fiber
  snICX661024FSwitch      OBJECT IDENTIFIER ::= { snICX661024F 1 }            -- ICX661024F switch 
  snICX661024FBaseL3Router      OBJECT IDENTIFIER ::= { snICX661024F 2 }            -- ICX661024F Base L3 router
  snICX661024FRouter      OBJECT IDENTIFIER ::= { snICX661024F 3 }            -- ICX661024F Base Router
  snICX661024FPRouter      OBJECT IDENTIFIER ::= { snICX661024F 4 }      -- ICX661024F Premium Router 
  snICX661024FARouter      OBJECT IDENTIFIER ::= { snICX661024F 5 }      -- ICX661024F Advanced Router  

  snICX661048Family       OBJECT IDENTIFIER ::= { snICX6610Family 2 }

  snICX661048BaseFamily  OBJECT IDENTIFIER ::= { snICX661048Family 1 }
  snICX661048            OBJECT IDENTIFIER ::= { snICX661048BaseFamily 1 }  -- FastIron CX Switch(ICX6610) 48-port 
  snICX661048Switch      OBJECT IDENTIFIER ::= { snICX661048 1 }            -- ICX661048 switch
  snICX661048BaseL3Router      OBJECT IDENTIFIER ::= { snICX661048 2 }            -- ICX661048 Base L3 router
  snICX661048Router      OBJECT IDENTIFIER ::= { snICX661048 3 }            -- ICX661048 Base Router
  snICX661048PRouter      OBJECT IDENTIFIER ::= { snICX661048 4 }            -- ICX661048 Premium Router
  snICX661048ARouter      OBJECT IDENTIFIER ::= { snICX661048 5}            -- ICX661048 Advanced Router 

  snICX661048HPOEFamily  OBJECT IDENTIFIER ::= { snICX661048Family 2 }
  snICX661048HPOE            OBJECT IDENTIFIER ::= { snICX661048HPOEFamily 1 }  -- FastIron CX Switch(ICX6610) 48-port HPOE
  snICX661048HPOESwitch      OBJECT IDENTIFIER ::= { snICX661048HPOE 1 }            -- ICX661048-HPOE switch
  snICX661048HPOEBaseL3Router      OBJECT IDENTIFIER ::= { snICX661048HPOE 2 }            -- ICX661048-HPOE Base L3 router
  snICX661048HPOERouter      OBJECT IDENTIFIER ::= { snICX661048HPOE 3 }            -- ICX661048-HPOE Base Router
  snICX661048HPOEPRouter      OBJECT IDENTIFIER ::= { snICX661048HPOE 4 }            -- ICX661048-HPOE Premium Router 
  snICX661048HPOEARouter      OBJECT IDENTIFIER ::= { snICX661048HPOE 5 }            -- ICX661048-HPOE Advanced Router 


--FastIron CX 6430 (ICX6430) family
  snICX6430Family          OBJECT IDENTIFIER ::= { registration 57}	-- FastIron CX 6430 series family

  snICX643024Family       OBJECT IDENTIFIER ::= { snICX6430Family 1 }

  snICX643024BaseFamily  OBJECT IDENTIFIER ::= { snICX643024Family 1 }
  snICX643024            OBJECT IDENTIFIER ::= { snICX643024BaseFamily 1 }   -- ICX6430 24-port  10/100/1G w/4x1G
  snICX643024Switch      OBJECT IDENTIFIER ::= { snICX643024 1 }                -- ICX643024 switch
  
  snICX643024HPOEFamily  OBJECT IDENTIFIER ::= { snICX643024Family 2 }
  snICX643024HPOE            OBJECT IDENTIFIER ::= { snICX643024HPOEFamily 1 }    -- ICX6430 24-port HPOE 10/100/1G w/4x1G
  snICX643024HPOESwitch      OBJECT IDENTIFIER ::= { snICX643024HPOE 1 }          -- ICX643024-HPOE switch 


  snICX643048Family       OBJECT IDENTIFIER ::= { snICX6430Family 2 }

  snICX643048BaseFamily  OBJECT IDENTIFIER ::= { snICX643048Family 1 }
  snICX643048            OBJECT IDENTIFIER ::= { snICX643048BaseFamily 1 }  -- ICX6430 48-port  10/100/1G w/4x1G
  snICX643048Switch      OBJECT IDENTIFIER ::= { snICX643048 1 }               -- ICX643048 switch

  snICX643048HPOEFamily  OBJECT IDENTIFIER ::= { snICX643048Family 2 }
  snICX643048HPOE            OBJECT IDENTIFIER ::= { snICX643048HPOEFamily 1 }      -- ICX6430 48-port HPOE 10/100/1G w/4x1G
  snICX643048HPOESwitch      OBJECT IDENTIFIER ::= { snICX643048HPOE 1 }            -- ICX643048-HPOE switch


  snICX6430C12Family       OBJECT IDENTIFIER ::= { snICX6430Family 3 }  

  snICX6430C12BaseFamily  OBJECT IDENTIFIER ::= { snICX6430C12Family 1 }
  snICX6430C12            OBJECT IDENTIFIER ::= { snICX6430C12BaseFamily 1 }   -- ICX6430C 12-port  10/100/1G
  snICX6430C12Switch      OBJECT IDENTIFIER ::= { snICX6430C12 1 }                -- ICX6430C12 switch


--FastIron CX 6450 (ICX6450) family
  snICX6450Family          OBJECT IDENTIFIER ::= { registration 58}	-- FastIron CX 6450 series family

  snICX645024Family       OBJECT IDENTIFIER ::= { snICX6450Family 1 }

  snICX645024BaseFamily  OBJECT IDENTIFIER ::= { snICX645024Family 1 }
  snICX645024            OBJECT IDENTIFIER ::= { snICX645024BaseFamily 1 }     -- ICX6450 24-port  10/100/1G w/4x1/10G
  snICX645024Switch      OBJECT IDENTIFIER ::= { snICX645024 1 }                  -- ICX645024 switch
  snICX645024BaseL3Router      OBJECT IDENTIFIER ::= { snICX645024 2 }      -- ICX645024 Base L3 router
  snICX645024Router      OBJECT IDENTIFIER ::= { snICX645024 3 }                  -- ICX645024 Base Router
  snICX645024PRouter      OBJECT IDENTIFIER ::= { snICX645024 4 }                -- ICX645024 Premium Router  
  
  snICX645024HPOEFamily  OBJECT IDENTIFIER ::= { snICX645024Family 2 }
  snICX645024HPOE            OBJECT IDENTIFIER ::= { snICX645024HPOEFamily 1 }           --ICX6450 24-port HPOE 10/100/1G w/4x1/10G
  snICX645024HPOESwitch      OBJECT IDENTIFIER ::= { snICX645024HPOE 1 }                 -- ICX645024-HPOE switch 
  snICX645024HPOEBaseL3Router      OBJECT IDENTIFIER ::= { snICX645024HPOE 2 }     -- ICX645024-HPOE Base L3 router
  snICX645024HPOERouter      OBJECT IDENTIFIER ::= { snICX645024HPOE 3 }                 -- ICX645024-HPOE Base Router
  snICX645024HPOEPRouter      OBJECT IDENTIFIER ::= { snICX645024HPOE 4 }               -- ICX645024-HPOE Premium Router 

  snICX645048Family       OBJECT IDENTIFIER ::= { snICX6450Family 2 }

  snICX645048BaseFamily  OBJECT IDENTIFIER ::= { snICX645048Family 1 }
  snICX645048            OBJECT IDENTIFIER ::= { snICX645048BaseFamily 1 }      -- ICX6450 48-port 10/100/1G w/4x1/10G
  snICX645048Switch      OBJECT IDENTIFIER ::= { snICX645048 1 }                   -- ICX645048 switch
  snICX645048BaseL3Router      OBJECT IDENTIFIER ::= { snICX645048 2 }       -- ICX645048 Base L3 router
  snICX645048Router      OBJECT IDENTIFIER ::= { snICX645048 3 }                   -- ICX645048 Base Router
  snICX645048PRouter      OBJECT IDENTIFIER ::= { snICX645048 4 }                  -- ICX645048 Premium Router

  snICX645048HPOEFamily  OBJECT IDENTIFIER ::= { snICX645048Family 2 }
  snICX645048HPOE            OBJECT IDENTIFIER ::= { snICX645048HPOEFamily 1 }            -- ICX6450 48-port HPOE 10/100/1G w/4x1/10G
  snICX645048HPOESwitch      OBJECT IDENTIFIER ::= { snICX645048HPOE 1 }                 -- ICX645048-HPOE switch
  snICX645048HPOEBaseL3Router      OBJECT IDENTIFIER ::= { snICX645048HPOE 2 }     -- ICX645048-HPOE Base L3 router
  snICX645048HPOERouter      OBJECT IDENTIFIER ::= { snICX645048HPOE 3 }                 -- ICX645048-HPOE Base Router
  snICX645048HPOEPRouter      OBJECT IDENTIFIER ::= { snICX645048HPOE 4 }               -- ICX645048-HPOE Premium Router 

  snICX6450C12PDFamily       OBJECT IDENTIFIER ::= { snICX6450Family 3 }  

  snICX6450C12PDBaseFamily  OBJECT IDENTIFIER ::= { snICX6450C12PDFamily 1 }
  snICX6450C12PD            OBJECT IDENTIFIER ::= { snICX6450C12PDBaseFamily 1 }   -- ICX6450C 12-port PD  10/100/1G
  snICX6450C12PDSwitch      OBJECT IDENTIFIER ::= { snICX6450C12PD 1 }                -- ICX6450C12-PD switch
  snICX6450C12PDBaseL3Router      OBJECT IDENTIFIER ::= { snICX6450C12PD 2 }                -- ICX6450C12-PD Base L3 router
  snICX6450C12PDRouter      OBJECT IDENTIFIER ::= { snICX6450C12PD 3 }                -- ICX6450C12-PD Base router
  snICX6450C12PDPRouter      OBJECT IDENTIFIER ::= { snICX6450C12PD 4 }                -- ICX6450C12-PD Premium router


--FastIron Brocade ICX 6650 (ICX6650) family
  snICX6650Family          OBJECT IDENTIFIER ::= { registration 59}               -- FastIron Brocade ICX 6650 series family

  snICX665064Family       OBJECT IDENTIFIER ::= { snICX6650Family 1 }

  snICX665064BaseFamily  OBJECT IDENTIFIER ::= { snICX665064Family 1 }
  snICX665064            OBJECT IDENTIFIER ::= { snICX665064BaseFamily 1 }     -- ICX6650 64-port  10G w/4x40G
  snICX665064Switch      OBJECT IDENTIFIER ::= { snICX665064 1 }                   -- ICX6650 64-port Switch
  snICX665064BaseL3Router      OBJECT IDENTIFIER ::= { snICX665064 2 }      -- ICX6650 64-port Base L3 router
  snICX665064Router      OBJECT IDENTIFIER ::= { snICX665064 3 }                  -- ICX6650 64-port Router


--FastIron Brocade ICX 7750 (ICX7750) family
  snICX7750Family          OBJECT IDENTIFIER ::= { registration 60}               -- FastIron Brocade ICX 7750 series family

  snICX775048CFamily       OBJECT IDENTIFIER ::= { snICX7750Family 1 }

  snICX775048CBaseFamily     OBJECT IDENTIFIER ::= { snICX775048CFamily 1 }
  snICX775048C               OBJECT IDENTIFIER ::= { snICX775048CBaseFamily 1 }    -- ICX775048C 48-port FE/GE/10GE RJ-45 w/12x40G
  snICX775048CSwitch         OBJECT IDENTIFIER ::= { snICX775048C 1 }              -- ICX775048C 48-port Switch
  snICX775048CBaseL3Router   OBJECT IDENTIFIER ::= { snICX775048C 2 }              -- ICX775048C 48-port Base L3 router
  snICX775048CRouter         OBJECT IDENTIFIER ::= { snICX775048C 3 }              -- ICX775048C 48-port Router

  snICX775048FFamily       OBJECT IDENTIFIER ::= { snICX7750Family 2 }

  snICX775048FBaseFamily     OBJECT IDENTIFIER ::= { snICX775048FFamily 1 }
  snICX775048F               OBJECT IDENTIFIER ::= { snICX775048FBaseFamily 1 }    -- ICX775048F 48-port GE/10GE SFP+ w/12x40G
  snICX775048FSwitch         OBJECT IDENTIFIER ::= { snICX775048F 1 }              -- ICX775048F 48-port Switch
  snICX775048FBaseL3Router   OBJECT IDENTIFIER ::= { snICX775048F 2 }              -- ICX775048F 48-port Base L3 router
  snICX775048FRouter         OBJECT IDENTIFIER ::= { snICX775048F 3 }              -- ICX775048F 48-port Router

  snICX775026QFamily       OBJECT IDENTIFIER ::= { snICX7750Family 3 }

  snICX775026QBaseFamily     OBJECT IDENTIFIER ::= { snICX775026QFamily 1 }
  snICX775026Q               OBJECT IDENTIFIER ::= { snICX775026QBaseFamily 1 }    -- ICX775026Q 26-port 40G QSFP w/6x40G
  snICX775026QSwitch         OBJECT IDENTIFIER ::= { snICX775026Q 1 }              -- ICX775026Q 26-port Switch
  snICX775026QBaseL3Router   OBJECT IDENTIFIER ::= { snICX775026Q 2 }              -- ICX775026Q 26-port Base L3 router
  snICX775026QRouter         OBJECT IDENTIFIER ::= { snICX775026Q 3 }              -- ICX775026Q 26-port Router


--FastIron Brocade ICX 7450 (ICX7450) family
  snICX7450Family           OBJECT IDENTIFIER ::= { registration 61}               -- FastIron Brocade ICX 7450 series family

  snICX745024Family         OBJECT IDENTIFIER ::= { snICX7450Family 1 }

  snICX745024BaseFamily     OBJECT IDENTIFIER ::= { snICX745024Family 1 }
  snICX745024               OBJECT IDENTIFIER ::= { snICX745024BaseFamily 1 }    -- ICX7450 24-port 1G
  snICX745024Switch         OBJECT IDENTIFIER ::= { snICX745024 1 }              -- ICX745024 switch
  snICX745024BaseL3Router   OBJECT IDENTIFIER ::= { snICX745024 2 }              -- ICX745024 Base L3 router
  snICX745024Router         OBJECT IDENTIFIER ::= { snICX745024 3 }              -- ICX745024 Router
 
  snICX745024HPOEFamily       OBJECT IDENTIFIER ::= { snICX745024Family 2 }
  snICX745024HPOE             OBJECT IDENTIFIER ::= { snICX745024HPOEFamily 1 }  -- ICX7450-HPOE 24-port POE+ 1G 
  snICX745024HPOESwitch       OBJECT IDENTIFIER ::= { snICX745024HPOE 1 }        -- ICX745024-HPOE switch 
  snICX745024HPOEBaseL3Router OBJECT IDENTIFIER ::= { snICX745024HPOE 2 }        -- ICX745024-HPOE Base L3 router
  snICX745024HPOERouter       OBJECT IDENTIFIER ::= { snICX745024HPOE 3 }        -- ICX745024-HPOE Base Router

  snICX745048Family       OBJECT IDENTIFIER ::= { snICX7450Family 2 }

  snICX745048BaseFamily    OBJECT IDENTIFIER ::= { snICX745048Family 1 }
  snICX745048              OBJECT IDENTIFIER ::= { snICX745048BaseFamily 1 }    -- ICX745048 48-port 1G
  snICX745048Switch        OBJECT IDENTIFIER ::= { snICX745048 1 }              -- ICX745048 48-port Switch
  snICX745048BaseL3Router  OBJECT IDENTIFIER ::= { snICX745048 2 }              -- ICX745048 48-port Base L3 router
  snICX745048Router        OBJECT IDENTIFIER ::= { snICX745048 3 }              -- ICX745048 48-port Router

  snICX745048HPOEBaseFamily   OBJECT IDENTIFIER ::= { snICX745048Family 2 }
  snICX745048HPOE             OBJECT IDENTIFIER ::= { snICX745048HPOEBaseFamily 1 }  -- ICX745048-HPOE 48-port POE+ 1G
  snICX745048HPOESwitch       OBJECT IDENTIFIER ::= { snICX745048HPOE 1 }            -- ICX745048-HPOE 48-port Switch
  snICX745048HPOEBaseL3Router OBJECT IDENTIFIER ::= { snICX745048HPOE 2 }            -- ICX745048-HPOE 48-port Base L3 router
  snICX745048HPOERouter       OBJECT IDENTIFIER ::= { snICX745048HPOE 3 }            -- ICX745048-HPOE 48-port Router

  snICX745048FBaseFamily    OBJECT IDENTIFIER ::= { snICX745048Family 3 }
  snICX745048F              OBJECT IDENTIFIER ::= { snICX745048FBaseFamily 1 }   -- ICX745048F 48-port SFP+ 1G 
  snICX745048FSwitch        OBJECT IDENTIFIER ::= { snICX745048F 1 }             -- ICX745048F 48-port Switch
  snICX745048FBaseL3Router  OBJECT IDENTIFIER ::= { snICX745048F 2 }             -- ICX745048F 48-port Base L3 router
  snICX745048FRouter        OBJECT IDENTIFIER ::= { snICX745048F 3 }             -- ICX745048F 48-port Router

  snICX745032Family       OBJECT IDENTIFIER ::= { snICX7450Family 3 }

  snICX745032ZPBaseFamily    OBJECT IDENTIFIER ::= { snICX745032Family 1 }
  snICX745032ZP              OBJECT IDENTIFIER ::= { snICX745032ZPBaseFamily 1 }    -- ICX745032ZP 24-port 1G + 8-port 2.5G
  snICX745032ZPSwitch        OBJECT IDENTIFIER ::= { snICX745032ZP 1 }              -- ICX745032ZP 32-port Switch
  snICX745032ZPBaseL3Router  OBJECT IDENTIFIER ::= { snICX745032ZP 2 }              -- ICX745032ZP 32-port Base L3 router
  snICX745032ZPRouter        OBJECT IDENTIFIER ::= { snICX745032ZP 3 }              -- ICX745032ZP 32-port Router
  
--FastIron Brocade ICX 7250 (ICX7250) family
  snICX7250Family           OBJECT IDENTIFIER ::= { registration 62}               -- FastIron Brocade ICX 7250 series family

  snICX725024Family         OBJECT IDENTIFIER ::= { snICX7250Family 1 }

  snICX725024BaseFamily     OBJECT IDENTIFIER ::= { snICX725024Family 1 }
  snICX725024               OBJECT IDENTIFIER ::= { snICX725024BaseFamily 1 }    -- ICX7250 24-port 1G
  snICX725024Switch         OBJECT IDENTIFIER ::= { snICX725024 1 }              -- ICX725024 switch
  snICX725024BaseL3Router   OBJECT IDENTIFIER ::= { snICX725024 2 }              -- ICX725024 Base L3 router
  snICX725024Router         OBJECT IDENTIFIER ::= { snICX725024 3 }              -- ICX725024 Router
 
  snICX725024HPOEFamily       OBJECT IDENTIFIER ::= { snICX725024Family 2 }
  snICX725024HPOE             OBJECT IDENTIFIER ::= { snICX725024HPOEFamily 1 }  -- ICX7250-HPOE 24-port POE+ 1G 
  snICX725024HPOESwitch       OBJECT IDENTIFIER ::= { snICX725024HPOE 1 }        -- ICX725024-HPOE switch 
  snICX725024HPOEBaseL3Router OBJECT IDENTIFIER ::= { snICX725024HPOE 2 }        -- ICX725024-HPOE Base L3 router
  snICX725024HPOERouter       OBJECT IDENTIFIER ::= { snICX725024HPOE 3 }        -- ICX725024-HPOE Base Router

  snICX725024GFamily     OBJECT IDENTIFIER ::= { snICX725024Family 3 }
  snICX725024G               OBJECT IDENTIFIER ::= { snICX725024GFamily 1 }      -- ICX7250G 24-port 1G
  snICX725024GSwitch         OBJECT IDENTIFIER ::= { snICX725024G 1 }            -- ICX725024G switch
  snICX725024GBaseL3Router   OBJECT IDENTIFIER ::= { snICX725024G 2 }            -- ICX725024G Base L3 router
  snICX725024GRouter         OBJECT IDENTIFIER ::= { snICX725024G 3 }            -- ICX725024G Router

  snICX725048Family       OBJECT IDENTIFIER ::= { snICX7250Family 2 }

  snICX725048BaseFamily    OBJECT IDENTIFIER ::= { snICX725048Family 1 }
  snICX725048              OBJECT IDENTIFIER ::= { snICX725048BaseFamily 1 }    -- ICX725048 48-port 1G
  snICX725048Switch        OBJECT IDENTIFIER ::= { snICX725048 1 }              -- ICX725048 48-port Switch
  snICX725048BaseL3Router  OBJECT IDENTIFIER ::= { snICX725048 2 }              -- ICX725048 48-port Base L3 router
  snICX725048Router        OBJECT IDENTIFIER ::= { snICX725048 3 }              -- ICX725048 48-port Router

  snICX725048HPOEBaseFamily   OBJECT IDENTIFIER ::= { snICX725048Family 2 }
  snICX725048HPOE             OBJECT IDENTIFIER ::= { snICX725048HPOEBaseFamily 1 }  -- ICX725048-HPOE 48-port POE+ 1G
  snICX725048HPOESwitch       OBJECT IDENTIFIER ::= { snICX725048HPOE 1 }            -- ICX725048-HPOE 48-port Switch
  snICX725048HPOEBaseL3Router OBJECT IDENTIFIER ::= { snICX725048HPOE 2 }            -- ICX725048-HPOE 48-port Base L3 router
  snICX725048HPOERouter       OBJECT IDENTIFIER ::= { snICX725048HPOE 3 }            -- ICX725048-HPOE 48-port Router

-- Brocade FastIron Switch Port Extender (SPX) family
  snFastIronSPXFamily      OBJECT IDENTIFIER ::= { registration 63 }	-- ICX 7750/7450 family
  
  snFastIronSPX            OBJECT IDENTIFIER ::= { snFastIronSPXFamily 1 } 
  snFastIronSPXSwitch      OBJECT IDENTIFIER ::= { snFastIronSPX 1}           --SPX switch
  snFastIronSPXRouter      OBJECT IDENTIFIER ::= { snFastIronSPX 2}           --SPX router

 
-- EdgeIron Stackable family
  edgeIron          OBJECT IDENTIFIER ::= { products 4 }
  edgeIronMib       OBJECT IDENTIFIER ::= { edgeIron 1 }  -- MIB root for EdgeIron family

-- EdgeIron Type 2 Stackable family
  edgeIronType2     OBJECT IDENTIFIER ::= { products 5 }
  edgeIronType2Mib  OBJECT IDENTIFIER ::= { edgeIronType2 1 } -- MIB root for EdgeIron type 2 family

-- IronPoint 200 family
  wirelessAp        OBJECT IDENTIFIER ::= { products 6 } -- wireless access point
  wirelessProbe     OBJECT IDENTIFIER ::= { products 7 } -- wireless probe

-- AccessIron family
  accessIron        OBJECT IDENTIFIER ::= { products 8 }

-- ServerIronSA family
  serverIronSA      OBJECT IDENTIFIER ::= { products 9 }

-- Wireless Application family
  wirelessApplication  OBJECT IDENTIFIER ::= { products 10 }
  wirelessLocation     OBJECT IDENTIFIER ::= { wirelessApplication 1 }
  
-- IronPoint Mobility family
  ironPointMobility  OBJECT IDENTIFIER ::= { products 11 } -- IronPoint Mobility Series
  ironPointMC        OBJECT IDENTIFIER ::= { ironPointMobility 1 } -- IronPoint Mobility Controller

-- NetIron MTU CPE family
  netIronMtuCpeFamily  OBJECT IDENTIFIER ::= { products 12 }
  netIronM2404         OBJECT IDENTIFIER ::= { netIronMtuCpeFamily 1 }

-- IronView family
  ironView             OBJECT IDENTIFIER ::= { products 13 }

-- main sub tree for new mib development
 platform		OBJECT IDENTIFIER ::= { products 14 }

-- IronPoint Wireless family
  ironPointWireless    OBJECT IDENTIFIER ::= { products 15 } -- IronPoint Wireless Series
  ironPointWirelessRFS OBJECT IDENTIFIER ::= { ironPointWireless 1 } -- IronPoint Wireless RF Switch
  ironPointWirelessAP  OBJECT IDENTIFIER ::= { ironPointWireless 2 } -- IronPoint Wireless Acess Point

-- VENDOR
  digitalChina      OBJECT IDENTIFIER ::= { vendors 1 }

  dcrs7504          OBJECT IDENTIFIER ::= { digitalChina 1 } -- DCRS-7504 family
  dcrs7504Switch    OBJECT IDENTIFIER ::= { dcrs7504 1 }     -- DCRS-7504 switch
  dcrs7504Router    OBJECT IDENTIFIER ::= { dcrs7504 2 }     -- DCRS-7504 router

  dcrs7508          OBJECT IDENTIFIER ::= { digitalChina 2 } -- DCRS-7508 family
  dcrs7508Switch    OBJECT IDENTIFIER ::= { dcrs7508 1 }     -- DCRS-7508 switch
  dcrs7508Router    OBJECT IDENTIFIER ::= { dcrs7508 2 }     -- DCRS-7508 router

  dcrs7515          OBJECT IDENTIFIER ::= { digitalChina 3 } -- DCRS-7515 family
  dcrs7515Switch    OBJECT IDENTIFIER ::= { dcrs7515 1 }     -- DCRS-7515 switch
  dcrs7515Router    OBJECT IDENTIFIER ::= { dcrs7515 2 }     -- DCRS-7515 router

-- Experimental mibs go here.
  experimental           OBJECT IDENTIFIER ::= { foundry 3 }
  pwe3           OBJECT IDENTIFIER ::= { experimental 1 }
  l3vpn           OBJECT IDENTIFIER ::= { experimental 2 }
  bfd            OBJECT IDENTIFIER ::= { experimental 3 }  -- IETF draft support for Bidirectional Fault Detection mib
  vplsRoot            OBJECT IDENTIFIER ::= { experimental 4 }  -- IETF draft support for VPLS
  bgp4V2Root     	OBJECT IDENTIFIER  ::=  { experimental 5 } -- IETF draft support for BGP4.

END
FOUNDRY-SN-AGENT-MIB DEFINITIONS ::= BEGIN

IMPORTS
	MODULE-IDENTITY, OBJECT-TYPE,TimeTicks, IpAddress, Counter32, Gauge32,Unsigned32,Integer32
		FROM SNMPv2-SMI
	TEXTUAL-CONVENTION, RowStatus
		FROM SNMPv2-TC
	InterfaceIndex
		FROM IF-MIB
	InetAddressType, InetAddress		
		FROM INET-ADDRESS-MIB		-- [RFC 4001]
	CounterBasedGauge64
		FROM HCNUM-TC
	EnabledStatus
		FROM P-BRIDGE-MIB
	snChassis, snAgentSys, snStack
		FROM FOUNDRY-SN-ROOT-MIB;

snAgent MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"        	
	REVISION     "200909300000Z" -- September 30, 2009
	DESCRIPTION
			"convert from SMIv1 to SMIv2"
   ::= { iso(1) org(3) dod(6) internet(1) private(4) enterprises(1) foundry(1991) 4}

		-- textual conventions

	MacAddress ::= TEXTUAL-CONVENTION
		STATUS	  current
		DESCRIPTION
			"
			   This data type is used to model media addresses.  For many
			   types of media, this will be in a binary representation.
			   For example, an ethernet address would be represented as
			   a string of 6 octets.			
			"
		SYNTAX	OCTET STRING (SIZE(6))        
		
	DisplayString ::= TEXTUAL-CONVENTION
		STATUS	  current
		DESCRIPTION
			"This data type is used to model textual information taken
			 from the NVT ASCII character set.  By convention, objects
			 with this syntax are declared as having
				SIZE (0..255)"
		SYNTAX	OCTET STRING        

-- Groups

snChasGen	OBJECT IDENTIFIER ::= { snChassis 1 }
snChasPwr	OBJECT IDENTIFIER ::= { snChassis 2 }
snChasFan	OBJECT IDENTIFIER ::= { snChassis 3 }
snChasUnit	OBJECT IDENTIFIER ::= { snChassis 4 }


-- SECTION 2: MIB Objects


-- General Chassis Information

snChasType OBJECT-TYPE
	SYNTAX DisplayString (SIZE(0..128))
	MAX-ACCESS	read-only
	STATUS	current
	DESCRIPTION
		"The chassis type represents the type 
		of Foundry product being managed. "
	::= { snChasGen 1 }



snChasSerNum OBJECT-TYPE
	SYNTAX	DisplayString (SIZE(0..128))
	MAX-ACCESS	read-only
	STATUS	current
	DESCRIPTION
		"The serial number of the chassis. If the
		serial number is unknown or unavailable then
		the value should be a zero length string."
	::= { snChasGen 2 }



-- Power Supply Status


snChasPwrSupplyStatus OBJECT-TYPE
	SYNTAX	Integer32
	MAX-ACCESS	read-only
	STATUS	deprecated
	DESCRIPTION
		"This object is being deprecated, please use snChasPwrSupplyTable instead.
	
		A bit array that contains the value of the
		Chassis Power Supplies. This is a packed bit string;
		the 2 power supplies status are encoded into 4 bits
		(a nibble). 

		There are multiple power supplies per chassis in this release.
		The following shows the meaning of each bit:
		(bit 0 is the least significant bit).

		  bit position   meaning
		  ------------   -------
			  20-31  reserved
			  19     Power  Supply 8 DC (0=bad, 1=good).
			  18     Power  Supply 7 DC (0=bad, 1=good).
			  17     Power  Supply 8 present status (0=present, 1=not-present).
			  16     Power  Supply 7 present status (0=present, 1=not-present).
			  15     Power  Supply 6 DC (0=bad, 1=good).
			  14     Power  Supply 5 DC (0=bad, 1=good).
			  13     Power  Supply 6 present status (0=present, 1=not-present).
			  12     Power  Supply 5 present status (0=present, 1=not-present).
			  11     Power  Supply 4 DC (0=bad, 1=good).
			  10     Power  Supply 3 DC (0=bad, 1=good).
			  9      Power  Supply 4 present status (0=present, 1=not-present).
			  8      Power  Supply 3 present status (0=present, 1=not-present).
			  4-7    reserved
			  3      Power  Supply 2 DC (0=bad, 1=good).
			  2      Power  Supply 1 DC (0=bad, 1=good).
			  1      Power  Supply 2 present status (0=present, 1=not-present).
			  0      Power  Supply 1 present status (0=present, 1=not-present)."
	::= { snChasGen 3 }


-- Fan Status


snChasFanStatus OBJECT-TYPE
	SYNTAX	Integer32
	MAX-ACCESS	read-only
	STATUS	deprecated
	DESCRIPTION
		"This object is being deprecated, please use snChasFanTable instead.
	
		A bit array that contains the value of the
		fan status. This is a packed bit string. The
		status of each fan is encoded into one bit.

		  bit value    meaning
		  ---------    -------
			  0         fan failure.
			  1         fan good.

		There are two fans per VLAN Switch chassis in this release.
		The following shows the meaning of each bit:
		(bit 0 is the least significant bit).

		  bit position   meaning
		  ------------   -------
			  6-31       reserved
			  5          fan6 status
			  4          fan5 status
			  3          fan4 status
			  2          fan3 status
			  1          fan2 status
			  0          fan1 status"
	::= { snChasGen 4 }




snChasMainBrdDescription OBJECT-TYPE
	SYNTAX DisplayString (SIZE(0..128))
	MAX-ACCESS read-only
	STATUS current
	DESCRIPTION
		"The main board description string. (It is obsoleted for Chassis Product)"
	::= { snChasGen 5 }


snChasMainPortTotal OBJECT-TYPE
	SYNTAX INTEGER (1..24)
	MAX-ACCESS read-only
	STATUS current
	DESCRIPTION
		"The total number of ports for the main board. (It is obsoleted for Chassis Product)"
	::= { snChasGen 6 }


snChasExpBrdDescription OBJECT-TYPE
	SYNTAX DisplayString (SIZE(0..128))
	MAX-ACCESS read-only
	STATUS current
	DESCRIPTION
		"The expansion board description string. Expansion
		board are those boards attaching on the main board.
		(It is obsoleted for Chassis Product)"
	::= { snChasGen 7 }


snChasExpPortTotal OBJECT-TYPE
	SYNTAX INTEGER (1..24)
	MAX-ACCESS read-only
	STATUS current
	DESCRIPTION
		"The total number of ports for the expansion board.
		(It is obsoleted for Chassis Product)"
	::= { snChasGen 8 }


snChasStatusLeds OBJECT-TYPE
	SYNTAX	Integer32
	MAX-ACCESS	read-only
	STATUS	current
	DESCRIPTION
		"A bit array that contains the value of the
		front panel status LEDs. This is a bit-map; 
		each LED is encoded into 1 bit for each switch
		port.  The maximum number of ports in one chassis 
		is 24 that means 24 Ports Status LEDs. The expansion port 
		number always begins from the last main port number.  
		The following shows the meaning of each bit for each 
		switch port:

		  bit value  meaning
		  --------   ---------  
			 0         off (Link off)
			 1         on  (Link on)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snChasGen 9 }


snChasTrafficLeds OBJECT-TYPE
	SYNTAX	Integer32
	MAX-ACCESS	read-only
	STATUS	current
	DESCRIPTION
		"A bit array that contains the value of the
		front panel traffic LEDs. This is a packed bit string; 
		each LED is encoded into 1 bit for each switch
		port.  The maximum number of ports in one chassis 
		is 24 that means 24 Ports Traffic LEDs. The expansion port 
		number always begins from the last main port number.  
		The following shows the meaning of each bit for each 
		switch port:

		  bit value  meaning
		  --------   ---------  
			 0         off (no traffic)
			 1         on  (traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snChasGen 10 }


snChasMediaLeds OBJECT-TYPE
	SYNTAX	Integer32
	MAX-ACCESS	read-only
	STATUS	current
	DESCRIPTION
		"A bit array that contains the value of the
		front panel media LEDs. This is a packed bit string; 
		each LED is encoded into 1 bit for each switch port.  
		The maximum number of ports in one chassis is 24 
		that means 24 Ports Media LEDs.  The expansion port 
		number always begins from the last main port number. 
		The following shows the meaning of each bit for each 
		switch port:

		bit value  meaning   
		---------  -------
		  0        half duplex
		  1        full duplex

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snChasGen 11 }


snChasEnablePwrSupplyTrap OBJECT-TYPE
	SYNTAX	INTEGER { disabled(0), enabled(1) }
	MAX-ACCESS	read-write
	STATUS	current
	DESCRIPTION
		"Indicates whether the SNMP agent process is
		permitted to generate power supply failure traps."
	DEFVAL { enabled }
	::= { snChasGen 12 }

snChasMainBrdId OBJECT-TYPE
	SYNTAX OCTET STRING
	MAX-ACCESS read-only
	STATUS current
	DESCRIPTION
		"The main board identifier, which can uniquely identify a board
		type. It is an encoded octet string with the following meaning:
		  octet 0  - octet string format version, which identifies the
					 format of this string.

		If format version octet has the value 1, the octets after the
		version octet have the following meaning:
		  octet 1  - product type, FIWG=0x57, FIBB=0x42, FIMLS=0x4D
					 NI=0x4E, TI=0x54, TIRT=0x52
		  octet 2  - board type, POWERPC=1, ALPHA=2
		  The length of the octet string is 27.

		If format version octet has the value 2, the octets after the
		version octet have the following meaning:
		  octet 1  - product type: 
						BI_WG					0x57
						BI_BB					0x42
						BI_NI					0x4E
						NI_M4					0x4D
						BI_SLB					0x53
		  octet 2  - module type:
						MASTER_FIBER_8G			0x0
						MASTER_FIBER_4G			0x1
						MASTER_COPPER_16		0x2
						SLAVE_FIBER_4G			0x3
						FI_MASTER_FIBER_2G		0x4
						FI_MASTER_FIBER_4G		0x5
						MASTER_COPPER_8G		0x6
						FI_MASTER_FIBER_8G		0x7
						SLAVE_FIBER_8G			0x8
						MASTER_COPPER_12_2		0x9
						SLAVE_COPPER_24			0xA
						FI_SLAVE_COPPER_24		0xB
						SLAVE_100FX_8			0xD
						SLAVE_100FX_16			0xC
						SLAVE_COPPER_8G			0xE
						SLAVE_COPPER_16_2		0xF
						STACK_FIBER_8G			0x10
						STACK_COPPER_8G			0x11
						MASTER_FIBER_2G			0x12	
						SLAVE_100FX_24			0x13
						MASTER_FIBER_0G			0x14	
						POS_622M				0x15
						POS_155M				0x16
						SLAVE_FIBER_2G			0x17
						SLAVE_COPPER_2G			0x18
						FI_SLAVE_FIBER_2G		0x19
						FI_SLAVE_FIBER_4G		0x1A
						FI_SLAVE_FIBER_8G		0x1B
						FI_SLAVE_COPPER_8G		0x1C
						FI_MASTER_COPPER_8G		0x1D
						POS_155M2P				0x1E
						FI_MASTER_COPPER_4G		0x1F
						FI_MASTER_COPPER_2G		0x20
						MASTER_COPPER_4G		0x21
						MASTER_COPPER_2G		0x22
						MASTER_M4_8G			0x23
						MASTER_M4_4G			0x24
						MASTER_M4_2G			0x25
						MASTER_M4_0G			0x26	
						MASTER_M5_0G			0x27	
						POS_2488M				0x28	
						SLAVE_M5_0G				0x29	
						POS_N2488M				0x2A	
						STACK_IPC_48_2			0x2B	
						SLAVE_NPA_FIBER_4G		0x2C	
						ATM_2PORT				0x2D	
						ATM_4PORT				0x2E	
						SLAVE_FIBER_10G			0x2F
						STACK_FES_48_2			0x30
						STACK_FES_24_2			0x31
						STACK_FES_96_4			0x32
						STACK_FES_12G			0x33
						STACK_FESX_24G			0x34
						STACK_FESX_24_2_G		0x35
						STACK_FESX_24_1_G		0x36
						STACK_FESX_48G			0x37
						STACK_FESX_48_2_G		0x38
						STACK_FESX_48_1_G		0x39
						SUPERX_FI_MGMT		    0x40
						SUPERX_FI_2P10G 		0x41
						SUPERX_FI_24GC  		0x42
						SUPERX_FI_24GF  		0x43
						SUPERX_FI_2P10G_WAN 	0x44
						SUPERX_FI_MGMT_II       0x4a
						SLAVE_JC_48E			0xC3	
						SLAVE_JC_48T			0xC4	
						MASTER_JC_M4_8G		0xC5
						SLAVE_JC_8G				0xC6	
						SLAVE_JC_B16GF			0xC8	
						MASTER_JC_B2404			0xC9	
						SLAVE_JC_B16GC			0xCA	

		  The length of the octet string is 28.

		  Both format version 1 and 2:
		  octet 3  - processor type, PVR_M603=3, PVR_M604=4, PVR_M603E=6,
					 PVR_M603EV=7, PVR_M750=8, PVR_M604E=9, PVR_M8245=81
		  octet 4 to
		  octet 5  - processor speed in MHz
		  octet 6  - MAC type:
						MAC_NONE=0
						MAC_SEEQ_10_100=1, 
						MAC_DEC_10_100=2,
						MAC_3COM_10_100=3,
						MAC_X10GMAC_10000=4,
						MAC_SEEQ_1000=5, 
						MAC_GMAC_1000=6,
						MAC_VLSI_1000=7
		  octet 7  - PHY type, PHY_NONE=0, PHY_QSI=1, PHY_BROADCOM=2,
					 PHY_ICS=3, PHY_NATIONAL=4, PHY_LEVEL1=6,
					 PHY_BROADCOM_10_100=7, PHY_LEVEL24=8,
					 PHY_BROADCOM_10000=9 (for 10G),
					 PHY_3COM_10_100=9 (for others)
		  octet 8  - port type, COPPER=0, FIBER=1
		  octet 9  - fiber port type, NONFIBER=0, SX_FIBER=1,
					 LX_FIBER=2, LHX_FIBER=3, LX_SX_FIBER=4,
					 LHB_FIBER=5
		  octet 10 to
		  octet 13 - DRAM size in KBytes
		  octet 14 to
		  octet 17 - boot flash size in KBytes
		  octet 18 to
		  octet 21 - code flash size in KBytes
		  octet 22 to
		  octet 27 - serial number.

		  Format version 1 only:
		  octet 28 - chassis backplane type. 
			chassis4000	= 	0x00
			chassis8000	=	0x02
			chassis15000	=	0x01
			chassisFISX	=	0x04
			Turbo8			=	0x07 (stack2)
			FastIron2		=	0x06 (stack1)"
	::= { snChasGen 13 }


snChasExpBrdId OBJECT-TYPE
	SYNTAX OCTET STRING
	MAX-ACCESS read-only
	STATUS current
	DESCRIPTION
		"The expansion board identifier. Expansion board are those
		boards attaching on the main board. It is an encoded octet
		string with the following meaning:
		  octet 0  - octet string format version, which identifies
					 the format of this string.
		If format version octet has the value 1, the octets after
		the version octet have the following meaning:
		  octet 1  - expansion board type, HUNDRED_MEG_1PORT=1,
					 HUNDRED_MEG_2PORT=2, HUNDRED_MEG_1PORT_COPPER=3,
					 HUNDRED_MEG_2PORT_COPPER=4, HUNDRED_MEG_2PORT_LX=5,
					 GIGA_1PORT=8, GIGA_2PORT=9
		  octet 2  - fiber port type, NONFIBER=0, SX_FIBER=1,
					 LX_FIBER=2, LHX_FIBER=3, LX_SX_FIBER=4
		(It is obsoleted for Chassis Product)"
	::= { snChasGen 14 }


snChasSpeedLeds OBJECT-TYPE
	SYNTAX	Integer32
	MAX-ACCESS	read-only
	STATUS	current
	DESCRIPTION
		"A bit array that contains the value of the
		front panel media LEDs. This is a packed bit string; 
		each LED is encoded into 1 bit for each switch port.  
		The maximum number of ports in one chassis is 24 
		that means 24 Ports Speed LEDs.  The expansion port 
		number always begins from the last main port number. 
		The following shows the meaning of each bit for each 
		switch port:

		bit value  meaning   
		---------  -------
		  0        10 MBit
		  1        100 MBit

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snChasGen 15 }


snChasEnableFanTrap OBJECT-TYPE
	SYNTAX	INTEGER { disabled(0), enabled(1) }
	MAX-ACCESS	read-write
	STATUS	current
	DESCRIPTION
		"Indicates whether the SNMP agent process is
		permitted to generate fan failure traps."
	DEFVAL { enabled }
	::= { snChasGen 16 }


snChasIdNumber OBJECT-TYPE
	SYNTAX  DisplayString (SIZE (0..64))
	MAX-ACCESS  read-write
	STATUS  current
	DESCRIPTION
		"An administratively-assigned chassis identity number,
		used by inventory control."
	::= { snChasGen 17 }


snChasActualTemperature OBJECT-TYPE
	SYNTAX  INTEGER (-110..250)
	MAX-ACCESS	read-only
	STATUS	current
	DESCRIPTION
		"Temperature of the chassis. Each unit is 0.5 degrees Celcius.
		Only management module built with temperature sensor hardware
		is applicable. For those non-applicable management module, it
		returns no-such-name."
	::= { snChasGen 18 }


snChasWarningTemperature OBJECT-TYPE
	SYNTAX  INTEGER (0..250)
	MAX-ACCESS	read-write
	STATUS	current
	DESCRIPTION
		"Actual temperature higher than this threshold value will trigger
		the switch to send a temperature warning trap. Each unit is 0.5
		degrees Celcius. Only management module built with temperature
		sensor hardware is applicable. For those non-applicable management
		module, it returns no-such-name."
	::= { snChasGen 19 }


snChasShutdownTemperature OBJECT-TYPE
	SYNTAX  INTEGER (0..250)
	MAX-ACCESS	read-write
	STATUS	current
	DESCRIPTION
		"Actual temperature higher than this threshold value will shutdown
		a partial of the switch hardware to cool down the system. Each unit
		is 0.5 degrees Celcius. Only management module built with temperature
		sensor hardware is applicable. For those non-applicable management
		module, it returns no-such-name."
	::= { snChasGen 20 }

snChasEnableTempWarnTrap OBJECT-TYPE
	SYNTAX	INTEGER { disabled(0), enabled(1) }
	MAX-ACCESS	read-write
	STATUS	current
	DESCRIPTION
		"Indicates whether the SNMP agent process is
		permitted to generate temperature warning traps."
	DEFVAL { enabled }
	::= { snChasGen 21 }

-- Flash Card

snChasFlashCard OBJECT-TYPE
	SYNTAX	Integer32
	MAX-ACCESS	read-only
	STATUS	current
	DESCRIPTION
		"A bit array that contains the value of the
		flash card status. This is a packed bit string. The
		status of each flash card is encoded into one bit.

		  bit value    meaning
		  ---------    -------
			  0         flash card absent.
			  1         flash card present.

		There are up to two flash cards in this release.
		This object is valid if M4 management module is present.
		The following shows the meaning of each bit:
		(bit 0 is the least significant bit).

		  bit position   meaning
		  ------------   -------
			  2-31       reserved
			  1          flash card 2 status
			  0          flash card 1 status"
	::= { snChasGen 22 }


snChasFlashCardLeds OBJECT-TYPE
	SYNTAX   Integer32
	MAX-ACCESS	read-only
	STATUS	current
	DESCRIPTION
		"A bit array that contains the value of the
		flash card LEDs. This is a packed bit string; 
		each LED is encoded into 1 bit for each flash card.

		  bit value  meaning
		  --------   ---------  
			 0         off 
			 1         on 
		"	  
	::= { snChasGen 23 }


snChasNumSlots OBJECT-TYPE
	SYNTAX   Integer32
	MAX-ACCESS	read-only
	STATUS	current
	DESCRIPTION
		"Number of slots of the chassis."
	::= { snChasGen 24 }


snChasArchitectureType OBJECT-TYPE
	SYNTAX		INTEGER {
					stackable(1), -- old stackable
					bigIron(2),
					terathon(3), -- MG-8, NI-40G, IMR
					fifthGen(4) -- XMR, MLX, RX
				}
	MAX-ACCESS	read-only
	STATUS	current
	DESCRIPTION
		"Architecture type."
	::= { snChasGen 25 }


snChasProductType OBJECT-TYPE
	SYNTAX		INTEGER {
		invalid(0),
		mg8(1),
		ni40G(2),
		imr(3),
		biRx800(4),
		niXmr16000(5),
		biRx400(6),
		niXmr8000(7),
		biRx200(8),
		niXmr4000(9),
		niMlx16(10),
		niMlx8(11),
		niMlx4(12),
		niMlx32(13),
		niXmr32000(14),
		biRx32(15),
		niCES2000Series(16),
		niCER2000Series(17),
		biNI2(50),
		biBB(66),
		biM4(77),
		biNI(78),
		biSLB(83),
		biWG(87)
	}
	MAX-ACCESS	read-only
	STATUS	current
	DESCRIPTION
		"Product type."
	::= { snChasGen 26 }

-- Power Supply Table


snChasPwrSupplyTable OBJECT-TYPE
	SYNTAX	SEQUENCE OF SnChasPwrSupplyEntry
	MAX-ACCESS	not-accessible
	STATUS	current
	DESCRIPTION
		"A table of each power supply information. Only installed
		power supply appears in a table row."
	::= { snChasPwr 1 }

snChasPwrSupplyEntry OBJECT-TYPE
	SYNTAX	SnChasPwrSupplyEntry
	MAX-ACCESS	not-accessible
	STATUS	current
	DESCRIPTION
		"A row in the power supply table."
	INDEX	{ snChasPwrSupplyIndex }
	::= { snChasPwrSupplyTable 1 }

SnChasPwrSupplyEntry ::= SEQUENCE {
	snChasPwrSupplyIndex
		Integer32,
	snChasPwrSupplyDescription
		DisplayString,
	snChasPwrSupplyOperStatus
		INTEGER
	}

snChasPwrSupplyIndex OBJECT-TYPE
	SYNTAX	Integer32
	MAX-ACCESS	read-only
	STATUS	current
	DESCRIPTION
		"The index to power supply table."
	::= { snChasPwrSupplyEntry 1 }

snChasPwrSupplyDescription OBJECT-TYPE
	SYNTAX DisplayString (SIZE(0..128))
	MAX-ACCESS read-only
	STATUS current
	DESCRIPTION
		"The power supply description string."
	::= { snChasPwrSupplyEntry 2 }

snChasPwrSupplyOperStatus OBJECT-TYPE
	SYNTAX  INTEGER {
		other(1),
		normal(2),
		failure(3)
		}
	MAX-ACCESS  read-only
	STATUS  current
	DESCRIPTION
		"The power supply operation status."
	::= { snChasPwrSupplyEntry 3 }


-- Stacking Power Supply Table


snChasPwrSupply2Table OBJECT-TYPE
	SYNTAX	SEQUENCE OF SnChasPwrSupply2Entry
	MAX-ACCESS	not-accessible
	STATUS	current
	DESCRIPTION
		"A table of each power supply information for each unit. Only installed
		power supply appears in a table row."
	::= { snChasPwr 2 }

snChasPwrSupply2Entry OBJECT-TYPE
	SYNTAX	SnChasPwrSupply2Entry
	MAX-ACCESS	not-accessible
	STATUS	current
	DESCRIPTION
		"A row in the power supply table."
	INDEX	{ snChasPwrSupply2Unit, snChasPwrSupply2Index }
	::= { snChasPwrSupply2Table 1 }

SnChasPwrSupply2Entry ::= SEQUENCE {
	snChasPwrSupply2Unit
		Integer32,
	snChasPwrSupply2Index
	Integer32	,
	snChasPwrSupply2Description
		DisplayString,
	snChasPwrSupply2OperStatus
		INTEGER
	}

snChasPwrSupply2Unit OBJECT-TYPE
	SYNTAX	Integer32
	MAX-ACCESS	read-only
	STATUS	current
	DESCRIPTION
		"The index to power supply table."
	::= { snChasPwrSupply2Entry 1 }

snChasPwrSupply2Index OBJECT-TYPE
	SYNTAX	Integer32
	MAX-ACCESS	read-only
	STATUS	current
	DESCRIPTION
		"The index to power supply table."
	::= { snChasPwrSupply2Entry 2}

snChasPwrSupply2Description OBJECT-TYPE
	SYNTAX DisplayString (SIZE(0..128))
	MAX-ACCESS read-only
	STATUS current
	DESCRIPTION
		"The power supply description string."
	::= { snChasPwrSupply2Entry 3 }

snChasPwrSupply2OperStatus OBJECT-TYPE
	SYNTAX  INTEGER {
		other(1),
		normal(2),
		failure(3)
		}
	MAX-ACCESS  read-only
	STATUS  current
	DESCRIPTION
		"The power supply operation status."
	::= { snChasPwrSupply2Entry 4 }


-- Fan Table


snChasFanTable OBJECT-TYPE
	SYNTAX	SEQUENCE OF SnChasFanEntry
	MAX-ACCESS	not-accessible
	STATUS	current
	DESCRIPTION
		"A table of each fan information. Only installed
		fan appears in a table row."
	::= { snChasFan 1 }

snChasFanEntry OBJECT-TYPE
	SYNTAX	SnChasFanEntry
	MAX-ACCESS	not-accessible
	STATUS	current
	DESCRIPTION
		"A row in the fan table."
	INDEX	{ snChasFanIndex }
	::= { snChasFanTable 1 }

SnChasFanEntry ::= SEQUENCE {
	snChasFanIndex
		Integer32,
	snChasFanDescription
		DisplayString,
	snChasFanOperStatus
		INTEGER
	}

snChasFanIndex OBJECT-TYPE
	SYNTAX	Integer32
	MAX-ACCESS	read-only
	STATUS	current
	DESCRIPTION
		"The index to fan table."
	::= { snChasFanEntry 1 }

snChasFanDescription OBJECT-TYPE
	SYNTAX DisplayString (SIZE(0..128))
	MAX-ACCESS read-only
	STATUS current
	DESCRIPTION
		"The fan description string."
	::= { snChasFanEntry 2 }

snChasFanOperStatus OBJECT-TYPE
	SYNTAX  INTEGER {
		other(1),
		normal(2),
		failure(3)
		}
	MAX-ACCESS  read-only
	STATUS  current
	DESCRIPTION
		"The fan operation status."
	::= { snChasFanEntry 3 }


-- Stacking Fan Table

snChasFan2Table OBJECT-TYPE
	SYNTAX	SEQUENCE OF SnChasFan2Entry
	MAX-ACCESS	not-accessible
	STATUS	current
	DESCRIPTION
		"A table of each fan information for each unit. Only installed
		fan appears in a table row."
	::= { snChasFan 2 }

snChasFan2Entry OBJECT-TYPE
	SYNTAX	SnChasFan2Entry
	MAX-ACCESS	not-accessible
	STATUS	current
	DESCRIPTION
		"A row in the fan table."
	INDEX	{ snChasFan2Unit, snChasFan2Index }
	::= { snChasFan2Table 1 }

SnChasFan2Entry ::= SEQUENCE {
	snChasFan2Unit
		Integer32,
	snChasFan2Index
		Integer32,
	snChasFan2Description
		DisplayString,
	snChasFan2OperStatus
		INTEGER
	}

snChasFan2Unit OBJECT-TYPE
	SYNTAX	Integer32
	MAX-ACCESS	read-only
	STATUS	current
	DESCRIPTION
		"The index to fan table."
	::= { snChasFan2Entry 1 }
	
snChasFan2Index OBJECT-TYPE
	SYNTAX	Integer32
	MAX-ACCESS	read-only
	STATUS	current
	DESCRIPTION
		"The index to fan table."
	::= { snChasFan2Entry 2 }

snChasFan2Description OBJECT-TYPE
	SYNTAX DisplayString (SIZE(0..128))
	MAX-ACCESS read-only
	STATUS current
	DESCRIPTION
		"The fan description string."
	::= { snChasFan2Entry 3 }

snChasFan2OperStatus OBJECT-TYPE
	SYNTAX  INTEGER {
		other(1),
		normal(2),
		failure(3)
		}
	MAX-ACCESS  read-only
	STATUS  current
	DESCRIPTION
		"The fan operation status."
	::= { snChasFan2Entry 4 }


-- Stacking Chassis unit Information

snChasUnitTable OBJECT-TYPE
	SYNTAX	SEQUENCE OF SnChasUnitEntry
	MAX-ACCESS	not-accessible
	STATUS	current
	DESCRIPTION
		"A table of chassis  information for each unit. Only active
		chassis appears in a table row."
	::= { snChasUnit 1 }

snChasUnitEntry OBJECT-TYPE
	SYNTAX	SnChasUnitEntry
	MAX-ACCESS	not-accessible
	STATUS	current
	DESCRIPTION
		"A row in the chassis table."
	INDEX	{ snChasUnitIndex }
	::= { snChasUnitTable 1 }

SnChasUnitEntry ::= SEQUENCE {
	snChasUnitIndex
		Integer32,
	snChasUnitSerNum
		DisplayString,
	snChasUnitNumSlots
		Integer32,
	snChasUnitActualTemperature
		INTEGER,
	snChasUnitWarningTemperature
		INTEGER,
	snChasUnitShutdownTemperature
		INTEGER,
	snChasUnitPartNum
		DisplayString
	}

snChasUnitIndex OBJECT-TYPE
	SYNTAX	Integer32
	MAX-ACCESS	read-only
	STATUS	current
	DESCRIPTION
		"The index to chassis table."
	::= { snChasUnitEntry 1 }

snChasUnitSerNum OBJECT-TYPE
	SYNTAX	DisplayString (SIZE(0..128))
	MAX-ACCESS	read-only
	STATUS	current
	DESCRIPTION
		"The serial number of the chassis for each unit. If the
		serial number is unknown or unavailable then
		the value should be a zero length string."
	::= { snChasUnitEntry 2 }

snChasUnitNumSlots OBJECT-TYPE
	SYNTAX	Integer32
	MAX-ACCESS	read-only
	STATUS	current
	DESCRIPTION
		"Number of slots of the chassis for each unit."
	::= { snChasUnitEntry 3 }

	
snChasUnitActualTemperature OBJECT-TYPE
	SYNTAX  INTEGER (-110..250)
	MAX-ACCESS	read-only
	STATUS	current
	DESCRIPTION
		"Temperature of the chassis. Each unit is 0.5 degrees Celcius.
		Only management module built with temperature sensor hardware
		is applicable. For those non-applicable management module, it
		returns no-such-name."
	::= { snChasUnitEntry 4 }


snChasUnitWarningTemperature OBJECT-TYPE
	SYNTAX  INTEGER (0..250)
	MAX-ACCESS	read-only
	STATUS	current
	DESCRIPTION
		"Actual temperature higher than this threshold value will trigger
		the switch to send a temperature warning trap. Each unit is 0.5
		degrees Celcius. Only management module built with temperature
		sensor hardware is applicable. For those non-applicable management
		module, it returns no-such-name."
	::= { snChasUnitEntry 5 }


snChasUnitShutdownTemperature OBJECT-TYPE
	SYNTAX  INTEGER (0..250)
	MAX-ACCESS	read-only
	STATUS	current
	DESCRIPTION
		"Actual temperature higher than this threshold value will shutdown
		a partial of the switch hardware to cool down the system. Each unit
		is 0.5 degrees Celcius. Only management module built with temperature
		sensor hardware is applicable. For those non-applicable management
		module, it returns no-such-name."
	::= { snChasUnitEntry 6 }

snChasUnitPartNum OBJECT-TYPE
	SYNTAX	DisplayString
	MAX-ACCESS	read-only
	STATUS	current
	DESCRIPTION
		"The part number of the chassis for each unit. If the
		part number is unknown or unavailable then
		the value should be a zero length string."
	::= { snChasUnitEntry 7 }


-- Agent Groups

snAgentGbl				OBJECT IDENTIFIER ::= { snAgentSys 1 }
snAgentBrd				OBJECT IDENTIFIER ::= { snAgentSys 2 }
snAgentTrp 				OBJECT IDENTIFIER ::= { snAgentSys 3 }
snAgentBoot				OBJECT IDENTIFIER ::= { snAgentSys 4 }
snAgCfgEos				OBJECT IDENTIFIER ::= { snAgentSys 5 }
snAgentLog				OBJECT IDENTIFIER ::= { snAgentSys 6 }
snAgentSysParaConfig	OBJECT IDENTIFIER ::= { snAgentSys 7 }
snAgentConfigModule		OBJECT IDENTIFIER ::= { snAgentSys 8 }
snAgentUser				OBJECT IDENTIFIER ::= { snAgentSys 9 }
snAgentRedundant		OBJECT IDENTIFIER ::= { snAgentSys 10 }
snAgentCpu			    OBJECT IDENTIFIER ::= { snAgentSys 11 }
snAgentHw			    OBJECT IDENTIFIER ::= { snAgentSys 12 }
snAgentTemp			    OBJECT IDENTIFIER ::= { snAgentSys 13 }
snAgentPoe				OBJECT IDENTIFIER ::= { snAgentSys 14 }
snAgentLicense			OBJECT IDENTIFIER ::= { snAgentSys 15 }
  


-- SECTION 2: MIB Objects


-- Agent's Global Group
	
snAgReload OBJECT-TYPE
	SYNTAX	INTEGER {
		other(1),
		running(2),
		reset(3),
		busy(4)
		}
	MAX-ACCESS	read-write
	STATUS	current
	DESCRIPTION
		"Action object to reboot the agent.
		The following values can only be read:
		  other(1).....agent in unknown or other state
		  running(2)...agent running
		  busy(4).......reload not allowed at this time, flash is busy

		The following value can be written:
		  reset(3).....do a hard reset

		The agent will return a
		response before the action occurs."
	::= { snAgentGbl 1 }

snAgEraseNVRAM OBJECT-TYPE
	SYNTAX	INTEGER {
		normal(1),
		error(2),
		erase(3),
		erasing(4),		
		busy(5)
		}
	MAX-ACCESS	read-write
	STATUS	current
	DESCRIPTION
		"Action object to erase NVRAM of the agent.
		The following values can only be read:
		  normal(1)
		  error(2)... operation failed or bad flash
		  erasing(4)...agent is erasing NVRAM flash
		  busy(5).......operation not allowed at this time, flash is busy

		The following value can be written:
		  erase(3).....do erase 

		The agent will return a response even before the erase is done.
		And the read value will be erasing until erase is done.
		And the erase request will be rejected until error or normal."
	::= { snAgentGbl 2 }

snAgWriteNVRAM OBJECT-TYPE
	SYNTAX	INTEGER {
		normal(1),
		error(2),
		write(3),
		writing(4),		
		busy(5)
		}
	MAX-ACCESS	read-write
	STATUS	current
	DESCRIPTION
		"Action object to save all configuration info to
		 NVRAM of the agent.
		The following values can only be read:
		  normal(1)
		  error(2)... operation failed or bad flash
		  writing(4)...agent is writing NVRAM flash
		  busy(5).......operation not allowed at this time, flash is busy

		The following value can be written:
		  write(3).....do write 

		The agent will return a response even before the write is done.
		And the read value will be writing until write is done.
		And the write request will be rejected until error or normal."
	::= { snAgentGbl 3 }

snAgConfigFromNVRAM OBJECT-TYPE
	SYNTAX	INTEGER {
		normal(1),
		error(2),
		config(3),
		configing(4),
		busy(5)
	}
	MAX-ACCESS	not-accessible
	STATUS	current
	DESCRIPTION
		"Action object to config the switch from NVRAM of the agent.
		The following values can only be read:
		  normal(1)
		  error(2)... operation failed or bad flash
		  configing(4)...configing from NVRAM flash is in process.
		  busy(5).......operation not allowed at this time, flash is busy
		The following value can be written:
		  config(3).....do config 

		The agent will return a response after config is done."
	::= { snAgentGbl 4 }

--  image and config file down/up load 

-- snAgTftpServerIp object is deprecated, and added following 2 new objects.
-- 1. "snAgTftpServerAddrType" represents Ipv4 and Ipv6 address types
-- 2. "snAgTftpServerAddr" reprasents Ipv4 and Ipv6 addresses

snAgTftpServerIp OBJECT-TYPE
	SYNTAX	IpAddress
	MAX-ACCESS	read-write
	STATUS	deprecated
	DESCRIPTION
		"The tftp server address, this will be used for both download/upload
		 image file and config file."
	::= { snAgentGbl 5 }

snAgImgFname OBJECT-TYPE
	SYNTAX	DisplayString (SIZE (0..32))
	MAX-ACCESS	read-write
	STATUS	current
	DESCRIPTION
		"Name of the image file including path currently associated
		with the system. When the object is not used, the value is a
		zero length string."
	::= { snAgentGbl 6 }


snAgImgLoad OBJECT-TYPE
	SYNTAX	INTEGER {
		normal(1),
		flashPrepareReadFailure(2),
		flashReadError(3),
		flashPrepareWriteFailure(4),
		flashWriteError(5),
		tftpTimeoutError(6),
		tftpOutOfBufferSpace(7),
		tftpBusy(8),
		tftpRemoteOtherErrors(9), 
		tftpRemoteNoFile(10), 
		tftpRemoteBadAccess(11), 
		tftpRemoteDiskFull(12), 
		tftpRemoteBadOperation(13), 
		tftpRemoteBadId(14), 
		tftpRemoteFileExists(15), 
		tftpRemoteNoUser(16), 
		operationError(17),
		loading(18),
		uploadMPPrimary(19),
		downloadMPPrimary(20),
		uploadMPSecondary(21),
		downloadMPSecondary(22),
		tftpWrongFileType(23),
		downloadSPPrimary(24),
		downloadSPSecondary(25),
		uploadMPBootROM(26),
		downloadMPBootROM(27),
		uploadMPBootTFTP(28),
		downloadMPBootTFTP(29),
		uploadMPMonitor(30),
		downloadMPMonitor(31),
		downloadSPBootROM(32)
		}
	MAX-ACCESS	read-write
	STATUS	current
	DESCRIPTION
		"Action object to down/up load a new image
		to the agent. The following values:
		Error values: from normal(1) to operationError(17) and tftpWrongFileType(23).
		  loading(18) .. operation is in process.

		The following values are used for set :
		  uploadMPPrimary(19)..upload the Primary image from MP flash to tftp server.
		  downloadMPPrimary(20)..download the Primary image from tftp server to MP flash.
		  uploadMPSecondary(21)..upload the Secondary image from MP flash to tftp server.
		  downloadMPSecondary(22)..download the Secondary image from tftp server to MP flash.
		  downloadSPPrimary(24)..download the Primary image from tftp server to SP flash.
		  downloadSPSecondary(25)..download the Secondary image from tftp server to SP flash.
		  uploadMPBootROM(26)..upload the Boot from flash image from MP flash to tftp server.
		  downloadMPBootROM(27)..download the Boot from flash image from tftp server to MP flash.
		  uploadMPBootTFTP(28)..upload the Boot from TFTP image from MP flash to tftp server.
		  downloadMPBootTFTP(29)..download the Boot from TFTP image from tftp server to MP flash.
		  uploadMPMonitor(30)..upload the Monitor image from MP flash to tftp server.
		  downloadMPMonitor(31)..download the Monitor image from tftp server to MP flash.
		  downloadSPBootROM(32)..download the Boot image from tftp server to SP flash.

		MP is the management processor, SP is the switch processor.

		The image filename is defined in
		snAgImgFname. The tftp server address is defined in snAgTftpServerIp.
		Atomic set of snAgImgLoad, snAgImgFname and  
		snAgTftpServerIp is required to allow down/up load to happen. 
		And the write request will be rejected during loading until error 
		or normal."
	::= { snAgentGbl 7 }

snAgCfgFname OBJECT-TYPE
	SYNTAX	DisplayString (SIZE (0..32))
	MAX-ACCESS	read-write
	STATUS	current
	DESCRIPTION
		"Name of the config file(s) including path currently associated
		with the system. Some agents in special
		situations may support a value which contains
		multiple file names instead of a single file
		name. Multiple names are specified as a list
		of file names separated by semicolons (;).
		When the object is not used, the value is a
		zero length string."
	::= { snAgentGbl 8 }

snAgCfgLoad OBJECT-TYPE
	SYNTAX	INTEGER {
		normal(1),
		flashPrepareReadFailure(2),
		flashReadError(3),
		flashPrepareWriteFailure(4),
		flashWriteError(5),
		tftpTimeoutError(6),
		tftpOutOfBufferSpace(7),
		tftpBusy(8),
		tftpRemoteOtherErrors(9), 
		tftpRemoteNoFile(10), 
		tftpRemoteBadAccess(11), 
		tftpRemoteDiskFull(12), 
		tftpRemoteBadOperation(13), 
		tftpRemoteBadId(14), 
		tftpRemoteFileExists(15), 
		tftpRemoteNoUser(16), 
		operationError(17),
		loading(18),
		uploadFromFlashToServer(20),
		downloadToFlashFromServer(21),
		uploadFromDramToServer(22),
		downloadToDramFromServer(23),
		uploadFromFlashToNMS(24),
		downloadToFlashFromNMS(25),
		uploadFromDramToNMS(26),
		downloadToDramFromNMS(27),
		operationDoneWithNMS(28),
		tftpWrongFileType(29),
		downloadToDramFromServerOverwrite(30)
		}
	MAX-ACCESS	read-write
	STATUS	current
	DESCRIPTION
		"Action object to down/up load a config image
		to the agent. The following values can be
		read :
		Error values: from normal(1) to operationError(17) and tftpWrongFileType(29).
		  loading(18) .. operation is in process.


		The following value can be used to set:
		  uploadFromFlashToServer(20)..upload the config from flash
											  to tftp server. 
		  downloadToFlashFromServer(21)..download the config to flash
												from tftp server.
		  uploadFromDramToServer(22)..upload the config from DRAM 
											 to tftp server.
		  downloadToDramFromServer(23)..download the config to DRAM
											   from tftp server.
		  downloadToDramFromServerOverwrite(30)..download the config to DRAM
											   from tftp server, clear the running-config,
											   and overwrite with the new config.

		The following value can be used to set:
		  uploadFromFlashToNMS(24)..upload the config from flash to NMS. 
		  downloadToFlashFromNMS(25)..download the config to flash from NMS.
		  uploadFromDramToNMS(26)..upload the config from DRAM to NMS.
		  downloadToDramFromNMS(27)..download the config to DRAM from NMS.

		The config filename is defined in
		snAgCfgFname. The tftp server address is defined in snAgTftpServerIp.
		Atomic set of snAgCfgLoad, snAgCfgFname and  snAgTftpServerIp is
		required to allow down/up load to happen. And the write request 
		will be rejected during loading until error or normal.
		For those NMS commands from (24) to (27), The snAgCfgEosTable MIB must
		be sent along in one PDU.  A seperate write memory cli or set 
		snAgWriteNVRAM is required to save the config to NVRAM."
	::= { snAgentGbl 9 }

-- default gateway ip address

snAgDefGwayIp OBJECT-TYPE
	SYNTAX	IpAddress
	MAX-ACCESS	read-write
	STATUS	current
	DESCRIPTION
		"The default gateway (router) address." 	
	::= { snAgentGbl 10 }


-- image version

snAgImgVer OBJECT-TYPE
	SYNTAX	DisplayString (SIZE(0..32))
	MAX-ACCESS	read-only
	STATUS	current
	DESCRIPTION
		"The version of the running software in the form
		'major.minor.maintenance[letters]'."
	::= { snAgentGbl 11 }

snAgFlashImgVer OBJECT-TYPE
	SYNTAX	DisplayString (SIZE(0..32))
	MAX-ACCESS	read-only
	STATUS	current
	DESCRIPTION
		"The version of the software image saved in local
		storage such as flash memory in the form
		'major.minor.maintenance[letters]'. If not
		known or not available, then the value is
		a zero length string."
	::= { snAgentGbl 12 }

snAgGblIfIpAddr OBJECT-TYPE
	SYNTAX	IpAddress
	MAX-ACCESS	read-write
	STATUS	current
	DESCRIPTION
		"The interface ip address."
	::= { snAgentGbl 13 }

snAgGblIfIpMask OBJECT-TYPE
	SYNTAX	IpAddress
	MAX-ACCESS	read-write
	STATUS	current
	DESCRIPTION
		"The interface ip address mask."
	::= { snAgentGbl 14 }

snAgGblPassword OBJECT-TYPE
	SYNTAX	DisplayString (SIZE (0..97))
	MAX-ACCESS	read-write
	STATUS	current
	DESCRIPTION
		"System Security Access Password and this is only 
		 allowed to use for setting but not for reading.
		   An SNMP-Get will get an null string.
		   By default, this object needs to be in the same PDU while
		 doing Set operation some critical SNMP objects.
		   If command 'no snmp-server pw-check' is configured on
		the device, then this object is not needed in the PDU.
		   The value of this object depends on the authentication
		 method configured for SNMP.
		   If there's no AAA authentication configuration for SNMP,
		this object will have the enable superuser password. 
		   If the AAA authentication for SNMP is configured and has 
		leading method as enable or line, this object will have 
		the corresponding enable or line password.
		   If the switch has AAA authentication for SNMP operation,
		and the method specified is one of local, TACACS+, or RADIUS,
		this object will have format '<username> <password>' 
		(note one space character in between).
		  The max size allows concatenation of max 48 octets of 
		 username and 48 octets of password, with one blank character"
	::= { snAgentGbl 15 }

snAgTrpRcvrCurEntry OBJECT-TYPE
	SYNTAX	INTEGER (0..255)
	MAX-ACCESS	read-only
	STATUS	current
	DESCRIPTION
		"The current total entries of the Trap 
		Receiver Table are created."
	::= { snAgentGbl 16 }

snAgGblDataRetrieveMode OBJECT-TYPE
	SYNTAX  INTEGER {
		nextbootCfg(0),             
		operationalData(1)
		}
	MAX-ACCESS  read-write
	STATUS  current
	DESCRIPTION
		"By default, this mode is set to nextbootCfg(0).
		 The VLAN Table and Port-STP Table data will be retrieved
		 according to this mode.
		 nextbootCfg(0).........the nextboot configuration data are retrieved
		 operationalData(1)..........the current running data are retrieved"  
	::= { snAgentGbl 19 }


snAgSystemLog OBJECT-TYPE
	SYNTAX	OCTET STRING (SIZE(5))	
	MAX-ACCESS	read-write
	STATUS	current
	DESCRIPTION
		"The system log object to indicate whether any Network
		 Management Station(NMS) has login.  The first byte
		 of the octet string is the value decribed below and 
		 followed by 4 bytes of secret code.
		  login(1)..... a value for a NMS to login.
		  heartbeat(2)... a value for the login NMS periodically to 
						checkin; Otherwise, the Agent will automatically
						set this object to logout(3) after a timeout 
						period. 
		  logout(3).... a value for a NMS to logout.
		  changePassword(4).... a value for the login NMS to change
						password, only if snAgGblPasswordChangeMode
						was configured to 'anyMgmtEntity'.
		  changeReadOnlyCommunity(5).... a value for the login NMS
						to change the read-only community string,
						only if snAgGblPasswordChangeMode was
						configured to 'anyMgmtEntity'.
		  changeReadWriteCommunity(6).... a value for the login NMS
						to change the read-write community string,
						only if snAgGblPasswordChangeMode was
						configured to 'anyMgmtEntity'."
	::= { snAgentGbl 20 }


snAgGblEnableColdStartTrap OBJECT-TYPE
	SYNTAX	INTEGER { disabled(0), enabled(1) }
	MAX-ACCESS	read-write
	STATUS	current
	DESCRIPTION
		"Indicates whether the SNMP agent process is
		permitted to generate cold start traps."
	DEFVAL { enabled }
	::= { snAgentGbl 21 }


snAgGblEnableLinkUpTrap OBJECT-TYPE
	SYNTAX	INTEGER { disabled(0), enabled(1) }
	MAX-ACCESS	read-write
	STATUS	current
	DESCRIPTION
		"Indicates whether the SNMP agent process is
		permitted to generate link up traps."
	DEFVAL { enabled }
	::= { snAgentGbl 22 }


snAgGblEnableLinkDownTrap OBJECT-TYPE
	SYNTAX	INTEGER { disabled(0), enabled(1) }
	MAX-ACCESS	read-write
	STATUS	current
	DESCRIPTION
		"Indicates whether the SNMP agent process is
		permitted to generate link down traps."
	DEFVAL { enabled }
	::= { snAgentGbl 23 }

snAgGblPasswordChangeMode OBJECT-TYPE
	SYNTAX	INTEGER {
			  anyMgmtEntity(1),
			  consoleAndTelnet(2),
			  consoleOnly(3),
			  telnetOnly(4) }
	MAX-ACCESS	read-only
	STATUS	current
	DESCRIPTION
		"Specify which management entity is allowed to change
		the password. 'anyMgmtEntity' management entities are
		SNMP management station, console command line interface,
		and telnet command line interface. For security reason,
		this object can only be modified by console command line
		interface or telnet command line interface. The default
		value is 'consoleAndTelnet', of which both console and
		telnet command line interfaces are allowed to change
		the password."
	::= { snAgentGbl 24 }

snAgGblReadOnlyCommunity OBJECT-TYPE
	SYNTAX	DisplayString (SIZE (0..32))
	MAX-ACCESS	read-write
	STATUS	current
	DESCRIPTION
		"SNMP read community string and this is only allowed
		to use for setting but not for reading. An SNMP-Get
		will get an zero length string.
		  Set operation on this object is allowed only if command
		'password-change any' is configured on the target device."
	::= { snAgentGbl 25 }

snAgGblReadWriteCommunity OBJECT-TYPE
	SYNTAX	DisplayString (SIZE (0..32))
	MAX-ACCESS	read-write
	STATUS	current
	DESCRIPTION
		"SNMP read-write community string and this is only
		allowed to use for setting but not for reading. An
		SNMP-Get will get an zero length string.
		  Set operation on this object is allowed only if command
		'password-change any' is configured on the target device."
	::= { snAgentGbl 26 }

snAgGblCurrentSecurityLevel OBJECT-TYPE
	SYNTAX	INTEGER (0..5)
	MAX-ACCESS	read-only
	STATUS	current
	DESCRIPTION
		"This represnts the current log-in security level.
		Each level of security requires a password to permit
		user for different system configurations."
	::= { snAgentGbl 27 }

snAgGblSecurityLevelSet OBJECT-TYPE
	SYNTAX	INTEGER (0..5)
	MAX-ACCESS	read-write
	STATUS	current
	DESCRIPTION
		"This shows which the security level password to be set."
	::= { snAgentGbl 28 }

snAgGblLevelPasswordsMask OBJECT-TYPE
	SYNTAX   Integer32 
	MAX-ACCESS	read-only
	STATUS	current
	DESCRIPTION
		"This shows the bitmap of level passwords which successfully assigned to the system."
	::= { snAgentGbl 29 }

snAgGblQueueOverflow OBJECT-TYPE
	SYNTAX	INTEGER	{ false(0), true(1) } 
	MAX-ACCESS	read-only
	STATUS	current
	DESCRIPTION
		"false - The device queues are not overflow.
		 true  - The device queues are overflow."
	::= { snAgentGbl 30 }

snAgGblBufferShortage OBJECT-TYPE
	SYNTAX	INTEGER	{ false(0), true(1) } 
	MAX-ACCESS	read-only
	STATUS	current
	DESCRIPTION
		"false - The device buffers are adequate.
		 true  - The device buffers are in shortage."
	::= { snAgentGbl 31 }

snAgGblDmaFailure OBJECT-TYPE
	SYNTAX	INTEGER	{ false(0), true(1) } 
	MAX-ACCESS	read-only
	STATUS	current
	DESCRIPTION
		"false - The device DMAs are in good condition.
		 true  - One of the DMAs in the device fails."
	::= { snAgentGbl 32 }

snAgGblResourceLowWarning OBJECT-TYPE
	SYNTAX	INTEGER	{ false(0), true(1) } 
	MAX-ACCESS	read-only
	STATUS	current
	DESCRIPTION
		"false - No, the device does not have resource-low-warning.
		 true  - Yes, the device does have resource-low-warning."
	::= { snAgentGbl 33 }

snAgGblExcessiveErrorWarning OBJECT-TYPE
	SYNTAX	INTEGER	{ false(0), true(1) } 
	MAX-ACCESS	read-only
	STATUS	current
	DESCRIPTION
		"false - No, the device does not have any excessive collision, FCS errors, alignment warning etc.
		 true  - Yes, the device does have."
	::= { snAgentGbl 34 }

snAgGblCpuUtilData OBJECT-TYPE
	SYNTAX	Gauge32
	MAX-ACCESS	read-only
	STATUS	current
	DESCRIPTION
		"The statistics collection of utilization of the CPU in the device. Reading this object resets all the counters.  Therefore, a user need not set snAgGblUtilCollect."
	::= { snAgentGbl 35 }

snAgGblCpuUtilCollect OBJECT-TYPE
	SYNTAX	INTEGER { disabled(0), enabled(1) }
	MAX-ACCESS	read-write
	STATUS	deprecated
	DESCRIPTION
		"enable(1)  - The beginning of statistics collection of utilization of the CPU in the device.
		 disable(0) - The end of statistics collection of utilization of the CPU in the device.
			   This object is deprecated. User need not set this object. User can read snAgGblCpuUtilData to reset all the counters. "
	::= { snAgentGbl 36 }

snAgGblTelnetTimeout OBJECT-TYPE
	SYNTAX	INTEGER (0..240)
	MAX-ACCESS	read-write
	STATUS	current
	DESCRIPTION
		"Telnet session idling timeout value. Writing value 0 to
		this object never timeouts any telnet sessions. Each value
		unit is one minute."
	::= { snAgentGbl 37 }

snAgGblEnableWebMgmt OBJECT-TYPE
	SYNTAX	INTEGER { disabled(0), enabled(1) }
	MAX-ACCESS	read-write
	STATUS	current
	DESCRIPTION
		"Enable/disable web management."
	DEFVAL { enabled }
	::= { snAgentGbl 38 }

snAgGblSecurityLevelBinding OBJECT-TYPE
	SYNTAX   Integer32
	MAX-ACCESS	read-only
	STATUS	current
	DESCRIPTION
		"This represnts the binding of a given password to which
		security level. A value of 255 indicates an invalid
		binding."
	::= { snAgentGbl 39 }

snAgGblEnableSLB OBJECT-TYPE
	SYNTAX	INTEGER { disabled(0), enabled(1) }
	MAX-ACCESS	read-only
	STATUS	current
	DESCRIPTION
		"Enable/disable Server Load Balancing."
	::= { snAgentGbl 40 }

snAgSoftwareFeature OBJECT-TYPE
	SYNTAX  OCTET STRING
	MAX-ACCESS	read-only
	STATUS	current
	DESCRIPTION
		"A bit string representing the software feature of the running
		switch/router image. These features were conditional compiled
		to different product images. For each bit, exist feature has
		a value of 1, but non-exist feature has a value of 0.
		  octet 0, bit 0 - RMON
		  octet 0, bit 1 - ipx switching
		  octet 0, bit 2 - server load balancing
		  octet 0, bit 3 - layer 3 filter in switch
		  octet 0, bit 4 - ipx routing
		  octet 0, bit 5 - appletalk routing
		  octet 0, bit 6 - ip multicast routing
		  octet 0, bit 7 - local access control
		  octet 1, bit 0 - BGP routing
		  octet 1, bit 1 - loopback interface
		  octet 1, bit 2 - BigIron multi-management module
		  octet 1, bit 3 - BigIron SYSIF II
		  octet 1, bit 4 - BigIron POS support
		  octet 1, bit 5 - appletalk cable vlan
		  octet 1, bit 6 - 64 subnet
		  octet 1, bit 7 - multi-slot trunk
		  octet 2, bit 0 - TACACS
		  octet 2, bit 1 - Gigabit Ethernet port auto-negotiation mode
		  octet 2, bit 2 - FSRP
		  octet 2, bit 3 - Exodus requested OSPF enhancement
		  octet 2, bit 4 - OSPF NSSA
		  octet 2, bit 5 - POS
		  octet 2, bit 6 - QOS
		  octet 2, bit 7 - Single Span
		  octet 3, bit 0 - Fast Span
		  octet 3, bit 1 - Base L3
		  octet 3, bit 2 - static log buffer
		  octet 3, bit 3 - L2 POS
		  octet 3, bit 4 - BI15K
		  octet 3, bit 5 - L2 ATM
		  octet 3, bit 6 - ATM
		  octet 3, bit 7 - NETFLOW
		  octet 4, bit 0 - SFLOW
		  octet 4, bit 1 - GVRP
		  octet 4, bit 2 - GARP
		  octet 4, bit 3 - dynamic trunk
		  octet 4, bit 4 - IGC 8G
		  octet 4, bit 5 - rate limit
		  octet 4, bit 6 - IPC rate limit
		  octet 4, bit 7 - MPLS
		  octet 5, bit 0 - ISIS
		  octet 5, bit 1 - link aggregation
		  octet 5, bit 2 - port dual mode
		  octet 5, bit 3 - private vlan
		  octet 5, bit 4 - MBGP
		  octet 5, bit 5 - ipv6 protocol vlan
		  octet 5, bit 6 - X10G
		  octet 5, bit 7 - fastiron edge switch/router (gridiron)
		  octet 6, bit 0 - FDP
		  octet 6, bit 1 - port tag type
		  octet 6, bit 2 - wireless capable
		  octet 6, bit 3 - snSwPortVlanId object has changed from read-only to read-write
		  octet 6, bit 4 - LLDP
		Bit 0 is the least significant bit of an octet, and
		bit 7 is the most significant bit of an octet."
	::= { snAgentGbl 41 }

snAgGblEnableModuleInsertedTrap OBJECT-TYPE
	SYNTAX	INTEGER { disabled(0), enabled(1) }
	MAX-ACCESS	read-write
	STATUS	current
	DESCRIPTION
		"Indicates whether the SNMP agent process is permitted to
		generate hardware module inserted to chassis traps."
	DEFVAL { enabled }
	::= { snAgentGbl 42 }

snAgGblEnableModuleRemovedTrap OBJECT-TYPE
	SYNTAX	INTEGER { disabled(0), enabled(1) }
	MAX-ACCESS	read-write
	STATUS	current
	DESCRIPTION
		"Indicates whether the SNMP agent process is permitted to
		generate hardware module removed from chassis traps."
	DEFVAL { enabled }
	::= { snAgentGbl 43 }

snAgGblTrapMessage OBJECT-TYPE
	SYNTAX  DisplayString
	MAX-ACCESS	read-only
	STATUS	current
	DESCRIPTION
		"A generic trap message string."
	::= { snAgentGbl 44 }

snAgGblEnableTelnetServer OBJECT-TYPE
	SYNTAX	INTEGER { disabled(0), enabled(1) }
	MAX-ACCESS	read-write
	STATUS	current
	DESCRIPTION
		"Enable or disable telnet server in device."
	DEFVAL { enabled }
	::= { snAgentGbl 45 }

snAgGblTelnetPassword OBJECT-TYPE
	SYNTAX	DisplayString (SIZE (0..48))
	MAX-ACCESS	read-write
	STATUS	current
	DESCRIPTION
		"Telnet Access Password and this is only 
		 useful for write operation. A read operation
		 get a null string.
		  Set operation on this object is allowed only if command
		'password-change any' is configured on the target device.
		  Another configuration affecting this is
		'no snmp-server pw-check'. If its configured on the device,
		there's no need to pass another varbind snAgGblPassword.
		By default, 'snmp-server pw-check' is true, and thus needs
		to have snAgGblPassword along with this object.
		in the same Set PDU."
	::= { snAgentGbl 46 }

snAgBuildDate OBJECT-TYPE
	SYNTAX	DisplayString (SIZE(0..32))
	MAX-ACCESS	read-only
	STATUS	current
	DESCRIPTION
		"The date of the built software."
	::= { snAgentGbl 47 }

snAgBuildtime OBJECT-TYPE
	SYNTAX	DisplayString (SIZE(0..32))
	MAX-ACCESS	read-only
	STATUS	current
	DESCRIPTION
		"The time of the built software."
	::= { snAgentGbl 48 }

snAgBuildVer OBJECT-TYPE
	SYNTAX	DisplayString (SIZE(0..32))
	MAX-ACCESS	read-only
	STATUS	current
	DESCRIPTION
		"The version of the built software in the form
		'major.minor.maintenance[letters]'."
	::= { snAgentGbl 49 }

snAgGblCpuUtil1SecAvg OBJECT-TYPE
	SYNTAX	Gauge32
	MAX-ACCESS	read-only
	STATUS	current
	DESCRIPTION
		"The statistics collection of 1 second CPU utilization."
	::= { snAgentGbl 50 }

snAgGblCpuUtil5SecAvg OBJECT-TYPE
	SYNTAX	Gauge32
	MAX-ACCESS	read-only
	STATUS	current
	DESCRIPTION
		"The statistics collection of 5 second CPU utilization."
	::= { snAgentGbl 51 }

snAgGblCpuUtil1MinAvg OBJECT-TYPE
	SYNTAX	Gauge32
	MAX-ACCESS	read-only
	STATUS	current
	DESCRIPTION
		"The statistics collection of 1 minute CPU utilization."
	::= { snAgentGbl 52 }

snAgGblDynMemUtil OBJECT-TYPE
	SYNTAX	Gauge32
	MAX-ACCESS	read-only
	STATUS  deprecated
	DESCRIPTION
		"The system dynamic memory utilization, in unit of percentage.
		Deprecated: Refer to snAgSystemDRAMUtil"
	::= { snAgentGbl 53 }

snAgGblDynMemTotal OBJECT-TYPE
	SYNTAX   Gauge32
	MAX-ACCESS	read-only
	STATUS  deprecated
	DESCRIPTION
		"The total amount of system dynamic memory, in number of bytes.
		Deprecated: Refer to snAgSystemDRAMTotal"
	::= { snAgentGbl 54 }

snAgGblDynMemFree OBJECT-TYPE
	SYNTAX		Gauge32
	MAX-ACCESS	read-only
	STATUS  deprecated
	DESCRIPTION
		"The free amount of system dynamic memory, in number of bytes.
		Deprecated: Refer to snAgSystemDRAMFree"
	::= { snAgentGbl 55 }

snAgImgLoadSPModuleType OBJECT-TYPE
	SYNTAX	INTEGER {
		other(1),
		vm1(2),
		pos12(3),
		pos48(4),
		atm(5),
		gignpa(6),
		lp(7)
		}
	MAX-ACCESS	read-write
	STATUS	current
	DESCRIPTION
		"The switch processor module type of which that receives
		the downloaded image."
	::= { snAgentGbl 56 }

snAgImgLoadSPModuleNumber OBJECT-TYPE
	SYNTAX   Integer32
	MAX-ACCESS	read-write
	STATUS	current
	DESCRIPTION
		"The slot numner of a switch processor module that receives
		the downloaded image. Setting value 0 applies to all SP
		modules."
	::= { snAgentGbl 57 }

snAgTrapHoldTime OBJECT-TYPE
	SYNTAX	INTEGER (1..600)
	MAX-ACCESS	read-write
	STATUS	current
	DESCRIPTION
		"The time in seconds for which traps will be witheld
		during system initialization."
	::= { snAgentGbl 58 }

snAgSFlowSourceInterface OBJECT-TYPE
	SYNTAX   InterfaceIndex
	MAX-ACCESS   read-write
	STATUS   current
	DESCRIPTION
		"Use the ifIndex value here to specify the
		source interface to be used for sFlow packets.
		The interface should have IP address configured
		on it. Value of 0 indicates that source interface
		has not been configured for sFlow. Port 65534
		is used to specify a null port."
	::= { snAgentGbl 59 }

snAgGblTelnetLoginTimeout OBJECT-TYPE
	SYNTAX	INTEGER (1..10)
	MAX-ACCESS	read-write
	STATUS	current
	DESCRIPTION
		"Telnet session login timeout value in minutes. Default is 2 minutes."
	::= { snAgentGbl 60 }

snAgGblBannerExec OBJECT-TYPE
	SYNTAX	DisplayString
	MAX-ACCESS	read-write
	STATUS	current
	DESCRIPTION
		"EXEC process creation banner. Insert newlines using '\n' within the string."
	::= { snAgentGbl 61 }

snAgGblBannerIncoming OBJECT-TYPE
	SYNTAX	DisplayString
	MAX-ACCESS	read-write
	STATUS	current
	DESCRIPTION
		"Incoming terminal line banner. Insert newlines using '\n' within the string."
	::= { snAgentGbl 62 }

snAgGblBannerMotd OBJECT-TYPE
	SYNTAX	DisplayString
	MAX-ACCESS	read-write
	STATUS	current
	DESCRIPTION
		"Message-of-the-day banner. Insert newlines using '\n' within the string."
	::= { snAgentGbl 63 }

snAgWebMgmtServerTcpPort OBJECT-TYPE
	SYNTAX	INTEGER (1..65535)
	MAX-ACCESS	read-write
	STATUS	current
	DESCRIPTION
		"The TCP port number of web management interface."
	::= { snAgentGbl 64 }

--  image and config file down/up load 

snAgTftpServerAddrType			 OBJECT-TYPE
	SYNTAX	InetAddressType
	MAX-ACCESS	read-write
	STATUS	current
	DESCRIPTION
		  "TFTP server IP address Type. Supported address types are ipv4(1) and ipv6(2)"
	DEFVAL	{ ipv4 }
	::= { snAgentGbl 65 }

snAgTftpServerAddr			 OBJECT-TYPE
	SYNTAX	InetAddress
	MAX-ACCESS	read-write
	STATUS	current
	DESCRIPTION
		  "TFTP server IP address."
	::= { snAgentGbl 66 }

snAgGblPasswordCheckMode OBJECT-TYPE
	SYNTAX	EnabledStatus
	MAX-ACCESS	read-only
	STATUS	current
	DESCRIPTION
		"enabled(1)  - The password checking for SNMP set requests is enabled. The default value is enable.
		 disabled(2) -  The password checking for SNMP set requests is disabled. 
		When enabled all image/file related MIB object set requests  PDU must include the password using the snAgGblPassword."
	DEFVAL { enabled }
	::= { snAgentGbl 68 }

-- Agent Board Table


snAgentBrdTable OBJECT-TYPE
	SYNTAX	SEQUENCE OF SnAgentBrdEntry
	MAX-ACCESS	not-accessible
	STATUS	current
	DESCRIPTION
		"A table of each physical board information."
	::= { snAgentBrd 1 }

snAgentBrdEntry OBJECT-TYPE
	SYNTAX	SnAgentBrdEntry
	MAX-ACCESS	not-accessible
	STATUS	current
	DESCRIPTION
		"A row in the Agent Board table."
	INDEX	{ snAgentBrdIndex }
	::= { snAgentBrdTable 1 }

SnAgentBrdEntry ::= SEQUENCE {
	snAgentBrdIndex
		Integer32,
	snAgentBrdMainBrdDescription
		DisplayString,
	snAgentBrdMainBrdId
		OCTET STRING,
	snAgentBrdMainPortTotal
		Integer32,
	snAgentBrdExpBrdDescription
		DisplayString,
	snAgentBrdExpBrdId
		OCTET STRING,
	snAgentBrdExpPortTotal
		INTEGER,
	snAgentBrdStatusLeds 
		Integer32,
	snAgentBrdTrafficLeds 
		Integer32,
	snAgentBrdMediaLeds 
		Integer32,
	snAgentBrdSpeedLeds 
		Integer32,
	snAgentBrdModuleStatus
		INTEGER,
	snAgentBrdRedundantStatus
		INTEGER,
	snAgentBrdAlarmLeds 
		Integer32,
	snAgentBrdTxTrafficLeds 
		Integer32,
	snAgentBrdRxTrafficLeds 
		Integer32,
	snAgentBrdStatusLedString
		OCTET STRING,
	snAgentBrdTrafficLedString
		OCTET STRING,
	snAgentBrdMediaLedString
		OCTET STRING,
	snAgentBrdSpeedLedString
		OCTET STRING,
	snAgentBrdAlarmLedString
		OCTET STRING,
	snAgentBrdTxTrafficLedString
		OCTET STRING,
	snAgentBrdRxTrafficLedString
		OCTET STRING,
	snAgentBrdMemoryTotal
		CounterBasedGauge64,
	snAgentBrdMemoryAvailable
		CounterBasedGauge64,
	snAgentBrdSerialNumber
		DisplayString,
	snAgentBrdPartNumber
		DisplayString
	}

snAgentBrdIndex OBJECT-TYPE
	SYNTAX	Integer32 
	MAX-ACCESS	read-only
	STATUS	current
	DESCRIPTION
		"The index to the Agent Interface Table."
	::= { snAgentBrdEntry 1 }

snAgentBrdMainBrdDescription OBJECT-TYPE
	SYNTAX DisplayString (SIZE(0..128))
	MAX-ACCESS read-only
	STATUS current
	DESCRIPTION
		"The main board description string."
	::= { snAgentBrdEntry 2 }

snAgentBrdMainBrdId OBJECT-TYPE
	SYNTAX OCTET STRING
	MAX-ACCESS read-only
	STATUS current
	DESCRIPTION
		"The main board identifier, which can uniquely identify a board
		type. It is an encoded octet string with the following meaning:
		  octet 0  - octet string format version, which identifies the
					 format of this string.
		If format version octet has the value 2, the octets after the
		version octet have the following meaning:
		  octet 1  - product type: 
						BI_WG					0x57
						BI_BB					0x42
						BI_NI					0x4E
						BI_NI2					0x32
						NI_M4					0x4D
						BI_SLB					0x53
		  octet 2  - module type:
						MASTER_FIBER_8G			0x0
						MASTER_FIBER_4G			0x1
						MASTER_COPPER_16		0x2
						SLAVE_FIBER_4G			0x3
						FI_MASTER_FIBER_2G		0x4
						FI_MASTER_FIBER_4G		0x5
						MASTER_COPPER_8G		0x6
						FI_MASTER_FIBER_8G		0x7
						SLAVE_FIBER_8G			0x8
						MASTER_COPPER_12_2		0x9
						SLAVE_COPPER_24			0xA
						FI_SLAVE_COPPER_24		0xB
						SLAVE_100FX_8			0xD
						SLAVE_100FX_16			0xC
						SLAVE_COPPER_8G			0xE
						SLAVE_COPPER_16_2		0xF
						STACK_FIBER_8G			0x10
						STACK_COPPER_8G			0x11
						MASTER_FIBER_2G			0x12	
						SLAVE_100FX_24			0x13
						MASTER_FIBER_0G			0x14	
						POS_622M				0x15
						POS_155M				0x16
						SLAVE_FIBER_2G			0x17
						SLAVE_COPPER_2G			0x18
						FI_SLAVE_FIBER_2G		0x19
						FI_SLAVE_FIBER_4G		0x1A
						FI_SLAVE_FIBER_8G		0x1B
						FI_SLAVE_COPPER_8G		0x1C
						FI_MASTER_COPPER_8G		0x1D
						POS_155M2P				0x1E
						FI_MASTER_COPPER_4G		0x1F
						FI_MASTER_COPPER_2G		0x20
						MASTER_COPPER_4G		0x21
						MASTER_COPPER_2G		0x22
						MASTER_M4_8G			0x23
						MASTER_M4_4G			0x24
						MASTER_M4_2G			0x25
						MASTER_M4_0G			0x26	
						MASTER_M5_0G			0x27	
						POS_2488M				0x28	
						SLAVE_M5_0G				0x29	
						POS_N2488M				0x2A	
						STACK_IPC_48_2			0x2B	
						SLAVE_NPA_FIBER_4G		0x2C	
						ATM_2PORT				0x2D	
						ATM_4PORT				0x2E	
						SLAVE_FIBER_10G			0x2F
						STACK_FES_48_2			0x30
						STACK_FES_24_2			0x31
						STACK_FES_96_4			0x32
						STACK_FES_12G			0x33
						STACK_FESX_24G			0x34
						STACK_FESX_24_2_G		0x35
						STACK_FESX_24_1_G		0x36
						STACK_FESX_48G			0x37
						STACK_FESX_48_2_G		0x38
						STACK_FESX_48_1_G		0x39
						SUPERX_FI_MGMT		    0x40
						SUPERX_FI_2P10G 		0x41
						SUPERX_FI_24GC  		0x42
						SUPERX_FI_24GF  		0x43
						SUPERX_FI_2P10G_WAN 	0x44
						SUPERX_FI_MGMT_II       0x4a
						SLAVE_JC_48E			0xC3	
						SLAVE_JC_48T			0xC4	
						MASTER_JC_M4_8G			0xC5	
						SLAVE_JC_8G				0xC6	
						SLAVE_JC_B16GF			0xC8	
						MASTER_JC_B2404			0xC9	
						SLAVE_JC_B16GC			0xCA
						SLAVE_JC_B24FX			0xCE
		  octet 3  - processor type, PVR_M603=3, PVR_M604=4, PVR_M603E=6,
					 PVR_M603EV=7, PVR_M750=8, PVR_M604E=9, PVR_M8245=81
		  octet 4 to
		  octet 5  - processor speed in MHz
		  octet 6  - MAC type:
						MAC_NONE=0
						MAC_SEEQ_10_100=1, 
						MAC_DEC_10_100=2,
						MAC_3COM_10_100=3,
						MAC_X10GMAC_10000=4,
						MAC_SEEQ_1000=5, 
						MAC_GMAC_1000=6,
						MAC_VLSI_1000=7
		  octet 7  - PHY type, PHY_NONE=0, PHY_QSI=1, PHY_BROADCOM=2,
					 PHY_ICS=3, PHY_NATIONAL=4, PHY_LEVEL1=6,
					 PHY_BROADCOM_10_100=7, PHY_LEVEL24=8,
					 PHY_BROADCOM_10000=9 (for 10G),
					 PHY_3COM_10_100=9 (for others)
		  octet 8  - port type, COPPER=0, FIBER=1
		  octet 9  - fiber port type, NONFIBER=0, SX_FIBER=1,
					 LX_FIBER=2, LHX_FIBER=3, LX_SX_FIBER=4,
					 LHB_FIBER=5
		  octet 10 to
		  octet 13 - DRAM size in KBytes
		  octet 14 to
		  octet 17 - boot flash size in KBytes
		  octet 18 to
		  octet 21 - code flash size in KBytes
		  octet 22 to
		  octet 27 - serial number.
		  octet 28 - chassis backplane type. 
			chassis4000	= 	0x00
			chassis8000	=	0x02
			chassis15000	=	0x01
			chassisFISX	=	0x04
			Turbo8		=	0x07 (stack2)
			FastIron2	=	0x06 (stack1)"
	::= { snAgentBrdEntry 3 }


snAgentBrdMainPortTotal OBJECT-TYPE
	SYNTAX Integer32
	MAX-ACCESS read-only
	STATUS current
	DESCRIPTION
		"The total number of ports for the main board."
	::= { snAgentBrdEntry 4 }


snAgentBrdExpBrdDescription OBJECT-TYPE
	SYNTAX DisplayString (SIZE(0..128))
	MAX-ACCESS read-only
	STATUS current
	DESCRIPTION
		"The expansion board description string. Expansion
		board are those boards attaching on the main board."
	::= { snAgentBrdEntry 5 }


snAgentBrdExpBrdId OBJECT-TYPE
	SYNTAX OCTET STRING
	MAX-ACCESS read-only
	STATUS current
	DESCRIPTION
		"The expansion board identifier. Expansion board are those
		boards attaching on the main board. It is an encoded octet
		string with the following meaning:
		  octet 0  - octet string format version, which identifies
					 the format of this string.
		If format version octet has the value 1, the octets after
		the version octet have the following meaning:
		  octet 1  - expansion board type, HUNDRED_MEG_1PORT=1,
					 HUNDRED_MEG_2PORT=2, HUNDRED_MEG_1PORT_COPPER=3,
					 HUNDRED_MEG_2PORT_COPPER=4, HUNDRED_MEG_2PORT_LX=5,
					 GIGA_1PORT=8, GIGA_2PORT=9
		  octet 2  - fiber port type, NONFIBER=0, SX_FIBER=1,
					 LX_FIBER=2, LHX_FIBER=3, LX_SX_FIBER=4, LHB_FIBER=5"
	::= { snAgentBrdEntry 6 }


snAgentBrdExpPortTotal OBJECT-TYPE
	SYNTAX INTEGER (0..24)
	MAX-ACCESS read-only
	STATUS current
	DESCRIPTION
		"The total number of ports for the expansion board."
	::= { snAgentBrdEntry 7 }


snAgentBrdStatusLeds OBJECT-TYPE
	SYNTAX	Integer32
	MAX-ACCESS	read-only
	STATUS  deprecated
	DESCRIPTION
		"A bit array that contains the value of the
		front panel status LEDs. This is a bit-map; 
		each LED is encoded into 1 bit for each switch
		port.  The maximum number of ports in one chassis 
		is 32 that means 32 Ports Status LEDs. The expansion port 
		number always begins from the last main port number.  
		The following shows the meaning of each bit for each 
		switch port:

		  bit value  meaning
		  --------   ---------  
			 0         off (Link off)
			 1         on  (Link on)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdStatusLedString)"
	::= { snAgentBrdEntry 8 }


snAgentBrdTrafficLeds OBJECT-TYPE
	SYNTAX	Integer32
	MAX-ACCESS	read-only
	STATUS  deprecated
	DESCRIPTION
		"A bit array that contains the value of the
		front panel traffic LEDs. This is a packed bit string; 
		each LED is encoded into 1 bit for each switch
		port.  The maximum number of ports in one chassis 
		is 24 that means 24 Ports Traffic LEDs. The expansion port 
		number always begins from the last main port number.  
		The following shows the meaning of each bit for each 
		switch port:

		  bit value  meaning
		  --------   ---------  
			 0         off (no traffic)
			 1         on  (traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdTrafficLedString)"
	::= { snAgentBrdEntry 9 }


snAgentBrdMediaLeds OBJECT-TYPE
	SYNTAX	Integer32
	MAX-ACCESS	read-only
	STATUS  deprecated
	DESCRIPTION
		"A bit array that contains the value of the
		front panel media LEDs. This is a packed bit string; 
		each LED is encoded into 1 bit for each switch port.  
		The maximum number of ports in one chassis is 24 
		that means 24 Ports Media LEDs.  The expansion port 
		number always begins from the last main port number. 
		The following shows the meaning of each bit for each 
		switch port:

		bit value  meaning   
		---------  -------
		  0        half duplex
		  1        full duplex

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		(It was obsoleted after release 07100, replaced by snAgentBrdMediaLedString)"
	::= { snAgentBrdEntry 10 }



snAgentBrdSpeedLeds OBJECT-TYPE
	SYNTAX	Integer32
	MAX-ACCESS	read-only
	STATUS  deprecated
	DESCRIPTION
		"A bit array that contains the value of the
		front panel media LEDs. This is a packed bit string; 
		each LED is encoded into 1 bit for each switch port.  
		The maximum number of ports in one chassis is 24 
		that means 24 Ports Speed LEDs.  The expansion port 
		number always begins from the last main port number. 
		The following shows the meaning of each bit for each 
		switch port:

		bit value  meaning   
		---------  -------
		  0        10 MBit
		  1        100 MBit

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		(It was obsoleted after release 07100, replaced by snAgentBrdSpeedLedString)"
	::= { snAgentBrdEntry 11 }

snAgentBrdModuleStatus OBJECT-TYPE
	SYNTAX  INTEGER {
		moduleEmpty(0),             
		moduleGoingDown(2),
		moduleRejected(3),
		moduleBad(4),
		moduleConfigured(8),
		moduleComingUp(9),
		moduleRunning(10)
		}
	MAX-ACCESS  read-only
	STATUS  current
	DESCRIPTION
		"By default, this mode is set to notActivated(0).
		moduleEmpty(0) ......... The slot of the chassis is empty.
		moduleGoingDown(2) ..... The module is going down.
		moduleRejected(3) ...... The module is being rejected due to wrong configuration.
		moduleBad(4) ........... The module Hardware is bad.
		moduleConfigured(8) ...... The module is configured (stacking)
		moduleComingUp(9) ...... The module is in power-up cycle.
		moduleRunning(10) ....... The module is running."
	::= { snAgentBrdEntry 12 }

snAgentBrdRedundantStatus OBJECT-TYPE
	SYNTAX  INTEGER {
		other(1),
		active(2),             
		standby(3),
		crashed(4),
		comingUp(5)
		}
	MAX-ACCESS  read-only
	STATUS  current
	DESCRIPTION
		"The redundant status of a module. Non-management module always
		returns other(1). Management module returns the rest of the
		states."
	::= { snAgentBrdEntry 13 }

snAgentBrdAlarmLeds OBJECT-TYPE
	SYNTAX   Integer32
	MAX-ACCESS	read-only
	STATUS  deprecated
	DESCRIPTION
		"A bit array that contains the value of the
		front panel media LEDs (for POS Module Only). This is a packed bit string; 
		each LED is encoded into 1 bit for each switch port.  
		The maximum number of ports in one chassis is 24 
		that means 24 Ports Speed LEDs.  The expansion port 
		number always begins from the last main port number. 
		The following shows the meaning of each bit for each 
		switch port:

		bit value  meaning   
		---------  -------
		  0        no alarm
		  1        alarm

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		(It was obsoleted after release 07100, replaced by snAgentBrdAlarmLedString)"
	::= { snAgentBrdEntry 14 }


snAgentBrdTxTrafficLeds OBJECT-TYPE
	SYNTAX	Integer32
	MAX-ACCESS	read-only
	STATUS  deprecated
	DESCRIPTION
		"A bit array that contains the value of the
		front panel transmit traffic LEDs (for POS Module Only). This is a packed bit string; 
		each LED is encoded into 1 bit for each switch
		port.  The maximum number of ports in one chassis 
		is 24 that means 24 Ports Transmit Traffic LEDs. The expansion port 
		number always begins from the last main port number.  
		The following shows the meaning of each bit for each 
		switch port:

		  bit value  meaning
		  --------   ---------  
			 0         off (no transmit traffic)
			 1         on  (transmit traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdTxTrafficLedString)"
	::= { snAgentBrdEntry 15 }

snAgentBrdRxTrafficLeds OBJECT-TYPE
	SYNTAX   Integer32
	MAX-ACCESS	read-only
	STATUS  deprecated
	DESCRIPTION
		"A bit array that contains the value of the
		front panel receive traffic LEDs (for POS Module Only). This is a packed bit string; 
		each LED is encoded into 1 bit for each switch
		port.  The maximum number of ports in one chassis 
		is 24 that means 24 Ports Receive Traffic LEDs. The expansion port 
		number always begins from the last main port number.  
		The following shows the meaning of each bit for each 
		switch port:

		  bit value  meaning
		  --------   ---------  
			 0         off (no receive traffic)
			 1         on  (receive traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdRxTrafficLedString)"
	::= { snAgentBrdEntry 16 }

snAgentBrdStatusLedString OBJECT-TYPE
	SYNTAX	OCTET STRING
	MAX-ACCESS	read-only
	STATUS	current
	DESCRIPTION
		"A bit array that contains the value of the
		front panel status LEDs. This is a bit-map; 
		each LED is encoded into 1 bit for each switch
		port. The following shows the meaning of each
		bit for each switch port:

		  bit value  meaning
		  --------   ---------  
			 0         off (Link off)
			 1         on  (Link on)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snAgentBrdEntry 17 }

snAgentBrdTrafficLedString OBJECT-TYPE
	SYNTAX	OCTET STRING
	MAX-ACCESS	read-only
	STATUS	current
	DESCRIPTION
		"A bit array that contains the value of the
		front panel traffic LEDs. This is a packed bit string; 
		each LED is encoded into 1 bit for each switch
		port. The following shows the meaning of each
		bit for each switch port:

		  bit value  meaning
		  --------   ---------  
			 0         off (no traffic)
			 1         on  (traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snAgentBrdEntry 18 }

snAgentBrdMediaLedString OBJECT-TYPE
	SYNTAX	OCTET STRING
	MAX-ACCESS	read-only
	STATUS	current
	DESCRIPTION
		"A bit array that contains the value of the
		front panel media LEDs. This is a packed bit string;
		each LED is encoded into 1 bit for each switch port.
		The following shows the meaning of each bit for each
		switch port:

		bit value  meaning   
		---------  -------
		  0        half duplex
		  1        full duplex

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snAgentBrdEntry 19 }

snAgentBrdSpeedLedString OBJECT-TYPE
	SYNTAX	OCTET STRING
	MAX-ACCESS	read-only
	STATUS	current
	DESCRIPTION
		"A bit array that contains the value of the
		front panel media LEDs. This is a packed bit string;
		each LED is encoded into 1 bit for each switch port.
		The following shows the meaning of each bit for each
		switch port:

		bit value  meaning   
		---------  -------
		  0        10 MBit
		  1        100 MBit

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snAgentBrdEntry 20 }

snAgentBrdAlarmLedString OBJECT-TYPE
	SYNTAX	OCTET STRING
	MAX-ACCESS	read-only
	STATUS	current
	DESCRIPTION
		"A bit array that contains the value of the
		front panel media LEDs (for POS Module Only).
		This is a packed bit string; each LED is encoded
		into 1 bit for each switch port. The following
		shows the meaning of each bit for each switch port:

		bit value  meaning   
		---------  -------
		  0        no alarm
		  1        alarm

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snAgentBrdEntry 21 }

snAgentBrdTxTrafficLedString OBJECT-TYPE
	SYNTAX	OCTET STRING
	MAX-ACCESS	read-only
	STATUS	current
	DESCRIPTION
		"A bit array that contains the value of the
		front panel transmit traffic LEDs (for POS Module Only).
		This is a packed bit string; each LED is encoded into
		1 bit for each switch port. The following shows the
		meaning of each bit for each switch port:

		  bit value  meaning
		  --------   ---------  
			 0         off (no transmit traffic)
			 1         on  (transmit traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snAgentBrdEntry 22 }

snAgentBrdRxTrafficLedString OBJECT-TYPE
	SYNTAX	OCTET STRING
	MAX-ACCESS	read-only
	STATUS	current
	DESCRIPTION
		"A bit array that contains the value of the
		front panel receive traffic LEDs (for POS Module Only).
		This is a packed bit string; each LED is encoded into
		1 bit for each switch port. The following shows the
		meaning of each bit for each switch port:

		  bit value  meaning
		  --------   ---------  
			 0         off (no receive traffic)
			 1         on  (receive traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snAgentBrdEntry 23 }

snAgentBrdMemoryTotal  OBJECT-TYPE
	SYNTAX		CounterBasedGauge64
	MAX-ACCESS		read-only
	STATUS		current
	DESCRIPTION
		"The total memory in bytes within this module."
	::= { snAgentBrdEntry 24 }

snAgentBrdMemoryAvailable  OBJECT-TYPE
	SYNTAX		CounterBasedGauge64
	MAX-ACCESS		read-only
	STATUS		current
	DESCRIPTION
		"The total memory in bytes available for use within this module."
	::= { snAgentBrdEntry 25 }

snAgentBrdSerialNumber  OBJECT-TYPE
	SYNTAX		DisplayString
	MAX-ACCESS		read-only
	STATUS		current
	DESCRIPTION
		"The Board Serial number. Zero length string indicates that
		module serial number has not been programmed within 
		EEPROM or the module does not support serial number within EEPROM."
	::= { snAgentBrdEntry 26 }

snAgentBrdPartNumber  OBJECT-TYPE
	SYNTAX		DisplayString 
	MAX-ACCESS		read-only
	STATUS		current
	DESCRIPTION
		"The Board Part number. Zero length string indicates that
		module part number has not been programmed within 
		EEPROM or the module does not support part number within EEPROM."
	::= { snAgentBrdEntry 27 }


-- Agent Stacking Board Table


snAgentBrd2Table OBJECT-TYPE
	SYNTAX	SEQUENCE OF SnAgentBrd2Entry
	MAX-ACCESS	not-accessible
	STATUS	current
	DESCRIPTION
		"A table of each physical board information for each unit."
	::= { snAgentBrd 2 }

snAgentBrd2Entry OBJECT-TYPE
	SYNTAX	SnAgentBrd2Entry
	MAX-ACCESS	not-accessible
	STATUS	current
	DESCRIPTION
		"A row in the Agent Board table."
	INDEX	{ snAgentBrd2Unit,  snAgentBrd2Slot }
	::= { snAgentBrd2Table 1 }

SnAgentBrd2Entry ::= SEQUENCE {
	snAgentBrd2Unit
		Integer32,
	snAgentBrd2Slot
		Integer32,
	snAgentBrd2MainBrdDescription
		DisplayString,
	snAgentBrd2MainBrdId
		OCTET STRING,
	snAgentBrd2MainPortTotal
		Integer32,	
	snAgentBrd2ModuleStatus
		INTEGER,
	snAgentBrd2RedundantStatus
		INTEGER
	}

snAgentBrd2Unit OBJECT-TYPE
	SYNTAX   Integer32 
	MAX-ACCESS	read-only
	STATUS	current
	DESCRIPTION
		"The index to the Agent module Table."
	::= { snAgentBrd2Entry 1 }

snAgentBrd2Slot OBJECT-TYPE
	SYNTAX   Integer32
	MAX-ACCESS	read-only
	STATUS	current
	DESCRIPTION
		"The index to the Agent module Table."
	::= { snAgentBrd2Entry 2 }

snAgentBrd2MainBrdDescription OBJECT-TYPE
	SYNTAX DisplayString (SIZE(0..128))
	MAX-ACCESS read-only
	STATUS current
	DESCRIPTION
		"The main board description string."
	::= { snAgentBrd2Entry 3}

snAgentBrd2MainBrdId OBJECT-TYPE
	SYNTAX OCTET STRING
	MAX-ACCESS read-only
	STATUS current
	DESCRIPTION
		"The main board identifier, which can uniquely identify a board
		type. It is an encoded octet string with the following meaning:
		  octet 0  - octet string format version, which identifies the
					 format of this string.
		If format version octet has the value 2, the octets after the
		version octet have the following meaning:
		  octet 1  - product type: 
						BI_WG					0x57
						BI_BB					0x42
						BI_NI					0x4E
						BI_NI2					0x32
						NI_M4					0x4D
						BI_SLB					0x53
		  octet 2  - module type:
						MASTER_FIBER_8G			0x0
						MASTER_FIBER_4G			0x1
						MASTER_COPPER_16		0x2
						SLAVE_FIBER_4G			0x3
						FI_MASTER_FIBER_2G		0x4
						FI_MASTER_FIBER_4G		0x5
						MASTER_COPPER_8G		0x6
						FI_MASTER_FIBER_8G		0x7
						SLAVE_FIBER_8G			0x8
						MASTER_COPPER_12_2		0x9
						SLAVE_COPPER_24			0xA
						FI_SLAVE_COPPER_24		0xB
						SLAVE_100FX_8			0xD
						SLAVE_100FX_16			0xC
						SLAVE_COPPER_8G			0xE
						SLAVE_COPPER_16_2		0xF
						STACK_FIBER_8G			0x10
						STACK_COPPER_8G			0x11
						MASTER_FIBER_2G			0x12	
						SLAVE_100FX_24			0x13
						MASTER_FIBER_0G			0x14	
						POS_622M				0x15
						POS_155M				0x16
						SLAVE_FIBER_2G			0x17
						SLAVE_COPPER_2G			0x18
						FI_SLAVE_FIBER_2G		0x19
						FI_SLAVE_FIBER_4G		0x1A
						FI_SLAVE_FIBER_8G		0x1B
						FI_SLAVE_COPPER_8G		0x1C
						FI_MASTER_COPPER_8G		0x1D
						POS_155M2P				0x1E
						FI_MASTER_COPPER_4G		0x1F
						FI_MASTER_COPPER_2G		0x20
						MASTER_COPPER_4G		0x21
						MASTER_COPPER_2G		0x22
						MASTER_M4_8G			0x23
						MASTER_M4_4G			0x24
						MASTER_M4_2G			0x25
						MASTER_M4_0G			0x26	
						MASTER_M5_0G			0x27	
						POS_2488M				0x28	
						SLAVE_M5_0G				0x29	
						POS_N2488M				0x2A	
						STACK_IPC_48_2			0x2B	
						SLAVE_NPA_FIBER_4G		0x2C	
						ATM_2PORT				0x2D	
						ATM_4PORT				0x2E	
						SLAVE_FIBER_10G			0x2F
						STACK_FES_48_2			0x30
						STACK_FES_24_2			0x31
						STACK_FES_96_4			0x32
						STACK_FES_12G			0x33
						STACK_FESX_24G			0x34
						STACK_FESX_24_2_G		0x35
						STACK_FESX_24_1_G		0x36
						STACK_FESX_48G			0x37
						STACK_FESX_48_2_G		0x38
						STACK_FESX_48_1_G		0x39
						SUPERX_FI_MGMT		    0x40
						SUPERX_FI_2P10G 		0x41
						SUPERX_FI_24GC  		0x42
						SUPERX_FI_24GF  		0x43
						SUPERX_FI_2P10G_WAN 	0x44
						SUPERX_FI_MGMT_II       0x4a
						SLAVE_JC_48E			0xC3	
						SLAVE_JC_48T			0xC4	
						MASTER_JC_M4_8G			0xC5	
						SLAVE_JC_8G				0xC6	
						SLAVE_JC_B16GF			0xC8	
						MASTER_JC_B2404			0xC9	
						SLAVE_JC_B16GC			0xCA	
		  octet 3  - processor type, PVR_M603=3, PVR_M604=4, PVR_M603E=6,
					 PVR_M603EV=7, PVR_M750=8, PVR_M604E=9, PVR_M8245=81
		  octet 4 to
		  octet 5  - processor speed in MHz
		  octet 6  - MAC type:
						MAC_NONE=0
						MAC_SEEQ_10_100=1, 
						MAC_DEC_10_100=2,
						MAC_3COM_10_100=3,
						MAC_X10GMAC_10000=4,
						MAC_SEEQ_1000=5, 
						MAC_GMAC_1000=6,
						MAC_VLSI_1000=7
		  octet 7  - PHY type, PHY_NONE=0, PHY_QSI=1, PHY_BROADCOM=2,
					 PHY_ICS=3, PHY_NATIONAL=4, PHY_LEVEL1=6,
					 PHY_BROADCOM_10_100=7, PHY_LEVEL24=8,
					 PHY_BROADCOM_10000=9 (for 10G),
					 PHY_3COM_10_100=9 (for others)
		  octet 8  - port type, COPPER=0, FIBER=1
		  octet 9  - fiber port type, NONFIBER=0, SX_FIBER=1,
					 LX_FIBER=2, LHX_FIBER=3, LX_SX_FIBER=4,
					 LHB_FIBER=5
		  octet 10 to
		  octet 13 - DRAM size in KBytes
		  octet 14 to
		  octet 17 - boot flash size in KBytes
		  octet 18 to
		  octet 21 - code flash size in KBytes
		  octet 22 to
		  octet 27 - serial number.
		  octet 28 - chassis backplane type. 
			chassis4000	= 	0x00
			chassis8000	=	0x02
			chassis15000	=	0x01
			chassisFISX	=	0x04
			Turbo8		=	0x07 (stack2)
			FastIron2	=	0x06 (stack1)"
	::= { snAgentBrd2Entry 4 }


snAgentBrd2MainPortTotal OBJECT-TYPE
	SYNTAX Integer32
	MAX-ACCESS read-only
	STATUS current
	DESCRIPTION
		"The total number of ports for the main board."
	::= { snAgentBrd2Entry 5 }

snAgentBrd2ModuleStatus OBJECT-TYPE
	SYNTAX  INTEGER {
		moduleEmpty(0),             
		moduleGoingDown(2),
		moduleRejected(3),
		moduleBad(4),
		moduleConfigured(8),
		moduleComingUp(9),
		moduleRunning(10)
		}
	MAX-ACCESS  read-only
	STATUS  current
	DESCRIPTION
		"By default, this mode is set to notActivated(0).
		moduleEmpty(0) ......... The slot of the chassis is empty.
		moduleGoingDown(2) ..... The module is going down.
		moduleRejected(3) ...... The module is being rejected due to wrong configuration.
		moduleBad(4) ........... The module Hardware is bad.
		moduleConfigured(8) ...... The module is configured (stacking)
		moduleComingUp(9) ...... The module is in power-up cycle.
		moduleRunning(10) ....... The module is running."
	::= { snAgentBrd2Entry 6 }

snAgentBrd2RedundantStatus OBJECT-TYPE
	SYNTAX  INTEGER {
		other(1),
		active(2),             
		standby(3),
		crashed(4),
		comingUp(5)
		}
	MAX-ACCESS  read-only
	STATUS  current
	DESCRIPTION
		"The redundant status of a module. Non-management module always
		returns other(1). Management module returns the rest of the
		states."
	::= { snAgentBrd2Entry 7}

-- Trap Receiver Table


-- Trap Receiver Table
-- snAgTrpRcvrTable is deprecated, replaced by fdryTrapReceiverTable.
-- The new table "fdryTrapReceiverTable" combines Ipv4 and Ipv6 configuration of 
-- trap Receiver/managers which to send traps.

snAgTrpRcvrTable OBJECT-TYPE
	SYNTAX	SEQUENCE OF SnAgTrpRcvrEntry
	MAX-ACCESS	not-accessible
	STATUS	deprecated
	DESCRIPTION
		"A table of managers which to send traps."
	::= { snAgentTrp 1 }

snAgTrpRcvrEntry OBJECT-TYPE
	SYNTAX	SnAgTrpRcvrEntry
	MAX-ACCESS	not-accessible
	STATUS	deprecated
	DESCRIPTION
		"A row in the trap receiver table.
		The column snAgTrpRcvrStatus is used to create
		and delete rows in the table. Creation requires
		a SET PDU with objects snAgTrpRcvrIndex,
		snAgTrpRcvrIpAddr, snAgTrpRcvrComm and 
		snAgTrpRcvrStatus."
	INDEX	{ snAgTrpRcvrIndex }
	::= { snAgTrpRcvrTable 1 }

SnAgTrpRcvrEntry ::= SEQUENCE {
	snAgTrpRcvrIndex
		Integer32,
	snAgTrpRcvrIpAddr
		IpAddress,
	snAgTrpRcvrCommunityOrSecurityName
		OCTET STRING,
	snAgTrpRcvrStatus
		INTEGER,
	snAgTrpRcvrUDPPort
		INTEGER,
	snAgTrpRcvrSecurityModel
		INTEGER,
	snAgTrpRcvrSecurityLevel
		INTEGER
	}

snAgTrpRcvrIndex OBJECT-TYPE
	SYNTAX   Integer32
	MAX-ACCESS	read-only
	STATUS	deprecated
	DESCRIPTION
		"The index to the Trap Receiver Table."
	::= { snAgTrpRcvrEntry 1 }

snAgTrpRcvrIpAddr OBJECT-TYPE
	SYNTAX	IpAddress
	MAX-ACCESS	read-write
	STATUS	deprecated
	DESCRIPTION
		"The ip address for
		SNMP manager that is to receive the trap."
	::= { snAgTrpRcvrEntry 2 }

snAgTrpRcvrCommunityOrSecurityName OBJECT-TYPE
	SYNTAX	OCTET STRING (SIZE(0..32))
	MAX-ACCESS	read-write
	STATUS	deprecated
	DESCRIPTION
		"Community string to use. In case of USM (SNMPv3) security model,
		this object is used to provide the security name."
	::= { snAgTrpRcvrEntry 3 }


snAgTrpRcvrStatus OBJECT-TYPE
	SYNTAX	INTEGER {
		other(1),
		valid(2),
		delete(3),
		create(4),
		ignore(5)
		}
	MAX-ACCESS	read-write
	STATUS	deprecated
	DESCRIPTION
		"This object is used to create and
		delete rows in the table and control
		if they are used. The values
		that can be written are:
		  ignore(5)...don't use this entry to
						send traps to at this time
		  delete(3)...deletes the row
		  create(4)...creates a new row

		If the row exists, then a SET with
		value of create(5) returns error
		'badValue'. Deleted rows go away
		immediately. The following values
		can be returned on reads:
		  other(1)....some other case
		  valid(2)....the row exists and is valid
		  ignore(5)...don't use this entry to
						send traps to at this time"
	::= { snAgTrpRcvrEntry 4 }

snAgTrpRcvrUDPPort       OBJECT-TYPE
	SYNTAX	INTEGER	 (0..65535)
	MAX-ACCESS  read-write
	STATUS	deprecated
	DESCRIPTION
		"UDP port number of the trap receiver."
	DEFVAL { 162 }
	::= { snAgTrpRcvrEntry 5 }

snAgTrpRcvrSecurityModel       OBJECT-TYPE
	SYNTAX	INTEGER {
		v1(1),
		v2c(2),
		usm(3)
		}
	MAX-ACCESS  read-write
	STATUS	deprecated
	DESCRIPTION
		"Version of trap format to be used."
	DEFVAL { 1 }
	::= { snAgTrpRcvrEntry 6 }

snAgTrpRcvrSecurityLevel       OBJECT-TYPE
	SYNTAX	INTEGER {
		noAuth(1),
		auth(2),
		authPriv(3)
		}
	MAX-ACCESS  read-write
	STATUS	deprecated
	DESCRIPTION
		"Used for USM (SNMPv3) security model to specify the level of security.
		The security name is provided by snAgTrpRcvrCommunityOrSecurityName."
	DEFVAL { 1 }
	::= { snAgTrpRcvrEntry 7 }


-- Boot Sequence Table


snAgBootSeqTable OBJECT-TYPE
	SYNTAX	SEQUENCE OF SnAgBootSeqEntry
	MAX-ACCESS	not-accessible
	STATUS	current
	DESCRIPTION
		"A table of image load sequnce instructions to the boot code.
		Boot code will start from instruction of the first valid entry
		to load the image. If failed, it will use the second valid
		entry and so on, until a succesful load has completed. Each
		entry must have an unique instruction, duplicate instructions
		will be rejected."
	::= { snAgentBoot 1 }

snAgBootSeqEntry OBJECT-TYPE
	SYNTAX	SnAgBootSeqEntry
	MAX-ACCESS	not-accessible
	STATUS	current
	DESCRIPTION
		"A row in the boot sequence table."
	INDEX	{ snAgBootSeqIndex }
	::= { snAgBootSeqTable 1 }

SnAgBootSeqEntry ::= SEQUENCE {
	snAgBootSeqIndex
		INTEGER,
	snAgBootSeqInstruction
		INTEGER,
	snAgBootSeqIpAddr
		IpAddress,
	snAgBootSeqFilename
		DisplayString,
	snAgBootSeqRowStatus
		INTEGER
	}

snAgBootSeqIndex OBJECT-TYPE
	SYNTAX	INTEGER (1..6)
	MAX-ACCESS	read-only
	STATUS	current
	DESCRIPTION
		"The index to the boot sequence table."
	::= { snAgBootSeqEntry 1 }

snAgBootSeqInstruction OBJECT-TYPE
	SYNTAX	INTEGER {
		fromPrimaryFlash(1),
		fromSecondaryFlash(2),
		fromTftpServer(3),
		fromBootpServer(4),
		fromPcmciaCard1(5),
		fromPcmciaCard2(6) }
	MAX-ACCESS	read-write
	STATUS	current
	DESCRIPTION
		"The instruction for the boot code."
	::= { snAgBootSeqEntry 2 }

snAgBootSeqIpAddr OBJECT-TYPE
	SYNTAX	IpAddress
	MAX-ACCESS	read-write
	STATUS	current
	DESCRIPTION
		"The ip address of the TFTP server if snAgBootSeqInstruction
		was set to 'fromTftpServer'; otherwise, this object is not
		used in any other boot instruction."
	::= { snAgBootSeqEntry 3 }

snAgBootSeqFilename OBJECT-TYPE
	SYNTAX	DisplayString (SIZE (0..32))
	MAX-ACCESS	read-write
	STATUS	current
	DESCRIPTION
		"The image filename on the TFTP server if snAgBootSeqInstruction
		was set to 'fromTftpServer'; otherwise, this object is not
		used in any other boot instruction."
	::= { snAgBootSeqEntry 4 }

snAgBootSeqRowStatus OBJECT-TYPE
	SYNTAX	INTEGER	{
		other(1),
		valid(2),
		delete(3),
		create(4) }
	MAX-ACCESS	read-write
	STATUS	current
	DESCRIPTION
		"To create or delete a boot sequence table entry."
	::= { snAgBootSeqEntry 5 }


-- SP Boot Sequence Table

snAgSpBootSeqTable OBJECT-TYPE
	SYNTAX	SEQUENCE OF SnAgSpBootSeqEntry
	MAX-ACCESS	not-accessible
	STATUS	current
	DESCRIPTION
		"A table of image load sequnce instructions to the boot code for
		the slave (line) modules. Boot code will start from instruction of
		the first valid entry to load the image. If failed, it will use
		the second valid entry and so on, until a succesful load has
		completed. Each entry must have an unique instruction, duplicate
		instructions will be rejected."
	::= { snAgentBoot 2 }

snAgSpBootSeqEntry OBJECT-TYPE
	SYNTAX	SnAgSpBootSeqEntry
	MAX-ACCESS	not-accessible
	STATUS	current
	DESCRIPTION
		"A row in the slave module boot sequence table."
	INDEX	{ snAgSpBootSeqSpNumber, snAgSpBootSeqIndex }
	::= { snAgSpBootSeqTable 1 }

SnAgSpBootSeqEntry ::= SEQUENCE {
	snAgSpBootSeqSpNumber
		INTEGER,
	snAgSpBootSeqIndex
		Integer32,
	snAgSpBootSeqInstruction
		INTEGER,
	snAgSpBootSeqIpAddr
		IpAddress,
	snAgSpBootSeqFilename
		DisplayString,
	snAgSpBootSeqRowStatus
		INTEGER
	}

snAgSpBootSeqSpNumber OBJECT-TYPE
	SYNTAX	INTEGER (0..32)
	MAX-ACCESS  not-accessible
	STATUS	current
	DESCRIPTION
		"The slot numner of a slave/witch processor module for which 
		this boot sequence applies. Setting value 0 applies to all SP
		modules. Index 0 is valid only for setting to simplify the set
		operation for all the modules."
	::= { snAgSpBootSeqEntry 1 }
	
snAgSpBootSeqIndex OBJECT-TYPE
	SYNTAX	Integer32
	MAX-ACCESS  not-accessible
	STATUS	current
	DESCRIPTION
		"The index to the boot sequence table."
	::= { snAgSpBootSeqEntry 2 }

snAgSpBootSeqInstruction OBJECT-TYPE
	SYNTAX	INTEGER {
					fromSpPrimaryFlash(1),
					fromSpSecondaryFlash(2),
					fromMpPrimaryFlash(3),
					fromMpSecondaryFlash(4),
					fromPcmciaCard1(5),
					fromPcmciaCard2(6),
					fromTftpServer(7),
					interactively(8)
				}
	MAX-ACCESS	read-write
	STATUS	current
	DESCRIPTION
		"The instruction for the boot code."
	::= { snAgSpBootSeqEntry 3 }

snAgSpBootSeqIpAddr OBJECT-TYPE
	SYNTAX	IpAddress
	MAX-ACCESS	read-write
	STATUS	current
	DESCRIPTION
		"The ip address of the TFTP server if snAgBootSeqInstruction
		was set to 'fromTftpServer'; otherwise, this object is not
		used in any other boot instruction."
	::= { snAgSpBootSeqEntry 4 }

snAgSpBootSeqFilename OBJECT-TYPE
	SYNTAX	DisplayString (SIZE (0..32))
	MAX-ACCESS	read-write
	STATUS	current
	DESCRIPTION
		"The image filename on the TFTP server if snAgBootSeqInstruction
		was set to 'fromTftpServer'; otherwise, this object is not
		used in any other boot instruction."
	::= { snAgSpBootSeqEntry 5 }

snAgSpBootSeqRowStatus OBJECT-TYPE
	SYNTAX	INTEGER	{
					valid(1),
					delete(2),
					create(3)
				}
	MAX-ACCESS	read-write
	STATUS	current
	DESCRIPTION
		"To create or delete a boot sequence table entry."
	::= { snAgSpBootSeqEntry 6 }

--- Encoded Octet Strings for the Configuration File Transfer


snAgCfgEosTable OBJECT-TYPE
	SYNTAX	SEQUENCE OF SnAgCfgEosEntry
	MAX-ACCESS	not-accessible
	STATUS	current
	DESCRIPTION
		"This table represents the fragmented Configuration File data packet 
		with checksum include in each rows of this table.  A SNMP-SET
		represents configuration file download, and a SNMP-GET represents
		configuration file upload.  This action is only if the SNMP-SET of
		snAgCfgLoad command is sent along with this table consecutively.  The 
		applicable snAgCfgLoad command value is as followings:
		uploadFromFlashToNMS(23),
		downloadToFlashFromNMS(24),
		uploadFromDramToNMS(25),
		downloadToDramFromNMS(26)." 
	::= { snAgCfgEos 1 }


snAgCfgEosEntry OBJECT-TYPE
	SYNTAX	SnAgCfgEosEntry	
	MAX-ACCESS	not-accessible
	STATUS	current
	DESCRIPTION
		"An EOS row in the table of encoded octet strings for table 
		snAgCfgEosTable. "
	INDEX  { snAgCfgEosIndex }
	::= { snAgCfgEosTable 1 }



SnAgCfgEosEntry ::= 
	SEQUENCE {
	snAgCfgEosIndex
		Integer32,
	snAgCfgEosPacket 
		OCTET STRING,
	snAgCfgEosChkSum
		Integer32
	}


snAgCfgEosIndex OBJECT-TYPE
	SYNTAX  Integer32
	MAX-ACCESS  read-only
	STATUS  current
	DESCRIPTION
		 "Each VLAN EOS Buffer Identifier have a multiple 
		 VLAN table entries."
	::= { snAgCfgEosEntry 1 }

snAgCfgEosPacket OBJECT-TYPE
	SYNTAX	OCTET STRING (SIZE(0..1000))
	MAX-ACCESS	read-write
	STATUS	current
	DESCRIPTION
		"An encoded octet string. On reads it contains an integral 
		number of configuration file data packets. The size 
		of each encoded octet string is less than or equal to 1400
		bytes."
	::= { snAgCfgEosEntry 2 }


snAgCfgEosChkSum OBJECT-TYPE
	SYNTAX Integer32
	MAX-ACCESS  read-write
	STATUS  current
	DESCRIPTION
		 "A checksum of each configuration file data packet." 
	::= { snAgCfgEosEntry 3 }


-- Stackable Management Group

snStackGen				OBJECT IDENTIFIER ::= { snStack 1 }
snStackSecSwitchInfo	OBJECT IDENTIFIER ::= { snStack 2 }

-- MIB Objects


-- General Stackable Management Information

snStackPriSwitchMode OBJECT-TYPE
	SYNTAX  INTEGER {
		disabled(0),             
		enabled(1)
		}
	MAX-ACCESS  read-write
	STATUS  current
	DESCRIPTION
		"The Stackable Management Primary Switch mode
		 either enabled or disabled and the default is 
		 disabled mode.
		 enabled(1)...........primary switch enabled
		 disabled(0)..........primary switch disabled"  
	::= { snStackGen 1 }

snStackMaxSecSwitch OBJECT-TYPE
	SYNTAX Integer32
	MAX-ACCESS  read-only
	STATUS  current
	DESCRIPTION
		"The Maximum Secondary Switches are allowed in the
		 Stackable Management Group."
	::= { snStackGen 2 }

snStackTotalSecSwitch OBJECT-TYPE
	SYNTAX Integer32
	MAX-ACCESS  read-only
	STATUS  current
	DESCRIPTION
		"The Total Secondary Switches currently connected to the
		 Stackable Management Group."
	::= { snStackGen 3 }

snStackSyncAllSecSwitch OBJECT-TYPE
	SYNTAX  INTEGER {
		normal(0),
		invalid(1),
		device(2),
		global(3),
		local(4)
		}
	MAX-ACCESS  read-write
	STATUS  current
	DESCRIPTION
		"Synchronize all the secondary switches in the
		 Stackable Management Group with the following commands.
		 device(2)...........device related parameters.
		 global(3)...........global parameters.  
		 local(4)............local parameters.
		 The return result of the above commands are either
		 normal(0)...........normal condition.
		 invalid(1)...........invalid result."  
	::= { snStackGen 4 }

snStackSmSlotIndex OBJECT-TYPE
	SYNTAX	INTEGER (0..8)
	MAX-ACCESS	read-write
	STATUS	current
	DESCRIPTION
		"The Slot 0 is the Master slot and Slot 1-8 are slaves. 
		 All the slot-based MIB data can be retrieved with respect to 
		 this slot index such as snChassis global MIB. "
	::= { snStackGen 5 }

snStackFmpSetProcess OBJECT-TYPE
	SYNTAX	INTEGER { 
						normal(0), 
						pending(1), 
						failure(2)
					}
	MAX-ACCESS	read-only
	STATUS	current
	DESCRIPTION
		"normal(0)  - The set process is either in an idle state or FMP-SET-SUCCESS state.
		 pending(1) - The pending process is waiting for the result of an FMP-SET.
		 failure(2) - The failure result of an FMP-SET."
	::= { snStackGen 6 }




-- Stackable Management Secondary Switch Information Table


snStackSecSwitchTable OBJECT-TYPE
	SYNTAX  SEQUENCE OF SnStackSecSwitchEntry
	MAX-ACCESS  not-accessible
	STATUS  current
	DESCRIPTION
		"If snSwGroupOperMode is configured as basic mode
		 which is VLAN by Port, Layer2 switching,
		 then this table is valid.  Each VLAN switch port
		 could have a number of VLAN IDs."
	::= { snStackSecSwitchInfo 1 }


snStackSecSwitchEntry OBJECT-TYPE
	SYNTAX  SnStackSecSwitchEntry
	MAX-ACCESS  not-accessible
	STATUS  current
	DESCRIPTION
		"An entry in the Stackable Management Secondary Switch 
		 Information table."
	INDEX   { 
		snStackSecSwitchIndex
	}
	::= { snStackSecSwitchTable 1 }


SnStackSecSwitchEntry ::= SEQUENCE {
	snStackSecSwitchIndex
		INTEGER,
	snStackSecSwitchSlotId
		INTEGER,
	snStackSecSwitchPortCnts
		INTEGER,
	snStackSecSwitchEnabled
		INTEGER,
	snStackSecSwitchAck
		INTEGER,
	snStackSecSwitchMacAddr
		MacAddress,
	snStackSecSwitchSyncCmd
		INTEGER, 
	snStackSecSwitchIpAddr
		IpAddress,
	snStackSecSwitchSubnetMask
		IpAddress,
	snStackSecSwitchCfgCmd
		INTEGER 
	}

snStackSecSwitchIndex OBJECT-TYPE
	SYNTAX  INTEGER (1..26)
	MAX-ACCESS  read-only
	STATUS  current
	DESCRIPTION
		"The secondary switch index must not be greater than the snStackMaxSecSwitch."
	::= { snStackSecSwitchEntry 1 }


snStackSecSwitchSlotId OBJECT-TYPE
	SYNTAX  INTEGER (1..26)
	MAX-ACCESS  read-write
	STATUS  current
	DESCRIPTION
		"The secondary switch slot ID must be set before the Configuration 
		 command sent from the primary switch to the secondary switch 
		 either manually or automatically - snStackSecSwitchCfgCmd."
	::= { snStackSecSwitchEntry 2 }

snStackSecSwitchPortCnts OBJECT-TYPE
	SYNTAX  INTEGER (1..26)
	MAX-ACCESS  read-only
	STATUS  current
	DESCRIPTION
		"The number of ports in this secondary switch."
	::= { snStackSecSwitchEntry 3 }

snStackSecSwitchEnabled OBJECT-TYPE
	SYNTAX  INTEGER {
		disabled(0),             
		enabled(1)
		}
	MAX-ACCESS  read-write
	STATUS  current
	DESCRIPTION
		"The secondary switch has been selected to Stackable Management Group."
	::= { snStackSecSwitchEntry 4 }

snStackSecSwitchAck OBJECT-TYPE
	SYNTAX  INTEGER {
		disabled(0),             
		enabled(1)
		}
	MAX-ACCESS  read-only
	STATUS  current
	DESCRIPTION
		"The secondary switch has sent reponse to the primary switch."
	::= { snStackSecSwitchEntry 5 }

snStackSecSwitchMacAddr OBJECT-TYPE
	SYNTAX  MacAddress
	MAX-ACCESS  read-only
	STATUS  current
	DESCRIPTION
		"The secondary switch physical address. The physical address 
		represents a MAC Station."
	::= { snStackSecSwitchEntry 6 }

snStackSecSwitchSyncCmd OBJECT-TYPE
	SYNTAX  INTEGER {
		normal(0),
		invalid(1),
		device(2),
		global(3),
		local(4)
		}
	MAX-ACCESS  read-write
	STATUS  current
	DESCRIPTION
		"Synchronize the secondary switches in the
		 Stackable Management Group with the following commands.
		 device(2)...........device related parameters.
		 global(3)...........global parameters.  
		 local(4)............local parameters.
		 The return result of the above commands are either
		 normal(0)...........normal condition.
		 invalid(1)...........invalid result."  
	::= { snStackSecSwitchEntry 7 }

snStackSecSwitchIpAddr OBJECT-TYPE
	SYNTAX	IpAddress
	MAX-ACCESS  read-write
	STATUS  current
	DESCRIPTION
		"The secondary switch IP Address and is used for 
		 manual-command of snStackSecSwitchCfgCmd."
	::= { snStackSecSwitchEntry 8 }

snStackSecSwitchSubnetMask OBJECT-TYPE
	SYNTAX	IpAddress
	MAX-ACCESS  read-write
	STATUS  current
	DESCRIPTION
		"The secondary switch IP Subnet Mask and is used for 
		 manual-command of snStackSecSwitchCfgCmd."
	::= { snStackSecSwitchEntry 9 }

snStackSecSwitchCfgCmd OBJECT-TYPE
	SYNTAX  INTEGER {
		normal(0),
		invalid(1),
		auto(2),
		manual(3)
		}
	MAX-ACCESS  read-write
	STATUS  current
	DESCRIPTION
		"snStackSecSwitchSlotId must be set before the Configuration 
		 command sent from the primary switch to the secondary switch 
		 either manually or automatically.
		 auto(2)...........auto-configuration command sent.
		 manual(3).........manual-configuration command sent.
						   if manual-mode is used, snStackSecSwitchIpAddr
						   and snStackSecSwitchSubnetMask must be
						   first set before this command is sent.
		 The return result of the above commands are either
		 normal(0)...........normal condition.
		 invalid(1)..........invalid result."  
	::= { snStackSecSwitchEntry 10 }

-- System Logging Group

snAgSysLogGbl	OBJECT IDENTIFIER ::= { snAgentLog 1 }

snAgSysLogGblEnable OBJECT-TYPE
	SYNTAX	INTEGER { disabled(0), enabled(1) }
	MAX-ACCESS	read-write
	STATUS	current
	DESCRIPTION
		"Enable/disable system logging."
	DEFVAL { enabled }
	::= { snAgSysLogGbl 1 }

snAgSysLogGblBufferSize OBJECT-TYPE
	SYNTAX   Integer32
	MAX-ACCESS	read-write
	STATUS	current
	DESCRIPTION
		"The number of dynamic system logging entries."
	DEFVAL { 50 }
	::= { snAgSysLogGbl 2 }

snAgSysLogGblClear OBJECT-TYPE
	SYNTAX	INTEGER { normal(0), clearAll(1), clearDynamic(2), clearStatic(3) }
	MAX-ACCESS	read-write
	STATUS	current
	DESCRIPTION
		"Clear dynamic and/or static system logging buffers."
	::= { snAgSysLogGbl 3 }

snAgSysLogGblCriticalLevel OBJECT-TYPE
	SYNTAX   Integer32
	MAX-ACCESS	read-write
	STATUS	current
	DESCRIPTION
		"Filter events going to the logging buffer. This is a packed
		bit string object of which each bit has the following meaning:
		(bit 0 is the least significant bit).

		  bit position   meaning
		  ------------   -------
			  8-31	 reserved
			  7		 Warning (warning conditions)
			  6		 Notification (normal but significant conditions)
			  5		 Informational (informational messages)
			  4		 Error (error conditions)
			  3		 Emergency (system is unusable)
			  2		 Debugging (debugging messages)
			  1		 Critical (critical conditions)
			  0		 Alert (immediate action needed)

		Setting a critical level bit to 1 makes the logging buffer
		accept the corresponding event. Resetting a critical level
		bit to 0 makes the logging buffer reject the corresponding
		event."
	DEFVAL { 255 }
	::= { snAgSysLogGbl 4 }

snAgSysLogGblLoggedCount OBJECT-TYPE
	SYNTAX	Counter32
	MAX-ACCESS	read-only
	STATUS	current
	DESCRIPTION
		"The number events logged in the system logging buffer."
	::= { snAgSysLogGbl 5 }

snAgSysLogGblDroppedCount OBJECT-TYPE
	SYNTAX	Counter32
	MAX-ACCESS	read-only
	STATUS	current
	DESCRIPTION
		"The number of events dropped."
	::= { snAgSysLogGbl 6 }

snAgSysLogGblFlushedCount OBJECT-TYPE
	SYNTAX	Counter32
	MAX-ACCESS	read-only
	STATUS	current
	DESCRIPTION
		"The number of times that the system logging buffer was cleared."
	::= { snAgSysLogGbl 7 }

snAgSysLogGblOverrunCount OBJECT-TYPE
	SYNTAX	Counter32
	MAX-ACCESS	read-only
	STATUS	current
	DESCRIPTION
		"The number of times that the system logging buffer was wrapped
		around."
	::= { snAgSysLogGbl 8 }

snAgSysLogGblServer OBJECT-TYPE
	SYNTAX  IpAddress
	MAX-ACCESS	read-write
	STATUS	deprecated
	DESCRIPTION
		"IP address of syslog server."
	::= { snAgSysLogGbl 9 }

snAgSysLogGblFacility OBJECT-TYPE
	SYNTAX  INTEGER {
		kern(1),
		user(2),
		mail(3),
		daemon(4),
		auth(5),
		syslog(6),
		lpr(7),
		news(8),
		uucp(9),
		sys9(10),
		sys10(11),
		sys11(12),
		sys12(13),
		sys13(14),
		sys14(15),
		cron(16),
		local0(17),
		local1(18),
		local2(19),
		local3(20),
		local4(21),
		local5(22),
		local6(23),
		local7(24)
		}
	MAX-ACCESS	read-write
	STATUS	current
	DESCRIPTION
		"Facility code."
	DEFVAL { user }
	::= { snAgSysLogGbl 10 }

snAgSysLogGblPersistenceEnable OBJECT-TYPE
	SYNTAX	INTEGER { disabled(0), enabled(1) }
	MAX-ACCESS	read-write
	STATUS	current
	DESCRIPTION
		"Enable/disable system logging persistence."
	DEFVAL { enabled }
	::= { snAgSysLogGbl 11 }

-- Dynamic System Logging Buffer Table

snAgSysLogBufferTable OBJECT-TYPE
	SYNTAX	SEQUENCE OF SnAgSysLogBufferEntry
	MAX-ACCESS	not-accessible
	STATUS	current
	DESCRIPTION
		"Dynamic system logging buffer table."
	::= { snAgentLog 2 }

snAgSysLogBufferEntry OBJECT-TYPE
	SYNTAX	SnAgSysLogBufferEntry
	MAX-ACCESS	not-accessible
	STATUS	current
	DESCRIPTION
		"A row in the dynamic system logging buffer table."
	INDEX	{ snAgSysLogBufferIndex }
	::= { snAgSysLogBufferTable 1 }

SnAgSysLogBufferEntry ::= SEQUENCE {
	snAgSysLogBufferIndex
		Integer32,
	snAgSysLogBufferTimeStamp
		TimeTicks,
	snAgSysLogBufferCriticalLevel
		INTEGER,
	snAgSysLogBufferMessage
		DisplayString,
	snAgSysLogBufferCalTimeStamp
		DisplayString
	}

snAgSysLogBufferIndex OBJECT-TYPE
	SYNTAX   Integer32
	MAX-ACCESS	read-only
	STATUS	current
	DESCRIPTION
		"The index to the dynamic system logging buffer table."
	::= { snAgSysLogBufferEntry 1 }

snAgSysLogBufferTimeStamp OBJECT-TYPE
	SYNTAX	TimeTicks
	MAX-ACCESS	read-only
	STATUS	current
	DESCRIPTION
		"A time stamp when the event is logged."
	::= { snAgSysLogBufferEntry 2 }

snAgSysLogBufferCriticalLevel OBJECT-TYPE
	SYNTAX	INTEGER {
		other(1),
		alert(2),
		critical(3),
		debugging(4),
		emergency(5),
		error(6),
		informational(7),
		notification(8),
		warning(9) }
	MAX-ACCESS	read-only
	STATUS	current
	DESCRIPTION
		"The critical level of this event."
	::= { snAgSysLogBufferEntry 3 }

snAgSysLogBufferMessage OBJECT-TYPE
	SYNTAX	DisplayString
	MAX-ACCESS	read-only
	STATUS	current
	DESCRIPTION
		"The system logging message."
	::= { snAgSysLogBufferEntry 4 }

snAgSysLogBufferCalTimeStamp OBJECT-TYPE
	SYNTAX	DisplayString
	MAX-ACCESS	read-only
	STATUS	current
	DESCRIPTION
		"A time stamp when the event is logged. This object returns
		a NULL terminated time stamp string if the system calendar
		time was set. It returns a zero length string if the system
		calendar time was not set."
	::= { snAgSysLogBufferEntry 5 }


-- Static System Logging Buffer Table

snAgStaticSysLogBufferTable OBJECT-TYPE
	SYNTAX	SEQUENCE OF SnAgStaticSysLogBufferEntry
	MAX-ACCESS	not-accessible
	STATUS	current
	DESCRIPTION
		"Static system logging buffer table."
	::= { snAgentLog 3 }

snAgStaticSysLogBufferEntry OBJECT-TYPE
	SYNTAX	SnAgStaticSysLogBufferEntry
	MAX-ACCESS	not-accessible
	STATUS	current
	DESCRIPTION
		"A row in the static system logging buffer table."
	INDEX	{ snAgStaticSysLogBufferIndex }
	::= { snAgStaticSysLogBufferTable 1 }

SnAgStaticSysLogBufferEntry ::= SEQUENCE {
	snAgStaticSysLogBufferIndex
		INTEGER,
	snAgStaticSysLogBufferTimeStamp
		TimeTicks,
	snAgStaticSysLogBufferCriticalLevel
		INTEGER,
	snAgStaticSysLogBufferMessage
		DisplayString,
	snAgStaticSysLogBufferCalTimeStamp
		DisplayString
	}

snAgStaticSysLogBufferIndex OBJECT-TYPE
	SYNTAX	INTEGER (1..100)
	MAX-ACCESS	read-only
	STATUS	current
	DESCRIPTION
		"The index to the static system logging buffer table."
	::= { snAgStaticSysLogBufferEntry 1 }

snAgStaticSysLogBufferTimeStamp OBJECT-TYPE
	SYNTAX	TimeTicks
	MAX-ACCESS	read-only
	STATUS	current
	DESCRIPTION
		"A time stamp when the event is logged."
	::= { snAgStaticSysLogBufferEntry 2 }

snAgStaticSysLogBufferCriticalLevel OBJECT-TYPE
	SYNTAX	INTEGER {
		other(1),
		alert(2),
		critical(3),
		debugging(4),
		emergency(5),
		error(6),
		informational(7),
		notification(8),
		warning(9) }
	MAX-ACCESS	read-only
	STATUS	current
	DESCRIPTION
		"The critical level of this event."
	::= { snAgStaticSysLogBufferEntry 3 }

snAgStaticSysLogBufferMessage OBJECT-TYPE
	SYNTAX	DisplayString
	MAX-ACCESS	read-only
	STATUS	current
	DESCRIPTION
		"The system logging message."
	::= { snAgStaticSysLogBufferEntry 4 }

snAgStaticSysLogBufferCalTimeStamp OBJECT-TYPE
	SYNTAX	DisplayString
	MAX-ACCESS	read-only
	STATUS	current
	DESCRIPTION
		"A time stamp when the event is logged. This object returns
		a NULL terminated time stamp string if the system calendar
		time was set. It returns a zero length string if the system
		calendar time was not set."
	::= { snAgStaticSysLogBufferEntry 5 }

-- SysLog Server Table

snAgSysLogServerTable OBJECT-TYPE
	SYNTAX	SEQUENCE OF SnAgSysLogServerEntry
	MAX-ACCESS	not-accessible
	STATUS	current
	DESCRIPTION
		"System Log Server table."
	::= { snAgentLog 4 }

snAgSysLogServerEntry OBJECT-TYPE
	SYNTAX	SnAgSysLogServerEntry
	MAX-ACCESS	not-accessible
	STATUS	current
	DESCRIPTION
		"A row in the SysLog Server table."
	INDEX	{snAgSysLogServerIP, snAgSysLogServerUDPPort}
	::= { snAgSysLogServerTable 1 }

SnAgSysLogServerEntry ::= SEQUENCE {
	snAgSysLogServerIP
		IpAddress,
	snAgSysLogServerUDPPort
		INTEGER,
	snAgSysLogServerRowStatus
		INTEGER
	}

snAgSysLogServerIP OBJECT-TYPE
	SYNTAX  IpAddress
	MAX-ACCESS	read-only
	STATUS	current
	DESCRIPTION
		"IP address of syslog server."
	::= { snAgSysLogServerEntry 1 }

snAgSysLogServerUDPPort       OBJECT-TYPE
	SYNTAX	INTEGER	 (0..65535)
	MAX-ACCESS	read-only
	STATUS  current
	DESCRIPTION
		"UDP port number of syslog server."
	::= { snAgSysLogServerEntry 2 }

snAgSysLogServerRowStatus OBJECT-TYPE
	SYNTAX  INTEGER {
		other(1),
		valid(2),
		delete(3),
		create(4)
		}
	MAX-ACCESS  read-write
	STATUS  current
	DESCRIPTION
		"This object is used to create and
		delete row in the table and control
		if they are used. The values
		that can be written are:
		  delete(3)...deletes the row
		  create(4)...creates a new row

		If the row exists, then a SET with
		value of create(4) returns error
		'badValue'. Deleted rows go away
		immediately. The following values
		can be returned on reads:
		  other(1)....some other case
		  valid(2)....the row exists and is valid"
	::= { snAgSysLogServerEntry 3 }

-- Agent System Parameters Configuration Table


snAgentSysParaConfigTable OBJECT-TYPE
	SYNTAX	SEQUENCE OF SnAgentSysParaConfigEntry
	MAX-ACCESS	not-accessible
	STATUS	current
	DESCRIPTION
		"A table of Agent of each board."
	::= { snAgentSysParaConfig 1 }

snAgentSysParaConfigEntry OBJECT-TYPE
	SYNTAX	SnAgentSysParaConfigEntry
	MAX-ACCESS	not-accessible
	STATUS	current
	DESCRIPTION
		"A row in the Agent System Parameters Configuation table."
	INDEX	{ snAgentSysParaConfigIndex }
	::= { snAgentSysParaConfigTable 1 }

SnAgentSysParaConfigEntry ::= SEQUENCE {
	snAgentSysParaConfigIndex
		Integer32,
	snAgentSysParaConfigDescription
		DisplayString,
	snAgentSysParaConfigMin
		Integer32,
	snAgentSysParaConfigMax 
		Integer32,
	snAgentSysParaConfigDefault 
		Integer32,
	snAgentSysParaConfigCurrent
		Integer32
	}

snAgentSysParaConfigIndex OBJECT-TYPE
	SYNTAX  Integer32
	MAX-ACCESS	read-only
	STATUS	current
	DESCRIPTION
		"The index to the Agent System Parameters Configuation Table."
	::= { snAgentSysParaConfigEntry 1 }

snAgentSysParaConfigDescription OBJECT-TYPE
	SYNTAX DisplayString (SIZE(0..32))
	MAX-ACCESS read-only
	STATUS current
	DESCRIPTION
		"The main board description string."
	::= { snAgentSysParaConfigEntry 2 }

snAgentSysParaConfigMin OBJECT-TYPE
	SYNTAX   Integer32
	MAX-ACCESS	read-only
	STATUS	current
	DESCRIPTION
		"The minimum value of this Agent System Parameter."
	::= { snAgentSysParaConfigEntry 3 }

snAgentSysParaConfigMax OBJECT-TYPE
	SYNTAX   Integer32
	MAX-ACCESS	read-only
	STATUS	current
	DESCRIPTION
		"The maximum value of this Agent System Parameter."
	::= { snAgentSysParaConfigEntry 4 }

snAgentSysParaConfigDefault OBJECT-TYPE
	SYNTAX   Integer32
	MAX-ACCESS	read-only
	STATUS	current
	DESCRIPTION
		"The default value of this Agent System Parameter."
	::= { snAgentSysParaConfigEntry 5 }

snAgentSysParaConfigCurrent OBJECT-TYPE
	SYNTAX   Integer32
	MAX-ACCESS	read-write
	STATUS	current
	DESCRIPTION
		"The current configurated value of this Agent System Parameter."
	::= { snAgentSysParaConfigEntry 6 }


-- Agent Configured Module Table


snAgentConfigModuleTable OBJECT-TYPE
	SYNTAX	SEQUENCE OF SnAgentConfigModuleEntry
	MAX-ACCESS	not-accessible
	STATUS	current
	DESCRIPTION
		"A table of each configured module information."
	::= { snAgentConfigModule 1 }

snAgentConfigModuleEntry OBJECT-TYPE
	SYNTAX	SnAgentConfigModuleEntry
	MAX-ACCESS	not-accessible
	STATUS	current
	DESCRIPTION
		"A row in the Agent Configured Module table."
	INDEX	{ snAgentConfigModuleIndex }
	::= { snAgentConfigModuleTable 1 }

SnAgentConfigModuleEntry ::= SEQUENCE {
	snAgentConfigModuleIndex
		Integer32,
	snAgentConfigModuleType
		INTEGER,
	snAgentConfigModuleRowStatus
		INTEGER,
	snAgentConfigModuleDescription
		DisplayString,
	snAgentConfigModuleOperStatus
		DisplayString,
	snAgentConfigModuleSerialNumber
		DisplayString,
	snAgentConfigModuleNumberOfPorts
		Integer32,
	snAgentConfigModuleMgmtModuleType
		INTEGER,
	snAgentConfigModuleNumberOfCpus
		Integer32
	}

snAgentConfigModuleIndex OBJECT-TYPE
	SYNTAX   Integer32
	MAX-ACCESS	read-only
	STATUS	current
	DESCRIPTION
		"The index to the Agent Configured Module Table."
	::= { snAgentConfigModuleEntry 1 }

snAgentConfigModuleType OBJECT-TYPE
	SYNTAX	INTEGER	{
		bi8PortGigManagementModule(0),
		bi4PortGigManagementModule(1),
		bi16PortCopperManagementModule(2),
		bi4PortGigModule(3),
		fi2PortGigManagementModule(4),
		fi4PortGigManagementModule(5),
		bi8PortGigCopperManagementModule(6),
		fi8PortGigManagementModule(7),
		bi8PortGigModule(8),
		bi12PortGigCopper2PortGigFiberManagement(9),
		bi24PortCopperModule(10),
		fi24PortCopperModule(11),
		bi16Port100FXModule(12),
		bi8Port100FXModule(13),
		bi8PortGigCopperModule(14),
		bi12PortGigCopper2PortGigFiber(15),
		bi2PortGigManagementModule(18),
		bi24Port100FXModule(19),
		bi0PortManagementModule(20),
		pos622MbsModule(21),
		pos155MbsModule(22),
		bi2PortGigModule(23),
		bi2PortGigCopperModule(24),
		fi2PortGigModule(25),
		fi4PortGigModule(26),
		fi8PortGigModule(27),
		fi8PortGigCopperModule(28),
		fi8PortGigCopperManagementModule(29),
		pos155Mbs2PModule(30),
		fi4PortGigCopperManagementModule(31),
		fi2PortGigCopperManagementModule(32),
		bi4PortGigCopperManagementModule(33),
		bi2PortGigCopperManagementModule(34),
		bi8PortGigM4ManagementModule(35),
		bi4PortGigM4ManagementModule(36),
		bi2PortGigM4ManagementModule(37),
		bi0PortGigM4ManagementModule(38),
		bi0PortWSMManagementModule(39),
		biPos2Port2488MbsModule(40),
		bi0PortWSMModule(41),
		niPos2Port2488MbsModule(42),
		ni4802(43),
		bi4PortGigNPAModule(44),
		biAtm2Port155MbsModule(45),
		biAtm4Port155MbsModule(46),
		bi1Port10GigModule(47),
		fes4802Module(48),
		fes2402Module(49),
		fes9604Module(50),
		fes12GigCopperAndGigFiberModule(51),
		fesx24GigModule(52),
		fesx24Gig2TenGigModule(53),
		fesx24Gig1TenGigModule(54),
		fesx48GigModule(55),
		fesx48Gig2TenGigModule(56),
		fesx48Gig1TenGigModule(57),
		bi40PortGigCopperHVModule(58), --unused
		bi60PortGigCopperHVModule(59), --unused
		bi8Port10GigModule(60), --unused
		bi10PortGigHVModule(61), --unused
		bi20PortGigHVModule(62), --unused
		bi24PortGigModule(63), --unused
		bi24PortGigCopperModule(64), --unused
		bi48PortGigCopperModule(65), --unused
		bi24PortGigFiberModule(66), --unused
		ni4Port10GigSPModule(75), --unused
		ni40PortGigSPModule(76), --unused
		ni40PortGigCopperSPModule(77), --unused
		ni2Port10GigSPModule(78), --unused
		ni10PortGigSPModule(79), --unused
		ni20PortGigSPModule(80), --unused
		xmr4Port10GigSPModule(81), --unused
		xmr20PortGigSPModule(82), --unused
		xmr2Port10GigSPModule(83), --unused
		xmr20PortGigCopperSPModule(84), --unused
		xmr20PortGigFXSPModule(85), --unused
		niImrMrManagementModule(86), --unused
		niXmrMrManagementModule(87), --unused
		xer4Port10GigSPModule(88), --unused
		xer2Port10GigSPModule(89), --unused
		xer20PortGigCopperSPModule(90), --unused
		xer20PortGigFXSPModule(91), --unused
		mlx4Port10GigSPModule(92), --unused
		mlx2Port10GigSPModule(93), --unused
		mlx20PortGigCopperSPModule(94), --unused
		mlx20PortGigFXSPModule(95), --unused
		mlx48PortGigMrj21SPModule(103), --unused		
		fesx24GigFiberGigCopperModule(112),
		fesx24GigFiber2TenGigModule(113),
		fesx24GigFiber1TenGigModule(114),

		-- Modules for FGS/FLS family
		fgs24PortManagementModule(144),  
		fgs48PortManagementModule(145),   
		fgsXfp2Port10gModule(152),  
		fgsCx42Port10gModule(153), 
		fgsXfp1Cx41Port10gModule(154),  
		fgsXpf1Port10gModule(155),    
		fls24PortCopperBaseModule(160),   
		fls48PortCopperBaseModule(161),   
		flsXfp1Port10gModule(168),   
		flsCx41Port10gModule(169),  

		--Modules for FCX family
		fcx624SBaseModule(176),   
		fcx648SBaseModule(177),   
		fcx624SPoeBaseModule(180),   
		fcx648SPoeBaseModule(181),   
		fcxXfp2Port10gModule(184),    
		fcxCx42Port16gModule(185),   
		fcx624SFBaseModule(192),   

		biFiJc48ePort100fxIpcModule(195),
		biFiJc48tPort100fxIpcModule(196),
		biFiJc8PortGigM4ManagementModule(197),
		biFiJc8PortGigIgcModule(198),
		biFiJc16PortGigIgcModule(200),
		biJc24PortCopperIpc4GigIgcModule(201),
		biJc16PortGigCopperIgcModule(202),
		biFiJc24Port100fxIpcModule(206),
		bi2Port10GigModule(207),
		biJc48tPortRJ21OmpModule(208),
		biJc48ePortRJ45OmpModule(209),
		biJc24PortIpcRJ45PoeModule(212),
		biJc2PortGigIgcM4ManagementModule(214),

		--Modules for MG-8, RX, XMR, MLX
		
		fdryBi4Port10GigModule(1048), --
		fdryBi40PortGigModule(1049), --
		fdryBi1Port100FXManagementModule(1050),
		fdryBi2Port10GigModule(1051), --
		fdryBi40PortGigCopperModule(1052), --
		fdryBi60PortGigCopperModule(1053), --
		fdryBi4Port10GigHVModule(1054), --
		fdryBi2Port10GigHVModule(1055), --
		fdryBi8Port10GigHVModule(1056), --
		fdryBi40PortGigHVModule(1057), --
		fdryBi40PortGigCopperHVModule(1058), --
		fdryBi60PortGigCopperHVModule(1059), --
		fdryBi8Port10GigModule(1060), --
		fdryBi10PortGigHVModule(1061), --
		fdryBi20PortGigHVModule(1062), --
		fdryBi24PortGigModule(1063), --
		fdryBi24PortGigCopperModule(1064), --
		fdryBi48PortGigCopperModule(1065),
		fdryBi24PortGigFiberModule(1066),
		fdryBi16Port10GigModule(1067),
		fdryNi4Port10GigSPModule(1075),
		fdryNi40PortGigSPModule(1076),
		fdryNi40PortGigCopperSPModule(1077),
		fdryNi2Port10GigSPModule(1078),
		fdryNi10PortGigSPModule(1079),
		fdryNi20PortGigSPModule(1080),
		fdryXmr4Port10GigSPModule(1081), --
		fdryXmr20PortGigSPModule(1082), --
		fdryXmr2Port10GigSPModule(1083), --
		fdryXmr20PortGigCopperSPModule(1084), --
		fdryXmr20PortGigFXSPModule(1085), --
		fdryNiImrMrManagementModule(1086),
		fdryNiXmrMrManagementModule(1087),
		fdryMlx4Port10GigSPModule(1088), --
		fdryMlx2Port10GigSPModule(1089), --
		fdryMlx20PortGigCopperSPModule(1090), --
		fdryMlx20PortGigFXSPModule(1091), --
		niMlx8Port10GigSPModule (1092),
		niCes24PortFiberModule(1096),
		niCes24PortCopperModule(1097),
		niCes2Port10GigModule(1098),
		niCes48PortFiberModule(1099),
		niCes48PortCopperModule(1100),
		niCes48PortFiberWith2Port10GModule(1101),
		niCes48PortCopperWith2Port10GModule(1102),		
		fdryMlx48PortGigMrj21SPModule(1103), --
		fdryXmr2PortOC192SPModule(1104), --
		fdryXmr1PortOC192SPModule(1105), --
		fdryXmr8PortOC48SPModule(1106), --
		fdryXmr4PortOC48SPModule(1107), --
		fdryXmr2PortOC48SPModule(1108), --
		fdryNiMlxMrManagementModule(1109),--
		
		--Modules for FastIron Superx, SXR8, SXR16, V4 and V6 Modules

		fdryFiV4Sx12ComboPortManagementModule(2064),
		fdryFiV4Sx2Port10gModule(2065),
		fdryFiV4Sx24PortGigCopperModule(2066),
		fdryFiV4Sx24PortGigFiberModule(2067),
		fdryFiV4Sx2Port10gLanWanModule(2068),		
		fdryFiV4Sx24Port100m1gFiberModule(2069),		
		fdryFiV4Sx12ComboPortManagement2Module(2074),
		fdryFiV4Sx210gPortManagementModule(2080),
		fdryFiSx0PortManagementModule(2081),
		fdryFiV4Sx4g4fPortManagementModule(2083),
		fdryFiV6Sx12ComboPortManagementModule(2096),
		fdryFiV6Sx24PortGigCopperModule(2098),
		fdryFiV6Sx2Port10gModule(2100),
		fdryFiV6Sx24Port100m1gFiberModule(2101),
		fdryFiV6Sx210gPortManagementModule(2102),
		fdryFiV6Sx48PortGigCopperPoeModule(2103),
		fdryFiV6Sx4g4fPortManagementModule(2104),
		fdryFiV6Sx12ComboPortManagement2Module(2105),		
		fdryFiV6Sx48PortGigCopperModule(2106),
		fdryFiV6SxXl0PortManagementModule(2112),
		fdryFiV6SxXl210gPortManagementModule(2113),

		-- Modules for FWS family (unused after FI8.0.20)
		--fdryFws24PortCopperBaseModule(2224),  
		--fdryFws48PortCopperBaseModule(2225),   
		--fdryFws24GPortCopperBaseModule(2226),  
		--fdryFws48GPortCopperBaseModule(2227),  

		--Modules for FCX family
		fdryFcx624BaseModule(2208),
		fdryFcx648BaseModule(2209),
		fdryFcxSfpPlus4Port10gModule(2220),

		--Modules for ICX6610 family
		fdryIcx6610624BaseModule(2240),
		fdryIcx6610648BaseModule(2241),
		fdryIcx6610624PoeBaseModule(2244),
		fdryIcx6610648PoeBaseModule(2245),
		fdryIcx6610624FBaseModule(2246),
		fdryIcx6610DualMode8PortModule(2248),
		fdryIcx6610Qsfp10Port160gModule(2249),

		--Modules for ICX6430 family
		fdryIcx6430624BaseModule(2016),
		fdryIcx6430648BaseModule(2017),
		fdryIcx6430624PoeBaseModule(2020),
		fdryIcx6430648PoeBaseModule(2021),
		fdryIcx6430sfp4Port4gModule(2024),
		fdryIcx6430612CBaseModule(2137),
		fdryIcx6430Copper2Port2gModule(2138),
		fdryIcx6430sfp2Port2gModule(2139),
	
		--Modules for ICX6450 family
		fdryIcx6450624BaseModule(2032),
		fdryIcx6450648BaseModule(2033),
		fdryIcx6450624PoeBaseModule(2036),
		fdryIcx6450648PoeBaseModule(2037),
		fdryIcx6450sfp4Port40gModule(2040),
		fdryIcx6450612CPDBaseModule(2140),
		fdryIcx6450Copper2Port2gModule(2141),
		fdryIcx6450sfp2Port2gModule(2142),

		--Modules for ICX6650 family
		fdryIcx665056BaseModule(2055),
		fdryIcx6650sfp4Port40gModule(2056),
		fdryIcx6650sfp8Port10gModule(2057),

		--Modules for ICX7750 family
		fdryIcx775048CBaseModule(2136),
		fdryIcx775048FBaseModule(2135),
		fdryIcx775026QBaseModule(2134),
		fdryIcx7750QSFP6port40gModule(2132),
		fdryIcx77506Q6port40gModule(2133),

		--Modules for ICX7450 family
		fdryIcx7450624BaseModule(2224),
		fdryIcx7450648BaseModule(2225),
		fdryIcx7450648FBaseModule(2227),
		fdryIcx7450624PoeBaseModule(2228),
		fdryIcx7450648PoeBaseModule(2229),
		fdryIcx7450632ZPBaseModule(2230),
		fdryIcx7400sfpplus4Port40gModule(2233),
		fdryIcx7400copper4Port40gModule(2234),
		fdryIcx7400sfp4Port4gModule(2235),
		fdryIcx7400qsfpplus1Port40gModule(2236),
		
		--Modules for ICX7250 family
		fdryIcx7250624BaseModule(2162),
		fdryIcx7250648BaseModule(2163),
		fdryIcx7250624GBaseModule(2160),
		fdryIcx7250624PoeBaseModule(2164),
		fdryIcx7250648PoeBaseModule(2165),
		fdryIcx7250sfpplus8Port80gModule(2169),
		fdryIcx7250sfpplus4Port4gModule(2168)
		}	
	MAX-ACCESS read-write
	STATUS current
	DESCRIPTION
		"The Configured Module Type."
	::= { snAgentConfigModuleEntry 2 }


snAgentConfigModuleRowStatus OBJECT-TYPE
	SYNTAX	INTEGER	{
		other(1),
		valid(2),
		delete(3),
		create(4) }
	MAX-ACCESS	read-write
	STATUS	current
	DESCRIPTION
		"To create or delete a configured module table entry."
	::= { snAgentConfigModuleEntry 3 }


snAgentConfigModuleDescription OBJECT-TYPE
	SYNTAX	DisplayString
	MAX-ACCESS	read-only
	STATUS	current
	DESCRIPTION
		"A description of the configured module."
	::= { snAgentConfigModuleEntry 4 }


snAgentConfigModuleOperStatus OBJECT-TYPE
	SYNTAX	DisplayString
	MAX-ACCESS	read-only
	STATUS	current
	DESCRIPTION
		"Module operational status. Zero length string indicates
		that physical module has not been inserted to the chassis."
	::= { snAgentConfigModuleEntry 5 }


snAgentConfigModuleSerialNumber OBJECT-TYPE
	SYNTAX	DisplayString
	MAX-ACCESS	read-only
	STATUS	current
	DESCRIPTION
		"Module serial number. Zero length string indicates that
		module serial number EEPROM has not been programmed or
		the module does not support serial number EEPROM."
	::= { snAgentConfigModuleEntry 6 }


snAgentConfigModuleNumberOfPorts OBJECT-TYPE
	SYNTAX   Integer32
	MAX-ACCESS	read-only
	STATUS	current
	DESCRIPTION
		"The number of ports of module."
	::= { snAgentConfigModuleEntry 7 }


snAgentConfigModuleMgmtModuleType OBJECT-TYPE
	SYNTAX	INTEGER	{
		other(1),
		nonManagementModule(2),
		unknownManagementModule(3),
		m1ManagementModule(4),
		m2ManagementModule(5),
		m3ManagementModule(6),
		m4ManagementModule(7),
		m5ManagementModule(8),
		jetcoreStackManagementModule(9), 
		muchoManagementModule(10),
		rottWeilerManagementModule(11),
		fesXStackManagementModule(12),
		fgsStackManagementModule(13),
		niCesManagementModule(14),
		fastIronSuperXManagementModule(15),
		fastIronSXRManagementModule(16),
		fastIronV6SuperXManagementModule(17),
		fastIronV6SXRManagementModule(18)
		}	
	MAX-ACCESS	read-only
	STATUS	current
	DESCRIPTION
		"Management module type."
	::= { snAgentConfigModuleEntry 8 }


snAgentConfigModuleNumberOfCpus OBJECT-TYPE
	SYNTAX   Integer32
	MAX-ACCESS	read-only
	STATUS	current
	DESCRIPTION
		"The number of module CPUs."
	::= { snAgentConfigModuleEntry 9 }


-- Agent System Parameters stacking Configuration Table

snAgentConfigModule2Table OBJECT-TYPE
	SYNTAX	SEQUENCE OF SnAgentConfigModule2Entry
	MAX-ACCESS	not-accessible
	STATUS	current
	DESCRIPTION
		"A table of each configured stacking module information."
	::= { snAgentConfigModule 2 }

snAgentConfigModule2Entry OBJECT-TYPE
	SYNTAX	SnAgentConfigModule2Entry
	MAX-ACCESS	not-accessible
	STATUS	current
	DESCRIPTION
		"A row in the Agent Configured Stacking Module table."
	INDEX	{ snAgentConfigModule2Unit, 
					 snAgentConfigModule2Slot 
	}
	::= { snAgentConfigModule2Table 1 }

SnAgentConfigModule2Entry ::= SEQUENCE {
	snAgentConfigModule2Unit
		Integer32,
	snAgentConfigModule2Slot
		Integer32,
	snAgentConfigModule2Type
		INTEGER,
	snAgentConfigModule2RowStatus
		INTEGER,
	snAgentConfigModule2Description
		DisplayString,
	snAgentConfigModule2OperStatus
		DisplayString,
	snAgentConfigModule2SerialNumber
		DisplayString,
	snAgentConfigModule2NumberOfPorts
		Integer32,
	snAgentConfigModule2MgmtModuleType
		INTEGER,
	snAgentConfigModule2NumberOfCpus
		Integer32
	}

snAgentConfigModule2Unit OBJECT-TYPE
	SYNTAX   Integer32
	MAX-ACCESS	read-only
	STATUS	current
	DESCRIPTION
		"The index to the Agent Configured Module Table."
	::= { snAgentConfigModule2Entry 1 }
	
snAgentConfigModule2Slot OBJECT-TYPE
	SYNTAX   Integer32
	MAX-ACCESS	read-only
	STATUS	current
	DESCRIPTION
		"The index to the Agent Configured Module Table."
	::= { snAgentConfigModule2Entry 2 }

snAgentConfigModule2Type OBJECT-TYPE
	SYNTAX	INTEGER	{
		fgs24PortManagementModule(144),   
		fgs48PortManagementModule(145),   
		fgsXfp2Port10gModule(152),  
		fgsCx42Port10gModule(153),  
		fgsXfp1Cx41Port10gModule(154),  
		fgsXpf1Port10gModule(155),   
		fls24PortCopperBaseModule(160),   
		fls48PortCopperBaseModule(161),   
		flsXfp1Port10gModule(168),   
		flsCx41Port10gModule(169),  
		fcx624SBaseModule(176),   
		fcx648SBaseModule(177),   
		fcx624SPoeBaseModule(180),   
		fcx648SPoeBaseModule(181),   
		fcxXfp2Port10gModule(184),   
		fcxCx42Port16gModule(185),   
		fcx624SFBaseModule(192), 
		
		-- Modules for FWS family (unused after FI8.0.20)
		--fdryFws24PortCopperBaseModule(2224),   
		--fdryFws48PortCopperBaseModule(2225),  
		--fdryFws24GPortCopperBaseModule(2226),  
		--fdryFws48GPortCopperBaseModule(2227), 
		
		--Modules for FCX family
		fdryFcx624BaseModule(2208),
		fdryFcx648BaseModule(2209),
		fdryFcxSfpPlus4Port10gModule(2220),
		
		--Modules for ICX6610 family
		fdryIcx6610624BaseModule(2240),
		fdryIcx6610648BaseModule(2241),
		fdryIcx6610624PoeBaseModule(2244),
		fdryIcx6610648PoeBaseModule(2245),
		fdryIcx6610624FBaseModule(2246),
		fdryIcx6610DualMode8PortModule(2248),
		fdryIcx6610Qsfp10Port160gModule(2249),

		--Modules for ICX6430 family
		fdryIcx6430624BaseModule(2016),
		fdryIcx6430648BaseModule(2017),
		fdryIcx6430624PoeBaseModule(2020),
		fdryIcx6430648PoeBaseModule(2021),
		fdryIcx6430sfp4Port4gModule(2024),
		fdryIcx6430612CBaseModule(2137),
		fdryIcx6430Copper2Port2gModule(2138),
		fdryIcx6430sfp2Port2gModule(2139),
	
		--Modules for ICX6450 family
		fdryIcx6450624BaseModule(2032),
		fdryIcx6450648BaseModule(2033),
		fdryIcx6450624PoeBaseModule(2036),
		fdryIcx6450648PoeBaseModule(2037),
		fdryIcx6450sfp4Port40gModule(2040),
		fdryIcx6450612CPDBaseModule(2140),
		fdryIcx6450Copper2Port2gModule(2141),
		fdryIcx6450sfp2Port2gModule(2142),

		--Modules for ICX6650 family
		fdryIcx665056BaseModule(2055),
		fdryIcx6650sfp4Port40gModule(2056),
		fdryIcx6650sfp8Port10gModule(2057),

		--Modules for ICX7750 family
		fdryIcx775048CBaseModule(2136),
		fdryIcx775048FBaseModule(2135),
		fdryIcx775026QBaseModule(2134),
		fdryIcx7750QSFP6port40gModule(2132),
		fdryIcx77506Q6port40gModule(2133),

		--Modules for ICX7450 family
		fdryIcx7450624BaseModule(2224),
		fdryIcx7450648BaseModule(2225),
		fdryIcx7450648FBaseModule(2227),
		fdryIcx7450624PoeBaseModule(2228),
		fdryIcx7450648PoeBaseModule(2229),
		fdryIcx7450632ZPBaseModule(2230),
		fdryIcx7400sfpplus4Port40gModule(2233),
		fdryIcx7400copper4Port40gModule(2234),
		fdryIcx7400sfp4Port4gModule(2235),
		fdryIcx7400qsfpplus1Port40gModule(2236),

		--Modules for ICX7250 family
		fdryIcx7250624BaseModule(2162),
		fdryIcx7250648BaseModule(2163),
		fdryIcx7250624GBaseModule(2160),
		fdryIcx7250624PoeBaseModule(2164),
		fdryIcx7250648PoeBaseModule(2165),
		fdryIcx7250sfpplus8Port80gModule(2169),
		fdryIcx7250sfpplus4Port4gModule(2168)	
		}	
	MAX-ACCESS read-write
	STATUS current
	DESCRIPTION
		"The Configured Module Type."
	::= { snAgentConfigModule2Entry 3 }


snAgentConfigModule2RowStatus OBJECT-TYPE
	SYNTAX	INTEGER	{
		other(1),
		valid(2),
		delete(3),
		create(4) }
	MAX-ACCESS	read-write
	STATUS	current
	DESCRIPTION
		"To create or delete a configured module table entry."
	::= { snAgentConfigModule2Entry 4 }


snAgentConfigModule2Description OBJECT-TYPE
	SYNTAX	DisplayString
	MAX-ACCESS	read-only
	STATUS	current
	DESCRIPTION
		"A description of the configured module."
	::= { snAgentConfigModule2Entry 5 }


snAgentConfigModule2OperStatus OBJECT-TYPE
	SYNTAX	DisplayString
	MAX-ACCESS	read-only
	STATUS	current
	DESCRIPTION
		"Module operational status. Zero length string indicates
		that physical module has not been inserted to the chassis."
	::= { snAgentConfigModule2Entry 6 }


snAgentConfigModule2SerialNumber OBJECT-TYPE
	SYNTAX	DisplayString
	MAX-ACCESS	read-only
	STATUS	current
	DESCRIPTION
		"Module serial number. Zero length string indicates that
		module serial number EEPROM has not been programmed or
		the module does not support serial number EEPROM."
	::= { snAgentConfigModule2Entry 7 }


snAgentConfigModule2NumberOfPorts OBJECT-TYPE
	SYNTAX   Integer32
	MAX-ACCESS	read-only
	STATUS	current
	DESCRIPTION
		"The number of ports of module."
	::= { snAgentConfigModule2Entry 8 }


snAgentConfigModule2MgmtModuleType OBJECT-TYPE
	SYNTAX	INTEGER	{
		other(1),
		nonManagementModule(2),
		unknownManagementModule(3),
		m1ManagementModule(4),
		m2ManagementModule(5),
		m3ManagementModule(6),
		m4ManagementModule(7),
		m5ManagementModule(8),
		jetcoreStackManagementModule(9),
		muchoManagementModule(10),
		rottWeilerManagementModule(11),
		fesXStackManagementModule(12),
		fgsStackManagementModule(13) }
	MAX-ACCESS	read-only
	STATUS	current
	DESCRIPTION
		"Management module type."
	::= { snAgentConfigModule2Entry 9 }


snAgentConfigModule2NumberOfCpus OBJECT-TYPE
	SYNTAX   Integer32
	MAX-ACCESS	read-only
	STATUS	current
	DESCRIPTION
		"The number of module CPUs."
	::= { snAgentConfigModule2Entry 10 }


-- Agent User Access Group


snAgentUserGbl OBJECT IDENTIFIER ::= { snAgentUser 1 }

snAgentUserMaxAccnt         OBJECT-TYPE
	SYNTAX   Integer32
	MAX-ACCESS	read-only
	STATUS	current
	DESCRIPTION
		"Maximum number of user account entries can be configured."
	::= { snAgentUserGbl 1 }


-- Agent User Account Table


snAgentUserAccntTable       OBJECT-TYPE
	SYNTAX	SEQUENCE OF SnAgentUserAccntEntry
	MAX-ACCESS	not-accessible
	STATUS	current
	DESCRIPTION
		"A table of user account information."
	::= { snAgentUser 2 }

snAgentUserAccntEntry       OBJECT-TYPE
	SYNTAX	SnAgentUserAccntEntry
	MAX-ACCESS	not-accessible
	STATUS	current
	DESCRIPTION
		"A row in the Agent User table."
	INDEX	{ snAgentUserAccntName }
	::= { snAgentUserAccntTable 1 }

SnAgentUserAccntEntry ::= SEQUENCE {
	snAgentUserAccntName
		DisplayString,
	snAgentUserAccntPassword
		DisplayString,
	snAgentUserAccntEncryptCode
		Integer32,
	snAgentUserAccntPrivilege
		Integer32,
	snAgentUserAccntRowStatus
		INTEGER
	}

snAgentUserAccntName        OBJECT-TYPE
	SYNTAX  DisplayString (SIZE (1..48))
	MAX-ACCESS	read-only
	STATUS	current
	DESCRIPTION
		"The user name."
	::= { snAgentUserAccntEntry 1 }

snAgentUserAccntPassword    OBJECT-TYPE
	SYNTAX	DisplayString (SIZE (0..48))
	MAX-ACCESS	read-write
	STATUS	current
	DESCRIPTION
		"The user password."
	::= { snAgentUserAccntEntry 2 }

snAgentUserAccntEncryptCode OBJECT-TYPE
	SYNTAX   Integer32
	MAX-ACCESS	read-write
	STATUS	current
	DESCRIPTION
		"The password encryption method code."
	::= { snAgentUserAccntEntry 3 }

snAgentUserAccntPrivilege   OBJECT-TYPE
	SYNTAX   Integer32
	MAX-ACCESS	read-write
	STATUS	current
	DESCRIPTION
		"The user privilege."
	::= { snAgentUserAccntEntry 4 }

snAgentUserAccntRowStatus   OBJECT-TYPE
	SYNTAX	INTEGER	{
		other(1),
		valid(2),
		delete(3),
		create(4),
		modify(5) }
	MAX-ACCESS	read-write
	STATUS	current
	DESCRIPTION
		"To create or delete a user account table entry."
	::= { snAgentUserAccntEntry 5 }

-- Agent Redundant Group


snAgentRedunGbl OBJECT IDENTIFIER ::= { snAgentRedundant 1 }

snAgentRedunActiveMgmtMod      OBJECT-TYPE
	SYNTAX   Integer32
	MAX-ACCESS	read-write
	STATUS	current
	DESCRIPTION
		"Slot number of the active management module. Setting
		this object does not take effect immediately. Saving
		configuration data to flash storage and reboot the
		system are required to take effect. Setting a value of 0
		requests the system to auto-select an active management
		module after power up."
	DEFVAL { 0 }
	::= { snAgentRedunGbl 1 }

snAgentRedunSyncConfig         OBJECT-TYPE
	SYNTAX   Integer32
	MAX-ACCESS	read-write
	STATUS	current
	DESCRIPTION
		"Frequency of the backup management module copying the
		configuration data from the active management module.
		Each unit is 1 second. Setting a value 0 will disable
		the synchronization copy. Setting a negative value will
		initiate the synchronization copy once immediately."
	::= { snAgentRedunGbl 2 }

snAgentRedunBkupCopyBootCode   OBJECT-TYPE
	SYNTAX	INTEGER { disabled(0), enabled(1) }
	MAX-ACCESS	read-write
	STATUS	current
	DESCRIPTION
		"If enabled(1), the backup management module copies the boot code
		from the active management module to its boot code flash storage
		after power up, and whenever the active management module's boot
		code is updated. The backup management module does not copy if
		both boot codes were identical."
	DEFVAL { disabled }
	::= { snAgentRedunGbl 3 }

snAgentEnableMgmtModRedunStateChangeTrap OBJECT-TYPE
	SYNTAX	INTEGER { disabled(0), enabled(1) }
	MAX-ACCESS	read-write
	STATUS	current
	DESCRIPTION
		"Indicates whether the SNMP agent process is permitted to
		generate management module redundancy state change traps."
	DEFVAL { enabled }
	::= { snAgentRedunGbl 4 }

snAgentRedunBkupBootLoad       OBJECT-TYPE
	SYNTAX	INTEGER {
		normal(1),
		operationError(17),
		downloadBackup(20)
		}
	MAX-ACCESS	read-write
	STATUS	current
	DESCRIPTION
		"Action object to down load a new boot code from boot flash storage
		of the active management module to the backup management module.
		The following are returned values from get operation:
		  normal(1)............no operation
		  operationError(17)...error codes

		The following are input values from set operation:
		  downloadBackup(20)...download the boot code from the active
							   management module to the backup management
							   module

		Any set operation is rejected during loading until error
		or normal state is reached."
	::= { snAgentRedunGbl 5 }

snAgentRedunSwitchOver         OBJECT-TYPE
	SYNTAX	INTEGER {
		other(1),
		reset(2)
		}
	MAX-ACCESS	read-write
	STATUS	current
	DESCRIPTION
		"To force a switch-over from standby to active state
		if the backup management module exists in a chassis."
	::= { snAgentRedunGbl 6 }

-- System CPU Utilization Table.

snAgentCpuUtilTable     OBJECT-TYPE
	SYNTAX	SEQUENCE OF SnAgentCpuUtilEntry
	MAX-ACCESS	not-accessible
	STATUS	current
	DESCRIPTION
		"Table to list utilization for all CPUs in the device."
	::= { snAgentCpu 1 }

snAgentCpuUtilEntry	OBJECT-TYPE
	SYNTAX	SnAgentCpuUtilEntry
	MAX-ACCESS	not-accessible
	STATUS	current
	DESCRIPTION
		"A row in the CPU utilization table."
	INDEX	{ 
		snAgentCpuUtilSlotNum,
		snAgentCpuUtilCpuId,
		snAgentCpuUtilInterval
	}
	::= { snAgentCpuUtilTable 1 }

SnAgentCpuUtilEntry ::= SEQUENCE {
	snAgentCpuUtilSlotNum
		Integer32,
	snAgentCpuUtilCpuId
		Integer32,
	snAgentCpuUtilInterval
		Integer32,
	snAgentCpuUtilValue
		Gauge32,
	snAgentCpuUtilPercent
		Gauge32,
	snAgentCpuUtil100thPercent
		Gauge32
	}

snAgentCpuUtilSlotNum	OBJECT-TYPE
	SYNTAX Integer32
	MAX-ACCESS	read-only
	STATUS	current
	DESCRIPTION
		"The slot number of module which contains the cpu."
	::= { snAgentCpuUtilEntry 1 }

snAgentCpuUtilCpuId  OBJECT-TYPE
	SYNTAX   Integer32
	MAX-ACCESS	read-only
	STATUS	current
	DESCRIPTION
		"The id of cpu. For non-VM1/WSM management module, there is one CPU.
		For VM1/WSM there's one management CPU and three slave CPUs.
		The management CPU could be turned off. For POS and ATM
		there's no management CPU but  two slave CPUs.
		Id for management cpu is 1. Value of 2 or greater are for slave CPUs. "
	::= { snAgentCpuUtilEntry 2 }

snAgentCpuUtilInterval  OBJECT-TYPE
	SYNTAX   Integer32
	MAX-ACCESS	read-only
	STATUS	current
	DESCRIPTION
		"The value, in seconds, for this utilization. For both management and slave CPU, we display
		utilization for 1 sec, 5 sec, 60 sec and 300 sec interval."
	::= { snAgentCpuUtilEntry 3 }

snAgentCpuUtilValue OBJECT-TYPE
	SYNTAX	Gauge32
	MAX-ACCESS	read-only
	STATUS	deprecated
	DESCRIPTION
		"The statistical CPU utilization in units of one-hundredth
		 of a percent. This value is deprecated. Users are recommended
		 to use snAgentCpuUtilPercent or snAgentCpuUtil100thPercent
		 instead."
	::= { snAgentCpuUtilEntry 4 }

snAgentCpuUtilPercent OBJECT-TYPE
	SYNTAX	Gauge32
	MAX-ACCESS	read-only
	STATUS	current
	DESCRIPTION
		"The statistical CPU utilization in units of a percent."
	::= { snAgentCpuUtilEntry 5 }

snAgentCpuUtil100thPercent OBJECT-TYPE
	SYNTAX	Gauge32
	MAX-ACCESS	read-only
	STATUS	current
	DESCRIPTION
		"The statistical CPU utilization in units of one-hundredth
		 of a percent."
	::= { snAgentCpuUtilEntry 6 }

-- System Process Utilization Table.

snCpuProcessTable     OBJECT-TYPE
	SYNTAX	SEQUENCE OF SnCpuProcessEntry
	MAX-ACCESS	not-accessible
	STATUS	current
	DESCRIPTION
		"Table to list utilization and runtime for all CPU processes in the device."
	::= { snAgentCpu 2 }

snCpuProcessEntry	OBJECT-TYPE
	SYNTAX	SnCpuProcessEntry
	MAX-ACCESS	not-accessible
	STATUS	current
	DESCRIPTION
		"A row in the CPU process table."
	INDEX	{ 
		snCpuProcessName
	}
	::= { snCpuProcessTable 1 }

SnCpuProcessEntry ::= SEQUENCE {
	snCpuProcessName
		DisplayString,
	snCpuProcess5SecUtil
		Gauge32,
	snCpuProcess1MinUtil
		Gauge32,
	snCpuProcess5MinUtil
		Gauge32,
	snCpuProcess15MinUtil
		Gauge32,
	snCpuProcessRuntime
		Counter32
	}

snCpuProcessName        OBJECT-TYPE
	SYNTAX  DisplayString (SIZE (1..48))
	MAX-ACCESS	read-only
	STATUS	current
	DESCRIPTION
		"The process name."
	::= { snCpuProcessEntry 1 }

snCpuProcess5SecUtil OBJECT-TYPE
	SYNTAX	Gauge32
	MAX-ACCESS	read-only
	STATUS	current
	DESCRIPTION
		"The statistics collection of last 5 second process utilization."
	::= { snCpuProcessEntry 2 }

snCpuProcess1MinUtil OBJECT-TYPE
	SYNTAX	Gauge32
	MAX-ACCESS	read-only
	STATUS	current
	DESCRIPTION
		"The statistics collection of last 1 minute process utilization."
	::= { snCpuProcessEntry 3 }

snCpuProcess5MinUtil OBJECT-TYPE
	SYNTAX	Gauge32
	MAX-ACCESS	read-only
	STATUS	current
	DESCRIPTION
		"The statistics collection of last 5 minute process utilization."
	::= { snCpuProcessEntry 4 }

snCpuProcess15MinUtil OBJECT-TYPE
	SYNTAX	Gauge32
	MAX-ACCESS	read-only
	STATUS	current
	DESCRIPTION
		"The statistics collection of last 15 minute process utilization."
	::= { snCpuProcessEntry 5 }

snCpuProcessRuntime OBJECT-TYPE
	SYNTAX	Counter32
	MAX-ACCESS	read-only
	STATUS	current
	DESCRIPTION
		"Process runtime in milliseconds."
	::= { snCpuProcessEntry 6 }

-- Hardware ICBM (Integrated Central Buffer Manager) Counter Table.

snAgentHwICBMCounterTable     OBJECT-TYPE
	SYNTAX	SEQUENCE OF SnAgentHwICBMCounterEntry
	MAX-ACCESS	not-accessible
	STATUS	current
	DESCRIPTION
		"Table to list the ICBM counter values.
		This table is not supported on 10G module."
	::= { snAgentHw 1 }

snAgentHwICBMCounterEntry	OBJECT-TYPE
	SYNTAX	SnAgentHwICBMCounterEntry
	MAX-ACCESS	not-accessible
	STATUS	current
	DESCRIPTION
		"A row representing ICBM counter values for that slot."
	INDEX	{ 
		snAgentHwICBMCounterSlot,
		snAgentHwICBMCounterDMA
	}
	::= { snAgentHwICBMCounterTable 1 }

SnAgentHwICBMCounterEntry ::= SEQUENCE {
	snAgentHwICBMCounterSlot
		Unsigned32,
	snAgentHwICBMCounterDMA
		Unsigned32,
	snAgentHwICBMCounterFreeDepth
		Gauge32,
	snAgentHwICBMCounterWriteDrop
		Counter32,
	snAgentHwICBMCounterWriteInput
		Counter32,
	snAgentHwICBMCounterWriteOutput
		Counter32,
	snAgentHwICBMCounterReadInput
		Counter32,
	snAgentHwICBMCounterReadOutput
		Counter32
	}

snAgentHwICBMCounterSlot  OBJECT-TYPE
	SYNTAX	Unsigned32
	MAX-ACCESS	read-only
	STATUS	current
	DESCRIPTION
		"Slot number where ICBM resides."
	::= { snAgentHwICBMCounterEntry 1 }

snAgentHwICBMCounterDMA  OBJECT-TYPE
	SYNTAX	Unsigned32
	MAX-ACCESS	read-only
	STATUS	current
	DESCRIPTION
		"DMA Id within a slot where ICBM resides. Valid only for Jetcore modules.
		For non-Jetcore modules, this index is ignored by the agent. In this case, value
		0 will be returned by the agent."
	::= { snAgentHwICBMCounterEntry 2 }

snAgentHwICBMCounterFreeDepth  OBJECT-TYPE
	SYNTAX	Gauge32
	MAX-ACCESS	read-only
	STATUS	current
	DESCRIPTION
		"Current depth of the free queue for this ICBM."
	::= { snAgentHwICBMCounterEntry 3 }

snAgentHwICBMCounterWriteDrop  OBJECT-TYPE
	SYNTAX	Counter32
	MAX-ACCESS	read-only
	STATUS	current
	DESCRIPTION
		"Write sequencer drop count for this ICBM."
	::= { snAgentHwICBMCounterEntry 4 }

snAgentHwICBMCounterWriteInput  OBJECT-TYPE
	SYNTAX	Counter32
	MAX-ACCESS	read-only
	STATUS	current
	DESCRIPTION
		"Write sequencer input counter for this ICBM."
	::= { snAgentHwICBMCounterEntry 5 }

snAgentHwICBMCounterWriteOutput  OBJECT-TYPE
	SYNTAX	Counter32
	MAX-ACCESS	read-only
	STATUS	current
	DESCRIPTION
		"Write sequencer output counter for this ICBM."
	::= { snAgentHwICBMCounterEntry 6 }

snAgentHwICBMCounterReadInput  OBJECT-TYPE
	SYNTAX	Counter32
	MAX-ACCESS	read-only
	STATUS	current
	DESCRIPTION
		"Read sequencer input counter for this ICBM."
	::= { snAgentHwICBMCounterEntry 7 }

snAgentHwICBMCounterReadOutput  OBJECT-TYPE
	SYNTAX	Counter32
	MAX-ACCESS	read-only
	STATUS	current
	DESCRIPTION
		"Read sequencer output counter for this ICBM."
	::= { snAgentHwICBMCounterEntry 8 }

-- IP CAM Statistics Table.

snCAMIpStatTable     OBJECT-TYPE
	SYNTAX	SEQUENCE OF SnCAMIpStatEntry
	MAX-ACCESS	not-accessible
	STATUS	current
	DESCRIPTION
		"Table to list the IP CAM statistics.
		"
	::= { snAgentHw 2 }

snCAMIpStatEntry	OBJECT-TYPE
	SYNTAX	SnCAMIpStatEntry
	MAX-ACCESS	not-accessible
	STATUS	current
	DESCRIPTION
		"A row representing IP CAM statistics for a given interface and level."
	INDEX	{ 
		snCAMIpStatIfIndex,
		snCAMIpStatLevel
	}
	::= { snCAMIpStatTable 1 }

SnCAMIpStatEntry ::= SEQUENCE {
	snCAMIpStatIfIndex         Unsigned32,
	snCAMIpStatLevel           Unsigned32,
	snCAMIpStatFreeEntries   Unsigned32,
	snCAMIpStatTotalEntries  Unsigned32
}

snCAMIpStatIfIndex OBJECT-TYPE
	SYNTAX     Unsigned32
	MAX-ACCESS     read-only
	STATUS     current
	DESCRIPTION
			"ifIndex value of the local interface."
	::= { snCAMIpStatEntry 1 }

snCAMIpStatLevel OBJECT-TYPE
	SYNTAX     Unsigned32
	MAX-ACCESS     read-only
	STATUS     current
	DESCRIPTION
			"Level of CAM entry for that interface."
	::= { snCAMIpStatEntry 2 }

snCAMIpStatFreeEntries OBJECT-TYPE
	SYNTAX     Unsigned32
	MAX-ACCESS     read-only
	STATUS     current
	DESCRIPTION
			"Free entries in the IP CAM for that interface and level."
	::= { snCAMIpStatEntry 3 }

snCAMIpStatTotalEntries OBJECT-TYPE
	SYNTAX     Unsigned32
	MAX-ACCESS     read-only
	STATUS     current
	DESCRIPTION
			"Total entries in the IP CAM for that interface and level."
	::= { snCAMIpStatEntry 4 }

-- CAM Statistics Table.

snCAMStatTable     OBJECT-TYPE
	SYNTAX	SEQUENCE OF SnCAMStatEntry
	MAX-ACCESS	not-accessible
	STATUS	current
	DESCRIPTION
		"Table to list the CAM statistics.
		"
	::= { snAgentHw 3 }

snCAMStatEntry	OBJECT-TYPE
	SYNTAX	SnCAMStatEntry
	MAX-ACCESS	not-accessible
	STATUS	current
	DESCRIPTION
		"A row representing CAM statistics for a given DMA Id number."
	INDEX	{ 
		snCamStatDMAIdNumber
	}
	::= { snCAMStatTable 1 }

SnCAMStatEntry ::= SEQUENCE {
	snCamStatDMAIdNumber              Unsigned32,
	snCamStatDMAMasterNumber         Unsigned32,
	snCamStatFreePool0Entries            Unsigned32,
	snCamStatFreePool1Entries            Unsigned32,
	snCamStatFreePool2Entries            Unsigned32,
	snCamStatFreePool3Entries            Unsigned32,
	snCamStatFreeL2Entries                Unsigned32,
	snCamStatFreeL2LowestSection     Unsigned32,
	snCamStatHostLookupCount           Counter32,
	snCamStatRouteLookupCount         Counter32,
	snCamStatLevel1                         Unsigned32,
	snCamStatLevel2                         Unsigned32,
	snCamStatLevel3                         Unsigned32,
	snCamStatMacFailCount                Counter32,
	snCamStatIPRouteFailCount           Counter32,
	snCamStatIPSessionFailCount         Counter32,
	snCamStatIPMCastFailCount           Counter32,
	snCamStatL2SessionFailCount         Counter32,
	snCamStatAddMACCount               Counter32,
	snCamStatAddVLANCount              Counter32,
	snCamStatAddIPHostCount            Counter32,
	snCamStatAddIPRouteCount           Counter32,
	snCamStatAddIPSessionCount        Counter32,
	snCamStatAddIPMCastCount          Counter32,
	snCamStatAddL2SessionCount        Counter32,
	snCamStatAddIPXCount                Counter32,
	snCamStatDeleteDMACamCount      Counter32
}

snCamStatDMAIdNumber OBJECT-TYPE
	SYNTAX     Unsigned32
	MAX-ACCESS     read-only
	STATUS     current
	DESCRIPTION
			"DMA Id number."
	::= { snCAMStatEntry 1 }

snCamStatDMAMasterNumber OBJECT-TYPE
	SYNTAX     Unsigned32
	MAX-ACCESS     read-only
	STATUS     current
	DESCRIPTION
			"DMA Master for that DMA Id."
	::= { snCAMStatEntry 2 }

snCamStatFreePool0Entries OBJECT-TYPE
	SYNTAX     Unsigned32
	MAX-ACCESS     read-only
	STATUS     current
	DESCRIPTION
			"CAM free pool0 entries."
	::= { snCAMStatEntry 3 }

snCamStatFreePool1Entries OBJECT-TYPE
	SYNTAX     Unsigned32
	MAX-ACCESS     read-only
	STATUS     current
	DESCRIPTION
			"CAM free pool1 entries."
	::= { snCAMStatEntry 4 }

snCamStatFreePool2Entries OBJECT-TYPE
	SYNTAX     Unsigned32
	MAX-ACCESS     read-only
	STATUS     current
	DESCRIPTION
			"CAM free pool2 entries."
	::= { snCAMStatEntry 5 }

snCamStatFreePool3Entries OBJECT-TYPE
	SYNTAX     Unsigned32
	MAX-ACCESS     read-only
	STATUS     current
	DESCRIPTION
			"CAM free pool3 entries."
	::= { snCAMStatEntry 6 }

snCamStatFreeL2Entries OBJECT-TYPE
	SYNTAX     Unsigned32
	MAX-ACCESS     read-only
	STATUS     current
	DESCRIPTION
			"CAM Free L2 entries."
	::= { snCAMStatEntry 7 }

snCamStatFreeL2LowestSection OBJECT-TYPE
	SYNTAX     Unsigned32
	MAX-ACCESS     read-only
	STATUS     current
	DESCRIPTION
			"CAM Free L2 lowest section entries."
	::= { snCAMStatEntry 8 }

snCamStatHostLookupCount OBJECT-TYPE
	SYNTAX     Counter32
	MAX-ACCESS     read-only
	STATUS     current
	DESCRIPTION
			"CAM host lookup count for router."
	::= { snCAMStatEntry 9 }

snCamStatRouteLookupCount OBJECT-TYPE
	SYNTAX     Counter32
	MAX-ACCESS     read-only
	STATUS     current
	DESCRIPTION
			"CAM route lookup count for router."
	::= { snCAMStatEntry 10 }

snCamStatLevel1 OBJECT-TYPE
	SYNTAX     Unsigned32
	MAX-ACCESS     read-only
	STATUS     current
	DESCRIPTION
			"CAM stat level1 entries for router."
	::= { snCAMStatEntry 11 }

snCamStatLevel2 OBJECT-TYPE
	SYNTAX     Unsigned32
	MAX-ACCESS     read-only
	STATUS     current
	DESCRIPTION
			"CAM stat level2 entries for router."
	::= { snCAMStatEntry 12 }

snCamStatLevel3 OBJECT-TYPE
	SYNTAX     Unsigned32
	MAX-ACCESS     read-only
	STATUS     current
	DESCRIPTION
			"CAM stat level3 entries for router."
	::= { snCAMStatEntry 13 }

snCamStatMacFailCount OBJECT-TYPE
	SYNTAX     Counter32
	MAX-ACCESS     read-only
	STATUS     current
	DESCRIPTION
			"CAM MAC fail count."
	::= { snCAMStatEntry 14 }

snCamStatIPRouteFailCount OBJECT-TYPE
	SYNTAX     Counter32
	MAX-ACCESS     read-only
	STATUS     current
	DESCRIPTION
			"CAM IP route fail count."
	::= { snCAMStatEntry 15 }

snCamStatIPSessionFailCount OBJECT-TYPE
	SYNTAX     Counter32
	MAX-ACCESS     read-only
	STATUS     current
	DESCRIPTION
			"CAM IP session fail count."
	::= { snCAMStatEntry 16 }

snCamStatIPMCastFailCount OBJECT-TYPE
	SYNTAX     Counter32
	MAX-ACCESS     read-only
	STATUS     current
	DESCRIPTION
			"CAM IP multicast fail count."
	::= { snCAMStatEntry 17 }

snCamStatL2SessionFailCount OBJECT-TYPE
	SYNTAX     Counter32
	MAX-ACCESS     read-only
	STATUS     current
	DESCRIPTION
			"CAM L2 session fail count."
	::= { snCAMStatEntry 18 }

snCamStatAddMACCount OBJECT-TYPE
	SYNTAX     Counter32
	MAX-ACCESS     read-only
	STATUS     current
	DESCRIPTION
			"CAM add MAC count."
	::= { snCAMStatEntry 19 }

snCamStatAddVLANCount OBJECT-TYPE
	SYNTAX     Counter32
	MAX-ACCESS     read-only
	STATUS     current
	DESCRIPTION
			"CAM add VLAN count."
	::= { snCAMStatEntry 20 }

snCamStatAddIPHostCount OBJECT-TYPE
	SYNTAX     Counter32
	MAX-ACCESS     read-only
	STATUS     current
	DESCRIPTION
			"CAM add IP host count."
	::= { snCAMStatEntry 21 }

snCamStatAddIPRouteCount OBJECT-TYPE
	SYNTAX     Counter32
	MAX-ACCESS     read-only
	STATUS     current
	DESCRIPTION
			"CAM add IP route count."
	::= { snCAMStatEntry 22 }

snCamStatAddIPSessionCount OBJECT-TYPE
	SYNTAX     Counter32
	MAX-ACCESS     read-only
	STATUS     current
	DESCRIPTION
			"CAM add IP session count."
	::= { snCAMStatEntry 23 }

snCamStatAddIPMCastCount OBJECT-TYPE
	SYNTAX     Counter32
	MAX-ACCESS     read-only
	STATUS     current
	DESCRIPTION
			"CAM add IP multicast count."
	::= { snCAMStatEntry 24 }

snCamStatAddL2SessionCount OBJECT-TYPE
	SYNTAX     Counter32
	MAX-ACCESS     read-only
	STATUS     current
	DESCRIPTION
			"CAM add L2 session count."
	::= { snCAMStatEntry 25 }

snCamStatAddIPXCount OBJECT-TYPE
	SYNTAX     Counter32
	MAX-ACCESS     read-only
	STATUS     current
	DESCRIPTION
			"CAM add IPX count."
	::= { snCAMStatEntry 26 }

snCamStatDeleteDMACamCount OBJECT-TYPE
	SYNTAX     Counter32
	MAX-ACCESS     read-only
	STATUS     current
	DESCRIPTION
			"CAM delete DMA CAM count."
	::= { snCAMStatEntry 27 }

-- System DRAM info Group. 
snAgSystemDRAM       OBJECT IDENTIFIER ::= { snAgentHw 4 }

snAgSystemDRAMUtil OBJECT-TYPE
	SYNTAX	Gauge32
	MAX-ACCESS	read-only
	STATUS	current
	DESCRIPTION
		"The system dynamic memory utilization, in unit of percentage."
	::= { snAgSystemDRAM 1 }

snAgSystemDRAMTotal OBJECT-TYPE
	SYNTAX   Integer32
	MAX-ACCESS	read-only
	STATUS	current
	DESCRIPTION
		"The total amount of system dynamic memory, in number of bytes."
	::= { snAgSystemDRAM 2 }

snAgSystemDRAMFree OBJECT-TYPE
	SYNTAX   Integer32
	MAX-ACCESS	read-only
	STATUS	current
	DESCRIPTION
		"The free amount of system dynamic memory, in number of bytes."
	::= { snAgSystemDRAM 3 }

snAgSystemDRAMForBGP OBJECT-TYPE
	SYNTAX   Integer32
	MAX-ACCESS	read-only
	STATUS	current
	DESCRIPTION
		"The free amount of system dynamic memory used by BGP, in number of bytes."
	::= { snAgSystemDRAM 4 }

snAgSystemDRAMForOSPF OBJECT-TYPE
	SYNTAX   Integer32
	MAX-ACCESS	read-only
	STATUS	current
	DESCRIPTION
		"The free amount of system dynamic memory used by OSPF, in number of bytes."
	::= { snAgSystemDRAM 5 }

-- System Debug Group. You would see output of "de" command here.
snAgSystemDebug       OBJECT IDENTIFIER ::= { snAgentHw 5 }

snAgSystemDebugTotalIn OBJECT-TYPE
	SYNTAX Integer32
	MAX-ACCESS     read-only
	STATUS     current
	DESCRIPTION
			"Total incoming packet count. Sum of Buffer Manager and CPU read count."
	::= { snAgSystemDebug 1 }

snAgSystemDebugTotalOut OBJECT-TYPE
	SYNTAX Integer32
	MAX-ACCESS     read-only
	STATUS     current
	DESCRIPTION
			"Total outgoing packet count."
	::= { snAgSystemDebug 2 }

snAgSystemDebugCpuQueueRead OBJECT-TYPE
	SYNTAX Integer32
	MAX-ACCESS     read-only
	STATUS     current
	DESCRIPTION
			"CPU Queue read count."
	::= { snAgSystemDebug 3 }

snAgSystemDebugDRAMBuffer OBJECT-TYPE
	SYNTAX Integer32
	MAX-ACCESS     read-only
	STATUS     current
	DESCRIPTION
			"DRAM buffer count."
	::= { snAgSystemDebug 4 }

snAgSystemDebugBMBuffer OBJECT-TYPE
	SYNTAX Integer32
	MAX-ACCESS     read-only
	STATUS     current
	DESCRIPTION
			"BM buffer count."
	::= { snAgSystemDebug 5 }

snAgSystemDebugBMFreeBuffer OBJECT-TYPE
	SYNTAX Integer32
	MAX-ACCESS     read-only
	STATUS     current
	DESCRIPTION
			"BM free buffer count."
	::= { snAgSystemDebug 6 }

snAgSystemDebugBMFreeBufferMgmt OBJECT-TYPE
	SYNTAX Integer32
	MAX-ACCESS     read-only
	STATUS     current
	DESCRIPTION
			"BM free buffer management count."
	::= { snAgSystemDebug 7 }

snAgSystemDebugIpcGigLock OBJECT-TYPE
	SYNTAX Integer32
	MAX-ACCESS     read-only
	STATUS     current
	DESCRIPTION
			"IPC GIG lock count."
	::= { snAgSystemDebug 8 }

snAgSystemDebugDRAMGetError OBJECT-TYPE
	SYNTAX Integer32
	MAX-ACCESS     read-only
	STATUS     current
	DESCRIPTION
			"DRAM get error count."
	::= { snAgSystemDebug 9 }

snAgSystemDebugDRAMToBMCopyFail OBJECT-TYPE
	SYNTAX Integer32
	MAX-ACCESS     read-only
	STATUS     current
	DESCRIPTION
			"DRAM to Buffer Manager copy fail count."
	::= { snAgSystemDebug 10 }

-- System Temperature Table.

snAgentTempTable     OBJECT-TYPE
	SYNTAX		SEQUENCE OF SnAgentTempEntry
	MAX-ACCESS	not-accessible
	STATUS		current
	DESCRIPTION
		"Table to list temperatures of all the modules in the device. This
		 table is applicable to only those modules with temperature sensors."
	::= { snAgentTemp 1 }

snAgentTempEntry	OBJECT-TYPE
	SYNTAX		SnAgentTempEntry
	MAX-ACCESS	not-accessible
	STATUS		current
	DESCRIPTION
		"A row in the module temperature table."
	INDEX	{ snAgentTempSlotNum, snAgentTempSensorId }
	::= { snAgentTempTable 1 }

SnAgentTempEntry ::= SEQUENCE {
	snAgentTempSlotNum
		Integer32,
	snAgentTempSensorId
		Integer32,
	snAgentTempSensorDescr
		DisplayString,
	snAgentTempValue
		INTEGER
	}

snAgentTempSlotNum	OBJECT-TYPE
	SYNTAX		Integer32
	MAX-ACCESS	not-accessible
	STATUS		current
	DESCRIPTION
		"The slot number of module which contains the temperature sensor
		 represented by this row."
	::= { snAgentTempEntry 1 }

snAgentTempSensorId  OBJECT-TYPE
	SYNTAX		Integer32
	MAX-ACCESS	not-accessible
	STATUS		current
	DESCRIPTION
		"The temperature sensor identifier of Slave module whose temperature is
		 represented by this row, for management module: sensor#1 -  Intake Side Temperature
		 sensor# 2 - Exhaust Side Temperature."
	::= { snAgentTempEntry 2 }

snAgentTempSensorDescr  OBJECT-TYPE
	SYNTAX		DisplayString (SIZE (0..128))
	MAX-ACCESS	read-only
	STATUS		current
	DESCRIPTION
		"Describes the temperature sensor in a human readable form. This
		 is the same as snAgentTempSensorId, which is numeric and used to
		 traverse the temperature sensor table. The description provides
		 the meaning and purpose of this senor."
	::= { snAgentTempEntry 3 }

snAgentTempValue OBJECT-TYPE
	SYNTAX		INTEGER (-110..250)
	MAX-ACCESS	read-only
	STATUS		current
	DESCRIPTION
		"Temperature of the the sensor represented by this row. Each unit
		 is 0.5 degrees Celcius."
	::= { snAgentTempEntry 4 }


-- System Temperature Threshold Table.

snAgentTempThresholdTable     OBJECT-TYPE
	SYNTAX	SEQUENCE OF SnAgentTempThresholdEntry
	MAX-ACCESS	not-accessible
	STATUS	current
	DESCRIPTION
		"Table to list temperature threshold levels for 4 speeds of fan settings.
		 Depending on the temperature level, the fans run at diffrent speeds of RPM.
		 There are 4 levels of temperature settings for 4 fan speeds (low, medium,
		 medium-high, high). This table is applicable to only those modules with
		 temperature sensors. For each row, there are 2 temperature threshold values.
		 The high value, if reached causes the fan to run at next high level speed
		 and when it reduces the below the low value, the fan runs at next low spped."
	::= { snAgentTemp 2 }

snAgentTempThresholdEntry	OBJECT-TYPE
	SYNTAX	SnAgentTempThresholdEntry
	MAX-ACCESS	not-accessible
	STATUS	current
	DESCRIPTION
		"A row in the module temperature threshold table."
	INDEX	{ snAgentTempThresholdModule, snAgentTempThresholdLevel }
	::= { snAgentTempThresholdTable 1 }

SnAgentTempThresholdEntry ::= SEQUENCE {
	snAgentTempThresholdModule
		INTEGER,
	snAgentTempThresholdLevel
		INTEGER,
	snAgentTempThresholdHighValue
		INTEGER,
	snAgentTempThresholdLowValue
		INTEGER
	}

snAgentTempThresholdModule	OBJECT-TYPE
	SYNTAX	INTEGER {
					mgmtModule(1),			-- management module
					slaveModule(2),			-- slave/line module
					switchFabricModule(3)	-- switch fabric module
				}
	MAX-ACCESS	not-accessible
	STATUS	current
	DESCRIPTION
		"The module in the system for which threshold levels represented by this
		 row are applicable."
	::= { snAgentTempThresholdEntry 1 }

snAgentTempThresholdLevel OBJECT-TYPE
	SYNTAX	INTEGER {
					low(1),
					medium(2),
					mediumHhigh(3),
					high(4)
				}
	MAX-ACCESS	not-accessible
	STATUS	current
	DESCRIPTION
		"The temperature threshold level of the module for which threshold levels
		 represented by this row are applicable."
	::= { snAgentTempThresholdEntry 2 }

snAgentTempThresholdHighValue OBJECT-TYPE
	SYNTAX	INTEGER (-110..250)
	MAX-ACCESS	read-write
	STATUS	current
	DESCRIPTION
		"The high value for the temperature threshold, above which the fans would
		 need to operate at the next higher speed. If it reaches more than the
		 high threshold value for 'high' level, the module will be shutdown."
	::= { snAgentTempThresholdEntry 3 }

snAgentTempThresholdLowValue OBJECT-TYPE
	SYNTAX	INTEGER (-110..250)
	MAX-ACCESS	read-write
	STATUS	current
	DESCRIPTION
		"The low value for the temperature threshold, below which the fans would
		 need to operate at the next lower speed. This value is not applicable for
		 the 'low' level, as there is no more lower speeds than that."
	::= { snAgentTempThresholdEntry 4 }

-- System Stacking Temperature Table.

snAgentTemp2Table     OBJECT-TYPE
	SYNTAX		SEQUENCE OF SnAgentTemp2Entry
	MAX-ACCESS	not-accessible
	STATUS		current
	DESCRIPTION
		"Table to list temperatures of the modules in the device for each unit. This
		 table is applicable to only those modules with temperature sensors."
	::= { snAgentTemp 3 }

snAgentTemp2Entry	OBJECT-TYPE
	SYNTAX		SnAgentTemp2Entry
	MAX-ACCESS	not-accessible
	STATUS		current
	DESCRIPTION
		"A row in the module temperature table."
	INDEX	{ snAgentTemp2UnitNum, snAgentTemp2SlotNum, snAgentTemp2SensorId }
	::= { snAgentTemp2Table 1 }

SnAgentTemp2Entry ::= SEQUENCE {
	snAgentTemp2UnitNum
		Integer32,
	snAgentTemp2SlotNum
		Integer32,
	snAgentTemp2SensorId
		Integer32,
	snAgentTemp2SensorDescr
		DisplayString,
	snAgentTemp2Value
		INTEGER
	}

snAgentTemp2UnitNum	OBJECT-TYPE
	SYNTAX		Integer32
	MAX-ACCESS	not-accessible
	STATUS		current
	DESCRIPTION
		"The unit number of module which contains the temperature sensor
		 represented by this row."
	::= { snAgentTemp2Entry 1 }

snAgentTemp2SlotNum	OBJECT-TYPE
	SYNTAX		Integer32
	MAX-ACCESS	not-accessible
	STATUS		current
	DESCRIPTION
		"The slot number of module which contains the temperature sensor
		 represented by this row."
	::= { snAgentTemp2Entry 2 }

snAgentTemp2SensorId  OBJECT-TYPE
	SYNTAX		Integer32
	MAX-ACCESS	not-accessible
	STATUS		current
	DESCRIPTION
		"The temperature sensor identifier of Slave module whose temperature is
		 represented by this row, for management module: sensor#1 -  Intake Side Temperature
		 sensor# 2 - Exhaust Side Temperature."
	::= { snAgentTemp2Entry 3 }

snAgentTemp2SensorDescr  OBJECT-TYPE
	SYNTAX		DisplayString (SIZE (0..128))
	MAX-ACCESS	read-only
	STATUS		current
	DESCRIPTION
		"Describes the temperature sensor in a human readable form. This
		 is the same as snAgentTempSensorId, which is numeric and used to
		 traverse the temperature sensor table. The description provides
		 the meaning and purpose of this senor."
	::= { snAgentTemp2Entry 4 }

snAgentTemp2Value OBJECT-TYPE
	SYNTAX		INTEGER (-110..250)
	MAX-ACCESS	read-only
	STATUS		current
	DESCRIPTION
		"Temperature of the sensor represented by this row. Each unit
		 is 0.5 degrees Celsius."
	::= { snAgentTemp2Entry 5 }

fdryLicenseTable OBJECT-TYPE
	SYNTAX  SEQUENCE OF FdryLicenseEntry
	MAX-ACCESS  not-accessible
	STATUS  current
	DESCRIPTION
        "A list of licenses maintained by license sub-system."
	::= { snAgentLicense 1 }

fdryLicenseEntry OBJECT-TYPE
    SYNTAX      FdryLicenseEntry
    MAX-ACCESS  not-accessible
    STATUS      current
    DESCRIPTION
        "An entry in a license table."
    INDEX	{fdryLicensePackageName, fdryLicenseLid, fdryLicenseHash}
    ::= { fdryLicenseTable 1 }

FdryLicenseEntry ::= SEQUENCE {
	fdryLicensePackageName
		DisplayString,
	fdryLicenseLid
		DisplayString,
	fdryLicenseHash
		DisplayString,
	fdryLicenseType
		INTEGER,
	fdryLicensePrecedence
		Unsigned32,
	fdryLicenseTrialDays
		Unsigned32,
	fdryLicenseTrialTimeElapsed
		Unsigned32,
	fdryLicenseTrialTimeLeft
		Unsigned32,
	fdryLicenseTrialState
		INTEGER,
	fdryLicenseVendorInfo
		DisplayString,
	fdryLicenseSlot
		Integer32,
	fdryLicenseMode	
		INTEGER,
	fdryLicenseSerialNumber	
		DisplayString,
	fdryLicenseCapacity
		Integer32
    }

fdryLicensePackageName OBJECT-TYPE
	SYNTAX		DisplayString (SIZE(1..24))
	MAX-ACCESS	not-accessible
	STATUS		current
	DESCRIPTION
		"Name of the package, whose license information, this entry displays."
	::= { fdryLicenseEntry 1 }
	
fdryLicenseLid OBJECT-TYPE
	SYNTAX		DisplayString (SIZE(1..11))
	MAX-ACCESS	not-accessible
	STATUS		current
	DESCRIPTION
		"License Id (LID) of the license from the package. For the node locked license, 
		this LID is same as LID of the device. For the non-node locked license, this LID 
		is set as 2.0. This entry displays license information."
	::= { fdryLicenseEntry 2 }
	
fdryLicenseHash OBJECT-TYPE
	SYNTAX		DisplayString (SIZE(1..17))
	MAX-ACCESS	not-accessible
	STATUS		current
	DESCRIPTION
		"A unique hash for identifying a license entry in the system. This helps
		 traverse through the entries with same package name and LID."
	::= { fdryLicenseEntry 3 }
	
fdryLicenseType OBJECT-TYPE
	SYNTAX		INTEGER {
					normal(1),
					trial(2)
				}
	MAX-ACCESS	read-only
	STATUS		current
	DESCRIPTION
		"The type of the license, which can be either normal or trial."
	::= { fdryLicenseEntry 4 }

fdryLicensePrecedence OBJECT-TYPE
	SYNTAX		Unsigned32 (0..65535)
	MAX-ACCESS	read-only
	STATUS		current
	DESCRIPTION
		"Defines the priority of a particular trial license among those having
		 the same package and LID. This is primarily used for determining which
		 license to use, when there are many trial and normal licenses with same
		 package name and LID."
	::= { fdryLicenseEntry 5 }
	
fdryLicenseTrialDays OBJECT-TYPE
	SYNTAX		Unsigned32 (0..65535)
	MAX-ACCESS	read-only
	STATUS		current
	DESCRIPTION
		"The number of trial days for the license, if it's a trial license.
		 Otherwise, the value has no meaning for normal licenses and read
		 as 0 on Get operation."
	::= { fdryLicenseEntry 6 }

fdryLicenseTrialTimeElapsed OBJECT-TYPE
	SYNTAX		Unsigned32 (0..65535)
	MAX-ACCESS	read-only
	STATUS		current
	DESCRIPTION
		"The cumulative number of hours used for this trial license. This
		 counts all the usages of the trial license. For a normal license,
		 this is 0."
	::= { fdryLicenseEntry 7 }
	
fdryLicenseTrialTimeLeft OBJECT-TYPE
	SYNTAX		Unsigned32 (0..65535)
	MAX-ACCESS	read-only
	STATUS		current
	DESCRIPTION
		"The number of hours left for the trial license. This is derived
		 from the total number of hours and the cumulative number of hours
		 used. For a normal license, this is 0."
	::= { fdryLicenseEntry 8 }

fdryLicenseTrialState OBJECT-TYPE
	SYNTAX		INTEGER {
					invalid(1),
					unused(2),
					active(3),
					expired(4),
					duplicated (5)
				}
	MAX-ACCESS	read-only
	STATUS		current
	DESCRIPTION
		"This indicates the state of the trial license. Invalid means the 
		 license is not valid for this box, unused means the license is
		 never used, avtive means it has been used at least once and expired
		 means it has expired and can't be used any more. Duplicated means 
		 the license has same package name with other license and but both 
		 serial numbers are different in the same device, this is only for 
		 the non-node locked license"
	::= { fdryLicenseEntry 9 }

fdryLicenseVendorInfo OBJECT-TYPE
	SYNTAX		DisplayString
	MAX-ACCESS	read-only
	STATUS		current
	DESCRIPTION
		"This is the Brocade specific package data which is an octet string.
		 This contains encoded information of license specific information
		 such as package bit mask, number of ports, etc."
	::= { fdryLicenseEntry 10 }

fdryLicenseSlot OBJECT-TYPE
	SYNTAX		Integer32
	MAX-ACCESS	read-only
	STATUS		current
	DESCRIPTION
		"This indicates the slot number of the module, the license belongs to.
		 There is a one to one mapping between LID and slot number, as each
		 module has unique LID and can be present only in one slot."
	::= { fdryLicenseEntry 11 }
	
fdryLicenseMode OBJECT-TYPE
	SYNTAX		INTEGER {
					nodeLocked(1),
					nonNodeLocked(2)
				}
	MAX-ACCESS	read-only
	STATUS		current
	DESCRIPTION
		"The mode of the license, which can be either node locked or non-node locked mode."
	::= { fdryLicenseEntry 12 }

fdryLicenseSerialNumber OBJECT-TYPE
	SYNTAX		DisplayString
	MAX-ACCESS	read-only
	STATUS		current
	DESCRIPTION
		"This is the serial number of the license. This is only for the non-node locked license"
	::= { fdryLicenseEntry 13 }

fdryLicenseCapacity OBJECT-TYPE
	SYNTAX		Integer32
	MAX-ACCESS	read-only
	STATUS		current
	DESCRIPTION
		"The capacity of the license. For POD license, this is the number of ports.
		For premium or advance license, it is 1"
	::= { fdryLicenseEntry 14 }


-- the port table contains the port which requirs the port license

brcdPortLicenseTable OBJECT-TYPE
	SYNTAX  SEQUENCE OF BrcdPortLicenseEntry
	MAX-ACCESS  not-accessible
	STATUS  current
	DESCRIPTION
        "A list of ports which require the port license."
	::= { snAgentLicense 3 }

brcdPortLicenseEntry OBJECT-TYPE
    SYNTAX      BrcdPortLicenseEntry
    MAX-ACCESS  not-accessible
    STATUS      current
    DESCRIPTION
        "An entry in a licensed port table."
    INDEX	{ brcdPortLicenseIndex }
    ::= { brcdPortLicenseTable 1 }

BrcdPortLicenseEntry ::= SEQUENCE {
	brcdPortLicenseIndex
		InterfaceIndex,
	brcdPortLicenseStatus
		INTEGER
    }

brcdPortLicenseIndex OBJECT-TYPE
	SYNTAX	InterfaceIndex
	MAX-ACCESS  not-accessible
	STATUS	current
	DESCRIPTION
		"The port/interface index (ifindex)."
	::= { brcdPortLicenseEntry 1 }

brcdPortLicenseStatus OBJECT-TYPE
	SYNTAX  INTEGER {
				validLic(1),       
				noLic(2)  
			}
	MAX-ACCESS  read-only
	STATUS  current
	DESCRIPTION
		"The current license state of the port.
		 validLic(1)  ............ the port requires port license, and has valid license      
		 noLic(2)      ........... the port requires port license, and doesn't have valid license "
	::= { brcdPortLicenseEntry 2 }



END
FOUNDRY-SN-SWITCH-GROUP-MIB DEFINITIONS ::= BEGIN

IMPORTS
	MODULE-IDENTITY, OBJECT-TYPE,Integer32,Unsigned32, Gauge32, Counter32, Counter64, TimeTicks, IpAddress
		FROM SNMPv2-SMI
	switch
		FROM FOUNDRY-SN-ROOT-MIB
	DisplayString,MacAddress
		FROM FOUNDRY-SN-AGENT-MIB
	InterfaceIndex, ifIndex
		FROM IF-MIB		
	TruthValue,TEXTUAL-CONVENTION
		FROM SNMPv2-TC;
		
snSwitch MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"        	
	REVISION     "200909300000Z" -- September 30, 2009
	DESCRIPTION
			"convert from SMIv1 to SMIv2"
   ::= {  switch 3 }

		-- textual conventions



	PhysAddress ::= TEXTUAL-CONVENTION
		STATUS	  current
		DESCRIPTION
			"
			  This data type is used to model media addresses.  For many
			  types of media, this will be in a binary representation.
			  For example, an ethernet address would be represented as
			  a string of 6 octets.
			"
		SYNTAX	OCTET STRING

	BridgeId ::= TEXTUAL-CONVENTION
		STATUS	  current
		DESCRIPTION
			"
			 the Bridge-Identifier as used in the Spanning Tree
			"
		SYNTAX	OCTET STRING (SIZE(8))

	Timeout ::= TEXTUAL-CONVENTION
		STATUS	  current
		DESCRIPTION
			"
			a STP timer in units of 1/100 seconds
			"
		SYNTAX	Integer32

	PortMask ::= TEXTUAL-CONVENTION
		STATUS	  current
		DESCRIPTION
			"
			  This data type is used to model port bitmask.  The 
			  maximum of ports are 32.  			
			"
		SYNTAX	Integer32


	 InterfaceId ::= TEXTUAL-CONVENTION
		STATUS	  current
		DESCRIPTION
			"
	  -- This data type is used to specify an interface ID.
	  -- The first object identifier is port type, and the
	  -- format of the rest of the object identifiers depend
	  -- on the port type.
	  --
	  -- ethernet(1), format: type.slot.port
	  --   e.g. 1.3.6 is port ethernet 3/6
	  --
	  -- pos(2), format: type.slot.port
	  --   e.g. 2.10.1 is port pos 10/1
	  --
	  -- atm(3), format: type.slot.port
	  --   e.g. 3.8.2 is port atm 8/2
	  --
	  -- virtual router interface(4), format: type.ve
	  --   e.g. 4.9 is port ve 9
	  --
	  -- loopback(5), format: type.lb
	  --   e.g. 5.7 is port loopback 7
	  --
	  -- gre tunnel(6), format: type.tn, not supported
	  --
	  -- subinterface(7), format: type.slot.port.subInterface
	  --   e.g. 7.3.2.4 is port atm 3/2.4
	  --
	  -- mpls tunnel(8), format: type.tn
	  --   e.g. 8.3 is port tunnel 3
	  --
	  -- pvc(9), format: type.slot.port.subInterface.vpi.vci
	  --   e.g. 9.3.1.2.1.2 is port atm 3/1.2.1.2
	  --
	  -- management(10), format: type.slot.port
	  --   e.g. 10.17.1 is port management 17/1
	  --
	  -- tunnel(11), format: type.trunkid
	  --   e.g. 11.3 is trunk id 3
	  --
	  -- virtual management(12), format: type
	  --   e.g. 10 is the virtual management interface			
			"
		SYNTAX	OBJECT IDENTIFIER

	  
	  

	 InterfaceId2 ::= TEXTUAL-CONVENTION
		STATUS	  current
		DESCRIPTION
			"
	  -- This data type is used to specify an interface ID.  The
	  -- first object identifier is port type, and the format of
	  -- the rest of the object identifiers depend on the port
	  -- type.  Note that for types which include a reference to a
	  -- physical port, the formats vary according to the type of
	  -- port identifiers that the device uses (e.g. 6, 3/6, or
	  -- 2/3/6).  New port type values will be added in the future
	  -- as needed.  For a given type code, new formats may also
	  -- be added in the future.  Each format for a given type
	  -- code will have a unique length.  Applications should
	  -- check the OID length and not assume that it will match
	  -- one of the currently defined formats.
	  --
	  -- Though the OIDs are shown here in a shortened form, the
	  -- actual OIDs are prefixed with the OID of snInterfaceId
	  -- (so the OID for 1.2.3.6 would actually be
	  -- snInterfaceId.1.2.3.6, which is equivalent to
	  -- snEthernetInterface.2.3.6.).
	  --
	  -- ethernet(1), formats:
	  --  type.port (e.g. 1.6 is port ethernet 6)
	  --  type.slot.port (e.g. 1.3.6 is port ethernet 3/6)
	  --  type.unit.slot.port (e.g. 1.2.3.6 is port ethernet 2/3/6)
	  --
	  -- pos(2), formats:
	  --  type.port (e.g. 2.6 is port pos 6)
	  --  type.slot.port (e.g. 2.3.6 is port pos 3/6)
	  --  type.unit.slot.port (e.g. 2.2.3.6 is port pos 2/3/6)
	  --
	  -- atm(3), format: type.slot.port
	  --  type.port (e.g. 3.6 is port atm 6)
	  --  type.slot.port (e.g. 3.3.6 is port atm 3/6)
	  --  type.unit.slot.port (e.g. 3.2.3.6 is port atm 2/3/6)
	  --
	  -- virtual router interface(4), format: type.ve
	  --   e.g. 4.9 is port ve 9
	  --
	  -- loopback(5), format: type.lb
	  --   e.g. 5.7 is port loopback 7
	  --
	  -- gre tunnel(6), format: type.tn, not supported
	  --
	  -- subinterface(7), formats:
	  --  type.port.subInterface (e.g. 7.6.4 is port atm 6.4)
	  --  type.slot.port.subInterface (e.g. 7.3.6.4 is port atm 3/6.4)
	  --  type.unit.slot.port.subInterface
	  --    (e.g. 7.2.3.6.4 is port atm 2/3/6.4)
	  --
	  -- mpls tunnel(8), format: type.tn
	  --   e.g. 8.3 is port tunnel 3
	  --
	  -- pvc(9), formats:
	  --  type.port.subInterface.vpi.vci
	  --    (e.g. 9.6.2.1.2 is port atm 6.2.1.2)
	  --  type.slot.port.subInterface.vpi.vci
	  --    (e.g. 9.3.6.2.1.2 is port atm 3/6.2.1.2)
	  --  type.unit.slot.port.subInterface.vpi.vci
	  --    (e.g. 9.2.3.6.2.1.2 is port atm 2/3/6.2.1.2)
	  --
	  -- management(10), formats:
	  --  type.port (e.g. 10.1 is port management 1)
	  --  type.slot.port (e.g. 10.2.1 is port management 2/1)
	  --  type.unit.slot.port (e.g. 10.4.2.1 is port management 4/2/1)
	  --
	  -- trunk(11), format: type.trunkid
	  --   e.g. 11.3 is trunk id 3
	  --
	  -- virtual management(12), format: type
	  --   e.g. 12 is the virtual management interface			
			"
		SYNTAX	OBJECT IDENTIFIER

VlanTagMode ::= TEXTUAL-CONVENTION
   STATUS        current
   DESCRIPTION
	   "Vlan tag mode for a given vlan member."
	 SYNTAX        INTEGER{
							 tagged(1),
							 untagged(2),
							 dual(3)
						 }

	FdryVlanIdOrNoneTC ::= TEXTUAL-CONVENTION
		DISPLAY-HINT "d"
		STATUS       current
		DESCRIPTION
			"The VLAN-ID that uniquely identifies a specific VLAN,
			or no VLAN.  The special value of zero is used to
			indicate that no VLAN-ID is present or used.  This can
			be used in any situation where an object or a table entry
			must refer either to a specific VLAN, or to no VLAN.

			Note that a MIB object that is defined using this
			TEXTUAL-CONVENTION should clarify the meaning of
			'no VLAN' (i.e., the special value 0)."
		SYNTAX       Integer32 (0 | 1..4094)

BrcdVlanIdTC ::= TEXTUAL-CONVENTION
		DISPLAY-HINT "d"
		STATUS       current
		DESCRIPTION
			"The VLAN-ID that uniquely identifies a specific VLAN."
		SYNTAX       Integer32 (1..4090)

BrcdVlanIdOrNoneTC ::= TEXTUAL-CONVENTION
		DISPLAY-HINT "d"
		STATUS       current
		DESCRIPTION
			"The VLAN-ID that uniquely identifies a specific VLAN
                         or to no VLAN."
		SYNTAX       Integer32 (0 | 1..4090)

PortQosTC ::= TEXTUAL-CONVENTION
   STATUS      current
   DESCRIPTION
		"The port QOS Priority hardware queue. 0 is lowest priority, 7 is the highest."
   SYNTAX  INTEGER {
				   level0(0),
				   level1(1),
				   level2(2),
				   level3(3),
				   level4(4),
				   level5(5),
				   level6(6),
				   level7(7),
				   invalid(127)
				   }

-- Groups

snSwInfo 	            OBJECT IDENTIFIER ::= { snSwitch 1 }
snVLanInfo				OBJECT IDENTIFIER ::= { snSwitch 2 }
snSwPortInfo 	  		OBJECT IDENTIFIER ::= { snSwitch 3 }
snFdbInfo				OBJECT IDENTIFIER ::= { snSwitch 4 }
snPortStpInfo			OBJECT IDENTIFIER ::= { snSwitch 5 }
snTrunkInfo				OBJECT IDENTIFIER ::= { snSwitch 6 }
snSwSummary				OBJECT IDENTIFIER ::= { snSwitch 7 }
snDhcpGatewayListInfo	OBJECT IDENTIFIER ::= { snSwitch 8 }
snDnsInfo				OBJECT IDENTIFIER ::= { snSwitch 9 }
snMacFilter				OBJECT IDENTIFIER ::= { snSwitch 10 }
snNTP					OBJECT IDENTIFIER ::= { snSwitch 11 }
snRadius				OBJECT IDENTIFIER ::= { snSwitch 12 }
snTacacs				OBJECT IDENTIFIER ::= { snSwitch 13 }
snQos					OBJECT IDENTIFIER ::= { snSwitch 14 }
snAAA					OBJECT IDENTIFIER ::= { snSwitch 15 }
snCAR 					OBJECT IDENTIFIER ::= { snSwitch 16 }
snVLanCAR 				OBJECT IDENTIFIER ::= { snSwitch 17 }
snNetFlow 				OBJECT IDENTIFIER ::= { snSwitch 18 }
snSFlow 				OBJECT IDENTIFIER ::= { snSwitch 19 }
snFDP 				    OBJECT IDENTIFIER ::= { snSwitch 20 }
snVsrp   				OBJECT IDENTIFIER ::= { snSwitch 21 }
snArpInfo				OBJECT IDENTIFIER ::= { snSwitch 22 }
snWireless 				OBJECT IDENTIFIER ::= { snSwitch 23 }
snMac	 				OBJECT IDENTIFIER ::= { snSwitch 24 }
snPortMonitor			OBJECT IDENTIFIER ::= { snSwitch 25 }
snSSH					OBJECT IDENTIFIER ::= { snSwitch 26 }
snSSL					OBJECT IDENTIFIER ::= { snSwitch 27 }
snMacAuth				OBJECT IDENTIFIER ::= { snSwitch 28 }
snMetroRing				OBJECT IDENTIFIER ::= { snSwitch 29 }
-- snSwitch 30 should not be used
snStacking				OBJECT IDENTIFIER ::= { snSwitch 31 }
fdryMacVlanMIB          OBJECT IDENTIFIER ::= { snSwitch 32 }
fdryLinkAggregationGroupMIB OBJECT IDENTIFIER ::= { snSwitch 33 }
fdryDns2MIB				OBJECT IDENTIFIER ::= { snSwitch 34 }
fdryDaiMIB				OBJECT IDENTIFIER ::= { snSwitch 35 }
fdryDhcpSnoopMIB			OBJECT IDENTIFIER ::= { snSwitch 36 }
fdryIpSrcGuardMIB			OBJECT IDENTIFIER ::= { snSwitch 37 }
--brcdDot1xAuth			OBJECT IDENTIFIER ::= { snSwitch 38 }
brcdRouteMap				OBJECT IDENTIFIER ::= { snSwitch 39 }
brcdSPXMIB				OBJECT IDENTIFIER ::= { snSwitch 40 }


-- SECTION 2: Switch Group Configuration MIBs


snSwGroupOperMode OBJECT-TYPE
	SYNTAX  INTEGER {
		noVLan(1),
		vlanByPort(2)
		}
	MAX-ACCESS  read-write
	STATUS  current
	DESCRIPTION
		"noVLan(1) represents all switch ports with no virtual 
		 LAN by port (no Port VLAN), and with no tag assigned.
		 vlanByPort(2) represents all switch ports with Basic 
		 VLAN (layer2 Switch). "
	::= { snSwInfo 1 }

snSwGroupIpL3SwMode OBJECT-TYPE
	SYNTAX  INTEGER {
		disabled(0),             
		enabled(1)
		}
	MAX-ACCESS  read-write
	STATUS  current
	DESCRIPTION
		"The Switch Group is configured with the Layer3
		 IP Switch mode either enabled or disabled and the
		 default is disabled mode.
		 enabled(1)...........activate Layer3 IP Switch
		 disabled(0)..........disable Layer3 IP Switch"  
	::= { snSwInfo 2 }


snSwGroupIpMcastMode OBJECT-TYPE
	SYNTAX  INTEGER {
		disabled(0),
		enabled(1)
		}
	MAX-ACCESS  read-write
	STATUS  current
	DESCRIPTION
		"The Switch Group is configured with the IP Multicast
		 pruning mode either enabled or disabled and the
		 default is disabled mode.
		 enabled(1)...........activate IP Multicast pruning
		 disabled(0)..........no IP Multicast pruning"
	::= { snSwInfo 3 }


snSwGroupDefaultCfgMode OBJECT-TYPE
	SYNTAX  INTEGER {
		default(1),
		nonDefault(2)
		}
	MAX-ACCESS  read-write
	STATUS  current
	DESCRIPTION
		"The Switch Group is configured with the Default
		 configuration. If the default configuration gets
		 overwritten, the state will change to non-default.
		 default(1)...........default configuration
		 nonDefault(2)..........non default configuration"
	::= { snSwInfo 4 }


snSwGroupSwitchAgeTime OBJECT-TYPE
	SYNTAX  Integer32
	MAX-ACCESS  read-write
	STATUS  current
	DESCRIPTION
		"Sets the aging period for ports on the device, defining how long a port
		address remains active in the address table.
		Valid values: 0 = no aging, or 67 - 65535 seconds
		Default: 300 seconds."
	::= { snSwInfo 5 }



snVLanGroupVlanCurEntry OBJECT-TYPE
	SYNTAX  Integer32
	MAX-ACCESS  read-only
	STATUS  current
	DESCRIPTION
		"The current total entry number of VLANs are configured." 
	::= { snSwInfo 6 }


snVLanGroupSetAllVLan OBJECT-TYPE
	SYNTAX  Integer32
	MAX-ACCESS  read-write
	STATUS  current
	DESCRIPTION
		"The value of this object is the VLanIndex of a particalur
		 entry in snVLanByPortCfgTable (snVLanByPortCfgVLanId).  
		 All the attributes of that row of table except PortMask
		 will be used to set the same attributes for the 
		 entire VLan group. VLanId and PortMask must be set for 
				 that particular entry prior to setting this object.
		 Switch software will base on that VLAN information
		 to set the entire VLAN.   
		 Note: All the intended attributes of the given 
		 row of the table (given VLAN) must be set prior
		 setting this object.  When this object is set,
		 Set-All-VLAN action will take place simultaneously.
		 The previous setting will be overwritten by the 
		 new one."
	::= { snSwInfo 7 }


snSwPortSetAll OBJECT-TYPE
	SYNTAX  Integer32
	MAX-ACCESS  read-write
	STATUS  current
	DESCRIPTION
		"The value of this object is the index number of the
		 snSwPortInfoTable (snSwPortInfoPortIndex).  
		 snSwPortInfoMonitorMode, snSwPortInfoTagMode, 
		 snSwPortInfoChnMode, snSwPortInfoSpeed,
		 snSwPortInfoAdminStatus are all the
		 read-write attributes of that row of table.
		 They will be used to set the same attributes for
		 all the ports in the system.
		 Note: prior setting this object, all the intended 
		 attributes of the given row of the table must be set.  
		 Otherwise, the current data of the row will be used to 
		 set the entire port-table. The previous setting will
		 be overwritten by the new one." 
	::= { snSwInfo 8 }



snFdbTableCurEntry OBJECT-TYPE
	SYNTAX  Integer32
	MAX-ACCESS  read-only
	STATUS  current
	DESCRIPTION
		"The current total entry number of FDB are configured." 
	::= { snSwInfo 9 }


snFdbTableStationFlush OBJECT-TYPE
	SYNTAX  INTEGER {
		normal(1),
		error(2),
		flush(3),
		flushing(4)
	}
	MAX-ACCESS  read-write
	STATUS  current
	DESCRIPTION
		"The following values of the flush state
		 can only be read:
		  normal(1)... normal state
		  error(2)... operation failed
		  flushing(4)... in process

		The following value can be written:
		  flush(3).....do flush 

		The agent will return a response even before the flush is done.
		And the read value will be flushing until flush is done.
		And the flush request will be rejected until error or normal."
	::= { snSwInfo 10 }


snPortStpSetAll OBJECT-TYPE
	SYNTAX  Integer32
	MAX-ACCESS  read-write
	STATUS  current
	DESCRIPTION
		"The value of this object is 1 which means invoking
				 Port STP Set-all command.  The snPortStpPriority, 
				 snPortStpPathCost, the read-write STP related 
				 attributes of the first row of table will be used 
				 to set the same attributes for all the ports in the 
				 system. 
		 Note: prior setting this object, all the intended 
		 attributes of the given row of the table must be set.  
		 Otherwise, the current data of the row will be used to 
		 set the entire port-table. The previous setting will
		 be overwritten by the new one." 
	::= { snSwInfo 11 }


snSwProbePortNum OBJECT-TYPE
	SYNTAX  Integer32
	MAX-ACCESS  read-write
	STATUS  current
	DESCRIPTION
		"A chassis switch probe port is operated as a traffic analyzer
		 port and only one port can be assigned in the chassis.
		 The bit 0 to bit 7: port number. 
		 The bit 8 to bit 11: slot number.
		 A stackable switch is only assigned with one probe port as a 
		 traffic analyzer."
	::= { snSwInfo 12 }


snSw8021qTagMode OBJECT-TYPE
	SYNTAX  INTEGER {
		disabled(0),
		enabled(1)
		}
	MAX-ACCESS  read-write
	STATUS  current
	DESCRIPTION
		"The Switch Group is configured with the IEEE802.1q
		 Tagging mode either enabled or disabled and the
		 default is disabled mode.
		 enabled(1)...........activate IEEE802.1q Tagging mode.
		 disabled(0)..........no IEEE802.1q Tagging."
	::= { snSwInfo 13 }


snSwGlobalStpMode OBJECT-TYPE
	SYNTAX  INTEGER {
		disabled(0),
		enabled(1)       
		}
	MAX-ACCESS  read-write
	STATUS  current
	DESCRIPTION
		"Spanning Tree System Global Mode in the Switch Group 
		 can be set either enabled or disabled and the default is 
		 enabled mode.
		 enabled(1)...........activate Spanning Tree
		 disabled(0)..........no Spanning Tree"
	::= { snSwInfo 14 }


snSwIpMcastQuerierMode OBJECT-TYPE
	SYNTAX  INTEGER {
		querier(1),
		nonQuerier(2)
		}
	MAX-ACCESS  read-write
	STATUS  current
	DESCRIPTION
		"The IP Multicast pruning mode is configured either 
		 Non-Querier or Querier mode and the default is 
		 querier mode.
		 querier(1)...........when prunning traffic locally 
							  within the VLAN.
		 nonQuerier(2)........when running with a multicast 
							  capable router in the network."
	::= { snSwInfo 15 }

snSwViolatorPortNumber OBJECT-TYPE
	SYNTAX   Integer32
	MAX-ACCESS  read-only
	STATUS	current
	DESCRIPTION
		"The port number of the switch or router that received
		 a violator packet. It is included in the locked
		 address violation trap.
		 The bit 0 to bit 7: port number. 
		 The bit 8 to bit 11: slot number (slot for chassis only)."
	::= { snSwInfo 17 }

snSwViolatorMacAddress OBJECT-TYPE
	SYNTAX  MacAddress
	MAX-ACCESS  read-only
	STATUS	current
	DESCRIPTION
		"The source address of the violator packet received
		 by the switch or router. It is included in the locked
		 address violation trap."
	::= { snSwInfo 18 }

snVLanGroupVlanMaxEntry OBJECT-TYPE
	SYNTAX  Integer32
	MAX-ACCESS  read-write
	STATUS  current
	DESCRIPTION
		"The maximum number of VLAN entries are allowed to configure."
	::= { snSwInfo 19 }

snSwEosBufferSize OBJECT-TYPE
	SYNTAX  Integer32
	MAX-ACCESS  read-only
	STATUS  current
	DESCRIPTION
		"A specific buffer size for all the different EOS buffers."
	::= { snSwInfo 20 }

snVLanByPortEntrySize OBJECT-TYPE
	SYNTAX  Integer32 
	MAX-ACCESS  read-only
	STATUS  current
	DESCRIPTION
		 "The size of each VLAN table entry."
	::= { snSwInfo 21 }

snSwPortEntrySize OBJECT-TYPE
	SYNTAX  Integer32 
	MAX-ACCESS  read-only
	STATUS  current
	DESCRIPTION
		 "The size of each port table entry."
	::= { snSwInfo 22 }

snFdbStationEntrySize OBJECT-TYPE
	SYNTAX  Integer32 
	MAX-ACCESS  read-only
	STATUS  current
	DESCRIPTION
		 "The size of each Fdb station table entry."
	::= { snSwInfo 23 }

snPortStpEntrySize OBJECT-TYPE
	SYNTAX  Integer32 
	MAX-ACCESS  read-only
	STATUS  current
	DESCRIPTION
		 "The size of each port stp table entry."
	::= { snSwInfo 24 }

snSwEnableBridgeNewRootTrap OBJECT-TYPE
	SYNTAX	INTEGER { disabled(0), enabled(1) }
	MAX-ACCESS	read-write
	STATUS	current
	DESCRIPTION
		"Indicates whether the SNMP agent process is
		permitted to generate bridge new root traps."
	DEFVAL { enabled }
	::= { snSwInfo 25 }

snSwEnableBridgeTopoChangeTrap OBJECT-TYPE
	SYNTAX	INTEGER { disabled(0), enabled(1) }
	MAX-ACCESS	read-write
	STATUS	current
	DESCRIPTION
		"Indicates whether the SNMP agent process is
		permitted to generate bridge topology change
		traps."
	DEFVAL { enabled }
	::= { snSwInfo 26 }

snSwEnableLockedAddrViolationTrap OBJECT-TYPE
	SYNTAX	INTEGER { disabled(0), enabled(1) }
	MAX-ACCESS	read-write
	STATUS	current
	DESCRIPTION
		"Indicates whether the SNMP agent process is
		permitted to generate locked address violation
		traps."
	DEFVAL { enabled }
	::= { snSwInfo 27 }

snSwIpxL3SwMode OBJECT-TYPE
	SYNTAX  INTEGER {
		disabled(0),             
		enabled(1)
		}
	MAX-ACCESS  read-write
	STATUS  current
	DESCRIPTION
		"The Switch Group is configured with the Layer3
		 IPX Switch mode either enabled or disabled and 
		 the default is disabled mode.
		 enabled(1)...........activate Layer3 Switch
		 disabled(0)..........disable Layer3 Switch"  
	::= { snSwInfo 28 }

snVLanByIpSubnetMaxSubnets OBJECT-TYPE
	SYNTAX  Integer32 
	MAX-ACCESS  read-only
	STATUS  current
	DESCRIPTION
		"The maximum number of subnets for each IP VLAN."
	::= { snSwInfo 29 }

snVLanByIpxNetMaxNetworks OBJECT-TYPE
	SYNTAX  Integer32 
	MAX-ACCESS  read-only
	STATUS  current
	DESCRIPTION
		"The maximum number of networks for each IPX VLAN."
	::= { snSwInfo 30 }

snSwProtocolVLanMode OBJECT-TYPE
	SYNTAX  INTEGER {
		disabled(0),
		enabled(1)
		}
	MAX-ACCESS  read-write
	STATUS  deprecated
	DESCRIPTION
		"disabled(0) - represents system with Protocol VLAN disabled. 
		 enabled(1) - represents system with Protocol VLAN enabled (Layer3 VLAN)."
	::= { snSwInfo 31 }

snMacStationVLanId OBJECT-TYPE
	SYNTAX  INTEGER (0..4095)
	MAX-ACCESS  read-write
	STATUS  deprecated
	DESCRIPTION
		"This VLAN ID controls filtering of the Forwarding Database
		table in the standard Bridge MIB (dot1dTpFdbTable).  Since the
		dot1dTpFdbTable contains MAC addresses associated with each of
		the ports in the bridge, and each MAC address can be
		associated with different VLANs, the snMacStationVLanId can be
		used by users to specify which VLAN's MAC Station information
		the dot1dTpFdbTable should provide.  If this variable is set
		to zero (the default value), all MAC station entries will be
		returned when the dot1dTpFdbTable is retrieved.  The
		VLAN-aware dot1qTpFdbTable described in RFC 2674 should be
		used as a replacement for this variable."
	::= { snSwInfo 32 }

snSwClearCounters OBJECT-TYPE
	SYNTAX  INTEGER {
		valid(0),
		clear(1)
		}
	MAX-ACCESS  read-write
	STATUS  current
	DESCRIPTION
		"valid(0) - a SNMP-GET of this mib shows that it is valid command to use. 
		 clear(1) - represents clear counter command of the following counters:
					Dot3, MIB2, IP and IPX counters for all ports."
	::= { snSwInfo 33 }

snSw8021qTagType OBJECT-TYPE
	SYNTAX  Integer32
	MAX-ACCESS  read-write
	STATUS  current
	DESCRIPTION
		"The IEEE802.1q tag type embedded in the length/type field of
		an Ethernet packet. It specifies that the 2 octets after the
		length/type field in an Ethernet packet is the tag value."
	DEFVAL { 33024 }
	::= { snSwInfo 34 }

snSwBroadcastLimit OBJECT-TYPE
	SYNTAX  Integer32
	MAX-ACCESS  read-write
	STATUS  current
	DESCRIPTION
		"Limit the number of broadcast packets to forward out of the
		switch ports. This object specifies the number of broadcast
		packets per second. Setting a value of 0 to this object
		disables the limitation check."
	DEFVAL { 0 }
	::= { snSwInfo 35 }

snSwMaxMacFilterPerSystem  OBJECT-TYPE
	SYNTAX  Integer32 
	MAX-ACCESS  read-only
	STATUS  current
	DESCRIPTION
		"The maximum number of MAC Filters per system in the MAC Filter table."
	::= { snSwInfo 36 }

snSwMaxMacFilterPerPort  OBJECT-TYPE
	SYNTAX  Integer32 
	MAX-ACCESS  read-only
	STATUS  current
	DESCRIPTION
		"The maximum number of MAC Filters per port in the Port MAC Access Filter table."
	::= { snSwInfo 37 }

snSwDefaultVLanId OBJECT-TYPE
	SYNTAX  INTEGER (1..4095)
	MAX-ACCESS  read-write
	STATUS  current
	DESCRIPTION
		"The VLAN ID of the DEFAULT PORT-VLAN."
	::= { snSwInfo 38 }

snSwGlobalAutoNegotiate OBJECT-TYPE
	SYNTAX  INTEGER {
		disabled(0),
		enabled(1),
		negFullAuto(2),
		other(3)
		}
	MAX-ACCESS  read-write
	STATUS  current
	DESCRIPTION
		"This feature only applies to Gigabit Ethernet ports. If set
		to disable(0), all Gigabit Ethernet ports will be put to non-
		negotiation mode. If set to enable(1), all Gigabit Ethernet
		ports will start auto-negotiation indefinitely until succeed.
		If set to negFullAuto(2), all Gigabit Ethernet ports will start
		with auto-negotiation, if the negotiation failed, then they
		will automatically switch to non-negotiation mode. Stackable
		products (except TurboIron 8) Gigabit Ethernet ports do not
		support negFullAuto(2). If the snSwPortInfoAutoNegotiate value
		of a port was not set to global, this global value does not
		apply to the negotiation mode of that port."
	DEFVAL { negFullAuto }
	::= { snSwInfo 39 }

snSwQosMechanism OBJECT-TYPE
	SYNTAX	INTEGER { strict(0), weighted(1) }
	MAX-ACCESS	read-write
	STATUS	current
	DESCRIPTION
		"Indicates whether the qos mechanism is
		 strict or weighted."
	DEFVAL { weighted }
	::= { snSwInfo 40 }

snSwSingleStpMode OBJECT-TYPE
	SYNTAX  INTEGER {
				disable(0),
				enableStp(1),
				enableRstp(2)
			}
	MAX-ACCESS  read-write
	STATUS  current
	DESCRIPTION
		"Single Spanning Tree System Mode in the Switch Group 
		 can be set either enabled or disabled and the default is 
		 disabled mode.
		 disable(0)...........no Single Spanning Tree
		 enableStp(1).........activate SSTP control vlan to run Spanning Tree
		 enableRstp(2)........activate SSTP control vlan to run Rapid Spanning Tree"
	::= { snSwInfo 41 }

snSwFastStpMode OBJECT-TYPE
	SYNTAX  INTEGER {
		disabled(0),
		enabled(1)       
		}
	MAX-ACCESS  read-write
	STATUS  current
	DESCRIPTION
		"Fast Spanning Tree System Mode in the Switch Group 
		 can be set either enabled or disabled and the default is 
		 enabled mode.
		 enabled(1)...........activate Fast Spanning Tree
		 disabled(0)..........no Fast Spanning Tree"
	::= { snSwInfo 42 }

snSwViolatorIfIndex OBJECT-TYPE
	SYNTAX   Integer32
	MAX-ACCESS  read-only
	STATUS  current
	DESCRIPTION
		"The port number of the switch or router that received
		 a violator packet. It is included in the locked
		 address violation trap."
	::= { snSwInfo 43 }

snSwSingleStpVLanId OBJECT-TYPE
	SYNTAX  Integer32
	MAX-ACCESS  read-only
	STATUS  current
	DESCRIPTION
		"The VLAN ID of the Single Spanning Tree VLAN if Single
		Spanning Tree was enabled. This object returns zero if
		Single Spanning Tree was disabled."
	::= { snSwInfo 44 }


-- VLAN Layer 2 Switch VLAN By Port Information Table


snVLanByPortTable OBJECT-TYPE
	SYNTAX  SEQUENCE OF SnVLanByPortEntry
	MAX-ACCESS  not-accessible
	STATUS  deprecated
	DESCRIPTION
		"If snSwGroupOperMode is configured as basic mode
		 which is VLAN by Port, Layer2 switching,
		 then this table is valid.  Each VLAN switch port
		 could have a number of VLAN IDs."
	::= { snVLanInfo 1 }


snVLanByPortEntry OBJECT-TYPE
	SYNTAX  SnVLanByPortEntry
	MAX-ACCESS  not-accessible
	STATUS  deprecated
	DESCRIPTION
		"An entry in the VLAN By Port Information table.
		 snVLanByPortVLanIndex = 1 and with 
		 snVLanByPortVLanId = 1 together implies all attributes
		 applying to the Global switch group i.e. noVLan.
		 A SNMP SET PDU for a row of the snVLanByPortTable 
		 requires the entired sequence of the MIB Objects in each 
		 snVLanByPortEntry stored in one PDU.  Otherwise, 
	 GENERR return-value will be returned."
	INDEX   { 
		snVLanByPortVLanIndex
	}
	::= { snVLanByPortTable 1 }


SnVLanByPortEntry ::= SEQUENCE {
	snVLanByPortVLanIndex
		INTEGER,
	snVLanByPortVLanId
		INTEGER,
	snVLanByPortPortMask
		PortMask,
	snVLanByPortQos
		INTEGER,
	snVLanByPortStpMode
		INTEGER,
	snVLanByPortStpPriority 
		INTEGER,
	snVLanByPortStpGroupMaxAge 
		INTEGER,
	snVLanByPortStpGroupHelloTime 
		INTEGER,
	snVLanByPortStpGroupForwardDelay 
		INTEGER,
	snVLanByPortRowStatus 
		INTEGER,
	snVLanByPortOperState
		INTEGER,
	snVLanByPortBaseNumPorts
		Integer32,
	snVLanByPortBaseType
		INTEGER, 
	snVLanByPortStpProtocolSpecification 
		INTEGER,
	snVLanByPortStpMaxAge
		Timeout,
	snVLanByPortStpHelloTime 
		Timeout,
	snVLanByPortStpHoldTime 
		Integer32,
	snVLanByPortStpForwardDelay 
		Timeout,
	snVLanByPortStpTimeSinceTopologyChange 
		TimeTicks,
	snVLanByPortStpTopChanges
		Counter32,
	snVLanByPortStpRootCost
		Integer32,
	snVLanByPortStpRootPort
		Integer32,
	snVLanByPortStpDesignatedRoot
		BridgeId,
	snVLanByPortBaseBridgeAddress 
		MacAddress,
	snVLanByPortVLanName
		DisplayString,
	snVLanByPortRouterIntf
		Integer32,
	snVLanByPortChassisPortMask
		OCTET STRING,
	snVLanByPortPortList
		OCTET STRING
	}

snVLanByPortVLanIndex OBJECT-TYPE
	SYNTAX  INTEGER (1..4095)
	MAX-ACCESS  read-only
	STATUS  deprecated
	DESCRIPTION
		"The VLAN ID index must not be greater than the 
		 snVLanGroupVlanMaxEntry. Each VLAN Identifier can 
		 have a membership of multiple ports."
	::= { snVLanByPortEntry 1 }


snVLanByPortVLanId OBJECT-TYPE
	SYNTAX  INTEGER (1..4095)
	MAX-ACCESS  read-write
	STATUS  deprecated
	DESCRIPTION
		"The VLAN ID index to the VLAN By Port Info Table.
		 Each VLAN Identifier can have a membership of multiple 
		 ports."
	::= { snVLanByPortEntry 2 }


snVLanByPortPortMask OBJECT-TYPE
	SYNTAX  PortMask
	MAX-ACCESS  read-write
	STATUS  deprecated
	DESCRIPTION
		"The Standand-alone switch VLAN port membership. (It was obsoleted for Chassis Product)"
	::= { snVLanByPortEntry 3 }


snVLanByPortQos OBJECT-TYPE
	SYNTAX  INTEGER {
		level0(0),
		level1(1),
		level2(2),
		level3(3),
		level4(4),
		level5(5),
		level6(6),
		level7(7)
		}
	MAX-ACCESS  read-write
	STATUS  deprecated
	DESCRIPTION
		"The Stand alone stackable switch VLAN Priority values are:
		 low(0)   -- low prority
		 high(1) -- high prority.
		 The BigIron switch VLAN Priority values are:
		level0(0), level1(1), level2(2), level3(3),
		level4(4), level5(5), level6(6), level7(7) "
	::= { snVLanByPortEntry 4 }

snVLanByPortStpMode OBJECT-TYPE
	SYNTAX  INTEGER {
		disable(0),
		enableStp(1),
		enableRstp(2)
		}
	MAX-ACCESS  read-write
	STATUS  deprecated
	DESCRIPTION
		"Spanning Tree Mode in the Switch Group can be set
		 either enabled or disabled and the default is 
		 enabled mode.
		 disable(0)...........no Spanning Tree
		 enableStp(1).........activate Spanning Tree
		 enableRstp(2)........activate Rapid Spanning Tree"
	::= { snVLanByPortEntry 5 }

snVLanByPortStpPriority OBJECT-TYPE
	SYNTAX  INTEGER (0..65535)
	MAX-ACCESS  read-write
	STATUS  deprecated
	DESCRIPTION
	"dot1dStpPriority : The value of the write-able 
	 portion of the Stp ID, i.e., the first two octets 
	 of the (8 octet long) Bridge ID.  The other (last) 6 
	 octets of the Bridge ID are given by the value of the 
	 base bridge address - dot1dBaseBridgeAddress."
	::= { snVLanByPortEntry 6 }

snVLanByPortStpGroupMaxAge OBJECT-TYPE
	SYNTAX  INTEGER (0..40)
	MAX-ACCESS  read-write
	STATUS  deprecated
	DESCRIPTION
	"dot1dStpBridgeMaxAge: From RFC1493(Bridge MIB).
	 The value that all bridges use for MaxAge when 
	 this bridge is acting as the root. 
	 Note that 802.1D-1990 specifies that the 
	 range for this parameter is related to the value of
	 dot1dStpBridgeHelloTime. The granularity of this
	 timer is specified by 802.1D-1990 to be 1 second.
	 An agent may return a badValue error if a set is
	 attempted to a value which is not a whole number
	 of seconds."
	::= { snVLanByPortEntry 7 }

snVLanByPortStpGroupHelloTime OBJECT-TYPE
	SYNTAX  INTEGER (0..10)
	MAX-ACCESS  read-write
	STATUS  deprecated
	DESCRIPTION
	"dot1dStpBridgeHelloTime: From RFC1493(Bridge MIB).
	 The value that all bridges use for HelloTime when
	 this bridge is acting as the root.  The
	 granularity of this timer is specified by 802.1D-
	 1990 to be 1 second.  An agent may return a
	 badValue error if a set is attempted to a value
	 which is not a whole number of seconds."
	::= { snVLanByPortEntry 8 }

snVLanByPortStpGroupForwardDelay OBJECT-TYPE
	SYNTAX  INTEGER (0..30)
	MAX-ACCESS  read-write
	STATUS  deprecated
	DESCRIPTION
	"dot1dStpBridgeForwardDelay : From RFC1493(Bridge MIB).
	 The value that all bridges use for ForwardDelay
	 when this bridge is acting as the root.  Note that
	 802.1D-1990 specifies that the range for this
	 parameter is related to the value of
	 dot1dStpBridgeMaxAge.  The granularity of this
	 timer is specified by 802.1D-1990 to be 1 second.
	 An agent may return a badValue error if a set is
	 attempted to a value which is not a whole number
	 of seconds."
	::= { snVLanByPortEntry 9 }

snVLanByPortRowStatus OBJECT-TYPE
	SYNTAX  INTEGER {
		other(1),
		valid(2),
		delete(3),
		create(4),
		modify(5)
		}
	MAX-ACCESS  read-write
	STATUS  deprecated
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByPortEntry 10 }

snVLanByPortOperState OBJECT-TYPE
	SYNTAX  INTEGER {
		notActivated(0),             
		activated(1)
		}
	MAX-ACCESS  read-only
	STATUS  deprecated
	DESCRIPTION
		"By default, this mode is set to notActivated(0).
		 notActivated(0)...the VLAN entry is not activated and not in running mode.
		 activated(1)......the VLAN entry is activated and in running mode"  
	::= { snVLanByPortEntry 11 }

snVLanByPortBaseNumPorts OBJECT-TYPE
	SYNTAX  Integer32
	MAX-ACCESS  read-only
	STATUS  deprecated
	DESCRIPTION
	"The number of ports controlled by this bridging
	 entity."
	::= { snVLanByPortEntry 12 }

snVLanByPortBaseType OBJECT-TYPE
	SYNTAX  INTEGER {
			  unknown(1),
			  transparentOnly(2),
			  sourcerouteOnly(3),
			  srt(4)
			}
	MAX-ACCESS  read-only
	STATUS  deprecated
	DESCRIPTION
	"Indicates what type of bridging this bridge can
	 perform.  If a bridge is actually performing a
	 certain type of bridging this will be indicated by
	 entries in the port table for the given type."
	::= { snVLanByPortEntry 13 }

snVLanByPortStpProtocolSpecification OBJECT-TYPE
	SYNTAX  INTEGER {
		unknown(1),
		decLb100(2),
		ieee8021d(3)
		}
	MAX-ACCESS  read-only
	STATUS  deprecated
	DESCRIPTION
	"An indication of what version of the Spanning
	 Tree Protocol is being run.  The value
	 'decLb100(2)' indicates the DEC LANbridge 100
	 Spanning Tree protocol.  IEEE 802.1d
	 implementations will return 'ieee8021d(3)'.  If
	 future versions of the IEEE Spanning Tree Protocol
	 are released that are incompatible with the
	 current version a new value will be defined."
	::= { snVLanByPortEntry 14 }


snVLanByPortStpMaxAge OBJECT-TYPE
	SYNTAX  Timeout
	MAX-ACCESS  read-only
	STATUS  deprecated
	DESCRIPTION
	"dot1dStpMaxAge: From RFC1493(Bridge MIB).
	 The maximum age of Spanning Tree Protocol
	 information learned from the network on any port
	 before it is discarded, in units of hundredths of
	 a second.  This is the actual value that this
	 bridge is currently using."
	::= { snVLanByPortEntry 15 }

snVLanByPortStpHelloTime OBJECT-TYPE
	SYNTAX  Timeout
	MAX-ACCESS  read-only
	STATUS  deprecated
	DESCRIPTION
	"dot1dStpHelloTime: From RFC1493(Bridge MIB).
	 The amount of time between the transmission of
	 Configuration bridge PDUs by this node on any port
	 when it is the root of the spanning tree or trying
	 to become so, in units of hundredths of a second.
	 This is the actual value that this bridge is
	 currently using."
	::= { snVLanByPortEntry 16 }

snVLanByPortStpHoldTime OBJECT-TYPE
	SYNTAX  Integer32
	MAX-ACCESS  read-only
	STATUS  deprecated
	DESCRIPTION
	"dot1dStpHoldTime: From RFC1493(Bridge MIB).
	 This time value determines the interval length
	 during which no more than two Configuration bridge
	 PDUs shall be transmitted by this node, in units
	 of hundredths of a second."
	::= { snVLanByPortEntry 17 }

 snVLanByPortStpForwardDelay OBJECT-TYPE
	 SYNTAX  Timeout
	 MAX-ACCESS  read-only
	 STATUS  deprecated
	 DESCRIPTION
	 "dot1dStpForwardDelay: From RFC1493(Bridge MIB).
	  This time value, measured in units of hundredths
	  of a second, controls how fast a port changes its
	  spanning state when moving towards the Forwarding
	  state.  The value determines how long the port
	  stays in each of the Listening and Learning
	  states, which precede the Forwarding state.  This
	  value is also used, when a topology change has
	  been detected and is underway, to age all dynamic
	  entries in the Forwarding Database.  [Note that
	  this value is the one that this bridge is
	  currently using, in contrast to
	  dot1dStpBridgeForwardDelay which is the value that
	  this bridge and all others would start using
	  if/when this bridge were to become the root.]"
	::= { snVLanByPortEntry 18 }


snVLanByPortStpTimeSinceTopologyChange OBJECT-TYPE
	SYNTAX  TimeTicks
	MAX-ACCESS  read-only
	STATUS  deprecated
	DESCRIPTION
	"The time (in hundredths of a second) since the
	 last time a topology change was detected by the
	 bridge entity."
	::= { snVLanByPortEntry 19 }

snVLanByPortStpTopChanges OBJECT-TYPE
	SYNTAX  Counter32
	MAX-ACCESS  read-only
	STATUS  deprecated
	DESCRIPTION
	"The total number of topology changes detected by
	 this bridge since the management entity was last
	 reset or initialized."
	::= { snVLanByPortEntry 20 }

snVLanByPortStpRootCost OBJECT-TYPE
	SYNTAX  Integer32
	MAX-ACCESS  read-only
	STATUS  deprecated
	DESCRIPTION
	"dot1dStpRootCost: From RFC1493(Bridge MIB).     
	 The cost of the path to the root as seen from
	 this bridge."
	::= { snVLanByPortEntry 21 }

snVLanByPortStpRootPort OBJECT-TYPE
	SYNTAX  Integer32
	MAX-ACCESS  read-only
	STATUS  deprecated
	DESCRIPTION
	"dot1dStpRootPort: From RFC1493(Bridge MIB).
	 The port number of the port which offers the
	 lowest cost path from this bridge to the root
	 bridge."
	::= { snVLanByPortEntry 22 }

snVLanByPortStpDesignatedRoot OBJECT-TYPE
	SYNTAX  BridgeId
	MAX-ACCESS  read-only
	STATUS  deprecated
	DESCRIPTION
	"dot1dStpDesignatedRoot: From RFC1493(Bridge MIB).
	 The bridge identifier of the root of the spanning
	 tree as determined by the Spanning Tree Protocol
	 as executed by this node.  This value is used as
	 the Root Identifier parameter in all Configuration
	 Bridge PDUs originated by this node."
	::= { snVLanByPortEntry 23 }

snVLanByPortBaseBridgeAddress OBJECT-TYPE
	SYNTAX  MacAddress
	MAX-ACCESS  read-only
	STATUS  deprecated
	DESCRIPTION
	"The MAC address used by this bridge when it must
	 be referred to in a unique fashion.   It is
	 recommended that this be the numerically smallest
	 MAC address of all ports that belong to this
	 bridge.  However it is only required to be unique.
	 When concatenated with dot1dStpPriority a unique
	 BridgeIdentifier is formed which is used in the
	 Spanning Tree Protocol."
	::= { snVLanByPortEntry 24 }

snVLanByPortVLanName OBJECT-TYPE
	SYNTAX	DisplayString (SIZE(0..32))
	MAX-ACCESS	read-write
	STATUS	deprecated
	DESCRIPTION
		"VLAN Community Name string."
	::= { snVLanByPortEntry 25 }


snVLanByPortRouterIntf OBJECT-TYPE
	SYNTAX  Integer32
	MAX-ACCESS  read-write
	STATUS  deprecated
	DESCRIPTION
		"Optional: A virtual interface for router to the VLAN -- applied to router only.
		 If a SNMP-Get value is zero, that means this object was not configured."
	::= { snVLanByPortEntry 26 }


snVLanByPortChassisPortMask OBJECT-TYPE
	SYNTAX  OCTET STRING
	MAX-ACCESS  read-write
	STATUS  deprecated
	DESCRIPTION
		"The Chassis VLAN switch port membership.
		(It was obsoleted after release 07100, replaced by snVLanByPortPortList)"
	::= { snVLanByPortEntry 27 }

snVLanByPortPortList OBJECT-TYPE
	SYNTAX  OCTET STRING
	MAX-ACCESS  read-write
	STATUS  deprecated
	DESCRIPTION
		"A list of port indices which are the port
		membership of a VLAN By Port. Each port index is a
		16-bit integer in big endian order. 8-bit is the slot number,
		the other 8-bit is the port number."
	::= { snVLanByPortEntry 28 }


-- Port VLAN (Layer 2 VLAN) Port Membership Table
-- Use this table to create or delete a VLAN entry


snVLanByPortMemberTable OBJECT-TYPE
	SYNTAX  SEQUENCE OF SnVLanByPortMemberEntry
	MAX-ACCESS  not-accessible
	STATUS  current
	DESCRIPTION
		"Port VLAN (Layer 2 VLAN) port membership table."
	::= { snVLanInfo 6 }


snVLanByPortMemberEntry OBJECT-TYPE
	SYNTAX  SnVLanByPortMemberEntry
	MAX-ACCESS  not-accessible
	STATUS  current
	DESCRIPTION
		"An entry of the port VLAN membership table."
	INDEX   { snVLanByPortMemberVLanId, snVLanByPortMemberPortId }
	::= { snVLanByPortMemberTable 1 }

SnVLanByPortMemberEntry ::= SEQUENCE {
	snVLanByPortMemberVLanId
		INTEGER,
	snVLanByPortMemberPortId
		InterfaceIndex,
	snVLanByPortMemberRowStatus 
		INTEGER,
	snVLanByPortMemberTagMode
		INTEGER
	}

snVLanByPortMemberVLanId OBJECT-TYPE
	SYNTAX  INTEGER (1..4095)
	MAX-ACCESS  read-only
	STATUS  current
	DESCRIPTION
		"The VLAN identifier (VLAN ID)."
	::= { snVLanByPortMemberEntry 1 }

snVLanByPortMemberPortId OBJECT-TYPE
	SYNTAX  InterfaceIndex
	MAX-ACCESS  read-only
	STATUS  current
	DESCRIPTION
		"The ifIndex which is a member of the port VLAN."
	::= { snVLanByPortMemberEntry 2 }

snVLanByPortMemberRowStatus OBJECT-TYPE
	SYNTAX  INTEGER {
		other(1),
		valid(2),
		delete(3),
		create(4)
		}
	MAX-ACCESS  read-write
	STATUS  current
	DESCRIPTION
		"This object is used to create and
		delete row in the table and control
		if they are used. The values
		that can be written are:
		  delete(3)...deletes the row
		  create(4)...creates a new row

		If the row exists, then a SET with
		value of create(4) returns error
		'badValue'. Deleted rows go away
		immediately. The following values
		can be returned on reads:
		  noSuch(0)...no such row
		  other(1)....some other case
		  valid(2)....the row exists and is valid"
	::= { snVLanByPortMemberEntry 3 }

snVLanByPortMemberTagMode OBJECT-TYPE
	SYNTAX  INTEGER {
				tagged(1),      
				untagged(2)
			}
	MAX-ACCESS  read-write
	STATUS  current
	DESCRIPTION
		"For tagged/dual-mode port, we could have multiple VLANs per
		 port. For untagged port, there is only one VLAN ID per port."  
	::= { snVLanByPortMemberEntry 4 }


-- Port VLAN (Layer 2 VLAN) Configuration Table
-- Use this table to configure a VLAN entry


snVLanByPortCfgTable OBJECT-TYPE
	SYNTAX  SEQUENCE OF SnVLanByPortCfgEntry
	MAX-ACCESS  not-accessible
	STATUS  current
	DESCRIPTION
		"Port VLAN (Layer 2 VLAN) configuration table."
	::= { snVLanInfo 7 }


snVLanByPortCfgEntry OBJECT-TYPE
	SYNTAX  SnVLanByPortCfgEntry
	MAX-ACCESS  not-accessible
	STATUS  current
	DESCRIPTION
		"An entry of the port VLAN configuration table."
	INDEX   { snVLanByPortCfgVLanId }
	::= { snVLanByPortCfgTable 1 }


SnVLanByPortCfgEntry ::= SEQUENCE {
	snVLanByPortCfgVLanId
		INTEGER,
	snVLanByPortCfgQos
		PortQosTC,
	snVLanByPortCfgStpMode
		INTEGER,
	snVLanByPortCfgStpPriority 
		INTEGER,	
	snVLanByPortCfgStpGroupMaxAge 
		Integer32,
	snVLanByPortCfgStpGroupHelloTime 
		Integer32,
	snVLanByPortCfgStpGroupForwardDelay 
		Integer32,
	snVLanByPortCfgBaseNumPorts
		Integer32,
	snVLanByPortCfgBaseType
		INTEGER, 
	snVLanByPortCfgStpProtocolSpecification 
		INTEGER,
	snVLanByPortCfgStpMaxAge
		Timeout,
	snVLanByPortCfgStpHelloTime 
		Timeout,
	snVLanByPortCfgStpHoldTime 
		Integer32,
	snVLanByPortCfgStpForwardDelay 
		Timeout,
	snVLanByPortCfgStpTimeSinceTopologyChange 
		TimeTicks,
	snVLanByPortCfgStpTopChanges
		Counter32,
	snVLanByPortCfgStpRootCost
		Integer32,
	snVLanByPortCfgStpRootPort
		Integer32,
	snVLanByPortCfgStpDesignatedRoot
		BridgeId,
	snVLanByPortCfgBaseBridgeAddress 
		MacAddress,
	snVLanByPortCfgVLanName
		DisplayString,
	snVLanByPortCfgRouterIntf
		Integer32,
	snVLanByPortCfgRowStatus
		INTEGER,
	snVLanByPortCfgStpVersion
		INTEGER,
	snVLanByPortCfgInOctets
		Counter64
	}

snVLanByPortCfgVLanId OBJECT-TYPE
	SYNTAX  INTEGER (1..4095)
	MAX-ACCESS  read-only
	STATUS  current
	DESCRIPTION
		"The VLAN identifier (VLAN ID)."
	::= { snVLanByPortCfgEntry 1 }

snVLanByPortCfgQos OBJECT-TYPE
	SYNTAX  PortQosTC
	MAX-ACCESS  read-write
	STATUS  current
	DESCRIPTION
		"The Stand alone stackable switch VLAN Priority values are:
		 level0(0)   -- low prority
		 level1(1) -- high prority.
		 The BigIron switch VLAN Priority values are:
		level0(0), level1(1), level2(2), level3(3),
		level4(4), level5(5), level6(6), level7(7).
		  Value invalid(127) is used by CES/CER products to signify
		that no QoS was specified for this VLAN."
	::= { snVLanByPortCfgEntry 2 }

snVLanByPortCfgStpMode OBJECT-TYPE
	SYNTAX  INTEGER {
		disable(0),
		enableStp(1),
		enableRstp(2)
		}
	MAX-ACCESS  read-write
	STATUS  current
	DESCRIPTION
		"Spanning Tree Mode in the Switch Group can be set
		 either enabled or disabled and the default is 
		 enabled mode.
		 disable(0)...........no Spanning Tree
		 enableStp(1).........activate Spanning Tree
		 enableRstp(2)........activate Rapid Spanning Tree"
	::= { snVLanByPortCfgEntry 3 }

snVLanByPortCfgStpPriority OBJECT-TYPE
	SYNTAX  INTEGER (0..65535)
	MAX-ACCESS  read-write
	STATUS  current
	DESCRIPTION
	"dot1dStpPriority : The value of the write-able 
	 portion of the Stp ID, i.e., the first two octets 
	 of the (8 octet long) Bridge ID.  The other (last) 6 
	 octets of the Bridge ID are given by the value of the 
	 base bridge address - dot1dBaseBridgeAddress."
	::= { snVLanByPortCfgEntry 4 }

snVLanByPortCfgStpGroupMaxAge OBJECT-TYPE
	SYNTAX  Integer32
	MAX-ACCESS  read-write
	STATUS  current
	DESCRIPTION
	"dot1dStpBridgeMaxAge: From RFC1493(Bridge MIB).
	 The value that all bridges use for MaxAge when 
	 this bridge is acting as the root. 
	 Note that 802.1D-1990 specifies that the 
	 range for this parameter is related to the value of
	 dot1dStpBridgeHelloTime. The granularity of this
	 timer is specified by 802.1D-1990 to be 1 second.
	 An agent may return a badValue error if a set is
	 attempted to a value which is not a whole number
	 of seconds.
	   Valid value between 6 and 40. Default is 20 seconds.
	 Value 0 is returned if no STP is not configured for this vlan."
		::= { snVLanByPortCfgEntry 5 }

snVLanByPortCfgStpGroupHelloTime OBJECT-TYPE
	SYNTAX  Integer32
	MAX-ACCESS  read-write
	STATUS  current
	DESCRIPTION
	"dot1dStpBridgeHelloTime: From RFC1493(Bridge MIB).
	 The value that all bridges use for HelloTime when
	 this bridge is acting as the root.  The
	 granularity of this timer is specified by 802.1D-
	 1990 to be 1 second.  An agent may return a
	 badValue error if a set is attempted to a value
	 which is not a whole number of seconds.
	   Valid value between 1 and 10. Default is 2 seconds.
	 Value 0 is returned if no STP is not configured for this vlan."
	::= { snVLanByPortCfgEntry 6 }

snVLanByPortCfgStpGroupForwardDelay OBJECT-TYPE
	SYNTAX  Integer32
	MAX-ACCESS  read-write
	STATUS  current
	DESCRIPTION
	"dot1dStpBridgeForwardDelay : From RFC1493(Bridge MIB).
	 The value that all bridges use for ForwardDelay
	 when this bridge is acting as the root.  Note that
	 802.1D-1990 specifies that the range for this
	 parameter is related to the value of
	 dot1dStpBridgeMaxAge.  The granularity of this
	 timer is specified by 802.1D-1990 to be 1 second.
	 An agent may return a badValue error if a set is
	 attempted to a value which is not a whole number
	 of seconds.
	   Valid value between 2 and 30. Default is 15 seconds.
	 Value 0 is returned if no STP is not configured for this vlan."
	::= { snVLanByPortCfgEntry 7 }

snVLanByPortCfgBaseNumPorts OBJECT-TYPE
	SYNTAX  Integer32
	MAX-ACCESS  read-only
	STATUS  current
	DESCRIPTION
	"The number of ports controlled by this bridging
	 entity."
	::= { snVLanByPortCfgEntry 8 }

snVLanByPortCfgBaseType OBJECT-TYPE
	SYNTAX  INTEGER {
			  unknown(1),
			  transparentOnly(2),
			  sourcerouteOnly(3),
			  srt(4)
			}
	MAX-ACCESS  read-only
	STATUS  current
	DESCRIPTION
	"Indicates what type of bridging this bridge can
	 perform.  If a bridge is actually performing a
	 certain type of bridging this will be indicated by
	 entries in the port table for the given type."
	::= { snVLanByPortCfgEntry 9 }

snVLanByPortCfgStpProtocolSpecification OBJECT-TYPE
	SYNTAX  INTEGER {
		unknown(1),
		decLb100(2),
		ieee8021d(3)
		}
	MAX-ACCESS  read-only
	STATUS  current
	DESCRIPTION
	"An indication of what version of the Spanning
	 Tree Protocol is being run.  The value
	 'decLb100(2)' indicates the DEC LANbridge 100
	 Spanning Tree protocol.  IEEE 802.1d
	 implementations will return 'ieee8021d(3)'.  If
	 future versions of the IEEE Spanning Tree Protocol
	 are released that are incompatible with the
	 current version a new value will be defined."
	::= { snVLanByPortCfgEntry 10 }


snVLanByPortCfgStpMaxAge OBJECT-TYPE
	SYNTAX  Timeout
	MAX-ACCESS  read-only
	STATUS  current
	DESCRIPTION
	"dot1dStpMaxAge: From RFC1493(Bridge MIB).
	 The maximum age of Spanning Tree Protocol
	 information learned from the network on any port
	 before it is discarded, in units of hundredths of
	 a second.  This is the actual value that this
	 bridge is currently using."
	::= { snVLanByPortCfgEntry 11 }

snVLanByPortCfgStpHelloTime OBJECT-TYPE
	SYNTAX  Timeout
	MAX-ACCESS  read-only
	STATUS  current
	DESCRIPTION
	"dot1dStpHelloTime: From RFC1493(Bridge MIB).
	 The amount of time between the transmission of
	 Configuration bridge PDUs by this node on any port
	 when it is the root of the spanning tree or trying
	 to become so, in units of hundredths of a second.
	 This is the actual value that this bridge is
	 currently using."
	::= { snVLanByPortCfgEntry 12 }

snVLanByPortCfgStpHoldTime OBJECT-TYPE
	SYNTAX  Integer32
	MAX-ACCESS  read-only
	STATUS  current
	DESCRIPTION
	"dot1dStpHoldTime: From RFC1493(Bridge MIB).
	 This time value determines the interval length
	 during which no more than two Configuration bridge
	 PDUs shall be transmitted by this node, in units
	 of hundredths of a second."
	::= { snVLanByPortCfgEntry 13 }

 snVLanByPortCfgStpForwardDelay OBJECT-TYPE
	 SYNTAX  Timeout
	 MAX-ACCESS  read-only
	 STATUS  current
	 DESCRIPTION
	 "dot1dStpForwardDelay: From RFC1493(Bridge MIB).
	  This time value, measured in units of hundredths
	  of a second, controls how fast a port changes its
	  spanning state when moving towards the Forwarding
	  state.  The value determines how long the port
	  stays in each of the Listening and Learning
	  states, which precede the Forwarding state.  This
	  value is also used, when a topology change has
	  been detected and is underway, to age all dynamic
	  entries in the Forwarding Database.  [Note that
	  this value is the one that this bridge is
	  currently using, in contrast to
	  dot1dStpBridgeForwardDelay which is the value that
	  this bridge and all others would start using
	  if/when this bridge were to become the root.]"
	::= { snVLanByPortCfgEntry 14 }


snVLanByPortCfgStpTimeSinceTopologyChange OBJECT-TYPE
	SYNTAX  TimeTicks
	MAX-ACCESS  read-only
	STATUS  current
	DESCRIPTION
	"The time (in hundredths of a second) since the
	 last time a topology change was detected by the
	 bridge entity."
	::= { snVLanByPortCfgEntry 15 }

snVLanByPortCfgStpTopChanges OBJECT-TYPE
	SYNTAX  Counter32
	MAX-ACCESS  read-only
	STATUS  current
	DESCRIPTION
	"The total number of topology changes detected by
	 this bridge since the management entity was last
	 reset or initialized."
	::= { snVLanByPortCfgEntry 16 }

snVLanByPortCfgStpRootCost OBJECT-TYPE
	SYNTAX  Integer32
	MAX-ACCESS  read-only
	STATUS  current
	DESCRIPTION
	"dot1dStpRootCost: From RFC1493(Bridge MIB).     
	 The cost of the path to the root as seen from
	 this bridge."
	::= { snVLanByPortCfgEntry 17 }

snVLanByPortCfgStpRootPort OBJECT-TYPE
	SYNTAX  Integer32
	MAX-ACCESS  read-only
	STATUS  current
	DESCRIPTION
	"dot1dStpRootPort: From RFC1493(Bridge MIB).
	 The port number of the port which offers the
	 lowest cost path from this bridge to the root
	 bridge."
	::= { snVLanByPortCfgEntry 18 }

snVLanByPortCfgStpDesignatedRoot OBJECT-TYPE
	SYNTAX  BridgeId
	MAX-ACCESS  read-only
	STATUS  current
	DESCRIPTION
	"dot1dStpDesignatedRoot: From RFC1493(Bridge MIB).
	 The bridge identifier of the root of the spanning
	 tree as determined by the Spanning Tree Protocol
	 as executed by this node.  This value is used as
	 the Root Identifier parameter in all Configuration
	 Bridge PDUs originated by this node."
	::= { snVLanByPortCfgEntry 19 }

snVLanByPortCfgBaseBridgeAddress OBJECT-TYPE
	SYNTAX  MacAddress
	MAX-ACCESS  read-only
	STATUS  current
	DESCRIPTION
	"The MAC address used by this bridge when it must
	 be referred to in a unique fashion.   It is
	 recommended that this be the numerically smallest
	 MAC address of all ports that belong to this
	 bridge.  However it is only required to be unique.
	 When concatenated with dot1dStpPriority a unique
	 BridgeIdentifier is formed which is used in the
	 Spanning Tree Protocol."
	::= { snVLanByPortCfgEntry 20 }

snVLanByPortCfgVLanName OBJECT-TYPE
	SYNTAX	DisplayString (SIZE(0..32))
	MAX-ACCESS	read-write
	STATUS	current
	DESCRIPTION
		"VLAN Community Name string."
	::= { snVLanByPortCfgEntry 21 }


snVLanByPortCfgRouterIntf OBJECT-TYPE
	SYNTAX  Integer32
	MAX-ACCESS  read-write
	STATUS  current
	DESCRIPTION
		"Optional: A virtual interface for router to the VLAN -- applied to router only.
		 If a SNMP-Get value is zero, that means this object was not configured."
	::= { snVLanByPortCfgEntry 22 }

snVLanByPortCfgRowStatus OBJECT-TYPE
	SYNTAX  INTEGER {
		other(1),
		valid(2),
		delete(3)
		}
	MAX-ACCESS  read-write
	STATUS  current
	DESCRIPTION
		"Use object to delete a vlan entry."
	::= { snVLanByPortCfgEntry 23 }

snVLanByPortCfgStpVersion OBJECT-TYPE
	SYNTAX  INTEGER {
		stpCompatible(0),
		rstp(2)
		}
	MAX-ACCESS  read-write
	STATUS  current
	DESCRIPTION
		"The version of Spanning Tree Protocol the bridge is
		 currently running.  The value 'stpCompatible(0)'
		 indicates the Spanning Tree Protocol specified in
		 IEEE 802.1D and 'rstp(2)' indicates the Rapid Spanning
		 Tree Protocol specified in IEEE 802.1w.  New value may
		 be defined as future versions of the protocol become
		 available."
	::= { snVLanByPortCfgEntry 24 }

snVLanByPortCfgInOctets OBJECT-TYPE
	SYNTAX  Counter64
	MAX-ACCESS  read-only
	STATUS  current
	DESCRIPTION
		"The number of bytes received on this VLAN. This can be used as the per VE
		 couter, if there is one-to-one map for VLAN-VE."
	::= { snVLanByPortCfgEntry 25 }


-- VLAN by Protocol Configuration Table 


snVLanByProtocolTable OBJECT-TYPE
	SYNTAX  SEQUENCE OF SnVLanByProtocolEntry
	MAX-ACCESS  not-accessible
	STATUS  current
	DESCRIPTION
		"."
	::= { snVLanInfo 2 }


snVLanByProtocolEntry OBJECT-TYPE
	SYNTAX  SnVLanByProtocolEntry
	MAX-ACCESS  not-accessible
	STATUS  current
	DESCRIPTION
		"An entry in the VLAN By Protocol Configuration table. "
	INDEX   { 
		snVLanByProtocolVLanId,
		snVLanByProtocolIndex
	}
	::= { snVLanByProtocolTable 1 }


SnVLanByProtocolEntry ::= SEQUENCE {
	snVLanByProtocolVLanId
		INTEGER,
	snVLanByProtocolIndex
		INTEGER,
	snVLanByProtocolDynamic
		INTEGER,
	snVLanByProtocolStaticMask
		PortMask,
	snVLanByProtocolExcludeMask
		PortMask,
	snVLanByProtocolRouterIntf
		INTEGER,	
	snVLanByProtocolRowStatus
		INTEGER,	
	snVLanByProtocolDynamicMask
		PortMask,
	snVLanByProtocolChassisStaticMask
		OCTET STRING,
	snVLanByProtocolChassisExcludeMask
		OCTET STRING,
	snVLanByProtocolChassisDynamicMask
		OCTET STRING,
	snVLanByProtocolVLanName
		DisplayString,
	snVLanByProtocolStaticPortList
		OCTET STRING,
	snVLanByProtocolExcludePortList
		OCTET STRING,
	snVLanByProtocolDynamicPortList
		OCTET STRING
	}

snVLanByProtocolVLanId OBJECT-TYPE
	SYNTAX  INTEGER (1..4095)
	MAX-ACCESS  read-only
	STATUS  current
	DESCRIPTION
		"The VLAN ID index to both of the VLAN By Port Info Table
		 and this table."
	::= { snVLanByProtocolEntry 1 }


snVLanByProtocolIndex OBJECT-TYPE
	SYNTAX  INTEGER {
		ip(1),
		ipx(2),
		appleTalk(3),
		decNet(4),
		netBios(5),
		others(6),
		ipv6(7)
		}
	MAX-ACCESS  read-only
	STATUS  current
	DESCRIPTION
		" The following IP/IPX protocol VLAN types are operated 
		in Layer3 VLAN such as : ip(1), ipx(2), ipv6(7)
		The following are operated in Layer2 bridging such as:
		appleTalk(3), decNet(4), netBios(5),
		others(6) -- other protocols which are defined here. "
	::= { snVLanByProtocolEntry 2 }

snVLanByProtocolDynamic OBJECT-TYPE
	SYNTAX  INTEGER {
		disabled(0),
		enabled(1)
		}
	MAX-ACCESS  read-write
	STATUS  current
	DESCRIPTION
		" disabled(0) : disabled dynamic port inclusion - applied to switch only.
		  enabled(1) : enabled dynamic port inclusion - applied to switch only. "
	::= { snVLanByProtocolEntry 3 }

snVLanByProtocolStaticMask OBJECT-TYPE
	SYNTAX  PortMask
	MAX-ACCESS  read-write
	STATUS  deprecated
	DESCRIPTION
		"The Standand-alone switch Protocol VLAN port membership applied in static mode.
		(It was obsoleted for Chassis Product)"
	::= { snVLanByProtocolEntry 4 }

snVLanByProtocolExcludeMask OBJECT-TYPE
	SYNTAX  PortMask
	MAX-ACCESS  read-write
	STATUS  deprecated
	DESCRIPTION
		"The Standand-alone switch Protocol VLAN port membership applied in exclusive mode.
		(It was obsoleted for Chassis Product)"
	::= { snVLanByProtocolEntry 5 }

snVLanByProtocolRouterIntf OBJECT-TYPE
	SYNTAX  INTEGER (1..60)
	MAX-ACCESS  read-write
	STATUS  current
	DESCRIPTION
		"Optional: A virtual interface for router to the VLAN -- applied to router only.
		 If a SNMP-Get value is zero, that means this object was not configured."
	::= { snVLanByProtocolEntry 6 }

snVLanByProtocolRowStatus OBJECT-TYPE
	SYNTAX  INTEGER {
		other(1),
		valid(2),
		delete(3),
		create(4),
		modify(5)
		}
	MAX-ACCESS  read-write
	STATUS  current
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByProtocolEntry 7 }

snVLanByProtocolDynamicMask OBJECT-TYPE
	SYNTAX  PortMask
	MAX-ACCESS  read-only
	STATUS  deprecated
	DESCRIPTION
		"The Standand-alone switch Protocol VLAN active port membership.
		(It was obsoleted for Chassis Product)"
	::= { snVLanByProtocolEntry 8 }

snVLanByProtocolChassisStaticMask OBJECT-TYPE
	SYNTAX  OCTET STRING (SIZE(32))
	MAX-ACCESS  read-write
	STATUS  deprecated
	DESCRIPTION
		"The Chassis Protocol VLAN port membership applied in static mode.
		(It was obsoleted after release 07100, replaced by snVLanByProtocolStaticPortList)"
	::= { snVLanByProtocolEntry 9 }

snVLanByProtocolChassisExcludeMask OBJECT-TYPE
	SYNTAX  OCTET STRING (SIZE(32))
	MAX-ACCESS  read-write
	STATUS  deprecated
	DESCRIPTION
		"The Chassis Protocol VLAN port membership applied in exclusive mode.
		(It was obsoleted after release 07100, replaced by snVLanByProtocolExcludePortList)"
	::= { snVLanByProtocolEntry 10 }

snVLanByProtocolChassisDynamicMask OBJECT-TYPE
	SYNTAX  OCTET STRING (SIZE(32))
	MAX-ACCESS  read-only
	STATUS  deprecated
	DESCRIPTION
		"The Chassis Protocol VLAN active port membership.
		(It was obsoleted after release 07100, replaced by snVLanByProtocolDynamicPortList)"
	::= { snVLanByProtocolEntry 11 }

snVLanByProtocolVLanName OBJECT-TYPE
	SYNTAX	DisplayString (SIZE(0..32))
	MAX-ACCESS	read-write
	STATUS	current
	DESCRIPTION
		"VLAN Community Name string."
	::= { snVLanByProtocolEntry 12 }

snVLanByProtocolStaticPortList OBJECT-TYPE
	SYNTAX  OCTET STRING
	MAX-ACCESS  read-write
	STATUS  current
	DESCRIPTION
		"A list of port indices which are the configured port
		membership of the Protocol VLAN. Each port index is a
		16-bit integer in big endian order. 8-bit is the slot number,
		the other 8-bit is the port number."
	::= { snVLanByProtocolEntry 13 }

snVLanByProtocolExcludePortList OBJECT-TYPE
	SYNTAX  OCTET STRING
	MAX-ACCESS  read-write
	STATUS  current
	DESCRIPTION
		"A list of port indices which are the excluded from port
		membership of the Protocol VLAN. Each port index is a
		16-bit integer in big endian order. 8-bit is the slot number,
		the other 8-bit is the port number."
	::= { snVLanByProtocolEntry 14 }

snVLanByProtocolDynamicPortList OBJECT-TYPE
	SYNTAX  OCTET STRING
	MAX-ACCESS  read-only
	STATUS  current
	DESCRIPTION
		"A list of port indices which are dynamically joining the port
		membership of the Protocol VLAN. Each port index is a
		16-bit integer in big endian order. 8-bit is the slot number,
		the other 8-bit is the port number."
	::= { snVLanByProtocolEntry 15 }


-- VLAN By IP Subnet Configuration Table


snVLanByIpSubnetTable OBJECT-TYPE
	SYNTAX  SEQUENCE OF SnVLanByIpSubnetEntry
	MAX-ACCESS  not-accessible
	STATUS  current
	DESCRIPTION
		"An entry of the VLAN By IPX Network Number Table."
	::= { snVLanInfo 3 }


snVLanByIpSubnetEntry OBJECT-TYPE
	SYNTAX  SnVLanByIpSubnetEntry
	MAX-ACCESS  not-accessible
	STATUS  current
	DESCRIPTION
		"An entry in the VLAN By IP Subnet Configuration table. "
	INDEX   { 
		snVLanByIpSubnetVLanId,
		snVLanByIpSubnetIpAddress,
		snVLanByIpSubnetSubnetMask
	}
	::= { snVLanByIpSubnetTable 1 }


SnVLanByIpSubnetEntry ::= SEQUENCE {
	snVLanByIpSubnetVLanId
		INTEGER,
	snVLanByIpSubnetIpAddress
		IpAddress,
	snVLanByIpSubnetSubnetMask
		IpAddress,
	snVLanByIpSubnetDynamic
		INTEGER,
	snVLanByIpSubnetStaticMask
		PortMask,
	snVLanByIpSubnetExcludeMask
		PortMask,
	snVLanByIpSubnetRouterIntf
		INTEGER,
	snVLanByIpSubnetRowStatus
		INTEGER,
	snVLanByIpSubnetDynamicMask
		PortMask,
	snVLanByIpSubnetChassisStaticMask
		OCTET STRING,
	snVLanByIpSubnetChassisExcludeMask
		OCTET STRING,
	snVLanByIpSubnetChassisDynamicMask
		OCTET STRING,
	snVLanByIpSubnetVLanName
		DisplayString,
	snVLanByIpSubnetStaticPortList
		OCTET STRING,
	snVLanByIpSubnetExcludePortList
		OCTET STRING,
	snVLanByIpSubnetDynamicPortList
		OCTET STRING
	}

snVLanByIpSubnetVLanId OBJECT-TYPE
	SYNTAX  INTEGER (1..4095)
	MAX-ACCESS  read-only
	STATUS  current
	DESCRIPTION
		"The VLAN ID index to both of the VLAN By Port Info Table
		 and this table."
	::= { snVLanByIpSubnetEntry 1 }


snVLanByIpSubnetIpAddress OBJECT-TYPE
	SYNTAX  IpAddress
	MAX-ACCESS  read-only
	STATUS  current
	DESCRIPTION
		"Subnet IP address."
	::= { snVLanByIpSubnetEntry 2 }

snVLanByIpSubnetSubnetMask OBJECT-TYPE
	SYNTAX  IpAddress
	MAX-ACCESS  read-only
	STATUS  current
	DESCRIPTION
		"Subnet mask associated with the Subnet IP address."
	::= { snVLanByIpSubnetEntry 3 }

snVLanByIpSubnetDynamic OBJECT-TYPE
	SYNTAX  INTEGER {
		disabled(0),
		enabled(1)
		}
	MAX-ACCESS  read-write
	STATUS  current
	DESCRIPTION
		" disabled(0) : disabled dynamic port inclusion - applied to switch only.
		  enabled(1) : enabled dynamic port inclusion - applied to switch only. "
	::= { snVLanByIpSubnetEntry 4 }

snVLanByIpSubnetStaticMask OBJECT-TYPE
	SYNTAX  PortMask
	MAX-ACCESS  read-write
	STATUS  deprecated
	DESCRIPTION
		"The Standand-alone switch VLAN By Subnet port membership applied in static mode.
		(It was obsoleted for Chassis Product)"
	::= { snVLanByIpSubnetEntry 5 }

snVLanByIpSubnetExcludeMask OBJECT-TYPE
	SYNTAX  PortMask
	MAX-ACCESS  read-write
	STATUS  deprecated
	DESCRIPTION
		"The Standand-alone switch VLAN By Subnet port membership applied in exclusive mode.
		(It was obsoleted for Chassis Product)"
	::= { snVLanByIpSubnetEntry 6 }

snVLanByIpSubnetRouterIntf OBJECT-TYPE
	SYNTAX  INTEGER (1..60)
	MAX-ACCESS  read-write
	STATUS  current
	DESCRIPTION
		"Optional: A virtual interface for router to the VLAN -- applied to router only.
		 If a SNMP-Get value is zero, that means this object was not configured."
	::= { snVLanByIpSubnetEntry 7 }


snVLanByIpSubnetRowStatus OBJECT-TYPE
	SYNTAX  INTEGER {
		other(1),
		valid(2),
		delete(3),
		create(4),
		modify(5)
		}
	MAX-ACCESS  read-write
	STATUS  current
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByIpSubnetEntry 8 }

snVLanByIpSubnetDynamicMask OBJECT-TYPE
	SYNTAX  PortMask
	MAX-ACCESS  read-only
	STATUS  deprecated
	DESCRIPTION
		"The Standand-alone switch VLAN By Subnet active port membership.
		(It was obsoleted for Chassis Product)"
	::= { snVLanByIpSubnetEntry 9 }

snVLanByIpSubnetChassisStaticMask OBJECT-TYPE
	SYNTAX  OCTET STRING (SIZE(32))
	MAX-ACCESS  read-write
	STATUS  deprecated
	DESCRIPTION
		"The Chassis VLAN By Subnet port membership applied in static mode.
		(It was obsoleted after release 07100, replaced by snVLanByIpSubnetStaticPortList)"
	::= { snVLanByIpSubnetEntry 10 }

snVLanByIpSubnetChassisExcludeMask OBJECT-TYPE
	SYNTAX  OCTET STRING (SIZE(32))
	MAX-ACCESS  read-write
	STATUS  deprecated
	DESCRIPTION
		"The Chassis VLAN By Subnet port membership applied in exclusive mode.
		(It was obsoleted after release 07100, replaced by snVLanByIpSubnetExcludePortList)"
	::= { snVLanByIpSubnetEntry 11 }

snVLanByIpSubnetChassisDynamicMask OBJECT-TYPE
	SYNTAX  OCTET STRING (SIZE(32))
	MAX-ACCESS  read-only
	STATUS  deprecated
	DESCRIPTION
		"The Chassis VLAN By Subnet active port membership.
		(It was obsoleted after release 07100, replaced by snVLanByIpSubnetDynamicPortList)"
	::= { snVLanByIpSubnetEntry 12 }

snVLanByIpSubnetVLanName OBJECT-TYPE
	SYNTAX	DisplayString (SIZE(0..32))
	MAX-ACCESS	read-write
	STATUS	current
	DESCRIPTION
		"VLAN Community Name string."
	::= { snVLanByIpSubnetEntry 13 }

snVLanByIpSubnetStaticPortList OBJECT-TYPE
	SYNTAX  OCTET STRING
	MAX-ACCESS  read-write
	STATUS  current
	DESCRIPTION
		"A list of port indices which are the configured port
		membership of the VLAN By IP Subnet. Each port index is a
		16-bit integer in big endian order. 8-bit is the slot number,
		the other 8-bit is the port number."
	::= { snVLanByIpSubnetEntry 14 }

snVLanByIpSubnetExcludePortList OBJECT-TYPE
	SYNTAX  OCTET STRING
	MAX-ACCESS  read-write
	STATUS  current
	DESCRIPTION
		"A list of port indices which are the excluded from port
		membership of the VLAN By IP Subnet. Each port index is a
		16-bit integer in big endian order. 8-bit is the slot number,
		the other 8-bit is the port number."
	::= { snVLanByIpSubnetEntry 15 }

snVLanByIpSubnetDynamicPortList OBJECT-TYPE
	SYNTAX  OCTET STRING
	MAX-ACCESS  read-only
	STATUS  current
	DESCRIPTION
		"A list of port indices which are dynamically joining the port
		membership of the VLAN By IP Subnet. Each port index is a
		16-bit integer in big endian order. 8-bit is the slot number,
		the other 8-bit is the port number."
	::= { snVLanByIpSubnetEntry 16 }


-- VLAN By IPX Net Configuration Table


snVLanByIpxNetTable OBJECT-TYPE
	SYNTAX  SEQUENCE OF SnVLanByIpxNetEntry
	MAX-ACCESS  not-accessible
	STATUS  current
	DESCRIPTION
		"An entry of the VLAN By IPX Network Number Table."
	::= { snVLanInfo 4 }


snVLanByIpxNetEntry OBJECT-TYPE
	SYNTAX  SnVLanByIpxNetEntry
	MAX-ACCESS  not-accessible
	STATUS  current
	DESCRIPTION
		"An entry in the VLAN By Ipx Network Number Configuration table. "
	INDEX   { 
		snVLanByIpxNetVLanId,
		snVLanByIpxNetNetworkNum,
		snVLanByIpxNetFrameType
	}
	::= { snVLanByIpxNetTable 1 }


SnVLanByIpxNetEntry ::= SEQUENCE {
	snVLanByIpxNetVLanId
		INTEGER,
	snVLanByIpxNetNetworkNum
		OCTET STRING,
	snVLanByIpxNetFrameType
		INTEGER,
	snVLanByIpxNetDynamic
		INTEGER,
	snVLanByIpxNetStaticMask
		PortMask,
	snVLanByIpxNetExcludeMask
		PortMask,
	snVLanByIpxNetRouterIntf
		INTEGER,
	snVLanByIpxNetRowStatus
		INTEGER,
	snVLanByIpxNetDynamicMask
		PortMask,
	snVLanByIpxNetChassisStaticMask
		OCTET STRING,
	snVLanByIpxNetChassisExcludeMask
		OCTET STRING,
	snVLanByIpxNetChassisDynamicMask
		OCTET STRING,
	snVLanByIpxNetVLanName
		DisplayString,
	snVLanByIpxNetStaticPortList
		OCTET STRING,
	snVLanByIpxNetExcludePortList
		OCTET STRING,
	snVLanByIpxNetDynamicPortList
		OCTET STRING
	}

snVLanByIpxNetVLanId OBJECT-TYPE
	SYNTAX  INTEGER (1..4095)
	MAX-ACCESS  read-only
	STATUS  current
	DESCRIPTION
		"The VLAN ID index to both of the VLAN By Port Info Table
		 and this table."
	::= { snVLanByIpxNetEntry 1 }


snVLanByIpxNetNetworkNum OBJECT-TYPE
	SYNTAX  OCTET STRING (SIZE(4))
	MAX-ACCESS  read-only
	STATUS  current
	DESCRIPTION
		"IPX Network Number."
	::= { snVLanByIpxNetEntry 2 }

snVLanByIpxNetFrameType OBJECT-TYPE
	SYNTAX  INTEGER {
		notApplicable(0),
		ipxEthernet8022(1),
		ipxEthernet8023(2),
		ipxEthernetII(3),
		ipxEthernetSnap(4)
		}
	MAX-ACCESS  read-only
	STATUS  current
	DESCRIPTION
		" The following IPX Frame types are operated 
		in Layer3 VLAN such as :  
		ipxEthernet8022(1), ipxEthernet8023(2),
		ipxEthernetII(3), ipxEthernetSnap(4).
		choose notApplicable(0) for other protocols.
		Note: Each Network Number can be assigned with one unique Frame type; Otherwise,
		a SNMP-SET error will be returned."
	::= { snVLanByIpxNetEntry 3 }

snVLanByIpxNetDynamic OBJECT-TYPE
	SYNTAX  INTEGER {
		disabled(0),
		enabled(1)
		}
	MAX-ACCESS  read-write
	STATUS  current
	DESCRIPTION
		" disabled(0) : disabled dynamic port inclusion - applied to switch only.
		  enabled(1) : enabled dynamic port inclusion - applied to switch only. "
	::= { snVLanByIpxNetEntry 4 }

snVLanByIpxNetStaticMask OBJECT-TYPE
	SYNTAX  PortMask
	MAX-ACCESS  read-write
	STATUS  deprecated
	DESCRIPTION
		"The VLAN By IPX network port membership applied in static mode.
		(It was obsoleted for Chassis Product)"
	::= { snVLanByIpxNetEntry 5 }

snVLanByIpxNetExcludeMask OBJECT-TYPE
	SYNTAX  PortMask
	MAX-ACCESS  read-write
	STATUS  deprecated
	DESCRIPTION
		"The VLAN By IPX network port membership applied in exclusive mode.
		(It was obsoleted for Chassis Product)"
	::= { snVLanByIpxNetEntry 6 }


snVLanByIpxNetRouterIntf OBJECT-TYPE
	SYNTAX  INTEGER (1..60)
	MAX-ACCESS  read-write
	STATUS  current
	DESCRIPTION
		"Optional: A virtual interface for router to the VLAN -- applied to router only.
		 If a SNMP-Get value is zero, that means this object was not configured."
	::= { snVLanByIpxNetEntry 7 }


snVLanByIpxNetRowStatus OBJECT-TYPE
	SYNTAX  INTEGER {
		other(1),
		valid(2),
		delete(3),
		create(4),
		modify(5)
		}
	MAX-ACCESS  read-write
	STATUS  current
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByIpxNetEntry 8 }

snVLanByIpxNetDynamicMask OBJECT-TYPE
	SYNTAX  PortMask
	MAX-ACCESS  read-only
	STATUS  deprecated
	DESCRIPTION
		"The VLAN By IPX network active port membership.
		(It was obsoleted for Chassis Product)"
	::= { snVLanByIpxNetEntry 9 }

snVLanByIpxNetChassisStaticMask OBJECT-TYPE
	SYNTAX  OCTET STRING (SIZE(32))
	MAX-ACCESS  read-write
	STATUS  deprecated
	DESCRIPTION
		"The Chassis VLAN By IPX network port membership applied in static mode.
		(It was obsoleted after release 07100, replaced by snVLanByIpxNetStaticPortList)"
	::= { snVLanByIpxNetEntry 10 }

snVLanByIpxNetChassisExcludeMask OBJECT-TYPE
	SYNTAX  OCTET STRING (SIZE(32))
	MAX-ACCESS  read-write
	STATUS  deprecated
	DESCRIPTION
		"The Chassis VLAN By IPX network port membership applied in exclusive mode.
		(It was obsoleted after release 07100, replaced by snVLanByIpxNetExcludePortList)"
	::= { snVLanByIpxNetEntry 11 }

snVLanByIpxNetChassisDynamicMask OBJECT-TYPE
	SYNTAX  OCTET STRING (SIZE(32))
	MAX-ACCESS  read-only
	STATUS  deprecated
	DESCRIPTION
		"The Chassis VLAN By IPX network active port membership.
		(It was obsoleted after release 07100, replaced by snVLanByIpxNetDynamicPortList)"
	::= { snVLanByIpxNetEntry 12 }

snVLanByIpxNetVLanName OBJECT-TYPE
	SYNTAX	DisplayString (SIZE(0..32))
	MAX-ACCESS	read-write
	STATUS	current
	DESCRIPTION
		"VLAN Community Name string."
	::= { snVLanByIpxNetEntry 13 }

snVLanByIpxNetStaticPortList OBJECT-TYPE
	SYNTAX  OCTET STRING
	MAX-ACCESS  read-write
	STATUS  current
	DESCRIPTION
		"A list of port indices which are the configured port
		membership of the VLAN By IPX network. Each port index is a
		16-bit integer in big endian order. 8-bit is the slot number,
		the other 8-bit is the port number."
	::= { snVLanByIpxNetEntry 14 }

snVLanByIpxNetExcludePortList OBJECT-TYPE
	SYNTAX  OCTET STRING
	MAX-ACCESS  read-write
	STATUS  current
	DESCRIPTION
		"A list of port indices which are the excluded from port
		membership of the VLAN By IPX network. Each port index is a
		16-bit integer in big endian order. 8-bit is the slot number,
		the other 8-bit is the port number."
	::= { snVLanByIpxNetEntry 15 }

snVLanByIpxNetDynamicPortList OBJECT-TYPE
	SYNTAX  OCTET STRING
	MAX-ACCESS  read-only
	STATUS  current
	DESCRIPTION
		"A list of port indices which are dynamically joining the port
		membership of the VLAN By IPX network. Each port index is a
		16-bit integer in big endian order. 8-bit is the slot number,
		the other 8-bit is the port number."
	::= { snVLanByIpxNetEntry 16 }


-- VLAN By AppleTalk Cable Configuration Table


snVLanByATCableTable OBJECT-TYPE
	SYNTAX  SEQUENCE OF SnVLanByATCableEntry
	MAX-ACCESS  not-accessible
	STATUS  current
	DESCRIPTION
		"A Table Of VLAN By AppleTalk Network Number."
	::= { snVLanInfo 5 }

snVLanByATCableEntry OBJECT-TYPE
	SYNTAX  SnVLanByATCableEntry
	MAX-ACCESS  not-accessible
	STATUS  current
	DESCRIPTION
		"An entry of the AppleTalk Cable VLAN table."
	INDEX   {snVLanByATCableVLanId, snVLanByATCableIndex}
	::= { snVLanByATCableTable 1 }

SnVLanByATCableEntry ::= SEQUENCE {
	snVLanByATCableVLanId
		INTEGER,
	snVLanByATCableIndex
		Integer32,
	snVLanByATCableRouterIntf
		INTEGER,
	snVLanByATCableRowStatus
		INTEGER,
	snVLanByATCableChassisStaticMask
		OCTET STRING,
	snVLanByATCableVLanName
		DisplayString,
	snVLanByATCableStaticPortList
		OCTET STRING
	}

snVLanByATCableVLanId OBJECT-TYPE
	SYNTAX  INTEGER (1..4095)
	MAX-ACCESS  read-only
	STATUS  current
	DESCRIPTION
		"The VLAN ID of a PORT VLAN of which the AppleTalk Cable
		VLAN was attaching to."
	::= { snVLanByATCableEntry 1 }

snVLanByATCableIndex OBJECT-TYPE
	SYNTAX  Integer32
	MAX-ACCESS  read-only
	STATUS  current
	DESCRIPTION
		"AppleTalk Cable VLAN index number."
	::= { snVLanByATCableEntry 2 }

snVLanByATCableRouterIntf OBJECT-TYPE
	SYNTAX  INTEGER (0..60)
	MAX-ACCESS  read-write
	STATUS  current
	DESCRIPTION
		"A virtual router interface to the AppleTalk Cable VLAN,
		only router products accept the SNMP-SET operation. The
		value zero indicates that virtual router interface was
		not configured."
	::= { snVLanByATCableEntry 3 }

snVLanByATCableRowStatus OBJECT-TYPE
	SYNTAX  INTEGER {
		other(1),
		valid(2),
		delete(3),
		create(4),
		modify(5)
		}
	MAX-ACCESS  read-write
	STATUS  current
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByATCableEntry 4 }

snVLanByATCableChassisStaticMask OBJECT-TYPE
	SYNTAX  OCTET STRING (SIZE(32))
	MAX-ACCESS  read-write
	STATUS  deprecated
	DESCRIPTION
		"A list of ports which are statically configured to
		become port members of a VLAN.
		(It was obsoleted after release 07100, replaced by snVLanByATCableStaticPortList)"
	::= { snVLanByATCableEntry 5 }

snVLanByATCableVLanName OBJECT-TYPE
	SYNTAX	DisplayString (SIZE(0..32))
	MAX-ACCESS	read-write
	STATUS	current
	DESCRIPTION
		"VLAN Name string."
	::= { snVLanByATCableEntry 6 }

snVLanByATCableStaticPortList OBJECT-TYPE
	SYNTAX  OCTET STRING
	MAX-ACCESS  read-write
	STATUS  current
	DESCRIPTION
		"A list of port indices which are the configured port
		membership of the AppleTalk Cable VLAN. Each port index is a
		16-bit integer in big endian order. 8-bit is the slot number,
		the other 8-bit is the port number."
	::= { snVLanByATCableEntry 7 }




-- Switch Port Information Group

-- begin of deprecated snSwPortInfoTable
snSwPortInfoTable OBJECT-TYPE
	SYNTAX  SEQUENCE OF SnSwPortInfoEntry
	MAX-ACCESS  not-accessible
	STATUS  deprecated
	DESCRIPTION
		"A specific snSwPortInfo group consists of a number of 
		 switch ports.  "
	::= { snSwPortInfo 1 }

snSwPortInfoEntry OBJECT-TYPE
	SYNTAX  SnSwPortInfoEntry
	MAX-ACCESS  not-accessible
	STATUS  deprecated
	DESCRIPTION
		"An entry in the snSwPortInfo table indicates the 
		 configuration on a specified port. A SNMP SET PDU 
		 for a row of the snSwPortInfoTable requires the entired 
		 sequence of the MIB Objects in each 
		 snSwPortInfoEntry stored in one PDU.  Otherwise, 
		 GENERR return-value will be returned."
	INDEX   { 
		snSwPortInfoPortNum
	}
	::= { snSwPortInfoTable 1 }

SnSwPortInfoEntry ::= SEQUENCE {
	snSwPortInfoPortNum
		Integer32,
	snSwPortInfoMonitorMode
		INTEGER,
	snSwPortInfoTagMode
		INTEGER,
	snSwPortInfoChnMode
		INTEGER,
	snSwPortInfoSpeed
		INTEGER,
	snSwPortInfoMediaType
		INTEGER,
	snSwPortInfoConnectorType
		INTEGER,
	snSwPortInfoAdminStatus
		INTEGER,
	snSwPortInfoLinkStatus
		INTEGER,
	snSwPortInfoPortQos
		INTEGER,
	snSwPortInfoPhysAddress
		PhysAddress,
	snSwPortStatsInFrames 
		Counter32,
	snSwPortStatsOutFrames 
		Counter32,
	snSwPortStatsAlignErrors            
		Counter32,
	snSwPortStatsFCSErrors                  
		Counter32,
	snSwPortStatsMultiColliFrames    
		Counter32,
	snSwPortStatsFrameTooLongs              
		Counter32,
	snSwPortStatsTxColliFrames
		Counter32,
	snSwPortStatsRxColliFrames
		Counter32,
	snSwPortStatsFrameTooShorts
		Counter32,
	snSwPortLockAddressCount
		INTEGER,
	snSwPortStpPortEnable
		INTEGER,
	snSwPortDhcpGateListId
		INTEGER,
	snSwPortName
		DisplayString,
	snSwPortStatsInBcastFrames
		Counter32,
	snSwPortStatsOutBcastFrames
		Counter32,
	snSwPortStatsInMcastFrames
		Counter32,
	snSwPortStatsOutMcastFrames
		Counter32,
	snSwPortStatsInDiscard
		Counter32,
	snSwPortStatsOutDiscard
		Counter32,
	snSwPortStatsMacStations
		Integer32,
	snSwPortCacheGroupId
		Integer32,
	snSwPortTransGroupId
		Integer32,
	snSwPortInfoAutoNegotiate
		INTEGER,
	snSwPortInfoFlowControl
		INTEGER,
	snSwPortInfoGigType
		INTEGER,
	snSwPortStatsLinkChange
		Counter32,
	snSwPortIfIndex
		Integer32,
	snSwPortDescr
		DisplayString,
	snSwPortInOctets
		OCTET STRING,
	snSwPortOutOctets
		OCTET STRING,
	snSwPortStatsInBitsPerSec
		Gauge32,
	snSwPortStatsOutBitsPerSec
		Gauge32,
	snSwPortStatsInPktsPerSec
		Gauge32,
	snSwPortStatsOutPktsPerSec
		Gauge32,
	snSwPortStatsInUtilization
		INTEGER ,
	snSwPortStatsOutUtilization
		INTEGER ,
	snSwPortFastSpanPortEnable
		INTEGER,
	snSwPortFastSpanUplinkEnable
		INTEGER,
	snSwPortVlanId
		INTEGER,
	snSwPortRouteOnly
		INTEGER,
	snSwPortPresent
		INTEGER,
	snSwPortGBICStatus
		INTEGER,
	snSwPortStatsInKiloBitsPerSec
		Unsigned32,
	snSwPortStatsOutKiloBitsPerSec    
		Unsigned32,
	snSwPortLoadInterval
		INTEGER,
	snSwPortTagType
		Integer32 ,
	snSwPortInLinePowerControl
		INTEGER,
	snSwPortInLinePowerWattage
		Integer32 ,
	snSwPortInLinePowerClass
		INTEGER,
	snSwPortInLinePowerPriority
		INTEGER,
	snSwPortInfoMirrorMode
		INTEGER,
	snSwPortStatsInJumboFrames
		Counter64,
	snSwPortStatsOutJumboFrames
		Counter64,
	snSwPortInLinePowerConsumed
		Integer32,
	snSwPortInLinePowerPDType
		DisplayString
	}

snSwPortInfoPortNum OBJECT-TYPE
	SYNTAX  Integer32
	MAX-ACCESS  read-only
	STATUS  deprecated
	DESCRIPTION
		"The port index.
		 The bit 0 to bit 7: port number. 
		 The bit 8 to bit 11: slot number (slot for chassis only)."
	::= { snSwPortInfoEntry 1 }


snSwPortInfoMonitorMode OBJECT-TYPE
	SYNTAX  INTEGER {
		disabled(0),
		input(1),
		output(2),
		both(3)
		}
	MAX-ACCESS  read-write
	STATUS  deprecated
	DESCRIPTION
		"DEPRECATED by snSwPortInfoMirrorMode and
		snPortMonitorTable."
	::= { snSwPortInfoEntry 2 }


snSwPortInfoTagMode OBJECT-TYPE
	SYNTAX  INTEGER {
		tagged(1),      
		untagged(2),    
		auto(3),
		disabled(4)
		}
	MAX-ACCESS  read-write
	STATUS  deprecated
	DESCRIPTION
		"For tagged port, we could have multiple VLANs 
		 per port. For untagged port or auto port, there 
		 is only one VLAN ID per port."  
	::= { snSwPortInfoEntry 3 }


snSwPortInfoChnMode OBJECT-TYPE
	SYNTAX  INTEGER {
		none(0),
		halfDuplex(1),  
		fullDuplex(2)   
		}
	MAX-ACCESS  read-write
	STATUS  deprecated
	DESCRIPTION
		"The port can be configured to operate in either
		half or full duplex mode. The values are:
			halfDuplex(1)...half duplex mode
			fullDuplex(2)...full duplex mode
		The read-back channel status from hardware are:
			none(0).........link down or port disabled.
			halfDuplex(1)...half duplex mode
			fullDuplex(2)...full duplex mode
		
		The port media type (expansion or regular)
		and port link type (trunk or feeder) determine
		value of this object.
		The port can not set to half duplex mode
		if the port connect mode is m200e(4).
		However, the value of this parameter may be
		automatically set whenever the expansion port
		is connected (e.g. cascade connecting device)."
	::= { snSwPortInfoEntry 4 }


snSwPortInfoSpeed OBJECT-TYPE
	SYNTAX  INTEGER {
		none(0),
		sAutoSense(1),
		s10M(2),
		s100M(3),
		s1G(4),
		s1GM(5),
		s155M(6),
		s10G(7),
		s622M(8),
		s2488M(9),
		s9953M(10),
		s16G(11),
		s40G(13),
		s2500M(14)
		}
	MAX-ACCESS  read-write
	STATUS  deprecated
	DESCRIPTION     
		"The speed configuration for a port. The values are:
		  none(0)..........link down or no traffic.
		  sAutoSense(1)....Auto-sensing 10 or 100Mbits.
		  s10M(2)..........10Mbits per second.
		  s100M(3).........100Mbits per second.
		  s1G(4)...........1Gbits per second.
		  s1GM(5)..........1Gbits per second master.
		  s155M(6).........155Mbits per second (ATM) (for expansion board only).
		  s10G(7)..........10Gbits per second.
		  s622M(8).........OC12 - 622Mbits per second
		  s2488M(9)........OC48 - 2.488Gbits per second
		  s9953M(10).......OC192 - 9.953Gbits per second
		  s16G(11)..........16Gbits per second.
		  s40G(13)..........40Gbits per second.
		  s2500M(14)..........2.5Gbits per second.

		 The read-back hardware status are the following:
		  none(0)..........link down or no traffic.
		  s10M(2)..........10Mbits per second.
		  s100M(3).........100Mbits per second.
		  s1G(4)...........1Gbits per second.
		  s1GM(5)..........1Gbits per second master.
		  s155M(6).........155Mbits per second (ATM) (for expansion board only).
		  s10G(7)..........10Gbits per second.
		  s622M(8).........OC12 - 622Mbits per second
		  s2488M(9)........OC48 - 2.488Gbits per second
		  s9953M(10).......OC192 - 9.953Gbits per second
		  s16G(11)..........16Gbits per second.
		  s40G(13)..........40Gbits per second.
		  s2500M(14)..........2.5Gbits per second.

		The port media type (expansion or regular)
		and port link type (trunk or feeder) determine
		whether this object can be written and the valid
		values.
		It is not allowed to change speed for trunks ports.
		For expansion ports, all of the above speed 
		can be set.
		However, the value of this parameter may be
		automatically set whenever the expansion port
		is connected (e.g. cascade connecting device)."
	::= { snSwPortInfoEntry 5 }



snSwPortInfoMediaType OBJECT-TYPE
	SYNTAX  INTEGER {
			other(1),
		m100BaseTX(2),
		m100BaseFX(3),
		m1000BaseFX(4),
		mT3(5),
		m155ATM(6),
		m1000BaseTX(7),
		m622ATM(8),
		m155POS(9),
		m622POS(10),
		m2488POS(11),
		m10000BaseFX(12),
		m9953POS(13),
		m16GStacking(14),
		m40GStacking(16),
		m2500BaseTX(19)
		}
	MAX-ACCESS  read-only
	STATUS  deprecated
	DESCRIPTION 
		"The media type for the port. The
		values are:
		  other(1).........other or unknown media.
		  m100BaseTX(2)....100Mbits per second copper.
		  m100BaseFX(3)....100Mbits per second fiber.
		  m1000BaseFX(4)...1Gbits per second fiber.
		  mT3(5)...........45Mbits per second (T3).
		  m155ATM(6).......155Mbits per second (ATM).
		  m1000BaseTX(7)...1Gbits per second copper.
		  m622ATM(8).......622Mbits per second (ATM).
		  m155POS(9).......155Mbits per second (POS).
		  m622POS(10)......622Mbits per second (POS).
		  m2488POS(11).....2488Mbits per second (POS).
		  m10000BaseFX(12).10Gbits per second fiber.
		  m9953POS(13).....9953Mbits per second (POS).
		  m16GStacking(14).16Gbits per second fiber.
		  m40GStacking(16). 40Gbits per second fiber.
		  m2500BaseTX(19) 2.5Gbits per second fiber."
	::= { snSwPortInfoEntry 6 }



snSwPortInfoConnectorType OBJECT-TYPE
	SYNTAX  INTEGER {
		other(1),
		copper(2),
		fiber(3)
		}
	MAX-ACCESS  read-only
	STATUS  deprecated
	DESCRIPTION 
		"The type of connector that the port offers.
		 The values are:
		  other(1)...........other or unknown connector
		  copper(2)..........Copper connector
		  fiber(3)...........Fiber connector
		 This describes the physical connector type"
	::= { snSwPortInfoEntry 7 }


snSwPortInfoAdminStatus OBJECT-TYPE
	SYNTAX  INTEGER {
		up(1),       -- ready to pass packets
		down(2),
		testing(3)   -- in some test mode
		}
	MAX-ACCESS  read-write
	STATUS  deprecated
	DESCRIPTION
		"The desired state of all ports.  The
		testing(3) state indicates that no operational
		packets can be passed. 
		(same as ifAdminStatus in MIB-II)"
	::= { snSwPortInfoEntry 8 }


snSwPortInfoLinkStatus OBJECT-TYPE
	SYNTAX  INTEGER {
		up(1),       -- ready to pass packets
		down(2),
		testing(3)   -- in some test mode
		}
	MAX-ACCESS  read-only
	STATUS  deprecated
	DESCRIPTION
		"The current operational state of the interface.
		 The testing(3) state indicates that no operational
		 packets can be passed. 
		 (same as ifOperStatus in MIB-II)"
	::= { snSwPortInfoEntry 9 }


snSwPortInfoPortQos OBJECT-TYPE
	SYNTAX  INTEGER {
		level0(0),
		level1(1),
		level2(2),
		level3(3),
		level4(4),
		level5(5),
		level6(6),
		level7(7)
		}
	MAX-ACCESS  read-write
	STATUS  deprecated
	DESCRIPTION
		"The Stand alone stackable switch Port Qos Priority values are:
		 low(0)   -- low prority
		 high(1) -- high prority.
		 The BigIron Port Qos Priority values are:
		level0(0), level1(1), level2(2), level3(3),
		level4(4), level5(5), level6(6), level7(7) "
	::= { snSwPortInfoEntry 10 }


snSwPortInfoPhysAddress OBJECT-TYPE
	SYNTAX  PhysAddress
	MAX-ACCESS  read-only
	STATUS  deprecated
	DESCRIPTION
		"The port physical address. The physical address 
		represents the switch port."
	::= { snSwPortInfoEntry 11 }



snSwPortStatsInFrames OBJECT-TYPE
	SYNTAX  Counter32
	MAX-ACCESS  read-only
	STATUS  deprecated
	DESCRIPTION
		"The total number of packets received on the interface."
	::= { snSwPortInfoEntry 12 }


snSwPortStatsOutFrames OBJECT-TYPE
	SYNTAX  Counter32
	MAX-ACCESS  read-only
	STATUS  deprecated
	DESCRIPTION
		"The total number of packets transmitted out of the interface."
	::= { snSwPortInfoEntry 13 }


snSwPortStatsAlignErrors   OBJECT-TYPE
	 SYNTAX     Counter32
	 MAX-ACCESS     read-only
	 STATUS     deprecated
	 DESCRIPTION
		"dot3StatsAlignmentErrors : A count of frames 
		received on a particular interface that are 
		not an integral number of octets in length 
		and do not pass the FCS check.

		The count represented by an instance of this
		object is incremented when the alignmentError
		status is returned by the MAC service to the
		LLC (or other MAC user). Received frames for
		which multiple error conditions obtain are,
		according to the conventions of IEEE 802.3
		Layer Management, counted exclusively according
		to the error status presented to the LLC."
	::= { snSwPortInfoEntry 14 }

snSwPortStatsFCSErrors   OBJECT-TYPE
	 SYNTAX      Counter32
	 MAX-ACCESS      read-only
	 STATUS      deprecated
	 DESCRIPTION
		"dot3StatsFCSErrors : A count of frames received 
		on a particular interface that are an integral 
		number of octets in length but do not pass the 
		FCS check.

		The count represented by an instance of this
		object is incremented when the frameCheckError
		status is returned by the MAC service to the
		LLC (or other MAC user). Received frames for
		which multiple error conditions obtain are,
		according to the conventions of IEEE 802.3
		Layer Management, counted exclusively according
		to the error status presented to the LLC."
	::= { snSwPortInfoEntry 15 }


snSwPortStatsMultiColliFrames   OBJECT-TYPE
	 SYNTAX      Counter32
	 MAX-ACCESS      read-only
	 STATUS      deprecated
	 DESCRIPTION
		"dot3StatsMultipleCollisionFrames : 
		A count of successfully transmitted frames on
		a particular interface for which transmission
		is inhibited by more than one collision.

		A frame that is counted by an instance of this
		object is also counted by the corresponding
		instance of either the ifOutUcastPkts,
		ifOutMulticastPkts, or ifOutBroadcastPkts,
		and is not counted by the corresponding
		instance of the dot3StatsSingleCollisionFrames
		object."
	::= { snSwPortInfoEntry 16 }


snSwPortStatsFrameTooLongs   OBJECT-TYPE
	 SYNTAX    Counter32
	 MAX-ACCESS    read-only
	 STATUS    deprecated
	 DESCRIPTION
		"dot3StatsFrameTooLongs : A count of frames 
		received on a particular interface that 
		exceed the maximum permitted frame size.

		The count represented by an instance of this
		object is incremented when the frameTooLong
		status is returned by the MAC service to the
		LLC (or other MAC user). Received frames for
		which multiple error conditions obtain are,
		according to the conventions of IEEE 802.3
		Layer Management, counted exclusively according
		to the error status presented to the LLC."
	::= { snSwPortInfoEntry 17 }


snSwPortStatsTxColliFrames   OBJECT-TYPE
	 SYNTAX      Counter32
	 MAX-ACCESS      read-only
	 STATUS      deprecated
	 DESCRIPTION
		"A count of successfully transmitted frames on
		a particular interface for which transmission
		is inhibited by more than one collision.

		A frame that is counted by a combination of
		both dot3StatsSingleCollisionFrames and
		dot3StatsMultipleCollisionFrames objects."
	::= { snSwPortInfoEntry 18 }

snSwPortStatsRxColliFrames   OBJECT-TYPE
	 SYNTAX      Counter32
	 MAX-ACCESS      read-only
	 STATUS      deprecated
	 DESCRIPTION
		"A count of successfully received frames on
		a particular interface for which transmission
		is inhibited by more than one collision.  This
		object is not specified in dot3 but it has the
		same functionarity as snSwPortStatsTxColliFrames."
	::= { snSwPortInfoEntry 19 }

snSwPortStatsFrameTooShorts   OBJECT-TYPE
	 SYNTAX    Counter32
	 MAX-ACCESS    read-only
	 STATUS    deprecated
	 DESCRIPTION
		" A count of frames received on a particular 
		interface that below the minimum permitted 
		frame size."
	::= { snSwPortInfoEntry 20 }

snSwPortLockAddressCount OBJECT-TYPE
	 SYNTAX  INTEGER (0..2048)
	 MAX-ACCESS  read-write
	 STATUS  deprecated
	 DESCRIPTION
		"The number of source MAC addresses are allowed
		for a port. Writing 0 to this object will allow
		any number of addresses."
	DEFVAL { 8 }
	::= { snSwPortInfoEntry 21 }

snSwPortStpPortEnable OBJECT-TYPE
	 SYNTAX  INTEGER {
			   disabled(0),
			   enabled(1)
			 }
	 MAX-ACCESS  read-write
	 STATUS  deprecated
	 DESCRIPTION
		"The enabled/disabled status of the port."
	 REFERENCE
		"IEEE 802.1D-1990: Section 4.5.5.2, dot1dStpPortEnable"
	 ::= { snSwPortInfoEntry 22 }

snSwPortDhcpGateListId OBJECT-TYPE
	SYNTAX  INTEGER (0..32)
	MAX-ACCESS  read-write
	STATUS  deprecated
	DESCRIPTION
		"The ID for a DHCP gateway list entry relative 
		 to this switch port. 0 = unset or no assigned ID"
	::= { snSwPortInfoEntry 23 }

snSwPortName OBJECT-TYPE
	SYNTAX	DisplayString (SIZE(0..255))
	MAX-ACCESS	read-write
	STATUS	deprecated
	DESCRIPTION
		"Port Name string."
	::= { snSwPortInfoEntry 24 }

snSwPortStatsInBcastFrames OBJECT-TYPE
	SYNTAX  Counter32
	MAX-ACCESS  read-only
	STATUS  deprecated
	DESCRIPTION
		"The total number of broadcast packets received on the interface."
	::= { snSwPortInfoEntry 25 }


snSwPortStatsOutBcastFrames OBJECT-TYPE
	SYNTAX  Counter32
	MAX-ACCESS  read-only
	STATUS  deprecated
	DESCRIPTION
		"The total number of broadcast packets transmitted out of the interface."
	::= { snSwPortInfoEntry 26 }

snSwPortStatsInMcastFrames OBJECT-TYPE
	SYNTAX  Counter32
	MAX-ACCESS  read-only
	STATUS  deprecated
	DESCRIPTION
		"The total number of multicast packets received on the interface."
	::= { snSwPortInfoEntry 27 }


snSwPortStatsOutMcastFrames OBJECT-TYPE
	SYNTAX  Counter32
	MAX-ACCESS  read-only
	STATUS  deprecated
	DESCRIPTION
		"The total number of multicast packets transmitted out of the interface."
	::= { snSwPortInfoEntry 28 }


snSwPortStatsInDiscard OBJECT-TYPE
	SYNTAX  Counter32
	MAX-ACCESS  read-only
	STATUS  deprecated
	DESCRIPTION
		"The number of inbound packets which were chosen
		 to be discarded even though no errors had been
		 detected to prevent their being deliverable to a
		 higher-layer protocol.  One possible reason for
		 discarding such a packet could be to free up
		 buffer space."
	::= { snSwPortInfoEntry 29 }


snSwPortStatsOutDiscard OBJECT-TYPE
	SYNTAX  Counter32
	MAX-ACCESS  read-only
	STATUS  deprecated
	DESCRIPTION
		"The number of outbound packets which were chosen
		 to be discarded even though no errors had been
		 detected to prevent their being transmitted.  One
		 possible reason for discarding such a packet could
		 be to free up buffer space."
	::= { snSwPortInfoEntry 30 }

snSwPortStatsMacStations OBJECT-TYPE
	SYNTAX  Integer32
	MAX-ACCESS  read-only
	STATUS  deprecated
	DESCRIPTION
		"The total number of MAC Stations connected to the interface."
	::= { snSwPortInfoEntry 31 }


snSwPortCacheGroupId OBJECT-TYPE
	SYNTAX  Integer32
	MAX-ACCESS  read-write
	STATUS  deprecated
	DESCRIPTION
		"Cache Group ID for the interface."
	::= { snSwPortInfoEntry 32 }

snSwPortTransGroupId OBJECT-TYPE
	SYNTAX  Integer32
	MAX-ACCESS  read-write
	STATUS  deprecated
	DESCRIPTION
		"Transparent Group ID for the interface."
	::= { snSwPortInfoEntry 33 }

snSwPortInfoAutoNegotiate OBJECT-TYPE
	SYNTAX  INTEGER {
		disabled(0),
		enabled(1),
		negFullAuto(2),
		global(3),
		other(4)
		}
	MAX-ACCESS  read-write
	STATUS  deprecated
	DESCRIPTION
		"This feature only applies to Gigabit Ethernet ports. If set to
		disable(0), port will be put to non-negotiation mode. If set to
		enable(1), port will start auto-negotiation indefinitely until
		succeed. If set to negFullAuto(2), the port will start with auto-
		negotiation, if the negotiation failed, then it will automatically
		switch to non-negotiation mode. Stackable products (except TurboIron
		8) Gigabit Ethernet ports do not support negFullAuto(2). If set
		to global(3), port negotiation mode follows the value of
		snSwGlobalAutoNegotiate. Non-Gigabit Ethernet port returns
		the value other(4)."
	DEFVAL { global }
	::= { snSwPortInfoEntry 34 }


snSwPortInfoFlowControl OBJECT-TYPE
	SYNTAX  INTEGER {
		disabled(0),
		enabled(1)
		}
	MAX-ACCESS  read-write
	STATUS  deprecated
	DESCRIPTION
		"Enable/Disbale port flow control."
	DEFVAL { enabled }
	::= { snSwPortInfoEntry 35 }

snSwPortInfoGigType OBJECT-TYPE
	SYNTAX  INTEGER {
		m1000BaseSX(0),
		m1000BaseLX(1),
		m1000BaseLH(2),
		m1000BaseLHA(3),
		m1000BaseLHB(4),
		m1000BaseTX(5),
		m10000BaseSR(6),
		m10000BaseLR(7),
		m10000BaseER(8),
		sfpCWDM1470nm80Km(9),
		sfpCWDM1490nm80Km(10),
		sfpCWDM1510nm80Km(11),
		sfpCWDM1530nm80Km(12),
		sfpCWDM1550nm80Km(13),
		sfpCWDM1570nm80Km(14),
		sfpCWDM1590nm80Km(15),
		sfpCWDM1610nm80Km(16),
		sfpCWDM1470nm100Km(17),
		sfpCWDM1490nm100Km(18),
		sfpCWDM1510nm100Km(19),
		sfpCWDM1530nm100Km(20),
		sfpCWDM1550nm100Km(21),
		sfpCWDM1570nm100Km(22),
		sfpCWDM1590nm100Km(23),
		sfpCWDM1610nm100Km(24),
		m1000BaseLHX(25),
		m1000BaseSX2(26),
		m1000BaseGBXU(27),
		m1000BaseGBXD(28),
		m2500BaseTX(50),
		notApplicable(255)
		}
	MAX-ACCESS  read-only
	STATUS  deprecated
	DESCRIPTION 
		"The media type for the port. The
		values are:
		  m1000BaseSX(0)....1Gbits per second fiber, with a short wavelength transceiver.
		  m1000BaseLX(1)....1Gbits per second fiber, with a long wavelength transceiver (3km).
		  m1000BaseLH(2)....1Gbits per second fiber, with a special wavelength transceiver (50km).
		  m1000BaseLHA(3)....1Gbits per second fiber, with a special wavelength transceiver (70km).
		  m1000BaseLHB(4)....1Gbits per second fiber, with a special wavelength transceiver (150km).
		  m1000BaseTX(5)....1Gbits per second copper (100meter).
		  m10000BaseSR(6)....10Gbits per second fiber, with a short range wavelength transceiver (100m).
		  m10000BaseLR(7)....10Gbits per second fiber, with a long range wavelength transceiver (10km).
		  m10000BaseER(8)....10Gbits per second fiber, with a extended range wavelength transceiver (40km).
		  sfpCWDM1470nm80Km(9)....1Gbits per second CWDM fiber, with a wavelength 1470nm, reach 80 kms.
		  sfpCWDM1490nm80Km(10)....1Gbits per second CWDM fiber, with a wavelength 1490nm, reach 80 kms.
		  sfpCWDM1510nm80Km(11)....1Gbits per second CWDM fiber, with a wavelength 1510nm, reach 80 kms.
		  sfpCWDM1530nm80Km(12)....1Gbits per second CWDM fiber, with a wavelength 1530nm, reach 80 kms.
		  sfpCWDM1550nm80Km(13)....1Gbits per second CWDM fiber, with a wavelength 1550nm, reach 80 kms.
		  sfpCWDM1570nm80Km(14)....1Gbits per second CWDM fiber, with a wavelength 1570nm, reach 80 kms.
		  sfpCWDM1590nm80Km(15)....1Gbits per second CWDM fiber, with a wavelength 1590nm, reach 80 kms.
		  sfpCWDM1610nm80Km(16)....1Gbits per second CWDM fiber, with a wavelength 1610nm, reach 80 kms.
		  sfpCWDM1470nm100Km(17)....1Gbits per second CWDM fiber, with a wavelength 1470nm, reach 100 kms.
		  sfpCWDM1490nm100Km(18)....1Gbits per second CWDM fiber, with a wavelength 1490nm, reach 100 kms.
		  sfpCWDM1510nm100Km(19)....1Gbits per second CWDM fiber, with a wavelength 1510nm, reach 100 kms.
		  sfpCWDM1530nm100Km(20)....1Gbits per second CWDM fiber, with a wavelength 1530nm, reach 100 kms.
		  sfpCWDM1550nm100Km(21)....1Gbits per second CWDM fiber, with a wavelength 1550nm, reach 100 kms.
		  sfpCWDM1570nm100Km(22)....1Gbits per second CWDM fiber, with a wavelength 1570nm, reach 100 kms.
		  sfpCWDM1590nm100Km(23)....1Gbits per second CWDM fiber, with a wavelength 1590nm, reach 100 kms.
		  sfpCWDM1610nm100Km(24)....1Gbits per second CWDM fiber, with a wavelength 1610nm, reach 100 kms.
		  m1000BaseLHX(25)...1Gbits per second fiber, with a special wavelength transceiver (150km).
		  m2500BaseTX(50)...2.5GBASE fiber.
		  notApplicable(255)....a non-gigabit port."
	::= { snSwPortInfoEntry 36 }


snSwPortStatsLinkChange OBJECT-TYPE
	SYNTAX  Counter32
	MAX-ACCESS  read-only
	STATUS  deprecated
	DESCRIPTION
		"The total number of link state change of the interface."
	::= { snSwPortInfoEntry 37 }


snSwPortIfIndex OBJECT-TYPE
	SYNTAX  Integer32
	MAX-ACCESS  read-only
	STATUS  deprecated
	DESCRIPTION
		"In order to identify a particular interface, this
		object shall identify the instance of the ifIndex
		object, defined in RFC 1213 and RFC 1573."
	::= { snSwPortInfoEntry 38 }


snSwPortDescr OBJECT-TYPE
	SYNTAX  DisplayString
	MAX-ACCESS  read-only
	STATUS  deprecated
	DESCRIPTION
		"A textual string containing the slot/port information
		about the interface."
	::= { snSwPortInfoEntry 39 }


snSwPortInOctets OBJECT-TYPE
	SYNTAX  OCTET STRING (SIZE(8))
	MAX-ACCESS  read-only
	STATUS  deprecated
	DESCRIPTION
		"The total number of octets received on the interface,
		including framing characters. This object is a 64-bit
		counter of the ifInOctets object, defined in RFC 1213.
		The octet string is in big-endian byte order."
	::= { snSwPortInfoEntry 40 }


snSwPortOutOctets OBJECT-TYPE
	SYNTAX  OCTET STRING (SIZE(8))
	MAX-ACCESS  read-only
	STATUS  deprecated
	DESCRIPTION
		"The total number of octets transmitted out of the interface,
		including framing characters. This object is a 64-bit
		counter of the ifOutOctets object, defined in RFC 1213.
		The octet string is in big-endian byte order."
	::= { snSwPortInfoEntry 41 }


snSwPortStatsInBitsPerSec OBJECT-TYPE
	SYNTAX  Gauge32
	MAX-ACCESS  read-only
	STATUS  deprecated
	DESCRIPTION
		"The number of bits per second received on the interface
		over a 5 minutes interval."
	::= { snSwPortInfoEntry 42 }


snSwPortStatsOutBitsPerSec OBJECT-TYPE
	SYNTAX  Gauge32
	MAX-ACCESS  read-only
	STATUS  deprecated
	DESCRIPTION
		"The number of bits per second transmitted out of the interface
		over a 5 minutes interval."
	::= { snSwPortInfoEntry 43 }


snSwPortStatsInPktsPerSec OBJECT-TYPE
	SYNTAX  Gauge32
	MAX-ACCESS  read-only
	STATUS  deprecated
	DESCRIPTION
		"The number of packets per second received on the interface
		over a 5 minutes interval."
	::= { snSwPortInfoEntry 44 }


snSwPortStatsOutPktsPerSec OBJECT-TYPE
	SYNTAX  Gauge32
	MAX-ACCESS  read-only
	STATUS  deprecated
	DESCRIPTION
		"The number of packets per second transmitted out of the interface
		over a 5 minutes interval."
	::= { snSwPortInfoEntry 45 }


snSwPortStatsInUtilization OBJECT-TYPE
	SYNTAX  INTEGER (0..10000)
	MAX-ACCESS  read-only
	STATUS  deprecated
	DESCRIPTION
		"The input network utilization in hundredths of a percent
		over a 5 minutes interval."
	::= { snSwPortInfoEntry 46 }


snSwPortStatsOutUtilization OBJECT-TYPE
	SYNTAX  INTEGER (0..10000)
	MAX-ACCESS  read-only
	STATUS  deprecated
	DESCRIPTION
		"The output network utilization in hundredths of a percent
		over a 5 minutes interval."
	::= { snSwPortInfoEntry 47 }

snSwPortFastSpanPortEnable OBJECT-TYPE
	 SYNTAX  INTEGER {
			   disabled(0),
			   enabled(1)
			 }
	 MAX-ACCESS  read-write
	 STATUS  deprecated
	 DESCRIPTION
		"The enabled/disabled fast span port status of the port."
	 ::= { snSwPortInfoEntry 48 }

snSwPortFastSpanUplinkEnable OBJECT-TYPE
	 SYNTAX  INTEGER {
			   disabled(0),
			   enabled(1)
			 }
	 MAX-ACCESS  read-write
	 STATUS  deprecated
	 DESCRIPTION
		"The enabled/disabled fast span uplink status of the port."
	 ::= { snSwPortInfoEntry 49 }

snSwPortVlanId OBJECT-TYPE
	 SYNTAX  INTEGER (0..4095)
	 MAX-ACCESS  read-write
	 STATUS  deprecated
	 DESCRIPTION
		"The ID of a VLAN of which this port is a member. Port must
		be untagged. For tagged port which belongs to multiple
		VLANs, this object return 0 which is an invalid VLAN ID
		value."
	 ::= { snSwPortInfoEntry 50 }

snSwPortRouteOnly OBJECT-TYPE
	 SYNTAX  INTEGER { disabled(0), enabled(1) }
	 MAX-ACCESS  read-write
	 STATUS  deprecated
	 DESCRIPTION
		"Enable/Disable L2 switching of a routing switch port.
		By default, the routing switch performs routing first.
		If routing failed, it performs switching. Enable route
		only instrcuts the routing switch to perform routing
		only. For a L2 switching only product, reading this
		object always return 'disabled', writing 'enabled' to
		this object takes no effect."
	 DEFVAL { disabled }
	 ::= { snSwPortInfoEntry 51 }

snSwPortPresent OBJECT-TYPE
	 SYNTAX  INTEGER {
			   false(0),
			   true(1)
			 }
	 MAX-ACCESS  read-only
	 STATUS  deprecated
	 DESCRIPTION
		"Indicate if the port is absent or present.
		 This object only valid for M4 module
		 "
	 ::= { snSwPortInfoEntry 52 }

snSwPortGBICStatus OBJECT-TYPE
	 SYNTAX  INTEGER {
			   gbic(1),
			   miniGBIC(2),
			   empty(3),
			   other(4)
			 }
	 MAX-ACCESS  read-only
	 STATUS  deprecated
	 DESCRIPTION
		"Indicate if the gig port has GBICs on them.
		 If set to  GBIC(1), it means that the port is GBIC.
		 If set to  miniGBIC(2), it means that the port miniGBIC.
		 If set to empty(3), it means that the GBIC is missing.
		 Value other(4) means that the port not a removable gig port.
		 "
	 ::= { snSwPortInfoEntry 53 }

snSwPortStatsInKiloBitsPerSec OBJECT-TYPE
	SYNTAX  Unsigned32
	MAX-ACCESS  read-only
	STATUS  deprecated
	DESCRIPTION
		"Bit rate in kilobits per second received on the 10G and faster interface
		over a 5 minutes interval."
	::= { snSwPortInfoEntry 54 }


snSwPortStatsOutKiloBitsPerSec OBJECT-TYPE
	SYNTAX  Unsigned32
	MAX-ACCESS  read-only
	STATUS  deprecated
	DESCRIPTION
		"Bit rate in kilobits per second transmitted out of the 10G and faster interface
		over a 5 minutes interval."
	::= { snSwPortInfoEntry 55 }

snSwPortLoadInterval OBJECT-TYPE
	 SYNTAX  INTEGER (30..300)
	 MAX-ACCESS  read-write
	 STATUS  deprecated
	 DESCRIPTION
		"The time in seconds for which average port utilization should be carried out.
		The value should be incremental of 30 seconds, between the ranges specified."
	 DEFVAL { 300 }
	 ::= { snSwPortInfoEntry 56 }

snSwPortTagType OBJECT-TYPE
	 SYNTAX  Integer32
	 MAX-ACCESS  read-write
	 STATUS  deprecated
	 DESCRIPTION
		"The IEEE802.1q tag type embedded in the length/type field of
		an Ethernet packet. It specifies that the 2 octets after the
		length/type field in an Ethernet packet is the tag value."
	 DEFVAL { 33024 }
	 ::= { snSwPortInfoEntry 57 }

snSwPortInLinePowerControl OBJECT-TYPE
	 SYNTAX  INTEGER {
			   other(1),
			   disable(2),
			   enable(3),
			   enableLegacyDevice(4)
			 }
	 MAX-ACCESS  read-write
	 STATUS  deprecated
	 DESCRIPTION
		"Control inline power on/off to a port. If a port does not
		have inline power capability, reading this object returns
		'other(1)'."
	 ::= { snSwPortInfoEntry 58 }

snSwPortInLinePowerWattage OBJECT-TYPE
	 SYNTAX  Integer32
	 MAX-ACCESS  read-write
	 STATUS  deprecated
	 DESCRIPTION
		"Adjust the inline power wattage. Valid value between 
		1000 and 15400. Each unit is milliwatts.
		This object can only be set after snSwPortInLinePowerControl
		has been set to 'enable(3)' or 'enableLegacyDevice(4)'. If
		a port does not have inline power capability, reading this
		object returns undefined value."
	 ::= { snSwPortInfoEntry 59 }

snSwPortInLinePowerClass OBJECT-TYPE
	 SYNTAX  INTEGER (0..3)
	 MAX-ACCESS  read-write
	 STATUS  deprecated
	 DESCRIPTION
		"Adjust the inline power class. This object can only be set
		after snSwPortInLinePowerControl has been set to 'enable(3)'
		or 'enableLegacyDevice(4)'. If a port does not have inline
		power capability, reading this object returns undefined value."
	 ::= { snSwPortInfoEntry 60 }

snSwPortInLinePowerPriority OBJECT-TYPE
	 SYNTAX  INTEGER {
			   invalid(0),
			   critical(1),
			   high(2),
			   low(3),
			   medium(4),
			   other(5)
			 }
	 MAX-ACCESS  read-write
	 STATUS  deprecated
	 DESCRIPTION
		"Inline power allocation priority for the power device
		 0- Not a POE port, 1- Critical, 2- High, 3- Low,
		 4- Medium, 5- other."
	 ::= { snSwPortInfoEntry 61 }

snSwPortInfoMirrorMode OBJECT-TYPE
	 SYNTAX  INTEGER {
			   disable(0),
			   enable(1)
			 }
	 MAX-ACCESS  read-write
	 STATUS  deprecated
	 DESCRIPTION
			 "Enable/disable mirror on this port."
	 ::= { snSwPortInfoEntry 62 }

snSwPortStatsInJumboFrames OBJECT-TYPE
	SYNTAX  Counter64
	MAX-ACCESS  read-only
	STATUS  deprecated
	DESCRIPTION
		"The total number of jumbo packets received on the interface."
	::= { snSwPortInfoEntry 63 }

snSwPortStatsOutJumboFrames OBJECT-TYPE
	SYNTAX  Counter64
	MAX-ACCESS  read-only
	STATUS  deprecated
	DESCRIPTION
		"The total number of jumbo packets transmitted out of the interface."
	::= { snSwPortInfoEntry 64 }

snSwPortInLinePowerConsumed OBJECT-TYPE
	 SYNTAX  Integer32
	 MAX-ACCESS  read-only
	 STATUS  deprecated
	 DESCRIPTION
		"Inline power consumed by the port. Each unit is milliwatts."
	 ::= { snSwPortInfoEntry 66 }

snSwPortInLinePowerPDType OBJECT-TYPE
	 SYNTAX	DisplayString
	 MAX-ACCESS  read-only
	 STATUS  deprecated
	 DESCRIPTION
		"Inline Power device type	802.3af or Legacy device."
	 ::= { snSwPortInfoEntry 67 }
-- end of deprecated snSwPortInfoTable

-- Switch Port Information Group
-- snSwIfInfoTable which is indexed by ifIndex port format is replacing the
-- snSwPortInfoTable which is indexed by a proprietary port format.

snSwIfInfoTable OBJECT-TYPE
	SYNTAX  SEQUENCE OF SnSwIfInfoEntry
	MAX-ACCESS  not-accessible
	STATUS  current
	DESCRIPTION
		"A specific snSwIfInfo group consists of a number of 
		 switch ports.  "
	::= { snSwPortInfo 5 }

snSwIfInfoEntry OBJECT-TYPE
	SYNTAX  SnSwIfInfoEntry
	MAX-ACCESS  not-accessible
	STATUS  current
	DESCRIPTION
		"An entry in the snSwIfInfo table indicates the 
		 configuration on a specified port. A SNMP SET PDU 
		 for a row of the snSwIfInfoTable requires the entire 
		 sequence of the MIB Objects in each 
		 snSwIfInfoEntry stored in one PDU.  Otherwise, 
		 GENERR return-value will be returned."
	INDEX   { snSwIfInfoPortNum }
	::= { snSwIfInfoTable 1 }

SnSwIfInfoEntry ::= SEQUENCE {
	snSwIfInfoPortNum
		InterfaceIndex,
	snSwIfInfoMonitorMode
		INTEGER,
	snSwIfInfoMirrorPorts
		OCTET STRING,
	snSwIfInfoTagMode
		INTEGER,
	snSwIfInfoTagType
		Integer32,
	snSwIfInfoChnMode
		INTEGER,
	snSwIfInfoSpeed
		INTEGER,
	snSwIfInfoMediaType
		INTEGER,
	snSwIfInfoConnectorType
		INTEGER,
	snSwIfInfoAdminStatus
		INTEGER,
	snSwIfInfoLinkStatus
		INTEGER,
	snSwIfInfoPortQos
		INTEGER,
	snSwIfInfoPhysAddress
		PhysAddress,
	snSwIfLockAddressCount
		INTEGER,
	snSwIfStpPortEnable
		INTEGER,
	snSwIfDhcpGateListId
		INTEGER,
	snSwIfName
		DisplayString,
	snSwIfDescr
		DisplayString,
	snSwIfInfoAutoNegotiate
		INTEGER,
	snSwIfInfoFlowControl
		INTEGER,
	snSwIfInfoGigType
		INTEGER,
	snSwIfFastSpanPortEnable
		INTEGER,
	snSwIfFastSpanUplinkEnable
		INTEGER,
	snSwIfVlanId
		INTEGER,
	snSwIfRouteOnly
		INTEGER,
	snSwIfPresent
		INTEGER,
	snSwIfGBICStatus
		INTEGER,
	snSwIfLoadInterval
		INTEGER ,
	snSwIfStatsInFrames 
		Counter32,
	snSwIfStatsOutFrames 
		Counter32,
	snSwIfStatsAlignErrors            
		Counter32,
	snSwIfStatsFCSErrors                  
		Counter32,
	snSwIfStatsMultiColliFrames    
		Counter32,
	snSwIfStatsTxColliFrames
		Counter32,
	snSwIfStatsRxColliFrames
		Counter32,
	snSwIfStatsFrameTooLongs              
		Counter32,
	snSwIfStatsFrameTooShorts
		Counter32,
	snSwIfStatsInBcastFrames
		Counter32,
	snSwIfStatsOutBcastFrames
		Counter32,
	snSwIfStatsInMcastFrames
		Counter32,
	snSwIfStatsOutMcastFrames
		Counter32,
	snSwIfStatsInDiscard
		Counter32,
	snSwIfStatsOutDiscard
		Counter32,
	snSwIfStatsMacStations
		Integer32,
	snSwIfStatsLinkChange
		Counter32,
	snSwIfInOctets
		Counter64,
	snSwIfOutOctets
		Counter64,
	snSwIfStatsInBitsPerSec
		Gauge32,
	snSwIfStatsOutBitsPerSec
		Gauge32,
	snSwIfStatsInPktsPerSec
		Gauge32,
	snSwIfStatsOutPktsPerSec
		Gauge32,
	snSwIfStatsInUtilization
		INTEGER ,
	snSwIfStatsOutUtilization
		INTEGER ,
	snSwIfStatsInKiloBitsPerSec
		Unsigned32,
	snSwIfStatsOutKiloBitsPerSec    
		Unsigned32,
	snSwIfStatsInJumboFrames
		Counter64,
	snSwIfStatsOutJumboFrames
		Counter64,
	snSwIfInfoMirrorMode
		INTEGER,
	snSwIfMacLearningDisable
		TruthValue,
	snSwIfInfoNativeMacAddress
		PhysAddress
	}

snSwIfInfoPortNum OBJECT-TYPE
	SYNTAX	InterfaceIndex
	MAX-ACCESS  read-only
	STATUS	current
	DESCRIPTION
		"The port/interface index (ifindex)."
	::= { snSwIfInfoEntry 1 }

snSwIfInfoMonitorMode OBJECT-TYPE
	SYNTAX  INTEGER {
				disabled(0),
				input(1),
				output(2),
				both(3)
			}
	MAX-ACCESS  read-write
	STATUS  deprecated
	DESCRIPTION
		"DEPRECATED by snSwIf2MirrorMode and
		snPortMonitorTable."
	::= { snSwIfInfoEntry 2 }

snSwIfInfoMirrorPorts OBJECT-TYPE
	SYNTAX		OCTET STRING
	MAX-ACCESS  read-write
	STATUS		current
	DESCRIPTION
		"The list of port/interface index (ifindex), which mirror this interface,
		 when monitoring is enabled."
	::= { snSwIfInfoEntry 3 }

snSwIfInfoTagMode OBJECT-TYPE
	SYNTAX  INTEGER {
				tagged(1),      
				untagged(2),
				dual(3)
			}
	MAX-ACCESS  read-write
	STATUS  current
	DESCRIPTION
		"For tagged/dual port, we could have multiple VLANs 
		 per port. For untagged port, there 
		 is only one VLAN ID per port,  dual mode is associated with
		 a vlan id 'snSwIfVlanId', dual mode with snSwIfVlanId zero
		 disables the dual mode."  
	::= { snSwIfInfoEntry 4 }

snSwIfInfoTagType OBJECT-TYPE
	 SYNTAX  Integer32
	 MAX-ACCESS  read-write
	 STATUS  current
	 DESCRIPTION
		"The IEEE802.1q tag type embedded in the length/type field of
		an Ethernet packet. It specifies that the 2 octets after the
		length/type field in an Ethernet packet is the tag value."
	 DEFVAL { 33024 }
	 ::= { snSwIfInfoEntry 5 }

snSwIfInfoChnMode OBJECT-TYPE
	SYNTAX  INTEGER {
				none(0),
				halfDuplex(1),  
				fullDuplex(2)   
			}
	MAX-ACCESS  read-write
	STATUS  current
	DESCRIPTION
		"The port can be configured to operate in either
		half or full duplex mode. The values are:
			halfDuplex(1)...half duplex mode
			fullDuplex(2)...full duplex mode
		The read-back channel status from hardware are:
			none(0).........link down or port disabled.
			halfDuplex(1)...half duplex mode
			fullDuplex(2)...full duplex mode
		
		The port media type (expansion or regular)
		and port link type (trunk or feeder) determine
		value of this object.
		The port can not set to half duplex mode
		if the port connect mode is m200e(4).
		However, the value of this parameter may be
		automatically set whenever the expansion port
		is connected (e.g. cascade connecting device)."
	::= { snSwIfInfoEntry 6 }

snSwIfInfoSpeed OBJECT-TYPE
	SYNTAX  INTEGER {
				none(0),
				sAutoSense(1),
				s10M(2),
				s100M(3),
				s1G(4),
				s1GM(5),
				s155M(6),
				s10G(7),
				s622M(8),
				s2488M(9),
				s9953M(10),
				s16G(11),
				s40G(13),
				s2500M(14)
			}
	MAX-ACCESS  read-write
	STATUS  current
	DESCRIPTION     
		"The speed configuration for a port. The values are:
		  none(0)..........link down or no traffic.
		  sAutoSense(1)....Auto-sensing 10 or 100Mbits.
		  s10M(2)..........10Mbits per second.
		  s100M(3).........100Mbits per second.
		  s1G(4)...........1Gbits per second.
		  s1GM(5)..........1Gbits per second master.
		  s155M(6).........155Mbits per second (ATM) (for expansion board only).
		  s10G(7)..........10Gbits per second.
		  s622M(8).........OC12 - 622Mbits per second
		  s2488M(9)........OC48 - 2.488Gbits per second
		  s9953M(10).......OC192 - 9.953Gbits per second
		  s16G(11)..........16Gbits per second.
		  s40G(13)..........40Gbits per second.
		  s2500M(14)..........2.5Gbits per second.

		 The read-back hardware status are the following:
		  none(0)..........link down or no traffic.
		  s10M(2)..........10Mbits per second.
		  s100M(3).........100Mbits per second.
		  s1G(4)...........1Gbits per second.
		  s1GM(5)..........1Gbits per second master.
		  s155M(6).........155Mbits per second (ATM) (for expansion board only).
		  s10G(7)..........10Gbits per second.
		  s622M(8).........OC12 - 622Mbits per second
		  s2488M(9)........OC48 - 2.488Gbits per second
		  s9953M(10).......OC192 - 9.953Gbits per second
		  s16G(11)..........16Gbits per second.
		  s40G(13)..........40Gbits per second.
		  s2500M(14)..........2.5Gbits per second.

		The port media type (expansion or regular)
		and port link type (trunk or feeder) determine
		whether this object can be written and the valid
		values.
		It is not allowed to change speed for trunks ports.
		For expansion ports, all of the above speed 
		can be set.
		However, the value of this parameter may be
		automatically set whenever the expansion port
		is connected (e.g. cascade connecting device)."
	::= { snSwIfInfoEntry 7 }

snSwIfInfoMediaType OBJECT-TYPE
	SYNTAX  INTEGER {
				other(1),
				m100BaseTX(2),
				m100BaseFX(3),
				m1000BaseFX(4),
				mT3(5),
				m155ATM(6),
				m1000BaseTX(7),
				m622ATM(8),
				m155POS(9),
				m622POS(10),
				m2488POS(11),
				m10000BaseFX(12),
				m9953POS(13),
				m16GStacking(14),
				m40GStacking(16),
				m2500BaseTX(19)
			}
	MAX-ACCESS  read-only
	STATUS  current
	DESCRIPTION 
		"The media type for the port. The
		values are:
		  other(1).........other or unknown media.
		  m100BaseTX(2)....100Mbits per second copper.
		  m100BaseFX(3)....100Mbits per second fiber.
		  m1000BaseFX(4)...1Gbits per second fiber.
		  mT3(5)...........45Mbits per second (T3).
		  m155ATM(6).......155Mbits per second (ATM).
		  m1000BaseTX(7)...1Gbits per second copper.
		  m622ATM(8).......622Mbits per second (ATM).
		  m155POS(9).......155Mbits per second (POS).
		  m622POS(10)......622Mbits per second (POS).
		  m2488POS(11).....2488Mbits per second (POS).
		  m10000BaseFX(12).10Gbits per second fiber.
		  m9953POS(13).....9953Mbits per second (POS).
		  m16GStacking(14)...16Gbits per second fiber.
		  m40GStacking(16). 40Gbits per second fiber.
		  m2500BaseTX(19). 2.5Gbits per second fiber."
	::= { snSwIfInfoEntry 8 }

snSwIfInfoConnectorType OBJECT-TYPE
	SYNTAX  INTEGER {
				other(1),
				copper(2),
				fiber(3)
			}
	MAX-ACCESS  read-only
	STATUS  current
	DESCRIPTION 
		"The type of connector that the port offers.
		 The values are:
		  other(1)...........other or unknown connector
		  copper(2)..........Copper connector
		  fiber(3)...........Fiber connector
		 This describes the physical connector type"
	::= { snSwIfInfoEntry 9 }

snSwIfInfoAdminStatus OBJECT-TYPE
	SYNTAX  INTEGER {
				up(1),       -- ready to pass packets
				down(2),
				testing(3)   -- in some test mode
			}
	MAX-ACCESS  read-write
	STATUS  current
	DESCRIPTION
		"The desired state of all ports.  The
		testing(3) state indicates that no operational
		packets can be passed. 
		(same as ifAdminStatus in MIB-II)"
	::= { snSwIfInfoEntry 10 }

snSwIfInfoLinkStatus OBJECT-TYPE
	SYNTAX  INTEGER {
				up(1),       -- ready to pass packets
				down(2),
				testing(3)   -- in some test mode
			}
	MAX-ACCESS  read-only
	STATUS  current
	DESCRIPTION
		"The current operational state of the interface.
		 The testing(3) state indicates that no operational
		 packets can be passed. 
		 (same as ifOperStatus in MIB-II)"
	::= { snSwIfInfoEntry 11 }

snSwIfInfoPortQos OBJECT-TYPE
	SYNTAX  INTEGER {
				level0(0),
				level1(1),
				level2(2),
				level3(3),
				level4(4),
				level5(5),
				level6(6),
				level7(7)
			}
	MAX-ACCESS  read-write
	STATUS  current
	DESCRIPTION
		"The Stand alone stackable switch Port Qos Priority values are:
		 low(0)   -- low prority
		 high(1) -- high prority.
		 The BigIron Port Qos Priority values are:
		level0(0), level1(1), level2(2), level3(3),
		level4(4), level5(5), level6(6), level7(7) "
	::= { snSwIfInfoEntry 12 }

snSwIfInfoPhysAddress OBJECT-TYPE
	SYNTAX  PhysAddress
	MAX-ACCESS  read-only
	STATUS  current
	DESCRIPTION
		"The port physical address. The physical address 
		represents the switch port."
	::= { snSwIfInfoEntry 13 }

snSwIfLockAddressCount OBJECT-TYPE
	 SYNTAX  INTEGER (0..2048)
	 MAX-ACCESS  read-write
	 STATUS  current
	 DESCRIPTION
		"The number of source MAC addresses are allowed
		for a port. Writing 0 to this object will allow
		any number of addresses."
	DEFVAL { 8 }
	::= { snSwIfInfoEntry 14 }

snSwIfStpPortEnable OBJECT-TYPE
	 SYNTAX  INTEGER {
				disabled(0),
				enabled(1)
			 }
	 MAX-ACCESS  read-write
	 STATUS  current
	 DESCRIPTION
		"The enabled/disabled status of the port."
	 REFERENCE
		"IEEE 802.1D-1990: Section 4.5.5.2, dot1dStpPortEnable"
	 ::= { snSwIfInfoEntry 15 }

snSwIfDhcpGateListId OBJECT-TYPE
	SYNTAX  INTEGER (0..32)
	MAX-ACCESS  read-write
	STATUS  current
	DESCRIPTION
		"The ID for a DHCP gateway list entry relative 
		 to this switch port. 0 = unset or no assigned ID"
	::= { snSwIfInfoEntry 16 }

snSwIfName OBJECT-TYPE
	SYNTAX	DisplayString (SIZE(0..255))
	MAX-ACCESS	read-write
	STATUS	current
	DESCRIPTION
		"Port Name string."
	::= { snSwIfInfoEntry 17 }

snSwIfDescr OBJECT-TYPE
	SYNTAX  DisplayString
	MAX-ACCESS  read-only
	STATUS  current
	DESCRIPTION
		"A textual string containing the slot/port information
		about the interface."
	::= { snSwIfInfoEntry 18 }

snSwIfInfoAutoNegotiate OBJECT-TYPE
	SYNTAX  INTEGER {
				disabled(0),
				enabled(1),
				negFullAuto(2),
				global(3),
				other(4)
			}
	MAX-ACCESS  read-write
	STATUS  current
	DESCRIPTION
		"This feature only applies to Gigabit Ethernet ports. If set to
		disable(0), port will be put to non-negotiation mode. If set to
		enable(1), port will start auto-negotiation indefinitely until
		succeed. If set to negFullAuto(2), the port will start with auto-
		negotiation, if the negotiation failed, then it will automatically
		switch to non-negotiation mode. Stackable products (except TurboIron
		8) Gigabit Ethernet ports do not support negFullAuto(2). If set
		to global(3), port negotiation mode follows the value of
		snSwGlobalAutoNegotiate. Non-Gigabit Ethernet port returns
		the value other(4)."
	DEFVAL { global }
	::= { snSwIfInfoEntry 19 }

snSwIfInfoFlowControl OBJECT-TYPE
	SYNTAX  INTEGER {
				disabled(0),
				enabled(1)
			}
	MAX-ACCESS  read-write
	STATUS  current
	DESCRIPTION
		"Enable/Disbale port flow control."
	DEFVAL { enabled }
	::= { snSwIfInfoEntry 20 }

snSwIfInfoGigType OBJECT-TYPE
	SYNTAX  INTEGER {
				m1000BaseSX(0),
				m1000BaseLX(1),
				m1000BaseLH(2),
				m1000BaseLHA(3),
				m1000BaseLHB(4),
				m1000BaseTX(5),
				m10000BaseSR(6),
				m10000BaseLR(7),
				m10000BaseER(8),
				sfpCWDM1470nm80Km(9),
				sfpCWDM1490nm80Km(10),
				sfpCWDM1510nm80Km(11),
				sfpCWDM1530nm80Km(12),
				sfpCWDM1550nm80Km(13),
				sfpCWDM1570nm80Km(14),
				sfpCWDM1590nm80Km(15),
				sfpCWDM1610nm80Km(16),
				sfpCWDM1470nm100Km(17),
				sfpCWDM1490nm100Km(18),
				sfpCWDM1510nm100Km(19),
				sfpCWDM1530nm100Km(20),
				sfpCWDM1550nm100Km(21),
				sfpCWDM1570nm100Km(22),
				sfpCWDM1590nm100Km(23),
				sfpCWDM1610nm100Km(24),
				m1000BaseLHX(25),
				m1000BaseSX2(26),
				mSFP1000BaseBXU(27),
				mSFP1000BaseBXD(28),
				mSFP100BaseBX(29),
				mSFP100BaseBXU(30),
				mSFP100BaseBXD(31),
				mSFP100BaseFX(32),
				mSFP100BaseFXIR(33),
				mSFP100BaseFXLR(34),
				m1000BaseLMC(35),
				mXFP10000BaseSR(36),
				mXFP10000BaseLR(37),
				mXFP10000BaseER(38),
				mXFP10000BaseSW(39),
				mXFP10000BaseLW(40),
				mXFP10000BaseEW(41),
				mXFP10000BaseCX4(42),
				mXFP10000BaseZR(43),
				mXFP10000BaseZRD(44),
				m1000BaseC6553(45),
				mXFP10000BaseSRSW(46),
				mXFP10000BaseLRLW(47),
				mXFP10000BaseEREW(48),
				m10000BaseT(49),
				m2500BaseTX(50), 
				m1000BaseGBXU(127),
				m1000BaseGBXD(128),
				m1000BaseFBX(129),
				m1000BaseFBXU(130),
				m1000BaseFBXD(131),
				m1000BaseFX(132),
				m1000BaseFXIR(133),
				m1000BaseFXLR(134),
				m1000BaseXGSR(136),
				m1000BaseXGLR(137),
				m1000BaseXGER(138),
				m1000BaseXGSW(139),
				m1000BaseXGLW(140),
				m1000BaseXGEW(141),
				m1000BaseXGCX4(142),
				m1000BaseXGZR(143),
				m1000BaseXGZRD(144), 
				notApplicable(255)
			}
	MAX-ACCESS  read-only
	STATUS  current
	DESCRIPTION 
		"The media type for the port. The
		values are:
		  m1000BaseSX(0)....1Gbits per second fiber, with a short wavelength transceiver.
		  m1000BaseLX(1)....1Gbits per second fiber, with a long wavelength transceiver (3km).
		  m1000BaseLH(2)....1Gbits per second fiber, with a special wavelength transceiver (50km).
		  m1000BaseLHA(3)....1Gbits per second fiber, with a special wavelength transceiver (70km).
		  m1000BaseLHB(4)....1Gbits per second fiber, with a special wavelength transceiver (150km).
		  m1000BaseTX(5)....1Gbits per second copper (100meter).
		  m10000BaseSR(6)....10Gbits per second fiber, with a short range wavelength transceiver (100m).
		  m10000BaseLR(7)....10Gbits per second fiber, with a long range wavelength transceiver (10km).
		  m10000BaseER(8)....10Gbits per second fiber, with a extended range wavelength transceiver (40km).
		  sfpCWDM1470nm80Km(9)....1Gbits per second CWDM fiber, with a wavelength 1470nm, reach 80 kms.
		  sfpCWDM1490nm80Km(10)....1Gbits per second CWDM fiber, with a wavelength 1490nm, reach 80 kms.
		  sfpCWDM1510nm80Km(11)....1Gbits per second CWDM fiber, with a wavelength 1510nm, reach 80 kms.
		  sfpCWDM1530nm80Km(12)....1Gbits per second CWDM fiber, with a wavelength 1530nm, reach 80 kms.
		  sfpCWDM1550nm80Km(13)....1Gbits per second CWDM fiber, with a wavelength 1550nm, reach 80 kms.
		  sfpCWDM1570nm80Km(14)....1Gbits per second CWDM fiber, with a wavelength 1570nm, reach 80 kms.
		  sfpCWDM1590nm80Km(15)....1Gbits per second CWDM fiber, with a wavelength 1590nm, reach 80 kms.
		  sfpCWDM1610nm80Km(16)....1Gbits per second CWDM fiber, with a wavelength 1610nm, reach 80 kms.
		  sfpCWDM1470nm100Km(17)....1Gbits per second CWDM fiber, with a wavelength 1470nm, reach 100 kms.
		  sfpCWDM1490nm100Km(18)....1Gbits per second CWDM fiber, with a wavelength 1490nm, reach 100 kms.
		  sfpCWDM1510nm100Km(19)....1Gbits per second CWDM fiber, with a wavelength 1510nm, reach 100 kms.
		  sfpCWDM1530nm100Km(20)....1Gbits per second CWDM fiber, with a wavelength 1530nm, reach 100 kms.
		  sfpCWDM1550nm100Km(21)....1Gbits per second CWDM fiber, with a wavelength 1550nm, reach 100 kms.
		  sfpCWDM1570nm100Km(22)....1Gbits per second CWDM fiber, with a wavelength 1570nm, reach 100 kms.
		  sfpCWDM1590nm100Km(23)....1Gbits per second CWDM fiber, with a wavelength 1590nm, reach 100 kms.
		  sfpCWDM1610nm100Km(24)....1Gbits per second CWDM fiber, with a wavelength 1610nm, reach 100 kms.
		  m1000BaseLHX(25)...1Gbits per second fiber, with a special wavelength transceiver (150km).
		  m1000BaseLMC(35)...Link Media Copper.
		  mXFP10000BaseSR(36)...10GBASE fiber, 850nm serial pluggable XFP optic (LC), target range 300m over MMF.
		  mXFP10000BaseLR(37)...10GBASE fiber, 1310nm serial pluggable XFP optic (LC) for up to 10km over SMF.
		  mXFP10000BaseER(38)...10GBASE fiber, 1550nm serial pluggable XFP optic (LC) for up to 40km over SMF.
		  mXFP10000BaseSW(39)...not used.
		  mXFP10000BaseLW(40)...not used.
		  mXFP10000BaseEW(41)...not used
		  mXFP10000BaseCX4(42)...10GBASE-CX4, XFP module,15m, CX4 connector.
		  mXFP10000BaseZR(43)...1550nm serial pluggable XFP optic (LC) for up to 80km over SMF.
		  mXFP10000BaseZRD(44)...10GBASE-ZR DWDM, XFP optic, 80km.
		  mXFP10000BaseSRSW(46)...same as .mXFP10000BaseSR(36)
		  mXFP10000BaseLRLW(47)...same as .mXFP10000BaseLR(37)
		  mXFP10000BaseEREW(48)...same as mXFP10000BaseER(38).
		  m10000BaseT(49))...10GBASE fiber.
		  m2500BaseTX(50)...2.5GBASE fiber.
		  notApplicable(255)....a non-gigabit port."
	::= { snSwIfInfoEntry 21 }

snSwIfFastSpanPortEnable OBJECT-TYPE
	 SYNTAX  INTEGER {
				disabled(0),
				enabled(1)
			 }
	 MAX-ACCESS  read-write
	 STATUS  current
	 DESCRIPTION
		"The enabled/disabled fast span port status of the port."
	 ::= { snSwIfInfoEntry 22 }

snSwIfFastSpanUplinkEnable OBJECT-TYPE
	 SYNTAX  INTEGER {
				disabled(0),
				enabled(1)
			 }
	 MAX-ACCESS  read-write
	 STATUS  current
	 DESCRIPTION
		"The enabled/disabled fast span uplink status of the port."
	 ::= { snSwIfInfoEntry 23 }

snSwIfVlanId OBJECT-TYPE
	 SYNTAX  INTEGER (0..4095)
	 MAX-ACCESS  read-write
	 STATUS  current
	 DESCRIPTION
		"The ID of a VLAN of which this port is a member. Port must
		be untagged. For tagged port which belongs to multiple
		VLANs, this object return 0 which is an invalid VLAN ID
		value, reading is valid only for untagged and dual mode,
		writing is valid for only dual mode."
	 ::= { snSwIfInfoEntry 24 }

snSwIfRouteOnly OBJECT-TYPE
	 SYNTAX INTEGER {
				disabled(0),
				enabled(1)
			}
	 MAX-ACCESS  read-write
	 STATUS  current
	 DESCRIPTION
		"Enable/Disable L2 switching of a routing switch port.
		By default, the routing switch performs routing first.
		If routing failed, it performs switching. Enable route
		only instrcuts the routing switch to perform routing
		only. For a L2 switching only product, reading this
		object always return 'disabled', writing 'enabled' to
		this object takes no effect."
	 DEFVAL { disabled }
	 ::= { snSwIfInfoEntry 25 }

snSwIfPresent OBJECT-TYPE
	 SYNTAX  INTEGER {
				false(0),
				true(1)
			 }
	 MAX-ACCESS  read-only
	 STATUS  current
	 DESCRIPTION
		"Indicate if the port is absent or present.
		 This object only valid for M4 module."
	 ::= { snSwIfInfoEntry 26 }

snSwIfGBICStatus OBJECT-TYPE
	 SYNTAX  INTEGER {
				gbic(1),
				miniGBIC(2),
				empty(3),
				other(4)
			 }
	 MAX-ACCESS  read-only
	 STATUS  current
	 DESCRIPTION
		"Indicate if the gig port has GBICs on them.
		 If set to  GBIC(1), it means that the port is GBIC.
		 If set to  miniGBIC(2), it means that the port miniGBIC.
		 If set to empty(3), it means that the GBIC is missing.
		 Value other(4) means that the port not a removable gig port.
		 "
	 ::= { snSwIfInfoEntry 27 }

snSwIfLoadInterval OBJECT-TYPE
	 SYNTAX  INTEGER (30..300)
	 MAX-ACCESS  read-write
	 STATUS  current
	 DESCRIPTION
		"The time in seconds for which average port utilization should be carried out.
		The value should be incremental of 30 seconds, between the ranges specified."
	 DEFVAL { 300 }
	 ::= { snSwIfInfoEntry 28 }

snSwIfStatsInFrames OBJECT-TYPE
	SYNTAX  Counter32
	MAX-ACCESS  read-only
	STATUS  current
	DESCRIPTION
		"The total number of packets received on the interface."
	::= { snSwIfInfoEntry 29 }

snSwIfStatsOutFrames OBJECT-TYPE
	SYNTAX  Counter32
	MAX-ACCESS  read-only
	STATUS  current
	DESCRIPTION
		"The total number of packets transmitted out of the interface."
	::= { snSwIfInfoEntry 30 }

snSwIfStatsAlignErrors   OBJECT-TYPE
	 SYNTAX     Counter32
	 MAX-ACCESS     read-only
	 STATUS     current
	 DESCRIPTION
		"dot3StatsAlignmentErrors : A count of frames 
		received on a particular interface that are 
		not an integral number of octets in length 
		and do not pass the FCS check.

		The count represented by an instance of this
		object is incremented when the alignmentError
		status is returned by the MAC service to the
		LLC (or other MAC user). Received frames for
		which multiple error conditions obtain are,
		according to the conventions of IEEE 802.3
		Layer Management, counted exclusively according
		to the error status presented to the LLC."
	::= { snSwIfInfoEntry 31 }

snSwIfStatsFCSErrors   OBJECT-TYPE
	 SYNTAX      Counter32
	 MAX-ACCESS      read-only
	 STATUS      current
	 DESCRIPTION
		"dot3StatsFCSErrors : A count of frames received 
		on a particular interface that are an integral 
		number of octets in length but do not pass the 
		FCS check.

		The count represented by an instance of this
		object is incremented when the frameCheckError
		status is returned by the MAC service to the
		LLC (or other MAC user). Received frames for
		which multiple error conditions obtain are,
		according to the conventions of IEEE 802.3
		Layer Management, counted exclusively according
		to the error status presented to the LLC."
	::= { snSwIfInfoEntry 32 }

snSwIfStatsMultiColliFrames   OBJECT-TYPE
	 SYNTAX      Counter32
	 MAX-ACCESS      read-only
	 STATUS      current
	 DESCRIPTION
		"dot3StatsMultipleCollisionFrames : 
		A count of successfully transmitted frames on
		a particular interface for which transmission
		is inhibited by more than one collision.

		A frame that is counted by an instance of this
		object is also counted by the corresponding
		instance of either the ifOutUcastPkts,
		ifOutMulticastPkts, or ifOutBroadcastPkts,
		and is not counted by the corresponding
		instance of the dot3StatsSingleCollisionFrames
		object."
	::= { snSwIfInfoEntry 33 }

snSwIfStatsTxColliFrames   OBJECT-TYPE
	 SYNTAX      Counter32
	 MAX-ACCESS      read-only
	 STATUS      current
	 DESCRIPTION
		"A count of successfully transmitted frames on
		a particular interface for which transmission
		is inhibited by more than one collision.

		A frame that is counted by a combination of
		both dot3StatsSingleCollisionFrames and
		dot3StatsMultipleCollisionFrames objects."
	::= { snSwIfInfoEntry 34 }

snSwIfStatsRxColliFrames   OBJECT-TYPE
	 SYNTAX      Counter32
	 MAX-ACCESS      read-only
	 STATUS      current
	 DESCRIPTION
		"A count of successfully received frames on
		a particular interface for which transmission
		is inhibited by more than one collision.  This
		object is not specified in dot3 but it has the
		same functionarity as snSwIfStatsTxColliFrames."
	::= { snSwIfInfoEntry 35 }

snSwIfStatsFrameTooLongs   OBJECT-TYPE
	 SYNTAX    Counter32
	 MAX-ACCESS    read-only
	 STATUS    current
	 DESCRIPTION
		"dot3StatsFrameTooLongs : A count of frames 
		received on a particular interface that 
		exceed the maximum permitted frame size.

		The count represented by an instance of this
		object is incremented when the frameTooLong
		status is returned by the MAC service to the
		LLC (or other MAC user). Received frames for
		which multiple error conditions obtain are,
		according to the conventions of IEEE 802.3
		Layer Management, counted exclusively according
		to the error status presented to the LLC."
	::= { snSwIfInfoEntry 36 }
	
snSwIfStatsFrameTooShorts   OBJECT-TYPE
	 SYNTAX    Counter32
	 MAX-ACCESS    read-only
	 STATUS    current
	 DESCRIPTION
		" A count of frames received on a particular 
		interface that below the minimum permitted 
		frame size."
	::= { snSwIfInfoEntry 37 }
	
snSwIfStatsInBcastFrames OBJECT-TYPE
	SYNTAX  Counter32
	MAX-ACCESS  read-only
	STATUS  current
	DESCRIPTION
		"The total number of broadcast packets received on the interface."
	::= { snSwIfInfoEntry 38 }

snSwIfStatsOutBcastFrames OBJECT-TYPE
	SYNTAX  Counter32
	MAX-ACCESS  read-only
	STATUS  current
	DESCRIPTION
		"The total number of broadcast packets transmitted out of the interface."
	::= { snSwIfInfoEntry 39 }

snSwIfStatsInMcastFrames OBJECT-TYPE
	SYNTAX  Counter32
	MAX-ACCESS  read-only
	STATUS  current
	DESCRIPTION
		"The total number of multicast packets received on the interface."
	::= { snSwIfInfoEntry 40 }

snSwIfStatsOutMcastFrames OBJECT-TYPE
	SYNTAX  Counter32
	MAX-ACCESS  read-only
	STATUS  current
	DESCRIPTION
		"The total number of multicast packets transmitted out of the interface."
	::= { snSwIfInfoEntry 41 }

snSwIfStatsInDiscard OBJECT-TYPE
	SYNTAX  Counter32
	MAX-ACCESS  read-only
	STATUS  current
	DESCRIPTION
		"The number of inbound packets which were chosen
		 to be discarded even though no errors had been
		 detected to prevent their being deliverable to a
		 higher-layer protocol.  One possible reason for
		 discarding such a packet could be to free up
		 buffer space."
	::= { snSwIfInfoEntry 42 }

snSwIfStatsOutDiscard OBJECT-TYPE
	SYNTAX  Counter32
	MAX-ACCESS  read-only
	STATUS  current
	DESCRIPTION
		"The number of outbound packets which were chosen
		 to be discarded even though no errors had been
		 detected to prevent their being transmitted.  One
		 possible reason for discarding such a packet could
		 be to free up buffer space."
	::= { snSwIfInfoEntry 43 }

snSwIfStatsMacStations OBJECT-TYPE
	SYNTAX  Integer32
	MAX-ACCESS  read-only
	STATUS  current
	DESCRIPTION
		"The total number of MAC Stations connected to the interface."
	::= { snSwIfInfoEntry 44 }

snSwIfStatsLinkChange OBJECT-TYPE
	SYNTAX  Counter32
	MAX-ACCESS  read-only
	STATUS  current
	DESCRIPTION
		"The total number of link state change of the interface."
	::= { snSwIfInfoEntry 45 }

snSwIfInOctets OBJECT-TYPE
	SYNTAX  Counter64
	MAX-ACCESS  read-only
	STATUS  current
	DESCRIPTION
		"The total number of octets received on the interface,
		including framing characters. This object is a 64-bit
		counter of the ifInOctets object, defined in RFC 1213.
		The octet string is in big-endian byte order."
	::= { snSwIfInfoEntry 46 }

snSwIfOutOctets OBJECT-TYPE
	SYNTAX  Counter64
	MAX-ACCESS  read-only
	STATUS  current
	DESCRIPTION
		"The total number of octets transmitted out of the interface,
		including framing characters. This object is a 64-bit
		counter of the ifOutOctets object, defined in RFC 1213.
		The octet string is in big-endian byte order."
	::= { snSwIfInfoEntry 47 }

snSwIfStatsInBitsPerSec OBJECT-TYPE
	SYNTAX  Gauge32
	MAX-ACCESS  read-only
	STATUS  current
	DESCRIPTION
		"The number of bits per second received on the interface
		over a 5 minutes interval."
	::= { snSwIfInfoEntry 48 }

snSwIfStatsOutBitsPerSec OBJECT-TYPE
	SYNTAX  Gauge32
	MAX-ACCESS  read-only
	STATUS  current
	DESCRIPTION
		"The number of bits per second transmitted out of the interface
		over a 5 minutes interval."
	::= { snSwIfInfoEntry 49 }

snSwIfStatsInPktsPerSec OBJECT-TYPE
	SYNTAX  Gauge32
	MAX-ACCESS  read-only
	STATUS  current
	DESCRIPTION
		"The number of packets per second received on the interface
		over a 5 minutes interval."
	::= { snSwIfInfoEntry 50 }

snSwIfStatsOutPktsPerSec OBJECT-TYPE
	SYNTAX  Gauge32
	MAX-ACCESS  read-only
	STATUS  current
	DESCRIPTION
		"The number of packets per second transmitted out of the interface
		over a 5 minutes interval."
	::= { snSwIfInfoEntry 51 }

snSwIfStatsInUtilization OBJECT-TYPE
	SYNTAX  INTEGER (0..10000)
	MAX-ACCESS  read-only
	STATUS  current
	DESCRIPTION
		"The input network utilization in hundredths of a percent
		over a 5 minutes interval."
	::= { snSwIfInfoEntry 52 }

snSwIfStatsOutUtilization OBJECT-TYPE
	SYNTAX  INTEGER (0..10000)
	MAX-ACCESS  read-only
	STATUS  current
	DESCRIPTION
		"The output network utilization in hundredths of a percent
		over a 5 minutes interval."
	::= { snSwIfInfoEntry 53 }
	
snSwIfStatsInKiloBitsPerSec OBJECT-TYPE
	SYNTAX  Unsigned32
	MAX-ACCESS  read-only
	STATUS  current
	DESCRIPTION
		"Bit rate in kilobits per second received on the 10G and
		 faster interface over a 5 minutes interval."
	::= { snSwIfInfoEntry 54 }

snSwIfStatsOutKiloBitsPerSec OBJECT-TYPE
	SYNTAX  Unsigned32
	MAX-ACCESS  read-only
	STATUS  current
	DESCRIPTION
		"Bit rate in kilobits per second transmitted out of the 10G
		 and faster interface over a 5 minutes interval."
	::= { snSwIfInfoEntry 55 }

snSwIfStatsInJumboFrames OBJECT-TYPE
	SYNTAX  Counter64
	MAX-ACCESS  read-only
	STATUS  current
	DESCRIPTION
		"The total number of jumbo packets received on the interface."
	::= { snSwIfInfoEntry 56 }

snSwIfStatsOutJumboFrames OBJECT-TYPE
	SYNTAX  Counter64
	MAX-ACCESS  read-only
	STATUS  current
	DESCRIPTION
		"The total number of jumbo packets transmitted out of the interface."
	::= { snSwIfInfoEntry 57 }

snSwIfInfoMirrorMode OBJECT-TYPE
	 SYNTAX  INTEGER {
			   disable(0),
			   enable(1)
			 }
	 MAX-ACCESS  read-write
	 STATUS  current
	 DESCRIPTION
			 "Enable/disable mirror on this port."
	 ::= { snSwIfInfoEntry 58 }

snSwIfMacLearningDisable OBJECT-TYPE
	 SYNTAX TruthValue
	 MAX-ACCESS  read-write
	 STATUS  current
	 DESCRIPTION
		"The status of MAC learning feature on an ethernet port.
		For POS port, Get operation will return the default value and Set operation will return an error."
	  DEFVAL 
		  { false } 
	 ::= { snSwIfInfoEntry 59 }

snSwIfInfoNativeMacAddress OBJECT-TYPE
	SYNTAX  PhysAddress
	MAX-ACCESS  read-only
	STATUS  current
	DESCRIPTION
		"The port native MAC address. The native MAC address 
		represents the switch port."
	::= { snSwIfInfoEntry 62 }

-- Interface ID Registration Group

snInterfaceId OBJECT IDENTIFIER				::= { snSwPortInfo 2 }
snEthernetInterface OBJECT IDENTIFIER		::= { snInterfaceId 1 }
snPosInterface OBJECT IDENTIFIER			::= { snInterfaceId 2 }
snAtmInterface OBJECT IDENTIFIER			::= { snInterfaceId 3 }
snVirtualInterface OBJECT IDENTIFIER		::= { snInterfaceId 4 }
snLoopbackInterface OBJECT IDENTIFIER		::= { snInterfaceId 5 }
snGreTunnelInterface OBJECT IDENTIFIER		::= { snInterfaceId 6 }
snSubInterface OBJECT IDENTIFIER			::= { snInterfaceId 7 }
snMplsTunnelInterface OBJECT IDENTIFIER		::= { snInterfaceId 8 }
snPvcInterface OBJECT IDENTIFIER			::= { snInterfaceId 9 }
snMgmtEthernetInterface OBJECT IDENTIFIER	::= { snInterfaceId 10 }
snTrunkInterface OBJECT IDENTIFIER			::= { snInterfaceId 11 }
snVirtualMgmtInterface OBJECT IDENTIFIER    ::= { snInterfaceId 12 }
sn6to4TunnelInterface OBJECT IDENTIFIER		::= { snInterfaceId 13 }

-- Interface ID to ifIndex Lookup Table
-- Given an interface ID, this table returns the ifIndex value.
-- 
-- Note: This table does not behave like most SNMP tables.  It does not
-- support GetNext.  If you try to walk the table using GetNext, no rows
-- will be returned.  The contents of the table can only be accessed
-- using Get operations.  The table is useful for mapping a known
-- interface to the corresponding ifIndex value.

snInterfaceLookupTable OBJECT-TYPE
	SYNTAX  SEQUENCE OF SnInterfaceLookupEntry
	MAX-ACCESS  not-accessible
	STATUS  current
	DESCRIPTION
		""
	::= { snSwPortInfo 3 }

snInterfaceLookupEntry OBJECT-TYPE
	SYNTAX  SnInterfaceLookupEntry
	MAX-ACCESS  not-accessible
	STATUS  current
	DESCRIPTION
		""
	INDEX { snInterfaceLookupInterfaceId }
	::= { snInterfaceLookupTable 1 }

SnInterfaceLookupEntry ::= SEQUENCE {
	snInterfaceLookupInterfaceId
		InterfaceId,
	snInterfaceLookupIfIndex
		Integer32
	}

snInterfaceLookupInterfaceId OBJECT-TYPE
	 SYNTAX  InterfaceId
	 MAX-ACCESS  read-only
	 STATUS  current
	 DESCRIPTION
		""
	 ::= { snInterfaceLookupEntry 1 }

snInterfaceLookupIfIndex OBJECT-TYPE
	 SYNTAX  Integer32
	 MAX-ACCESS  read-only
	 STATUS  current
	 DESCRIPTION
		""
	 ::= { snInterfaceLookupEntry 2 }


-- ifIndex to Interface ID Lookup Table
-- Given an ifIndex, this table returns the interface ID value.

snIfIndexLookupTable OBJECT-TYPE
	SYNTAX  SEQUENCE OF SnIfIndexLookupEntry
	MAX-ACCESS  not-accessible
	STATUS  current
	DESCRIPTION
		""
	::= { snSwPortInfo 4 }

snIfIndexLookupEntry OBJECT-TYPE
	SYNTAX  SnIfIndexLookupEntry
	MAX-ACCESS  not-accessible
	STATUS  current
	DESCRIPTION
		""
	INDEX { snIfIndexLookupIfIndex }
	::= { snIfIndexLookupTable 1 }

SnIfIndexLookupEntry ::= SEQUENCE {
	snIfIndexLookupIfIndex
		Integer32,
	snIfIndexLookupInterfaceId
		InterfaceId
	}

snIfIndexLookupIfIndex OBJECT-TYPE
	 SYNTAX  Integer32
	 MAX-ACCESS  read-only
	 STATUS  current
	 DESCRIPTION
		""
	 ::= { snIfIndexLookupEntry 1 }

snIfIndexLookupInterfaceId OBJECT-TYPE
	 SYNTAX  InterfaceId
	 MAX-ACCESS  read-only
	 STATUS  current
	 DESCRIPTION
		""
	 ::= { snIfIndexLookupEntry 2 }

-- Interface ID2 to ifIndex Lookup Table
-- Given an interface ID2, this table returns the ifIndex value.
-- 
-- Note: This table does not behave like most SNMP tables.  It does not
-- support GetNext.  If you try to walk the table using GetNext, no rows
-- will be returned.  The contents of the table can only be accessed
-- using Get operations.  The table is useful for mapping a known
-- interface to the corresponding ifIndex value.

snInterfaceLookup2Table OBJECT-TYPE
	SYNTAX  SEQUENCE OF SnInterfaceLookup2Entry
	MAX-ACCESS  not-accessible
	STATUS  current
	DESCRIPTION
		""
	::= { snSwPortInfo 7 }

snInterfaceLookup2Entry OBJECT-TYPE
	SYNTAX  SnInterfaceLookup2Entry
	MAX-ACCESS  not-accessible
	STATUS  current
	DESCRIPTION
		""
	INDEX { snInterfaceLookup2InterfaceId }
	::= { snInterfaceLookup2Table 1 }

SnInterfaceLookup2Entry ::= SEQUENCE {
	snInterfaceLookup2InterfaceId
		InterfaceId2,
	snInterfaceLookup2IfIndex
		Integer32
	}

snInterfaceLookup2InterfaceId OBJECT-TYPE
	 SYNTAX  InterfaceId2
	 MAX-ACCESS  not-accessible
	 STATUS  current
	 DESCRIPTION
		""
	 ::= { snInterfaceLookup2Entry 1 }

snInterfaceLookup2IfIndex OBJECT-TYPE
	 SYNTAX  Integer32
	 MAX-ACCESS  read-only
	 STATUS  current
	 DESCRIPTION
		""
	 ::= { snInterfaceLookup2Entry 2 }


-- ifIndex to Interface ID2 Lookup Table
-- Given an ifIndex, this table returns the interface ID2 value.
snIfIndexLookup2Table OBJECT-TYPE
	SYNTAX  SEQUENCE OF SnIfIndexLookup2Entry
	MAX-ACCESS  not-accessible
	STATUS  current
	DESCRIPTION
		""
	::= { snSwPortInfo 8 }

snIfIndexLookup2Entry OBJECT-TYPE
	SYNTAX  SnIfIndexLookup2Entry
	MAX-ACCESS  not-accessible
	STATUS  current
	DESCRIPTION
		""
	INDEX { snIfIndexLookup2IfIndex }
	::= { snIfIndexLookup2Table 1 }

SnIfIndexLookup2Entry ::= SEQUENCE {
	snIfIndexLookup2IfIndex
		Integer32,
	snIfIndexLookup2InterfaceId
		InterfaceId2
	}

snIfIndexLookup2IfIndex OBJECT-TYPE
	 SYNTAX  Integer32
	 MAX-ACCESS  not-accessible
	 STATUS  current
	 DESCRIPTION
		""
	 ::= { snIfIndexLookup2Entry 1 }

snIfIndexLookup2InterfaceId OBJECT-TYPE
	 SYNTAX  InterfaceId2
	 MAX-ACCESS  read-only
	 STATUS  current
	 DESCRIPTION
		""
	 ::= { snIfIndexLookup2Entry 2 }

-- ifIndex to Optical Parameters Table
-- Given an ifIndex, this table returns the optical parameters for the ifIndex.

snIfOpticalMonitoringInfoTable  OBJECT-TYPE
	 SYNTAX      SEQUENCE OF SnIfOpticalMonitoringInfoEntry
	 MAX-ACCESS      not-accessible
	 STATUS      current
	 DESCRIPTION
		  "This table lists the instrumented parameters of all
		  optical interfaces."
	 REFERENCE
		  "ITU recommendations G.783, G.784, G.953"

	::= { snSwPortInfo 6 }

snIfOpticalMonitoringInfoEntry  OBJECT-TYPE
	 SYNTAX      SnIfOpticalMonitoringInfoEntry
	 MAX-ACCESS      not-accessible
	 STATUS      current
	 DESCRIPTION
		  "Only the ifIndices of optical interfaces
		  whose parameters need to be monitored will
		  be used to index this table."
	 INDEX       { ifIndex }
	 ::= { snIfOpticalMonitoringInfoTable 1 }

SnIfOpticalMonitoringInfoEntry ::=
	 SEQUENCE  {
		 snIfOpticalMonitoringTemperature
				  DisplayString,
		 snIfOpticalMonitoringTxPower
				  DisplayString,
		 snIfOpticalMonitoringRxPower
				  DisplayString,
		 snIfOpticalMonitoringTxBiasCurrent
				  DisplayString
	 }

snIfOpticalMonitoringTemperature  OBJECT-TYPE
	  SYNTAX	DisplayString (SIZE(0..32))
	  MAX-ACCESS    read-only
	  STATUS    current
	  DESCRIPTION
		   "This object holds the value of the transmitter laser 
			diode temperature for the interface.  This object 
			indicates the health of the transmitter.
			
			The format is xxx.yyyy C(elcius), followed by whether
			the measured value is normal, high/low alarm or
			high/low warning."
	::= { snIfOpticalMonitoringInfoEntry 1 }

snIfOpticalMonitoringTxPower  OBJECT-TYPE
	  SYNTAX	DisplayString (SIZE(0..32))
	  MAX-ACCESS    read-only
	  STATUS    current
	  DESCRIPTION
		   "This object holds the value of the transmitter optical
			signal power for the interface, measured in dBm, followed
			by whether this is a normal value, or high/low warning
			or alarm."
	 ::= { snIfOpticalMonitoringInfoEntry 2 }

snIfOpticalMonitoringRxPower  OBJECT-TYPE
	  SYNTAX	DisplayString (SIZE(0..32))
	  MAX-ACCESS    read-only
	  STATUS    current
	  DESCRIPTION
		   "This object holds the value of the receiver optical
			signal power for the interface, measured in dBm, followed
			by whether this is a normal value, or high/low warning
			or alarm."
	::= { snIfOpticalMonitoringInfoEntry 3 }

snIfOpticalMonitoringTxBiasCurrent  OBJECT-TYPE
	  SYNTAX	DisplayString (SIZE(0..32))
	  MAX-ACCESS    read-only
	  STATUS    current
	  DESCRIPTION
		   "Tx Bias Current.  It is measured in mA, and is followed
		   by whether this is a normal value, or high/low warning or
		   alarm."
	 ::= { snIfOpticalMonitoringInfoEntry 4 }


 --
-- Show Media Information
-- Information of the media device installed in the physical ports.
--

snIfMediaInfoTable  OBJECT-TYPE
	 SYNTAX      SEQUENCE OF SnIfMediaInfoEntry
	 MAX-ACCESS      not-accessible
	 STATUS      current
	 DESCRIPTION
		  "This table lists the information of the media device
		   (SFP/XFP/Copper) installed in the physical port.
		   Only the ifIndices of Ethernet ports those are associated
		   with the operational cards will be included in this table."
		::= { snSwPortInfo 9 }

snIfMediaInfoEntry  OBJECT-TYPE
	 SYNTAX      SnIfMediaInfoEntry
	 MAX-ACCESS      not-accessible
	 STATUS      current
	 DESCRIPTION
		  "An entry in the Interface Media Information table. 
		   The ifIndices of ethernet interfaces will be used
		   to index this table."
	 INDEX       { ifIndex }
	 ::= { snIfMediaInfoTable 1 }

SnIfMediaInfoEntry ::=
	 SEQUENCE  {
		 snIfMediaType
			   DisplayString,
		 snIfMediaVendorName
			   DisplayString,
		 snIfMediaVersion
			   DisplayString,
		 snIfMediaPartNumber
			   DisplayString,
		 snIfMediaSerialNumber
			   DisplayString
	 }

snIfMediaType  OBJECT-TYPE
	 SYNTAX       DisplayString (SIZE (0..128))
	 MAX-ACCESS       read-only
	 STATUS       current
	 DESCRIPTION
		  "The type of the media installed in the physical port." 
	 ::= { snIfMediaInfoEntry 1 }

snIfMediaVendorName  OBJECT-TYPE
	 SYNTAX       DisplayString (SIZE (0..128))
	 MAX-ACCESS       read-only
	 STATUS       current
	 DESCRIPTION
		  "The media vendor name, full name of the corporation."
	 ::= { snIfMediaInfoEntry 2 }

snIfMediaVersion  OBJECT-TYPE
	 SYNTAX       DisplayString (SIZE (0..128))
	 MAX-ACCESS       read-only
	 STATUS       current
	 DESCRIPTION
		  "The media vendor product version number."
	 ::= { snIfMediaInfoEntry 3 }

snIfMediaPartNumber  OBJECT-TYPE
	 SYNTAX       DisplayString (SIZE (0..128))
	 MAX-ACCESS       read-only
	 STATUS       current
	 DESCRIPTION
		  "The media vendor part number."

	 ::= { snIfMediaInfoEntry 4 }

snIfMediaSerialNumber  OBJECT-TYPE
	 SYNTAX       DisplayString (SIZE (0..128))
	 MAX-ACCESS       read-only
	 STATUS       current
	 DESCRIPTION
		  "The vendor serial number of the media device."
	 ::= { snIfMediaInfoEntry 5 }

-- Optical Parameters Table per lane for a 100G LR4 and LR10 optic.

snIfOpticalLaneMonitoringTable  OBJECT-TYPE
	 SYNTAX      SEQUENCE OF SnIfOpticalLaneMonitoringEntry
	 MAX-ACCESS      not-accessible
	 STATUS      current
	 DESCRIPTION
		  "This table lists the instrumented parameters of all
		  lanes within a 100G optic of type LR4 and LR10.
		  LR4 has 4 lanes per optic, LR10 has 10 lanes per optic."
	 REFERENCE
		  "ITU recommendations G.783, G.784, G.953"
	::= { snSwPortInfo 10 }

snIfOpticalLaneMonitoringEntry  OBJECT-TYPE
	 SYNTAX      SnIfOpticalLaneMonitoringEntry
	 MAX-ACCESS      not-accessible
	 STATUS      current
	 DESCRIPTION
		  "Only the ifIndices of optical interfaces
		  whose parameters need to be monitored will
		  be used to index this table."
	 INDEX       { ifIndex, snIfOpticalLaneMonitoringLane }
	 ::= { snIfOpticalLaneMonitoringTable 1 }

SnIfOpticalLaneMonitoringEntry ::=
	 SEQUENCE  {
		 snIfOpticalLaneMonitoringLane
				  Unsigned32,
		 snIfOpticalLaneMonitoringTemperature
				  DisplayString,
		 snIfOpticalLaneMonitoringTxPower
				  DisplayString,
		 snIfOpticalLaneMonitoringRxPower
				  DisplayString,
		 snIfOpticalLaneMonitoringTxBiasCurrent
				  DisplayString
	 }

snIfOpticalLaneMonitoringLane  OBJECT-TYPE
	  SYNTAX    Unsigned32
	  MAX-ACCESS    not-accessible
	  STATUS    current
	  DESCRIPTION
		   "The lane number of this 100G optic. LR4 has 4, and LR10 has
			10 lanes."
	::= { snIfOpticalLaneMonitoringEntry 1 }

snIfOpticalLaneMonitoringTemperature  OBJECT-TYPE
	  SYNTAX	DisplayString (SIZE(0..32))
	  MAX-ACCESS    read-only
	  STATUS    current
	  DESCRIPTION
		   "This object holds the value of the transmitter laser
			diode temperature for the lane in the interface. This
			object indicates the health of the transmitter.

			The format is xxx.yyyy C(elcius), followed by whether
			the measured value is normal, high/low alarm or
			high/low warning."
	::= { snIfOpticalLaneMonitoringEntry 2 }

snIfOpticalLaneMonitoringTxPower  OBJECT-TYPE
	  SYNTAX	DisplayString (SIZE(0..32))
	  MAX-ACCESS    read-only
	  STATUS    current
	  DESCRIPTION
		   "This object holds the value of the transmitter optical
			signal power for the lane in the interface, measured in
			dBm, followed by whether this is a normal value, or
			high/low warning or alarm."
	 ::= { snIfOpticalLaneMonitoringEntry 3 }

snIfOpticalLaneMonitoringRxPower  OBJECT-TYPE
	  SYNTAX	DisplayString (SIZE(0..32))
	  MAX-ACCESS    read-only
	  STATUS    current
	  DESCRIPTION
		   "This object holds the value of the receiver optical
			signal power for the lane in the interface, measured in
			dBm, followed by whether this is a normal value, or
			high/low warning or alarm."
	::= { snIfOpticalLaneMonitoringEntry 4 }

snIfOpticalLaneMonitoringTxBiasCurrent  OBJECT-TYPE
	  SYNTAX	DisplayString (SIZE(0..32))
	  MAX-ACCESS    read-only
	  STATUS    current
	  DESCRIPTION
		   "Tx Bias Current.  It is measured in mA, and is followed
		   by whether this is a normal value, or high/low warning or
		   alarm."
	 ::= { snIfOpticalLaneMonitoringEntry 5 }



--
-- Show egress port counter information
-- The egress counters of all queues given a particular port.
--

brcdIfEgressCounterInfoTable  OBJECT-TYPE
	 SYNTAX      SEQUENCE OF BrcdIfEgressCounterInfoEntry
	 MAX-ACCESS      not-accessible
	 STATUS      current
	 DESCRIPTION
		  "This table lists the information of egress counters of 
		   all the queues in the physical ports."
		::= { snSwPortInfo 11 }

brcdIfEgressCounterInfoEntry  OBJECT-TYPE
	 SYNTAX      BrcdIfEgressCounterInfoEntry
	 MAX-ACCESS      not-accessible
	 STATUS      current
	 DESCRIPTION
		  "An entry in the Interface Egress Counter Information table. 
		   The ifIndices of ethernet interfaces and the queue number will 
		   be used to index this table."
	 INDEX       { brcdIfEgressCounterIfIndex, brcdIfEgressCounterQueueId }
	 ::= { brcdIfEgressCounterInfoTable 1 }

BrcdIfEgressCounterInfoEntry ::=
	 SEQUENCE  {
	     brcdIfEgressCounterIfIndex
			   InterfaceIndex,
		 brcdIfEgressCounterQueueId
			   INTEGER,
		 brcdIfEgressCounterType
			   INTEGER,
		 brcdIfEgressCounterPkts
			   Counter64,
		 brcdIfEgressCounterDropPkts
			   Counter64
	 }

brcdIfEgressCounterIfIndex  OBJECT-TYPE
	 SYNTAX       InterfaceIndex
	 MAX-ACCESS   not-accessible
	 STATUS       current
	 DESCRIPTION
		  "The port number of egress counter in the physical port. The port/interface index (ifindex)." 
	 ::= { brcdIfEgressCounterInfoEntry 1 }

brcdIfEgressCounterQueueId  OBJECT-TYPE
	 SYNTAX       INTEGER
	 MAX-ACCESS   not-accessible
	 STATUS       current
	 DESCRIPTION
		  "The queue number of egress counter in the given port." 
	 ::= { brcdIfEgressCounterInfoEntry 2 }

brcdIfEgressCounterType  OBJECT-TYPE
	 SYNTAX  INTEGER {
				other(1),
				unicast(2),
				multicast(3)
			}
	 MAX-ACCESS   read-only
	 STATUS       current
	 DESCRIPTION
		  "The queue type of the egress counter in a given port."
	 ::= { brcdIfEgressCounterInfoEntry 3 }

brcdIfEgressCounterPkts  OBJECT-TYPE
	 SYNTAX       Counter64
	 MAX-ACCESS   read-only
	 STATUS       current
	 DESCRIPTION
		  "The egress packet counters of the queue in a given port."
	 ::= { brcdIfEgressCounterInfoEntry 4 }

brcdIfEgressCounterDropPkts  OBJECT-TYPE
	 SYNTAX       Counter64
	 MAX-ACCESS   read-only
	 STATUS       current
	 DESCRIPTION
		  "The egress dropped packet counters of the queue in a given port."

	 ::= { brcdIfEgressCounterInfoEntry 5 }
	 

--      Forwarding Database Group
--
-- This group contains information relevant to 
-- the forwarding database in the system.



-- The Forward Database Static Table Information
--
-- This table contains all MAC addresses in the system. Static 
-- stations may be configured.


snFdbTable OBJECT-TYPE
	SYNTAX  SEQUENCE OF SnFdbEntry
	MAX-ACCESS  not-accessible
	STATUS  current
	DESCRIPTION
		"This table contains snFdb information for each station
		known to the system, one entry per station." 
	::= { snFdbInfo 1 }

snFdbEntry OBJECT-TYPE
	SYNTAX  SnFdbEntry
	MAX-ACCESS  not-accessible
	STATUS  current
	DESCRIPTION
		"Each entry represents the information of a static MAC station." 
	INDEX   { 
		snFdbStationIndex
	}
	::= { snFdbTable 1 }


SnFdbEntry ::= SEQUENCE {
	snFdbStationIndex
		INTEGER,
	snFdbStationAddr
		PhysAddress,
	snFdbStationPort
		Integer32,
	snFdbVLanId
		INTEGER,
	snFdbStationQos
		INTEGER,
	snFdbStationType
		INTEGER,
	snFdbRowStatus
		INTEGER,
	snFdbStationIf
		InterfaceIndex
	}

snFdbStationIndex OBJECT-TYPE
	SYNTAX  INTEGER (1..256)
	MAX-ACCESS  read-only
	STATUS  current
	DESCRIPTION
		"The FDB Station index to the Fdb Station Table."
	::= { snFdbEntry 1 }

snFdbStationAddr OBJECT-TYPE
	SYNTAX  PhysAddress
	MAX-ACCESS  read-write
	STATUS  current
	DESCRIPTION
		"The snFdbs physical address. The physical address 
		represents a MAC Station."
	::= { snFdbEntry 2 }


snFdbStationPort OBJECT-TYPE
	SYNTAX  Integer32
	MAX-ACCESS  read-write
	STATUS  current
	DESCRIPTION
		"Station slot/port number. 
		 The bit 0 to bit 7: port number. 
		 The bit 8 to bit 11: slot number (slot for chassis only)."
	::= { snFdbEntry 3 }


snFdbVLanId OBJECT-TYPE
	SYNTAX  INTEGER (1..65535)
	MAX-ACCESS  read-write
	STATUS  current
	DESCRIPTION
		"The Station VLan ID."
	::= { snFdbEntry 4 }

snFdbStationQos OBJECT-TYPE
	SYNTAX  INTEGER {
		level0(0),
		level1(1),
		level2(2),
		level3(3),
		level4(4),
		level5(5),
		level6(6),
		level7(7)
		}
	MAX-ACCESS  read-write
	STATUS  current
	DESCRIPTION
		"The Stand alone stackable station Qos Priority values are:
		 low(0)   -- low prority
		 high(1) -- high prority.
		 The BigIron switch station Priority values are:
		level0(0), level1(1), level2(2), level3(3),
		level4(4), level5(5), level6(6), level7(7) "
	::= { snFdbEntry 5 }

snFdbStationType OBJECT-TYPE
	SYNTAX  INTEGER {
		notSupported(0),
		host(1),
		router(2)
		}
	MAX-ACCESS  read-write
	STATUS  current
	DESCRIPTION
		"The station type values are:
		 notSupported    -- a read value only : this product does not 
							support MultiLayer Switching.
		 host    -- any MAC station.
		 router  -- a router-typed station."
	::= { snFdbEntry 6 }

snFdbRowStatus OBJECT-TYPE
	SYNTAX  INTEGER {
		other(1),
		valid(2),
		delete(3),
		create(4)
		}
	MAX-ACCESS  read-write
	STATUS  current
	DESCRIPTION
		"This object is used to create and
		delete row in the table and control
		if they are used. The values
		that can be written are:
		  delete(3)...deletes the row
		  create(4)...creates a new row

		If the row exists, then a SET with
		value of create(4) returns error
		'badValue'. Deleted rows go away
		immediately. The following values
		can be returned on reads:
		  noSuch(0)...no such row
		  other(1)....some other case
		  valid(2)....the row exists and is valid"
	::= { snFdbEntry 7 }

snFdbStationIf OBJECT-TYPE
	SYNTAX  InterfaceIndex
	MAX-ACCESS  read-write
	STATUS  current
	DESCRIPTION
		"Station interface index."
	::= { snFdbEntry 8 }


-- Port STP Configuration Group
-- snPortStpTable was deprecated. It has been replaced by snIfStpTable.


snPortStpTable OBJECT-TYPE
	SYNTAX  SEQUENCE OF SnPortStpEntry
	MAX-ACCESS  not-accessible
	STATUS  deprecated
	DESCRIPTION
		"A specific snPortStpTable consists of a number of 
		 switch ports. This table only exists if only if
		 snVLanByPortCfgTable exists and snVLanByPortCfgStpMode is
		 enabled for each VLAN."
	::= { snPortStpInfo 1 }

snPortStpEntry OBJECT-TYPE
	SYNTAX  SnPortStpEntry
	MAX-ACCESS  not-accessible
	STATUS  deprecated
	DESCRIPTION
		"An entry in the snPortStpTable indicates the 
		 configuration on a specified port. A SNMP SET PDU 
		 for a row of the snPortStpTable requires the entired 
		 sequence of the MIB Objects in each 
		 snPortStpEntry stored in one PDU.  Otherwise, 
		 GENERR return-value will be returned."
	INDEX   { 
			snPortStpVLanId,	
			snPortStpPortNum
	}
	::= { snPortStpTable 1 }

SnPortStpEntry ::= SEQUENCE {
	snPortStpVLanId
		INTEGER,
	snPortStpPortNum
		Integer32,
	snPortStpPortPriority
		INTEGER,
	snPortStpPathCost 
		INTEGER,
	snPortStpOperState
		INTEGER,
	snPortStpPortEnable
		INTEGER,
	snPortStpPortForwardTransitions
		Counter32,
	snPortStpPortState
		INTEGER,
	snPortStpPortDesignatedCost
		Integer32,
	snPortStpPortDesignatedRoot
		BridgeId,
	snPortStpPortDesignatedBridge
		BridgeId,
	snPortStpPortDesignatedPort
		OCTET STRING,
	snPortStpPortAdminRstp
		INTEGER,
	snPortStpPortProtocolMigration
		INTEGER,
	snPortStpPortAdminEdgePort
		INTEGER,
	snPortStpPortAdminPointToPoint
		INTEGER
	}

snPortStpVLanId OBJECT-TYPE
	SYNTAX  INTEGER (1..65535)
	MAX-ACCESS  read-only
	STATUS  deprecated
	DESCRIPTION
		"The VLAN ID of the VLAN switch community." 
	::= { snPortStpEntry 1 }

snPortStpPortNum OBJECT-TYPE
	SYNTAX  Integer32
	MAX-ACCESS  read-only
	STATUS  deprecated
	DESCRIPTION
		"The port number of the Switch. 
		 The bit 0 to bit 7: port number. 
		 The bit 8 to bit 11: slot number (slot for chassis only)."
	::= { snPortStpEntry 2 }

snPortStpPortPriority OBJECT-TYPE
	SYNTAX  INTEGER (0..255)
	MAX-ACCESS  read-write
	STATUS  deprecated
	DESCRIPTION
	"The value of the priority field which is
	 contained in the first (in network byte order)
	 octet of the (2 octet long) Port ID.  The other
	 octet of the Port ID is given by the value of
	 dot1dStpPort."
	::= { snPortStpEntry 3 }

snPortStpPathCost OBJECT-TYPE
	SYNTAX  INTEGER (0..65535)
	MAX-ACCESS  read-write
	STATUS  deprecated
	DESCRIPTION
	"dot1dStpPortPathCost : The contribution of this 
	 port to the path cost of paths towards the spanning 
	 tree root which include this port.  802.1D-1990 
	 recommends that the default value of this parameter 
	 be in inverse proportion to the speed of the 
	 attached LAN. Writing value zero to this object
	 sets path cost to a default value which automatically
	 changes according to port speed. Reading value zero
	 indicates an unknown path cost value because port
	 speed cannot be determined due to speed auto sense
	 in progress."
	::= { snPortStpEntry 4 }


snPortStpOperState OBJECT-TYPE
	SYNTAX  INTEGER {
		notActivated(0),             
		activated(1)
		}
	MAX-ACCESS  read-only
	STATUS  deprecated
	DESCRIPTION
		"By default, this mode is set to notActivated(0).
		 notActivated(0)...the Port STP entry is not activated and not in running mode.
		 activated(1)......the Port STP entry is activated and in running mode"  
	::= { snPortStpEntry 5 }

snPortStpPortEnable OBJECT-TYPE
	SYNTAX  INTEGER {
			  enabled(1),
			  disabled(2)
			}
	MAX-ACCESS  not-accessible
	STATUS  deprecated
	DESCRIPTION
	"The enabled/disabled status of the port."
	::= { snPortStpEntry 6 }

snPortStpPortForwardTransitions OBJECT-TYPE
	SYNTAX  Counter32
	MAX-ACCESS  not-accessible
	STATUS  deprecated
	DESCRIPTION
	"The number of times this port has transitioned
	 from the Learning state to the Forwarding state."
	::= { snPortStpEntry 7 }

snPortStpPortState OBJECT-TYPE
	SYNTAX  INTEGER {
			  disabled(1),
			  blocking(2),
			  listening(3),
			  learning(4),
			  forwarding(5),
			  broken(6),
			  preforwarding(7)
			}
	MAX-ACCESS  read-only
	STATUS  deprecated
	DESCRIPTION
	"The port's current state as defined by
	 application of the Spanning Tree Protocol.  This
	 state controls what action a port takes on
	 reception of a frame.  If the bridge has detected
	 a port that is malfunctioning it will place that
	 port into the broken(6) state.  For ports which
	 are disabled (see dot1dStpPortEnable), this object
	 will have a value of disabled(1)."
	::= { snPortStpEntry 8 }

snPortStpPortDesignatedCost OBJECT-TYPE
	SYNTAX  Integer32
	MAX-ACCESS  read-only
	STATUS  deprecated
	DESCRIPTION
	"The path cost of the Designated Port of the
	 segment connected to this port.  This value is
	 compared to the Root Path Cost field in received
	 bridge PDUs."
	::= { snPortStpEntry 9 }


snPortStpPortDesignatedRoot OBJECT-TYPE
	SYNTAX  BridgeId
	MAX-ACCESS  read-only
	STATUS  deprecated
	DESCRIPTION
	"The unique Bridge Identifier of the Bridge
	 recorded as the Root in the Configuration BPDUs
	 transmitted by the Designated Bridge for the
	 segment to which the port is attached."
	::= { snPortStpEntry 10 }

snPortStpPortDesignatedBridge OBJECT-TYPE
	SYNTAX  BridgeId
	MAX-ACCESS  read-only
	STATUS  deprecated
	DESCRIPTION
	"The Bridge Identifier of the bridge which this
	 port considers to be the Designated Bridge for
	 this port's segment."
	::= { snPortStpEntry 11 }

snPortStpPortDesignatedPort OBJECT-TYPE
	SYNTAX  OCTET STRING (SIZE (2))
	MAX-ACCESS  read-only
	STATUS  deprecated
	DESCRIPTION
	"The Port Identifier of the port on the Designated
	 Bridge for this port's segment."
	::= { snPortStpEntry 12 }

snPortStpPortAdminRstp OBJECT-TYPE
	SYNTAX  INTEGER {
			  true(1),
			  false(2)
			}
	MAX-ACCESS  read-write
	STATUS  deprecated
	DESCRIPTION
	"Enable or disable RSTP of a port which is a member of a VLAN.
	If the VLAN is not operating in RSTP, this object will return
	FALSE(2) and this object is not writable."
	::= { snPortStpEntry 13 }

snPortStpPortProtocolMigration OBJECT-TYPE
	SYNTAX  INTEGER {
			  true(1),
			  false(2)
			}
	MAX-ACCESS  read-write
	STATUS  deprecated
	DESCRIPTION
	"When operating in RSTP (version 2) mode, writing TRUE(1)
	 to this object forces this port to transmit RSTP BPDUs.
	 Any other operation on this object has no effect and
	 it always returns FALSE(2) when read."
	::= { snPortStpEntry 14 }

snPortStpPortAdminEdgePort OBJECT-TYPE
	SYNTAX  INTEGER {
			  true(1),
			  false(2)
			}
	MAX-ACCESS  read-write
	STATUS  deprecated
	DESCRIPTION
	"The administrative value of the Edge Port parameter.  A
	 value of TRUE(1) indicates that this port should be
	 assumed as an edge-port and a value of FALSE(2) indicates
	 that this port should be assumed as a non-edge-port."
	::= { snPortStpEntry 15 }

snPortStpPortAdminPointToPoint OBJECT-TYPE
	SYNTAX  INTEGER {
			  true(1),
			  false(2)
			}
	MAX-ACCESS  read-write
	STATUS  deprecated
	DESCRIPTION
	"The administrative point-to-point status of the LAN segment
	 attached to this port.  A value of TRUE(1) indicates that
	 this port should always be treated as if it is connected to
	 a point-to-point link.  A value of FALSE(2) indicates
	 that this port should be treated as having a shared media
	 connection."
	::= { snPortStpEntry 16 }

-- Port STP Configuration Group
-- snIfStpTable is replacing snPortStpTable.
-- snIfStpPortNum is using ifIndex value to index snIfStpTable.


snIfStpTable OBJECT-TYPE
	SYNTAX  SEQUENCE OF SnIfStpEntry
	MAX-ACCESS  not-accessible
	STATUS  current
	DESCRIPTION
		"A specific snIfStpTable consists of a number of 
		 switch ports. This table only exists if only if
		 snVLanByPortCfgTable exists and snVLanByPortCfgStpMode is
		 enabled for each VLAN."
	::= { snPortStpInfo 2 }

snIfStpEntry OBJECT-TYPE
	SYNTAX  SnIfStpEntry
	MAX-ACCESS  not-accessible
	STATUS  current
	DESCRIPTION
		"An entry in the snIfStpTable indicates the 
		 configuration on a specified port. A SNMP SET PDU 
		 for a row of the snIfStpTable requires the entired 
		 sequence of the MIB Objects in each 
		 snIfStpEntry stored in one PDU.  Otherwise, 
		 GENERR return-value will be returned."
	INDEX   { 
			snIfStpVLanId,	
			snIfStpPortNum
	}
	::= { snIfStpTable 1 }

SnIfStpEntry ::= SEQUENCE {
	snIfStpVLanId
		INTEGER,
	snIfStpPortNum
		InterfaceIndex,
	snIfStpPortPriority
		INTEGER,
	snIfStpCfgPathCost
		INTEGER,
	snIfStpOperState
		INTEGER,
	snIfStpPortState
		INTEGER,
	snIfStpPortDesignatedCost
		Integer32,
	snIfStpPortDesignatedRoot
		BridgeId,
	snIfStpPortDesignatedBridge
		BridgeId,
	snIfStpPortDesignatedPort
		OCTET STRING,
	snIfStpPortAdminRstp
		TruthValue,
	snIfStpPortProtocolMigration
		TruthValue,
	snIfStpPortAdminEdgePort
		TruthValue,
	snIfStpPortAdminPointToPoint
		TruthValue,
	snIfStpOperPathCost
		INTEGER,
	snIfStpPortRole
		INTEGER,
	snIfStpBPDUTransmitted
		Counter32,
	snIfStpBPDUReceived
		Counter32,
	snIfRstpConfigBPDUReceived
		Counter32,
	snIfRstpTCNBPDUReceived
		Counter32,
	snIfRstpConfigBPDUTransmitted
		Counter32,
	snIfRstpTCNBPDUTransmitted
		Counter32
	}

snIfStpVLanId OBJECT-TYPE
	SYNTAX  INTEGER (1..65535)
	MAX-ACCESS  read-only
	STATUS  current
	DESCRIPTION
		"The VLAN ID of the VLAN switch community." 
	::= { snIfStpEntry 1 }

snIfStpPortNum OBJECT-TYPE
	SYNTAX  InterfaceIndex
	MAX-ACCESS  read-only
	STATUS  current
	DESCRIPTION
		"The port number of the Switch. It has the ifIndex value."
	::= { snIfStpEntry 2 }

snIfStpPortPriority OBJECT-TYPE
	SYNTAX  INTEGER (0..255)
	MAX-ACCESS  read-write
	STATUS  current
	DESCRIPTION
	"The value of the priority field which is
	 contained in the first (in network byte order)
	 octet of the (2 octet long) Port ID.  The other
	 octet of the Port ID is given by the value of
	 dot1dStpPort."
	::= { snIfStpEntry 3 }

snIfStpCfgPathCost OBJECT-TYPE
	SYNTAX  INTEGER (0..200000000)
	MAX-ACCESS  read-write
	STATUS  current
	DESCRIPTION
	"dot1dStpPortPathCost : The contribution of this 
	 port to the path cost of paths towards the spanning 
	 tree root which include this port.  802.1D-1990 
	 recommends that the default value of this parameter 
	 be in inverse proportion to the speed of the 
	 attached LAN. Writing value zero to this object
	 sets path cost to a default value which automatically
	 changes according to port speed."
	::= { snIfStpEntry 4 }


snIfStpOperState OBJECT-TYPE
	SYNTAX  INTEGER {
		notActivated(0),             
		activated(1)
		}
	MAX-ACCESS  read-only
	STATUS  current
	DESCRIPTION
		"By default, this mode is set to notActivated(0).
		 notActivated(0)...the Port STP or RSTP entry is not configured  and not in running mode.
		 activated(1)......the Port STP or RSTP entry is enabled"  
	::= { snIfStpEntry 5 }

snIfStpPortState OBJECT-TYPE
	SYNTAX  INTEGER {
			  disabled(1),
			  blocking(2),
			  listening(3),
			  learning(4),
			  forwarding(5),
			  broken(6),
			  preforwarding(7)
			}
	MAX-ACCESS  read-only
	STATUS  current
	DESCRIPTION
	"The port's current state as defined by
	 application of the Spanning Tree Protocol.  This
	 state controls what action a port takes on
	 reception of a frame.  If the bridge has detected
	 a port that is malfunctioning it will place that
	 port into the broken(6) state.  For ports which
	 are disabled (see dot1dStpPortEnable), this object
	 will have a value of disabled(1)."
	::= { snIfStpEntry 8 }

snIfStpPortDesignatedCost OBJECT-TYPE
	SYNTAX Integer32
	MAX-ACCESS  read-only
	STATUS  current
	DESCRIPTION
	"The path cost of the Designated Port of the
	 segment connected to this port.  This value is
	 compared to the Root Path Cost field in received
	 bridge PDUs."
	::= { snIfStpEntry 9 }


snIfStpPortDesignatedRoot OBJECT-TYPE
	SYNTAX  BridgeId
	MAX-ACCESS  read-only
	STATUS  current
	DESCRIPTION
	"The unique Bridge Identifier of the Bridge
	 recorded as the Root in the Configuration BPDUs
	 transmitted by the Designated Bridge for the
	 segment to which the port is attached."
	::= { snIfStpEntry 10 }

snIfStpPortDesignatedBridge OBJECT-TYPE
	SYNTAX  BridgeId
	MAX-ACCESS  read-only
	STATUS  current
	DESCRIPTION
	"The Bridge Identifier of the bridge which this
	 port considers to be the Designated Bridge for
	 this port's segment."
	::= { snIfStpEntry 11 }

snIfStpPortDesignatedPort OBJECT-TYPE
	SYNTAX  OCTET STRING (SIZE (2))
	MAX-ACCESS  read-only
	STATUS  current
	DESCRIPTION
	"The Port Identifier of the port on the Designated
	 Bridge for this port's segment."
	::= { snIfStpEntry 12 }

snIfStpPortAdminRstp OBJECT-TYPE
	SYNTAX  TruthValue
	MAX-ACCESS  read-write
	STATUS  current
	DESCRIPTION
	"Enable or disable RSTP of a port which is a member of a VLAN.
	If the VLAN is not operating in RSTP, this object will return
	FALSE(2) and this object is not writable."
	::= { snIfStpEntry 13 }

snIfStpPortProtocolMigration OBJECT-TYPE
	SYNTAX  TruthValue
	MAX-ACCESS  read-write
	STATUS  current
	DESCRIPTION
	"When operating in RSTP (version 2) mode, writing TRUE(1)
	 to this object forces this port to transmit RSTP BPDUs.
	 Any other operation on this object has no effect and
	 it always returns FALSE(2) when read."
	::= { snIfStpEntry 14 }

snIfStpPortAdminEdgePort OBJECT-TYPE
	SYNTAX  TruthValue
	MAX-ACCESS  read-write
	STATUS  current
	DESCRIPTION
	"The administrative value of the Edge Port parameter.  A
	 value of TRUE(1) indicates that this port should be
	 assumed as an edge-port and a value of FALSE(2) indicates
	 that this port should be assumed as a non-edge-port."
	::= { snIfStpEntry 15 }

snIfStpPortAdminPointToPoint OBJECT-TYPE
	SYNTAX  TruthValue
	MAX-ACCESS  read-write
	STATUS  current
	DESCRIPTION
	"The administrative point-to-point status of the LAN segment
	 attached to this port.  A value of TRUE(1) indicates that
	 this port should always be treated as if it is connected to
	 a point-to-point link.  A value of FALSE(2) indicates
	 that this port should be treated as having a shared media
	 connection."
	::= { snIfStpEntry 16 }

snIfStpOperPathCost OBJECT-TYPE
	SYNTAX  INTEGER (0..200000000)
	MAX-ACCESS  read-only
	STATUS  current
	DESCRIPTION
	"dot1dStpPortPathCost : The contribution of this 
	 port to the path cost of paths towards the spanning 
	 tree root which include this port.  802.1D-1990 
	 recommends that the default value of this parameter 
	 be in inverse proportion to the speed of the 
	 attached LAN. Reading value zero indicates an unknown
	 path cost value because port speed cannot be determined
	 due to speed auto sense in progress or port link is down."
	::= { snIfStpEntry 17 }

snIfStpPortRole OBJECT-TYPE
	SYNTAX  INTEGER {
			  unknown(0),
			  alternate(1),
			  root(2),
			  designated(3),
			  backupRole(4),
			  disabledRole(5)
			}
	MAX-ACCESS  read-only
	STATUS  current
	DESCRIPTION
	"STP/RSTP port role."
	::= { snIfStpEntry 18 }

snIfStpBPDUTransmitted OBJECT-TYPE
	SYNTAX  Counter32
	MAX-ACCESS  read-only
	STATUS  current
	DESCRIPTION
	"STP/RSTP bridge protocol unit transmitted counter."
	::= { snIfStpEntry 19 }

snIfStpBPDUReceived OBJECT-TYPE
	SYNTAX  Counter32
	MAX-ACCESS  read-only
	STATUS  current
	DESCRIPTION
	"STP/RSTP bridge protocol unit received counter."
	::= { snIfStpEntry 20 }

snIfRstpConfigBPDUReceived OBJECT-TYPE
	SYNTAX  Counter32
	MAX-ACCESS  read-only
	STATUS  current
	DESCRIPTION
	"RSTP configuration bridge protocol unit received counter."
	::= { snIfStpEntry 21 }

snIfRstpTCNBPDUReceived OBJECT-TYPE
	SYNTAX  Counter32
	MAX-ACCESS  read-only
	STATUS  current
	DESCRIPTION
	"RSTP topology change notification bridge protocol unit received counter."
	::= { snIfStpEntry 22 }

snIfRstpConfigBPDUTransmitted OBJECT-TYPE
	SYNTAX  Counter32
	MAX-ACCESS  read-only
	STATUS  current
	DESCRIPTION
	"RSTP configuration bridge protocol unit transmitted counter."
	::= { snIfStpEntry 23 }

snIfRstpTCNBPDUTransmitted OBJECT-TYPE
	SYNTAX  Counter32
	MAX-ACCESS  read-only
	STATUS  current
	DESCRIPTION
	"RSTP topology change notification bridge protocol unit transmitted counter."
	::= { snIfStpEntry 24 }


-- Trunk Port Configuration Group


snTrunkTable OBJECT-TYPE
	SYNTAX  SEQUENCE OF SnTrunkEntry
	MAX-ACCESS  not-accessible
	STATUS  current
	DESCRIPTION
		"A specific snTrunkTable consists of a number of 
		 Trunk port-mask." 
	::= { snTrunkInfo 1 }

snTrunkEntry OBJECT-TYPE
	SYNTAX  SnTrunkEntry
	MAX-ACCESS  not-accessible
	STATUS  current
	DESCRIPTION
		"An entry in the snTrunkTable indicates the 
		 configuration on a specified Trunk port membership." 
	INDEX   { 
		snTrunkIndex
	}
	::= { snTrunkTable 1 }

SnTrunkEntry ::= SEQUENCE {
	snTrunkIndex
		Integer32,
	snTrunkPortMask
		PortMask,
	snTrunkType
		INTEGER
	}

snTrunkIndex OBJECT-TYPE
	SYNTAX  Integer32
	MAX-ACCESS  read-only
	STATUS  current
	DESCRIPTION
		"The number of the trunk entries can be configured.
		This can be 32*<slots> for Jetcore, and 16*<slots> for Ironcore."
	::= { snTrunkEntry 1 }


snTrunkPortMask OBJECT-TYPE
	SYNTAX  PortMask
	MAX-ACCESS  read-write
	STATUS  current
	DESCRIPTION
		"Trunk membership of the Switch." 
	::= { snTrunkEntry 2 }


snTrunkType OBJECT-TYPE
	SYNTAX  INTEGER {
		switch(1),
		server(2)
		}
	MAX-ACCESS  read-write
	STATUS  current
	DESCRIPTION
		"The trunk connection type which specifies what
		device the trunk ports are connected to."
	::= { snTrunkEntry 3 }


-- Multi-slot Trunk Port Configuration Group


snMSTrunkTable OBJECT-TYPE
	SYNTAX  SEQUENCE OF SnMSTrunkEntry
	MAX-ACCESS  not-accessible
	STATUS  current
	DESCRIPTION
		"A table contains the configuration of port members of
		multi-slot trunk groups."
	::= { snTrunkInfo 2 }

snMSTrunkEntry OBJECT-TYPE
	SYNTAX  SnMSTrunkEntry
	MAX-ACCESS  not-accessible
	STATUS  current
	DESCRIPTION
		"An entry of the snMSTrunkTable."
	INDEX {snMSTrunkPortIndex}
	::= { snMSTrunkTable 1 }

SnMSTrunkEntry ::= SEQUENCE {
	snMSTrunkPortIndex
		Integer32,
	snMSTrunkPortList
		OCTET STRING,
	snMSTrunkType
		INTEGER,
	snMSTrunkRowStatus
		INTEGER
	}

snMSTrunkPortIndex OBJECT-TYPE
	SYNTAX  Integer32
	MAX-ACCESS  read-only
	STATUS  current
	DESCRIPTION
		"The primary port of a trunk group. For module with Gig ports,
		primary port is port 1, 3, 5, 7. For module with 10/100 ports,
		primary port is port 1, 5, 9, 13, 17, 21."
	::= { snMSTrunkEntry 1 }


snMSTrunkPortList OBJECT-TYPE
	SYNTAX  OCTET STRING
	MAX-ACCESS  read-write
	STATUS  current
	DESCRIPTION
		"A list of port indices which are the port membership
		of a trunk group. Each port index is a 16-bit integer
		in big endian order. The first port index must be the
		primary port index."
	::= { snMSTrunkEntry 2 }


snMSTrunkType OBJECT-TYPE
	SYNTAX  INTEGER {
		switch(1),
		server(2)
		}
	MAX-ACCESS  read-write
	STATUS  current
	DESCRIPTION
		"The trunk connection type which specifies what
		device the trunk ports are connected to."
	::= { snMSTrunkEntry 3 }


snMSTrunkRowStatus OBJECT-TYPE
	SYNTAX  INTEGER {
		invalid(1),
		valid(2),
		delete(3),
		create(4),
		modify(5)
		}
	MAX-ACCESS  read-write
	STATUS  current
	DESCRIPTION
		"To create or delete a table entry."
	::= { snMSTrunkEntry 4 }

-- Multi-slot Trunk Port Configuration Group


snMSTrunkIfTable OBJECT-TYPE
	SYNTAX  SEQUENCE OF SnMSTrunkIfEntry
	MAX-ACCESS  not-accessible
	STATUS  current
	DESCRIPTION
		"A table contains the configuration of port members of
		multi-slot trunk groups."
	::= { snTrunkInfo 3 }

snMSTrunkIfEntry OBJECT-TYPE
	SYNTAX  SnMSTrunkIfEntry
	MAX-ACCESS  not-accessible
	STATUS  current
	DESCRIPTION
		"An entry of the snMSTrunkIfTable."
	INDEX {snMSTrunkIfIndex}
	::= { snMSTrunkIfTable 1 }

SnMSTrunkIfEntry ::= SEQUENCE {
	snMSTrunkIfIndex
		Integer32,
	snMSTrunkIfList
		OCTET STRING,
	snMSTrunkIfType
		INTEGER,
	snMSTrunkIfRowStatus
		INTEGER
	}

snMSTrunkIfIndex OBJECT-TYPE
	SYNTAX  Integer32
	MAX-ACCESS  read-only
	STATUS  current
	DESCRIPTION
		"The primary port(IfIndex) of a trunk group. For module with Gig ports,
		primary port is port 1, 3, 5, 7. For module with 10/100 ports,
		primary port is port 1, 5, 9, 13, 17, 21."
	::= { snMSTrunkIfEntry 1 }

snMSTrunkIfList OBJECT-TYPE
	SYNTAX  OCTET STRING
	MAX-ACCESS  read-write
	STATUS  current
	DESCRIPTION
		"A list of interface indices which are the port membership
		of a trunk group. Each interface index is a 16-bit integer
		in big endian order. The first interface/port index must be
		the primary port(ifIndex) index."
	::= { snMSTrunkIfEntry 2 }

snMSTrunkIfType OBJECT-TYPE
	SYNTAX  INTEGER {
		switch(1),
		server(2)
		}
	MAX-ACCESS  read-write
	STATUS  current
	DESCRIPTION
		"The trunk connection type which specifies what
		device the trunk ports are connected to."
	::= { snMSTrunkIfEntry 3 }

snMSTrunkIfRowStatus OBJECT-TYPE
	SYNTAX  INTEGER {
		invalid(1),
		valid(2),
		delete(3),
		create(4),
		modify(5)
		}
	MAX-ACCESS  read-write
	STATUS  current
	DESCRIPTION
		"To create or delete a table entry."
	::= { snMSTrunkIfEntry 4 }



-- Switch Configuration Summary Group


snSwSummaryMode OBJECT-TYPE
	SYNTAX  INTEGER {
		disabled(0),
		enabled(1)
		}
	MAX-ACCESS  read-write
	STATUS  current
	DESCRIPTION
		"The Switch Group Configuration Summary is configured 
		 either enabled or disabled and the
		 default is disabled mode.
		 enabled(1)...........activate Switch Configuration Summary.
		 disabled(0)..........no Switch Configuration Summary."
	::= { snSwSummary 1 }


--- DHCP Gateway List Table


snDhcpGatewayListTable OBJECT-TYPE
	SYNTAX  SEQUENCE OF SnDhcpGatewayListEntry
	MAX-ACCESS  not-accessible
	STATUS  current
	DESCRIPTION
		"A table of DHCP gateway list of addresses."
	::= { snDhcpGatewayListInfo 1 }

snDhcpGatewayListEntry             OBJECT-TYPE
	SYNTAX  SnDhcpGatewayListEntry
	MAX-ACCESS  not-accessible
	STATUS  current
	DESCRIPTION
		"An entry in the IP Port Address table."
	INDEX   { snDhcpGatewayListId }
	::= { snDhcpGatewayListTable 1 }

SnDhcpGatewayListEntry ::= SEQUENCE {
	snDhcpGatewayListId
		INTEGER,
	snDhcpGatewayListAddrList
		OCTET STRING,
	snDhcpGatewayListRowStatus
		INTEGER
	}


snDhcpGatewayListId                 OBJECT-TYPE
	SYNTAX  INTEGER (1..32)
	MAX-ACCESS  read-only
	STATUS  current
	DESCRIPTION
		"The ID for a DHCP gateway list entry."
	::= { snDhcpGatewayListEntry 1 }

snDhcpGatewayListAddrList          OBJECT-TYPE
	SYNTAX	OCTET STRING (SIZE(4..32))
	MAX-ACCESS  read-write
	STATUS  current
	DESCRIPTION
		"The DHCP gateway address list for each DHCP gateway list ID.
		This list contains 1 to 8 IP addresses represented by octet string."
	::= { snDhcpGatewayListEntry 2 }

snDhcpGatewayListRowStatus OBJECT-TYPE
	SYNTAX  INTEGER {
		other(1),
		valid(2),
		delete(3),
		create(4)
		}
	MAX-ACCESS  read-write
	STATUS  current
	DESCRIPTION
		"This object is used to create and
		delete row in the table and control
		if they are used. The values
		that can be written are:
		  delete(3)...deletes the row
		  create(4)...creates a new row or modifies an exsisting row

		If the row exists, then a SET with
		value of create(4) returns error
		'badValue'. Deleted rows go away
		immediately. The following values
		can be returned on reads:
		  noSuch(0)...no such row
		  other(1)....some other case
		  valid(2)....the row exists and is valid"
	::= { snDhcpGatewayListEntry 3 }


-- DNS MIB Group 
-- snDnsDomainName and snDnsGatewayIpAddrList are deprecated, replaced 
-- by fdryDnsDomainNameTable and fdryDnsServerAddressTable respectively.
-- The new table "fdryDnsDomainNameTable" and "fdryDnsServerAddressTable" 
-- combines Ipv4 and Ipv6 DNS Servers configuration

snDnsDomainName OBJECT-TYPE
	SYNTAX	DisplayString (SIZE(0..80))
	MAX-ACCESS	read-write
	STATUS	current
	DESCRIPTION
		"DNS Domain Name string."
	::= { snDnsInfo 1 }

snDnsGatewayIpAddrList OBJECT-TYPE
	SYNTAX	OCTET STRING (SIZE(16))
	MAX-ACCESS  read-write
	STATUS  current
	DESCRIPTION
		"The DNS Gateway IP address list. This list contains 4 
		IP addresses represented by octet string."
	::= { snDnsInfo 2 }

-- MAC filter table

snMacFilterTable       OBJECT-TYPE
	SYNTAX  SEQUENCE OF SnMacFilterEntry
	MAX-ACCESS  not-accessible
	STATUS  current
	DESCRIPTION
		"MAC filter table."
	::= { snMacFilter 1 }

snMacFilterEntry       OBJECT-TYPE
	SYNTAX  SnMacFilterEntry
	MAX-ACCESS  not-accessible
	STATUS  current
	DESCRIPTION
		"An entry in the MAC filter table."
	INDEX   { snMacFilterIndex }
	::= { snMacFilterTable 1 }

SnMacFilterEntry ::= SEQUENCE {
	snMacFilterIndex
		Integer32,
	snMacFilterAction              
		INTEGER,
	snMacFilterSourceMac
		MacAddress,
	snMacFilterSourceMask
		MacAddress,
	snMacFilterDestMac
		MacAddress,
	snMacFilterDestMask
		MacAddress,
	snMacFilterOperator
		INTEGER,
	snMacFilterFrameType
		INTEGER,
	snMacFilterFrameTypeNum
		INTEGER,
	snMacFilterRowStatus
		INTEGER
	}

snMacFilterIndex       OBJECT-TYPE
	SYNTAX  Integer32
	MAX-ACCESS  read-only
	STATUS  current
	DESCRIPTION
		"The table index for a filter entry."
	::= { snMacFilterEntry 1 }

snMacFilterAction      OBJECT-TYPE
	SYNTAX  INTEGER { deny(0), permit(1) } 
	MAX-ACCESS  read-write
	STATUS  current
	DESCRIPTION
		"Action to take if the Mac packet match
		with this filter."
	::= { snMacFilterEntry 2 }

snMacFilterSourceMac    OBJECT-TYPE
	SYNTAX  MacAddress
	MAX-ACCESS  read-write
	STATUS  current
	DESCRIPTION
		"Source MAC address."
	::= { snMacFilterEntry 3 }

snMacFilterSourceMask  OBJECT-TYPE
	SYNTAX  MacAddress
	MAX-ACCESS  read-write
	STATUS  current
	DESCRIPTION
		"Source MAC subnet mask."
	::= { snMacFilterEntry 4 }

snMacFilterDestMac      OBJECT-TYPE
	SYNTAX  MacAddress
	MAX-ACCESS  read-write
	STATUS  current
	DESCRIPTION
		"Destination MAC address."
	::= { snMacFilterEntry 5 }

snMacFilterDestMask    OBJECT-TYPE
	SYNTAX  MacAddress
	MAX-ACCESS  read-write
	STATUS  current
	DESCRIPTION
		"Destination MAC subnet mask."
	::= { snMacFilterEntry 6 }

snMacFilterOperator    OBJECT-TYPE
	SYNTAX  INTEGER { equal(0), notEqual(1), less(2), greater(3) }
	MAX-ACCESS  read-write
	STATUS  current
	DESCRIPTION
		"Type of comparison to perform."
	::= { snMacFilterEntry 7 }

snMacFilterFrameType     OBJECT-TYPE
	SYNTAX  INTEGER{ notUsed(0), ethernet(1), llc(2), snap(3) }
	MAX-ACCESS  read-write
	STATUS  current
	DESCRIPTION
		"Frame Type: ethernet-type, LLC and SNAP types"
	::= { snMacFilterEntry 8 }

snMacFilterFrameTypeNum     OBJECT-TYPE
	SYNTAX  INTEGER(0..65535)
	MAX-ACCESS  read-write
	STATUS  current
	DESCRIPTION
		"Frame Type Number. 0 means NA"
	::= { snMacFilterEntry 9 }

snMacFilterRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snMacFilterEntry 10 }

-- MAC Filter Port access table

snMacFilterPortAccessTable           OBJECT-TYPE
	SYNTAX  SEQUENCE OF SnMacFilterPortAccessEntry
	MAX-ACCESS  not-accessible
	STATUS  deprecated
	DESCRIPTION
		"MAC Filter port access table."
	::= { snMacFilter 2 }

snMacFilterPortAccessEntry           OBJECT-TYPE
	SYNTAX  SnMacFilterPortAccessEntry
	MAX-ACCESS  not-accessible
	STATUS  deprecated
	DESCRIPTION
		"An entry in the MAC Filter Port access table."
	INDEX   { snMacFilterPortAccessPortIndex }
	::= { snMacFilterPortAccessTable 1 }

SnMacFilterPortAccessEntry ::= SEQUENCE {
	snMacFilterPortAccessPortIndex
		INTEGER,
	snMacFilterPortAccessFilters
		OCTET STRING,
	snMacFilterPortAccessRowStatus
		INTEGER
	}

snMacFilterPortAccessPortIndex               OBJECT-TYPE
	SYNTAX  INTEGER (1..3900)
	MAX-ACCESS  read-only
	STATUS  deprecated
	DESCRIPTION
		"The port index.
		For FastIron/NetIron products, port index value is from 1 to 42
		For BigIron products, port index is an encoded number:
		The bit 0 to bit 7: port number.
		The bit 8 to bit 11: slot number.
		For virtual router interface, slot number is 15,
		port number is the virtual router port from 1 to 60.
		Therefore, port index value for BigIron is from 257 to 3900."
	::= { snMacFilterPortAccessEntry 1 }

snMacFilterPortAccessFilters                 OBJECT-TYPE
	SYNTAX  OCTET STRING
	MAX-ACCESS  read-write
	STATUS  deprecated
	DESCRIPTION
		"1st octet correspond to 1st filter 
		number and so on."
	::= { snMacFilterPortAccessEntry 2 }

snMacFilterPortAccessRowStatus       OBJECT-TYPE
	SYNTAX	 INTEGER {
		invalid(1),
		valid(2),
		delete(3),
		create(4)
	}
	MAX-ACCESS	 read-write
	STATUS   deprecated
	DESCRIPTION
	"This object is used to create and
	 delete row in the table and control
	 if they are used. The values
	 that can be written are:
	 delete(3)...deletes the row
	 create(4)...creates a new row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snMacFilterPortAccessEntry 3 }

-- MAC Filter Port access table

snMacFilterIfAccessTable           OBJECT-TYPE
	SYNTAX  SEQUENCE OF SnMacFilterIfAccessEntry
	MAX-ACCESS  not-accessible
	STATUS  current
	DESCRIPTION
		"MAC Filter port access table."
	::= { snMacFilter 3 }

snMacFilterIfAccessEntry           OBJECT-TYPE
	SYNTAX  SnMacFilterIfAccessEntry
	MAX-ACCESS  not-accessible
	STATUS  current
	DESCRIPTION
		"An entry in the MAC Filter Port access table."
	INDEX   { snMacFilterIfAccessPortIndex }
	::= { snMacFilterIfAccessTable 1 }

SnMacFilterIfAccessEntry ::= SEQUENCE {
	snMacFilterIfAccessPortIndex
		InterfaceIndex,
	snMacFilterIfAccessFilters
		OCTET STRING,
	snMacFilterIfAccessRowStatus
		INTEGER
	}

snMacFilterIfAccessPortIndex               OBJECT-TYPE
	SYNTAX  InterfaceIndex
	MAX-ACCESS  read-only
	STATUS  current
	DESCRIPTION
		"The port/interface index."
	::= { snMacFilterIfAccessEntry 1 }

snMacFilterIfAccessFilters                 OBJECT-TYPE
	SYNTAX  OCTET STRING
	MAX-ACCESS  read-write
	STATUS  current
	DESCRIPTION
		"1st octet correspond to 1st filter number and so on."
	::= { snMacFilterIfAccessEntry 2 }

snMacFilterIfAccessRowStatus       OBJECT-TYPE
	SYNTAX	INTEGER {
				invalid(1),
				valid(2),
				delete(3),
				create(4)
			}
	MAX-ACCESS	 read-write
	STATUS	 current
	DESCRIPTION
	"This object is used to create and
	 delete row in the table and control
	 if they are used. The values
	 that can be written are:
	 delete(3)...deletes the row
	 create(4)...creates a new row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snMacFilterIfAccessEntry 3 }

-- NTP general group

snNTPGeneral               OBJECT IDENTIFIER ::= { snNTP 1 }

snNTPPollInterval          OBJECT-TYPE
	SYNTAX  INTEGER (1..65535)
	MAX-ACCESS  read-write
	STATUS  current
	DESCRIPTION
		"Interval specifies how often to poll the NTP server.
		Each unit is one second."
	DEFVAL  { 1800 }
	::= { snNTPGeneral 1 }

snNTPTimeZone              OBJECT-TYPE
	SYNTAX  INTEGER {
				alaska(0),
				aleutian(1),
				arizona(2),
				central(3),
				eastIndiana(4),
				eastern(5),
				hawaii(6),
				michigan(7),
				mountain(8),
				pacific(9),
				samoa(10),
				gmtPlus1200(11),
				gmtPlus1100(12),
				gmtPlus1000(13),
				gmtPlus0900(14),
				gmtPlus0800(15),
				gmtPlus0700(16),
				gmtPlus0600(17),
				gmtPlus0500(18),
				gmtPlus0400(19),
				gmtPlus0300(20),
				gmtPlus0200(21),
				gmtPlus0100(22),
				gmt(23),
				gmtMinus0100(24),
				gmtMinus0200(25),
				gmtMinus0300(26),
				gmtMinus0400(27),
				gmtMinus0500(28),
				gmtMinus0600(29),
				gmtMinus0700(30),
				gmtMinus0800(31),
				gmtMinus0900(32),
				gmtMinus1000(33),
				gmtMinus1100(34),
				gmtMinus1200(35),
				gmtPlus1130(36),
				gmtPlus1030(37),
				gmtPlus0930(38),
				gmtPlus0630(39),
				gmtPlus0530(40),
				gmtPlus0430(41),
				gmtPlus0330(42),
				gmtMinus0330(43),
				gmtMinus0830(44),
				gmtMinus0930(45)	
			}				
	MAX-ACCESS  read-write
	STATUS  current
	DESCRIPTION
		"Time zone."
	DEFVAL  { gmt }
	::= { snNTPGeneral 2 }

snNTPSummerTimeEnable      OBJECT-TYPE
	SYNTAX  INTEGER { disabled(0), enabled (1) }
	MAX-ACCESS  read-write
	STATUS  current
	DESCRIPTION
		"Enable/Disable daylight saving time. This enables daylight
		saving time for time/date starting 02:00:00 of first Sunday
		in April and ending 02:00:00 of last Sunday in October every
		year."
	DEFVAL  { disabled }
	::= { snNTPGeneral 3 }

snNTPSystemClock           OBJECT-TYPE
	SYNTAX  OCTET STRING (SIZE (7))
	MAX-ACCESS  read-write
	STATUS  current
	DESCRIPTION
		"System clock, in the following format:
		octet   0: seconds after the minute [0-60]
		octet   1: minutes after the hour [0-59]
		octet   2: hours since midnight [0-23]
		octet   3: day of the month [1-31]
		octet   4: months since January [0-11]
		octet   5: years since 1900
		octet   6: days since Sunday [0-6]
		Setting this object requires valid value in octets 0 to 5,
		and zero in octet 6. System clock can be disabled by setting
		zero to all octets."
	::= { snNTPGeneral 4 }

snNTPSync                  OBJECT-TYPE
	SYNTAX  INTEGER { other(1), synchronize(2) }
	MAX-ACCESS  read-write
	STATUS  current
	DESCRIPTION
		"Initiate time synchronization to the NTP servers.
		For set operation, only 'synchronize(2)' is accepted.
		For get operation, always return 'other(1)'."
	::= { snNTPGeneral 5 }

-- NTP server table
-- snNTPServerTable is deprecated, replaced by fdrySntpServerTable.
-- The new table "fdrySntpServerTable" combines Ipv4 and Ipv6 Simple Network Time Protocol server configuration.

snNTPServerTable           OBJECT-TYPE
	SYNTAX  SEQUENCE OF SnNTPServerEntry
	MAX-ACCESS  not-accessible
	STATUS  current
	DESCRIPTION
		"NTP (Network Time Protocol) server table."
	::= { snNTP 2 }

snNTPServerEntry           OBJECT-TYPE
	SYNTAX  SnNTPServerEntry
	MAX-ACCESS  not-accessible
	STATUS  current
	DESCRIPTION
		"An entry in the NTP server table."
	INDEX   { snNTPServerIp }
	::= { snNTPServerTable 1 }

SnNTPServerEntry ::= SEQUENCE {
	snNTPServerIp
		IpAddress,
	snNTPServerVersion
		INTEGER,
	snNTPServerRowStatus
		INTEGER
	}

snNTPServerIp              OBJECT-TYPE
	SYNTAX  IpAddress
	MAX-ACCESS  read-only
	STATUS  current
	DESCRIPTION
		"NTP server IP address."
	::= { snNTPServerEntry 1 }

snNTPServerVersion         OBJECT-TYPE
	SYNTAX  INTEGER (1..4)
	MAX-ACCESS  read-write
	STATUS  current
	DESCRIPTION
		"NTP server version."
	DEFVAL  { 1 }
	::= { snNTPServerEntry 2 }

snNTPServerRowStatus       OBJECT-TYPE
	SYNTAX	INTEGER {
		other(1),
		valid(2),
		delete(3),
		create(4) }
	MAX-ACCESS  read-write
	STATUS  current
	DESCRIPTION
		"To create or delete a NTP server table entry."
	::= { snNTPServerEntry 3 }

-- Radius general group

snRadiusGeneral            OBJECT IDENTIFIER ::= { snRadius 1 }

snRadiusSNMPAccess         OBJECT-TYPE
	SYNTAX  INTEGER { disabled(0), enabled(1) }
	MAX-ACCESS  read-only
	STATUS  current
	DESCRIPTION
		"Indicate whether Radius group MIB obejcts can be
		accessed by SNMP manager. If value is disabled,
		all Radius group MIB objects return 'general error'."
	DEFVAL  { disabled }
	::= { snRadiusGeneral 1 }

snRadiusEnableTelnetAuth   OBJECT-TYPE
	SYNTAX  INTEGER { disabled(0), enabled(1) }
	MAX-ACCESS  read-write
	STATUS  current
	DESCRIPTION
		"Enable/Disable telnet authentication specified
		by 'snRadiusLoginMethod'."
	DEFVAL  { disabled }
	::= { snRadiusGeneral 2 }

snRadiusRetransmit         OBJECT-TYPE
	SYNTAX  INTEGER (0..5)
	MAX-ACCESS  read-write
	STATUS  current
	DESCRIPTION
		"The number of authentication query retransmissions
		to the Radius server."
	DEFVAL  { 3 }
	::= { snRadiusGeneral 3 }

snRadiusTimeOut            OBJECT-TYPE
	SYNTAX  INTEGER (1..60)
	MAX-ACCESS  read-write
	STATUS  current
	DESCRIPTION
		"Interval specifies how long to wait for authentication
		reply from the Radius server, each unit is one second."
	DEFVAL  { 3 }
	::= { snRadiusGeneral 4 }

snRadiusDeadTime           OBJECT-TYPE
	SYNTAX  INTEGER (1..5)
	MAX-ACCESS  read-write
	STATUS  current
	DESCRIPTION
		"Interval specifies Radius server dead time,
		each unit is one minute."
	DEFVAL  { 3 }
	::= { snRadiusGeneral 5 }

snRadiusKey                OBJECT-TYPE
	SYNTAX  DisplayString (SIZE(0..32))
	MAX-ACCESS  read-write
	STATUS  current
	DESCRIPTION
		"Authentication key displayed as encrypted text.
		Write operation can only be done if the SET request uses
		SNMPv3 with data encrypted using privacy key."
	::= { snRadiusGeneral 6 }

snRadiusLoginMethod        OBJECT-TYPE
	SYNTAX  OCTET STRING (SIZE(0..7))
	MAX-ACCESS  read-write
	STATUS  current
	DESCRIPTION
		"A sequence of authentication methods. Each octet represents
		a method to authenticate the user login process. Each octet
		has the following enumeration value:
		  enable(1) - authenticate by command line interface
					  enable password
		  radius(2) - authenticate by requesting radius server
		  local(3) - authenticate by local user account table
		  line(4) - authenticate by telnet password
		  tacplus(5) - authenticate by requesting tacplus server
		  none(6) - do not authenticate
		  tacacs(7) - authenticate by requesting tacacs server
		Setting a zero length octet string invalidates all
		previous authentication methods."
	::= { snRadiusGeneral 7 }

snRadiusEnableMethod       OBJECT-TYPE
	SYNTAX  OCTET STRING (SIZE(0..7))
	MAX-ACCESS  read-write
	STATUS  current
	DESCRIPTION
		"A sequence of authentication methods. Each octet represents
		a method to authenticate the user entering priviledge mode
		of the command line interface. Each octet has the following
		enumeration value:
		  enable(1) - authenticate by command line interface
					  enable password
		  radius(2) - authenticate by requesting radius server
		  local(3) - authenticate by local user account table
		  line(4) - authenticate by telnet password
		  tacplus(5) - authenticate by requesting tacplus server
		  none(6) - do not authenticate
		  tacacs(7) - authenticate by requesting tacacs server
		Setting a zero length octet string invalidates all
		previous authentication methods."
	::= { snRadiusGeneral 8 }

snRadiusWebServerMethod    OBJECT-TYPE
	SYNTAX  OCTET STRING (SIZE(0..7))
	MAX-ACCESS  read-write
	STATUS  current
	DESCRIPTION
		"A sequence of authentication methods. Each octet represents
		a method to authenticate the user accessing the web-server.
		Each octet has the following enumeration value:
		  enable(1) - authenticate by command line interface
					  enable password
		  radius(2) - authenticate by requesting radius server
		  local(3) - authenticate by local user account table
		  line(4) - authenticate by telnet password
		  tacplus(5) - authenticate by requesting tacplus server
		  none(6) - do not authenticate
		  tacacs(7) - authenticate by requesting tacacs server
		Setting a zero length octet string invalidates all
		previous authentication methods."
	::= { snRadiusGeneral 9 }

snRadiusSNMPServerMethod   OBJECT-TYPE
	SYNTAX  OCTET STRING (SIZE(0..7))
	MAX-ACCESS  read-write
	STATUS  current
	DESCRIPTION
		"A sequence of authentication methods. Each octet represents
		a method to authenticate the user accessing the snmp-server.
		Each octet has the following enumeration value:
		  enable(1) - authenticate by command line interface
					  enable password
		  radius(2) - authenticate by requesting radius server
		  local(3) - authenticate by local user account table
		  line(4) - authenticate by telnet password
		  tacplus(5) - authenticate by requesting tacplus server
		  none(6) - do not authenticate
		  tacacs(7) - authenticate by requesting tacacs server
		Setting a zero length octet string invalidates all
		previous authentication methods."
	::= { snRadiusGeneral 10 }

-- Radius server table
-- snRadiusServerTable is deprecated, replaced by fdryRadiusServerTable
-- The new table "fdryRadiusServerTable" combines Ipv4 and Ipv6 Radius Authentication Servers configuration

snRadiusServerTable        OBJECT-TYPE
	SYNTAX  SEQUENCE OF SnRadiusServerEntry
	MAX-ACCESS  not-accessible
	STATUS  current
	DESCRIPTION
		"Radius server table."
	::= { snRadius 2 }

snRadiusServerEntry        OBJECT-TYPE
	SYNTAX  SnRadiusServerEntry
	MAX-ACCESS  not-accessible
	STATUS  current
	DESCRIPTION
		"An entry in the Radius server table."
	INDEX   { snRadiusServerIp }
	::= { snRadiusServerTable 1 }

SnRadiusServerEntry ::= SEQUENCE {
	snRadiusServerIp
		IpAddress,
	snRadiusServerAuthPort
		Integer32,
	snRadiusServerAcctPort
		Integer32,
	snRadiusServerRowStatus
		INTEGER,
	snRadiusServerRowKey
		DisplayString,
	snRadiusServerUsage
		INTEGER
	}

snRadiusServerIp           OBJECT-TYPE
	SYNTAX  IpAddress
	MAX-ACCESS  read-only
	STATUS  current
	DESCRIPTION
		"Radius server IP address."
	::= { snRadiusServerEntry 1 }

snRadiusServerAuthPort     OBJECT-TYPE
	SYNTAX  Integer32
	MAX-ACCESS  read-write
	STATUS  current
	DESCRIPTION
		"Authentication UDP port number."
	DEFVAL  { 1812 }
	::= { snRadiusServerEntry 2 }

snRadiusServerAcctPort     OBJECT-TYPE
	SYNTAX  Integer32
	MAX-ACCESS  read-write
	STATUS  current
	DESCRIPTION
		"Account UDP port number."
	DEFVAL  { 1813 }
	::= { snRadiusServerEntry 3 }

snRadiusServerRowStatus    OBJECT-TYPE
	SYNTAX	INTEGER {
		other(1),
		valid(2),
		delete(3),
		create(4) }
	MAX-ACCESS  read-write
	STATUS  current
	DESCRIPTION
		"To create or delete a Radius server table entry."
	::= { snRadiusServerEntry 4 }

snRadiusServerRowKey       OBJECT-TYPE
	SYNTAX  DisplayString (SIZE(0..32))
	MAX-ACCESS  read-write
	STATUS  current
	DESCRIPTION
		"Authentication key displayed as encrypted text."
	::= { snRadiusServerEntry 5 }

snRadiusServerUsage    OBJECT-TYPE
	SYNTAX	INTEGER {
		default(1),
		authenticationOnly(2),
		authorizationOnly(3),
		accountingOnly(4) }
	MAX-ACCESS  read-write
	STATUS  current
	DESCRIPTION
		"To allow this server to be dedicated for a particular AAA activity."
	::= { snRadiusServerEntry 6 }

--- Tacacs General MIBs

snTacacsGeneral            OBJECT IDENTIFIER ::= { snTacacs 1 }

snTacacsRetransmit         OBJECT-TYPE
	SYNTAX  INTEGER (0..5)
	MAX-ACCESS  read-write
	STATUS  current
	DESCRIPTION
		"The number of authentication query retransmissions
		to the Tacacs server."
	DEFVAL  { 3 }
	::= { snTacacsGeneral 1 }

snTacacsTimeOut            OBJECT-TYPE
	SYNTAX  INTEGER (1..15)
	MAX-ACCESS  read-write
	STATUS  current
	DESCRIPTION
		"Interval specifies how long to wait for authentication
		reply from the Tacacs server, each unit is one second."
	DEFVAL  { 3 }
	::= { snTacacsGeneral 2 }

snTacacsDeadTime           OBJECT-TYPE
	SYNTAX  INTEGER (1..5)
	MAX-ACCESS  read-write
	STATUS  current
	DESCRIPTION
		"Interval specifies Tacacs server dead time,
		each unit is one minute."
	DEFVAL  { 3 }
	::= { snTacacsGeneral 3 }

snTacacsKey                OBJECT-TYPE
	SYNTAX  DisplayString (SIZE(0..32))
	MAX-ACCESS  read-write
	STATUS  current
	DESCRIPTION
		"Authentication key displayed as encrypted text.
		Write operation can only be done if the SET request uses
		SNMPv3 with data encrypted using privacy key."
	::= { snTacacsGeneral 4 }

snTacacsSNMPAccess         OBJECT-TYPE
	SYNTAX  INTEGER { disabled(0), enabled(1) }
	MAX-ACCESS  read-only
	STATUS  current
	DESCRIPTION
		"Indicate whether Tacacs group MIB obejcts can be
		accessed by SNMP manager. If value is disabled,
		all Tacacs group MIB objects return 'general error'."
	DEFVAL  { disabled }
	::= { snTacacsGeneral 5 }

-- Tacacs server table
-- snTacacsServerTable is deprecated, replaced by fdryTacacsServerTable
-- The new table "fdryTacacsServerTable" combines Ipv4 and Ipv6 Tacacs Authentication Servers configuration

snTacacsServerTable        OBJECT-TYPE
	SYNTAX  SEQUENCE OF SnTacacsServerEntry
	MAX-ACCESS  not-accessible
	STATUS  current
	DESCRIPTION
		"Tacacs server table."
	::= { snTacacs 2 }

snTacacsServerEntry        OBJECT-TYPE
	SYNTAX  SnTacacsServerEntry
	MAX-ACCESS  not-accessible
	STATUS  current
	DESCRIPTION
		"An entry in the Tacacs server table."
	INDEX   { snTacacsServerIp }
	::= { snTacacsServerTable 1 }

SnTacacsServerEntry ::= SEQUENCE {
	snTacacsServerIp
		IpAddress,
	snTacacsServerAuthPort
		Integer32,
	snTacacsServerRowStatus
		INTEGER,
	snTacacsServerRowKey
		DisplayString,
	snTacacsServerUsage
		INTEGER
	}

snTacacsServerIp           OBJECT-TYPE
	SYNTAX  IpAddress
	MAX-ACCESS  read-only
	STATUS  current
	DESCRIPTION
		"Tacacs server IP address."
	::= { snTacacsServerEntry 1 }

snTacacsServerAuthPort     OBJECT-TYPE
	SYNTAX  Integer32
	MAX-ACCESS  read-write
	STATUS  current
	DESCRIPTION
		"Authentication UDP port number."
	DEFVAL  { 49 }
	::= { snTacacsServerEntry 2 }

snTacacsServerRowStatus    OBJECT-TYPE
	SYNTAX	INTEGER {
		other(1),
		valid(2),
		delete(3),
		create(4) }
	MAX-ACCESS  read-write
	STATUS  current
	DESCRIPTION
		"To create or delete a Tacacs server table entry."
	::= { snTacacsServerEntry 3 }

snTacacsServerRowKey       OBJECT-TYPE
	SYNTAX  DisplayString (SIZE(0..32))
	MAX-ACCESS  read-write
	STATUS  current
	DESCRIPTION
		"Authentication key displayed as encrypted text.
		Write operation can only be done if the SET request uses
		SNMPv3 with data encrypted using privacy key."
	::= { snTacacsServerEntry 4 }

snTacacsServerUsage    OBJECT-TYPE
	SYNTAX	INTEGER {
		default(1),
		authenticationOnly(2),
		authorizationOnly(3),
		accountingOnly(4) }
	MAX-ACCESS  read-write
	STATUS  current
	DESCRIPTION
		"To allow this server to be dedicated for a particular AAA activity."
	::= { snTacacsServerEntry 5 }

-- QOS Profile Group

snQosProfileTable OBJECT-TYPE
	SYNTAX  SEQUENCE OF SnQosProfileEntry
	MAX-ACCESS  not-accessible
	STATUS  current
	DESCRIPTION
		"A table contains the configuration of qos profile 
		 groups."
	::= { snQos 1 }

snQosProfileEntry OBJECT-TYPE
	SYNTAX  SnQosProfileEntry
	MAX-ACCESS  not-accessible
	STATUS  current
	DESCRIPTION
		"An entry of the snQosProfileTable."
	INDEX {snQosProfileIndex}
	::= { snQosProfileTable 1 }

SnQosProfileEntry ::= SEQUENCE {
	snQosProfileIndex
		INTEGER,
	snQosProfileName
		DisplayString,
	snQosProfileRequestedBandwidth
		INTEGER,
	snQosProfileCalculatedBandwidth
		INTEGER
	}

snQosProfileIndex OBJECT-TYPE
	SYNTAX  INTEGER (1..8)
	MAX-ACCESS  read-only
	STATUS  current
	DESCRIPTION
		"The table index of QOS Profile." 
	::= { snQosProfileEntry 1 }

snQosProfileName OBJECT-TYPE
	SYNTAX	DisplayString (SIZE(0..32))
	MAX-ACCESS	read-write
	STATUS	current
	DESCRIPTION
		"Qos Profile Name string."
	::= { snQosProfileEntry 2 }

snQosProfileRequestedBandwidth OBJECT-TYPE
	SYNTAX  INTEGER (0..100)
	MAX-ACCESS  read-write
	STATUS  current
	DESCRIPTION
		"Qos Profile Requested Bandwidth."
	::= { snQosProfileEntry 3 }

snQosProfileCalculatedBandwidth OBJECT-TYPE
	SYNTAX  INTEGER (0..100)
	MAX-ACCESS  read-only
	STATUS  current
	DESCRIPTION
		"Qos Profile Calculated Bandwidth."
	::= { snQosProfileEntry 4 }

-- QOS Bind Group

snQosBindTable OBJECT-TYPE
	SYNTAX  SEQUENCE OF SnQosBindEntry
	MAX-ACCESS  not-accessible
	STATUS  current
	DESCRIPTION
		"A table contains the configuration of 802.1p to qos profile 
		 binding groups."
	::= { snQos 2 }

snQosBindEntry OBJECT-TYPE
	SYNTAX  SnQosBindEntry
	MAX-ACCESS  not-accessible
	STATUS  current
	DESCRIPTION
		"An entry of the snQosBindTable."
	INDEX {snQosBindIndex}
	::= { snQosBindTable 1 }

SnQosBindEntry ::= SEQUENCE {
	snQosBindIndex
		INTEGER,
	snQosBindPriority
		Integer32,
	snQosBindProfileIndex
		INTEGER
	}

snQosBindIndex OBJECT-TYPE
	SYNTAX  INTEGER (1..8)
	MAX-ACCESS  read-only
	STATUS  current
	DESCRIPTION
		"The table index of QOS Bind."
	::= { snQosBindEntry 1 }

snQosBindPriority OBJECT-TYPE
	SYNTAX  Integer32
	MAX-ACCESS  read-only
	STATUS  current
	DESCRIPTION
		 "QOS bind priority."
	::= { snQosBindEntry 2 }

snQosBindProfileIndex OBJECT-TYPE
	SYNTAX  INTEGER (1..8)
	MAX-ACCESS  read-write
	STATUS  current
	DESCRIPTION
		"QOS Bind Profile Index. This is pointer to the
		index of snQosProfile Table." 
	::= { snQosBindEntry 3 }

-- Denial of service attack

snDosAttack       OBJECT IDENTIFIER ::= { snQos 3 }
snDosAttackGlobal OBJECT IDENTIFIER ::= { snDosAttack 1 }

snDosAttackICMPDropCount OBJECT-TYPE
	SYNTAX  Counter32
	MAX-ACCESS  read-only
	STATUS  current
	DESCRIPTION
		"ICMP drop counter."
	::= { snDosAttackGlobal 1 }

snDosAttackICMPBlockCount OBJECT-TYPE
	SYNTAX  Counter32
	MAX-ACCESS  read-only
	STATUS  current
	DESCRIPTION
		"ICMP block counter."
	::= { snDosAttackGlobal 2 }

snDosAttackSYNDropCount OBJECT-TYPE
	SYNTAX  Counter32
	MAX-ACCESS  read-only
	STATUS  current
	DESCRIPTION
		"SYN drop counter."
	::= { snDosAttackGlobal 3 }

snDosAttackSYNBlockCount OBJECT-TYPE
	SYNTAX  Counter32
	MAX-ACCESS  read-only
	STATUS  current
	DESCRIPTION
		"SYN block counter."
	::= { snDosAttackGlobal 4 }

snDosAttackPortTable OBJECT-TYPE
	SYNTAX  SEQUENCE OF SnDosAttackPortEntry
	MAX-ACCESS  not-accessible
	STATUS  current
	DESCRIPTION
		"Denial of service attack port table."
	::= { snDosAttack 2 }

snDosAttackPortEntry OBJECT-TYPE
	SYNTAX  SnDosAttackPortEntry
	MAX-ACCESS  not-accessible
	STATUS  current
	DESCRIPTION
		"An entry of the denial of service attack port table."
	INDEX {snDosAttackPort}
	::= { snDosAttackPortTable 1 }

SnDosAttackPortEntry ::= SEQUENCE {
	snDosAttackPort
		Integer32,
	snDosAttackPortICMPDropCount
		Counter32,
	snDosAttackPortICMPBlockCount
		Counter32,
	snDosAttackPortSYNDropCount
		Counter32,
	snDosAttackPortSYNBlockCount
		Counter32
	}

snDosAttackPort OBJECT-TYPE
	SYNTAX  Integer32
	MAX-ACCESS  read-only
	STATUS  current
	DESCRIPTION
		"ifIndex value of a port." 
	::= { snDosAttackPortEntry 1 }

snDosAttackPortICMPDropCount OBJECT-TYPE
	SYNTAX  Counter32
	MAX-ACCESS  read-only
	STATUS  current
	DESCRIPTION
		"ICMP drop counter."
	::= { snDosAttackPortEntry 2 }

snDosAttackPortICMPBlockCount OBJECT-TYPE
	SYNTAX  Counter32
	MAX-ACCESS  read-only
	STATUS  current
	DESCRIPTION
		"ICMP block counter."
	::= { snDosAttackPortEntry 3 }

snDosAttackPortSYNDropCount OBJECT-TYPE
	SYNTAX  Counter32
	MAX-ACCESS  read-only
	STATUS  current
	DESCRIPTION
		"SYN drop counter."
	::= { snDosAttackPortEntry 4 }

snDosAttackPortSYNBlockCount OBJECT-TYPE
	SYNTAX  Counter32
	MAX-ACCESS  read-only
	STATUS  current
	DESCRIPTION
		"SYN block counter."
	::= { snDosAttackPortEntry 5 }

-- AAA Mib

snAuthentication			OBJECT IDENTIFIER ::= { snAAA 1 }
snAuthorization				OBJECT IDENTIFIER ::= { snAAA 2 }
snAccounting				OBJECT IDENTIFIER ::= { snAAA 3 }

snAuthorizationCommandMethods        OBJECT-TYPE
	SYNTAX  OCTET STRING (SIZE(0..3))
	MAX-ACCESS  read-write
	STATUS  current
	DESCRIPTION
		"A sequence of authorization methods. Each octet represents
		a method to authorize the user command. Each octet
		has the following value:
		  radius(2) - authorize by requesting radius server
		  tacplus(5) - authorize by requesting tacplus server
		  none(6) - skip authorization
		Setting a zero length octet string invalidates all
		previous authorization methods."
	::= { snAuthorization 1 }

snAuthorizationCommandLevel OBJECT-TYPE
	SYNTAX  INTEGER {
				 level0(0),
				 level4(4),
				 level5(5)
					}
	MAX-ACCESS  read-write
	STATUS  current
	DESCRIPTION
		"Commands, which are equal to and less than the specified
		command level here needs to be authorized. Possible enumeration
		values:
		0 - Privilege level 0
		4 - Privilege level 4
		5 - Privilege level 5." 
	::= { snAuthorization 2 }

snAuthorizationExec        OBJECT-TYPE
	SYNTAX  OCTET STRING (SIZE(0..3))
	MAX-ACCESS  read-write
	STATUS  current
	DESCRIPTION
		"A sequence of exec authorization methods. Each octet represents
		a method for telnet or SSH login authorization. Each octet
		has the following enumeration value:
		  radius(2) - send exec authorization request to radius server
		  tacplus(5) - send exec authorization request to tacplus server
		  none(6) - no exec authorization
		Setting a zero length octet string invalidates all
		authorization methods."
	::= { snAuthorization 3 }


snAccountingCommandMethods        OBJECT-TYPE
	SYNTAX  OCTET STRING (SIZE(0..3))
	MAX-ACCESS  read-write
	STATUS  current
	DESCRIPTION
		"A sequence of accounting methods. Each octet represents
		a method to account for the user command. Each octet
		has the following enumeration value:
		  radius(2) - send accounting info to radius server
		  tacplus(5) - send accounting info to tacplus server
		  none(6) - skip accounting
		Setting a zero length octet string invalidates all
		previous accounting methods."
	::= { snAccounting 1 }

snAccountingCommandLevel OBJECT-TYPE
	SYNTAX  INTEGER {
				 level0(0),
				 level4(4),
				 level5(5)
					}
	MAX-ACCESS  read-write
	STATUS  current
	DESCRIPTION
		"Commands, which are equal to and less than the specified
		command level here will be accounted. Possible enumeration
		values:
		level0 - Privilege level 0
		level4 - Privilege level 4
		level5 - Privilege level 5." 
	::= { snAccounting 2 }

snAccountingExec        OBJECT-TYPE
	SYNTAX  OCTET STRING (SIZE(0..3))
	MAX-ACCESS  read-write
	STATUS  current
	DESCRIPTION
		"A sequence of accounting methods. Each octet represents
		a method for telnet or SSH login accounting. Each octet
		has the following enumeration value:
		  radius(2) - send accounting info to radius server
		  tacplus(5) - send accounting info to tacplus server
		  none(6) - skip accounting
		Setting a zero length octet string invalidates all
		previous accounting methods."
	::= { snAccounting 3 }

snAccountingSystem        OBJECT-TYPE
	SYNTAX  OCTET STRING (SIZE(0..3))
	MAX-ACCESS  read-write
	STATUS  current
	DESCRIPTION
		"A sequence of accounting methods. Each octet represents
		a method to account for the system related events. Each octet
		has the following enumeration value:
		  radius(2) - send accounting info to radius server
		  tacplus(5) - send accounting info to tacplus server
		  none(6) - skip accounting
		Setting a zero length octet string invalidates all
		previous accounting methods."
	::= { snAccounting 4 }

-- NetFlow Mib

snNetFlowGlb	OBJECT IDENTIFIER ::= { snNetFlow 1 }

snNetFlowGblEnable OBJECT-TYPE
	SYNTAX	INTEGER { disabled(0), enabled(1) }
	MAX-ACCESS	read-write
	STATUS	current
	DESCRIPTION
		"Enable/disable NetFlow export operation."
	DEFVAL { disabled }
	::= { snNetFlowGlb 1 }

snNetFlowGblVersion OBJECT-TYPE
	SYNTAX	INTEGER { versionNotSet (0), version1 (1), version5 (5) }
	MAX-ACCESS	read-write
	STATUS	current
	DESCRIPTION
		"NetFlow export version."
	DEFVAL { version5 }
	::= { snNetFlowGlb 2 }

snNetFlowGblProtocolDisable OBJECT-TYPE
	SYNTAX   Integer32
	MAX-ACCESS	read-write
	STATUS	current
	DESCRIPTION
		"bit 0 - other, disable all protocols export except UDP and TCP
		 bit 1 - tcp, disable TCP protocol export
		 bit 2 - udp, disable UDP protocol export"
	DEFVAL { 0 }
	::= { snNetFlowGlb 3 }

snNetFlowGblActiveTimeout OBJECT-TYPE
	SYNTAX	Integer32
	MAX-ACCESS	read-write
	STATUS	current
	DESCRIPTION
		"Maximum time an active flow can be in the NetFlow cache (minutes: 1..60)"
	DEFVAL { 60 }
	::= { snNetFlowGlb 4 }

snNetFlowGblInactiveTimeout OBJECT-TYPE
	SYNTAX   Integer32
	MAX-ACCESS	read-write
	STATUS	current
	DESCRIPTION
		"Maximum time an inactive flow can be in the NetFlow cache (seconds: 10..600)"
	DEFVAL { 60 }
	::= { snNetFlowGlb 5 }


-- NetFlow Collector Table


snNetFlowCollectorTable OBJECT-TYPE
	SYNTAX	SEQUENCE OF SnNetFlowCollectorEntry
	MAX-ACCESS	not-accessible
	STATUS	current
	DESCRIPTION
		"A table of each NetFlow collector information."
	::= { snNetFlow 2 }

snNetFlowCollectorEntry OBJECT-TYPE
	SYNTAX	SnNetFlowCollectorEntry
	MAX-ACCESS	not-accessible
	STATUS	current
	DESCRIPTION
		"A row in the NetFlow collector table."
	INDEX	{ snNetFlowCollectorIndex }
	::= { snNetFlowCollectorTable 1 }

SnNetFlowCollectorEntry ::= SEQUENCE {
	snNetFlowCollectorIndex
		INTEGER,
	snNetFlowCollectorIp
		IpAddress,
	snNetFlowCollectorUdpPort
		Integer32,
	snNetFlowCollectorSourceInterface
		InterfaceIndex,
	snNetFlowCollectorRowStatus
		INTEGER
	}

snNetFlowCollectorIndex OBJECT-TYPE
	SYNTAX	INTEGER (1..10)
	MAX-ACCESS	read-only
	STATUS	current
	DESCRIPTION
		"The index to the NetFlow collector table."
	::= { snNetFlowCollectorEntry 1 }

snNetFlowCollectorIp OBJECT-TYPE
	SYNTAX	IpAddress
	MAX-ACCESS	read-write
	STATUS	current
	DESCRIPTION
		"The NetFlow collector ip address."
	::= { snNetFlowCollectorEntry 2 }

snNetFlowCollectorUdpPort OBJECT-TYPE
	SYNTAX   Integer32
	MAX-ACCESS	read-write
	STATUS	current
	DESCRIPTION
		"The NetFlow collector UDP port number."
	::= { snNetFlowCollectorEntry 3 }

snNetFlowCollectorSourceInterface OBJECT-TYPE
	SYNTAX	InterfaceIndex
	MAX-ACCESS	read-write
	STATUS	current
	DESCRIPTION
		"The ifIndex value to specify source port to
		 export NetFlow packet. Value 0 to indicate
		 default outgoing port."
	::= { snNetFlowCollectorEntry 4 }


snNetFlowCollectorRowStatus OBJECT-TYPE
	SYNTAX	INTEGER	{
		other(1),
		valid(2),
		delete(3),
		create(4) }
	MAX-ACCESS	read-write
	STATUS	current
	DESCRIPTION
		"To create or delete a NetFlow collector table entry."
	::= { snNetFlowCollectorEntry 5 }



-- NetFlow Aggregation Table


snNetFlowAggregationTable OBJECT-TYPE
	SYNTAX	SEQUENCE OF SnNetFlowAggregationEntry
	MAX-ACCESS	not-accessible
	STATUS	current
	DESCRIPTION
		"A table of each NetFlow aggregation scheme information."
	::= { snNetFlow 3 }

snNetFlowAggregationEntry OBJECT-TYPE
	SYNTAX	SnNetFlowAggregationEntry
	MAX-ACCESS	not-accessible
	STATUS	current
	DESCRIPTION
		"A row in the NetFlow Aggregation table."
	INDEX	{ snNetFlowAggregationIndex }
	::= { snNetFlowAggregationTable 1 }

SnNetFlowAggregationEntry ::= SEQUENCE {
	snNetFlowAggregationIndex
		INTEGER,
	snNetFlowAggregationIp
		IpAddress,
	snNetFlowAggregationUdpPort
		Integer32,
	snNetFlowAggregationSourceInterface
		InterfaceIndex,
	snNetFlowAggregationNumberOfCacheEntries
		Integer32,
	snNetFlowAggregationActiveTimeout
		Integer32,
	snNetFlowAggregationInactiveTimeout
		Integer32,
	snNetFlowAggregationEnable
		INTEGER,
	snNetFlowAggregationRowStatus
		INTEGER
	}

snNetFlowAggregationIndex OBJECT-TYPE
	SYNTAX	INTEGER { as (1), protocolPort (2), destPrefix (3),
					 sourcePrefix (4), prefix (5) }
	MAX-ACCESS	read-only
	STATUS	current
	DESCRIPTION
		"The Aggregation scheme ID"      
	::= { snNetFlowAggregationEntry 1 }

snNetFlowAggregationIp OBJECT-TYPE
	SYNTAX	IpAddress
	MAX-ACCESS	read-write
	STATUS	current
	DESCRIPTION
		"The NetFlow aggregation collector ip address."
	::= { snNetFlowAggregationEntry 2 }

snNetFlowAggregationUdpPort OBJECT-TYPE
	SYNTAX   Integer32
	MAX-ACCESS	read-write
	STATUS	current
	DESCRIPTION
		"The NetFlow aggregation collector UDP port number."
	::= { snNetFlowAggregationEntry 3 }

snNetFlowAggregationSourceInterface OBJECT-TYPE
	SYNTAX	InterfaceIndex
	MAX-ACCESS	read-write
	STATUS	current
	DESCRIPTION
		"The ifIndex value to specify source port to
		 export NetFlow aggregation packet.
		 Value 0 to indicate default outgoing port."
	::= { snNetFlowAggregationEntry 4 }

snNetFlowAggregationNumberOfCacheEntries OBJECT-TYPE
	SYNTAX   Integer32
	MAX-ACCESS	read-write
	STATUS	current
	DESCRIPTION
		"Number of cache entries for aggregation scheme"
	::= { snNetFlowAggregationEntry 5 }

snNetFlowAggregationActiveTimeout OBJECT-TYPE
	SYNTAX   Integer32
	MAX-ACCESS	read-write
	STATUS	current
	DESCRIPTION
		"Maximum time an active flow can be in
		 the aggregation cache"
	::= { snNetFlowAggregationEntry 6 }

snNetFlowAggregationInactiveTimeout OBJECT-TYPE
	SYNTAX   Integer32
	MAX-ACCESS	read-write
	STATUS	current
	DESCRIPTION
		"Maximum time an inactive flow can be in
		 the aggregation cache"
	::= { snNetFlowAggregationEntry 7 }

snNetFlowAggregationEnable OBJECT-TYPE
	SYNTAX	INTEGER { disabled(0), enabled(1) }
	MAX-ACCESS	read-write
	STATUS	current
	DESCRIPTION
		"Enable/disable NetFlow aggregation
		 for this aggregation scheme."
	DEFVAL { disabled }
	::= {  snNetFlowAggregationEntry 8 }

snNetFlowAggregationRowStatus OBJECT-TYPE
	SYNTAX	INTEGER	{
		other(1),
		valid(2),
		delete(3),
		create(4) }
	MAX-ACCESS	read-write
	STATUS	current
	DESCRIPTION
		"To create or delete a NetFlow collector table entry."
	::= { snNetFlowAggregationEntry 9 }


-- NetFlow Interface Table

-- Table containing information about the switching
-- type in every interface.

snNetFlowIfTable OBJECT-TYPE
	SYNTAX	SEQUENCE OF SnNetFlowIfEntry
	MAX-ACCESS	not-accessible
	STATUS	current
	DESCRIPTION
		"A list of interface entries.  The number of entries
		 is given by the value of ifNumber."
	::= { snNetFlow 4 }

snNetFlowIfEntry OBJECT-TYPE
	SYNTAX	SnNetFlowIfEntry
	MAX-ACCESS	not-accessible
	STATUS	current
	DESCRIPTION
		"Entry containing the type of switching performed
		 on that interface."
	INDEX	{ snNetFlowIfIndex }
	::= { snNetFlowIfTable 1 }

SnNetFlowIfEntry ::= SEQUENCE {
	snNetFlowIfIndex
		InterfaceIndex,
	snNetFlowIfFlowSwitching
		INTEGER
	}

 snNetFlowIfIndex OBJECT-TYPE
	   SYNTAX      InterfaceIndex
	   MAX-ACCESS      read-only
	   STATUS      current
	   DESCRIPTION
		   "A unique value, greater than zero, for each
			interface.  It is recommended that values are assigned
			contiguously starting from 1.  The value for each
			interface sub-layer must remain constant at least from
			one re-initialization of the entity's network
			management system to the next re-initialization."
	   ::= { snNetFlowIfEntry 1 }

snNetFlowIfFlowSwitching OBJECT-TYPE
	   SYNTAX      INTEGER { disabled (0), enabled (1) }
	   MAX-ACCESS      read-write
	   STATUS      current
	   DESCRIPTION
		   "To enable/disable flow switching in a particular
			interface:
			disable (0) - no flow switching
			enable  (1) - flow switching"
	   ::= { snNetFlowIfEntry 2 }

-- sFlow Collector Table.

snSFlowGlb	OBJECT IDENTIFIER ::= { snSFlow 1 }

snSflowCollectorTable     OBJECT-TYPE
	SYNTAX	SEQUENCE OF SnSflowCollectorEntry
	MAX-ACCESS	not-accessible
	STATUS	current
	DESCRIPTION
		"Table of all but first sFlow collectors. The first collector can be configured
		using sFlowTable in RFC 3176. The RFC cannot be used to configure more
		than one sFlow collectors. This table has been created to fill this gap."
	::= { snSFlow 2 }

snSflowCollectorEntry	OBJECT-TYPE
	SYNTAX	SnSflowCollectorEntry
	MAX-ACCESS	not-accessible
	STATUS	current
	DESCRIPTION
		"A row in the sFlow collector table."
	INDEX	{ snSflowCollectorIndex }
	::= { snSflowCollectorTable 1 }

SnSflowCollectorEntry ::= SEQUENCE {
	snSflowCollectorIndex
		Integer32,
	snSflowCollectorIP
		IpAddress,
	snSflowCollectorUDPPort
		Integer32,
	snSflowCollectorRowStatus
		INTEGER
	}

snSflowCollectorIndex  OBJECT-TYPE
	SYNTAX   Integer32
	MAX-ACCESS	read-only
	STATUS	current
	DESCRIPTION
		"The index to the sFlow collector table."
	::= { snSflowCollectorEntry 1 }

snSflowCollectorIP OBJECT-TYPE
	SYNTAX	IpAddress
	MAX-ACCESS	read-write
	STATUS	current
	DESCRIPTION
		"The sFlow collector ip address."
	::= { snSflowCollectorEntry 2 }

snSflowCollectorUDPPort OBJECT-TYPE
	SYNTAX   Integer32
	MAX-ACCESS	read-write
	STATUS	current
	DESCRIPTION
		"The sFlow collector UDP port number."
	::= { snSflowCollectorEntry 3 }

snSflowCollectorRowStatus OBJECT-TYPE
	SYNTAX	INTEGER	{
		noSuch(0),
		other(1),
		valid(2),
		delete(3),
		create(4),
		modify(5)
		}
	MAX-ACCESS	read-write
	STATUS	current
	DESCRIPTION
		"To create, update or delete a SFlow collector table entry.
		If the row exists, then a SET with
		value of create(4) returns error
		'badValue'. Deleted rows go away
		immediately. The following values
		can be returned on reads:
		  noSuch(0)...no such row
		  other(1)....some other case
		  valid(2)....the row exists and is valid"
	::= { snSflowCollectorEntry 4 }


snFdpMIBObjects OBJECT IDENTIFIER ::= { snFDP 1 }

snFdpInterface   OBJECT IDENTIFIER ::= { snFdpMIBObjects 1 }
snFdpCache       OBJECT IDENTIFIER ::= { snFdpMIBObjects 2 }
snFdpGlobal      OBJECT IDENTIFIER ::= { snFdpMIBObjects 3 }
snFdpCachedAddr  OBJECT IDENTIFIER ::= { snFdpMIBObjects 4 }

--
-- FDP Interface Group
--
snFdpInterfaceTable OBJECT-TYPE
	SYNTAX     SEQUENCE OF FdpInterfaceEntry
	MAX-ACCESS     not-accessible
	STATUS     current
	DESCRIPTION
			"Status of FDP on the device's interfaces."
	::= { snFdpInterface 1 }

snFdpInterfaceEntry OBJECT-TYPE
	SYNTAX     FdpInterfaceEntry
	MAX-ACCESS     not-accessible
	STATUS     current
	DESCRIPTION
			"An entry in the snFdpInterfaceTable,
			having the status of FDP on an interface."
	INDEX      { snFdpInterfaceIfIndex }
	::= { snFdpInterfaceTable 1 }

FdpInterfaceEntry ::= SEQUENCE {
	snFdpInterfaceIfIndex           InterfaceIndex,
	snFdpInterfaceFdpEnable            INTEGER,
	snFdpInterfaceCdpEnable            INTEGER
}

snFdpInterfaceIfIndex OBJECT-TYPE
	SYNTAX     InterfaceIndex
	MAX-ACCESS     not-accessible
	STATUS     current
	DESCRIPTION
			"ifIndex value of the local interface."
	::= { snFdpInterfaceEntry 1 }

snFdpInterfaceFdpEnable OBJECT-TYPE
	SYNTAX     INTEGER { false(0), true(1) }
	MAX-ACCESS     read-write
	STATUS     current
	DESCRIPTION
			"The flag, whether the Foundry Discovery Protocol
			is currently running on this interface.  It has no
			effect when FDP is disabled (snFdpGlobalRun = FALSE)."
	DEFVAL { true }
	::= { snFdpInterfaceEntry 2 }

snFdpInterfaceCdpEnable OBJECT-TYPE
	SYNTAX     INTEGER { false(0), true(1) }
	MAX-ACCESS     read-write
	STATUS     current
	DESCRIPTION
			"The flag, whether the Cisco Discovery Protocol
			is currently running on this interface.  It has no
			effect when CDP is disabled (snCdpGlobalRun = FALSE)."
	DEFVAL { true }
	::= { snFdpInterfaceEntry 3 }

--
-- FDP Cache Table
--

snFdpCacheTable OBJECT-TYPE
	SYNTAX     SEQUENCE OF FdpCacheEntry
	MAX-ACCESS     not-accessible
	STATUS     current
	DESCRIPTION
			"The table for the cached information obtained
			 via receiving FDP/CDP messages."
	::= { snFdpCache 1 }

snFdpCacheEntry OBJECT-TYPE
	SYNTAX     FdpCacheEntry
	MAX-ACCESS     not-accessible
	STATUS     current
	DESCRIPTION
			"An entry in the snFdpCacheTable, having the information 
			received via FDP/CDP on one interface from one device.  
			Entries appear when a FDP/CDP advertisement is received
			from a neighbor device.
			Entries disappear when FDP/CDP is disabled on the interface, or globally."
	INDEX      { snFdpCacheIfIndex, snFdpCacheDeviceIndex }
	::= { snFdpCacheTable 1 }

FdpCacheEntry ::= SEQUENCE {
	snFdpCacheIfIndex					InterfaceIndex,
	snFdpCacheDeviceIndex				Integer32,
	snFdpCacheDeviceId					DisplayString,
	snFdpCacheAddressType				INTEGER,
	snFdpCacheAddress					OCTET STRING,
	snFdpCacheVersion					DisplayString,
	snFdpCacheDevicePort				DisplayString,
	snFdpCachePlatform					DisplayString,
	snFdpCacheCapabilities				DisplayString, 
	snFdpCacheVendorId					INTEGER, 
	snFdpCacheIsAggregateVlan		INTEGER,
	snFdpCacheTagType				Integer32,
	snFdpCachePortVlanMask		OCTET STRING,
	snFdpCachePortTagMode         INTEGER,
	snFdpCacheDefaultTrafficeVlanIdForDualMode  Integer32
}

snFdpCacheIfIndex OBJECT-TYPE
	SYNTAX     InterfaceIndex
	MAX-ACCESS     not-accessible
	STATUS     current
	DESCRIPTION
			"ifIndex value of the local interface."
	::= { snFdpCacheEntry 1 }

snFdpCacheDeviceIndex OBJECT-TYPE
	SYNTAX     Integer32
	MAX-ACCESS     not-accessible
	STATUS     current
	DESCRIPTION
			"Identification of a device, which sent FDP/CDP messages"
	::= { snFdpCacheEntry 2 }

snFdpCacheDeviceId OBJECT-TYPE
	SYNTAX     DisplayString
	MAX-ACCESS     read-only
	STATUS     current
	DESCRIPTION
			"The Device-ID string as reported in the most recent FDP/CDP
			message.  The zero-length string indicates no Device-ID
			field (TLV) was reported in the most recent FDP/CDP
			message."
	::= { snFdpCacheEntry 3 }

snFdpCacheAddressType OBJECT-TYPE
	SYNTAX     INTEGER { ip(1), ipx(2), appletalk(3) }
	MAX-ACCESS     read-only
	STATUS     current
	DESCRIPTION
			"An indication of the type of address contained in the
			corresponding instance of snFdpCacheAddress."
	::= { snFdpCacheEntry 4 }

snFdpCacheAddress OBJECT-TYPE
	SYNTAX     OCTET STRING
	MAX-ACCESS     read-only
	STATUS     current
	DESCRIPTION
			"The (first) network-layer address of the device
			as reported in the most recent FDP/CDP message
			in the following format:
			  IP address:  4 octets, ip(1)
			  IPX address: 10 octets, ipx(2)
					 First 4-octet as the network number
					 Second 6-octet as the host number
			  Appletalk address: 3 octets, appletalk(3)
					 First 2-octet as the network number
					 Second 1-octet as the host number"
	::= { snFdpCacheEntry 5 }

snFdpCacheVersion OBJECT-TYPE
	SYNTAX     DisplayString
	MAX-ACCESS     read-only
	STATUS     current
	DESCRIPTION
			"Version string as reported in the most recent FDP/CDP message. "
	::= { snFdpCacheEntry 6 }


snFdpCacheDevicePort OBJECT-TYPE
	SYNTAX     DisplayString
	MAX-ACCESS     read-only
	STATUS     current
	DESCRIPTION
			"The Port-ID string as reported in the most recent FDP/CDP
			message.  This will typically be the value of the ifName
			object (e.g., Ethernet0).  The zero-length string
			indicates no Port-ID field (TLV) was reported in the
			most recent FDP/CDP message."
	::= { snFdpCacheEntry 7 }

snFdpCachePlatform OBJECT-TYPE
	SYNTAX     DisplayString
	MAX-ACCESS     read-only
	STATUS     current
	DESCRIPTION
			"The Device's Hardware Platform as reported in the most
			recent FDP/CDP message.  The zero-length string indicates
			that no Platform field (TLV) was reported in the most
			recent FDP/CDP message."
	::= { snFdpCacheEntry 8 }

snFdpCacheCapabilities OBJECT-TYPE
	SYNTAX     DisplayString
	MAX-ACCESS     read-only
	STATUS     current
	DESCRIPTION
			"The Device's Functional Capabilities as reported in the
			most recent FDP/CDP message. "
	::= { snFdpCacheEntry 9 }

snFdpCacheVendorId OBJECT-TYPE
	SYNTAX     INTEGER { fdp(1), cdp(2) }
	MAX-ACCESS     read-only
	STATUS     current
	DESCRIPTION
			"Indicates the entry received by either FDP or CDP."
	::= { snFdpCacheEntry 10 }

snFdpCacheIsAggregateVlan OBJECT-TYPE
	SYNTAX     INTEGER { false(0), true(1) }
	MAX-ACCESS     read-only
	STATUS     current
	DESCRIPTION
			"Neighbor device is in aggregated-vlan."
	::= { snFdpCacheEntry 11 }

snFdpCacheTagType OBJECT-TYPE
	SYNTAX     Integer32
	MAX-ACCESS     read-only
	STATUS     current
	DESCRIPTION
			"Neighbor device tag-type."
	::= { snFdpCacheEntry 12 }

snFdpCachePortVlanMask OBJECT-TYPE
	SYNTAX     OCTET STRING
	MAX-ACCESS     read-only
	STATUS     current
	DESCRIPTION
			"Neighbor device port VLAN masks in 512-byte octet string."
	::= { snFdpCacheEntry 13 }

snFdpCachePortTagMode OBJECT-TYPE
	SYNTAX     INTEGER { untagged(1), tagged(2), dual(3) }
	MAX-ACCESS     read-only
	STATUS     current
	DESCRIPTION
			"Neighbor device port tag mode"
	::= { snFdpCacheEntry 14 }

snFdpCacheDefaultTrafficeVlanIdForDualMode OBJECT-TYPE
	SYNTAX     Integer32
	MAX-ACCESS     read-only
	STATUS     current
	DESCRIPTION
			"Default traffic vlan id for neighbor device dual-mode port"
	::= { snFdpCacheEntry 15 }

--
-- FDP Global Group
--   

snFdpGlobalRun OBJECT-TYPE
	SYNTAX     INTEGER { false(0), true(1) }
	MAX-ACCESS     read-write
	STATUS     current
	DESCRIPTION
			"The flag, whether the Foundry Discovery Protocol
			is currently running.  FDP entries in snFdpCacheTable are
			deleted when FDP is disabled."
	DEFVAL     { false }
	::= { snFdpGlobal 1 }

snFdpGlobalMessageInterval OBJECT-TYPE
	SYNTAX     INTEGER (5..900)
	MAX-ACCESS     read-write
	STATUS     current
	DESCRIPTION
			"The interval at which FDP messages are to be generated.
			The default value is 60 seconds."
	DEFVAL     { 60 }
	::= { snFdpGlobal 2 }

snFdpGlobalHoldTime OBJECT-TYPE
	SYNTAX     INTEGER (10..255)
	MAX-ACCESS     read-write
	STATUS     current
	DESCRIPTION
			"The time for the receiving device holds FDP message.
			The default value is 180 seconds."
	DEFVAL     { 180 }
	::= { snFdpGlobal 3 }

snFdpGlobalCdpRun OBJECT-TYPE
	SYNTAX     INTEGER { false(0), true(1) }
	MAX-ACCESS     read-write
	STATUS     current
	DESCRIPTION
			"An indication of whether the Cisco Discovery Protocol
			is currently running.  CDP entries in snFdpCacheTable are
			deleted when CDP is disabled."
	DEFVAL     { false }
	::= { snFdpGlobal 4 }

--
-- FDP Cached Address Entry Table
--
snFdpCachedAddressTable OBJECT-TYPE
	SYNTAX     SEQUENCE OF FdpCachedAddressEntry
	MAX-ACCESS     not-accessible
	STATUS     current
	DESCRIPTION
			"Cached address table from receiving FDP/CDP messages."
	::= { snFdpCachedAddr 1 }

snFdpCachedAddressEntry OBJECT-TYPE
	SYNTAX     FdpCachedAddressEntry
	MAX-ACCESS     not-accessible
	STATUS     current
	DESCRIPTION
			"An entry (conceptual row) in the snFdpCacheAddressTable,
			containing one cached address from FDP/CDP messages."
	INDEX      { snFdpCachedAddrIfIndex, snFdpCachedAddrDeviceIndex, snFdpCachedAddrDeviceAddrEntryIndex }
	::= { snFdpCachedAddressTable 1 }

FdpCachedAddressEntry ::= SEQUENCE {
	snFdpCachedAddrIfIndex               InterfaceIndex,
	snFdpCachedAddrDeviceIndex           Integer32,
	snFdpCachedAddrDeviceAddrEntryIndex  Integer32,
	snFdpCachedAddrType				     INTEGER,
	snFdpCachedAddrValue				 OCTET STRING
}

snFdpCachedAddrIfIndex OBJECT-TYPE
	SYNTAX     InterfaceIndex
	MAX-ACCESS     not-accessible
	STATUS     current
	DESCRIPTION
			"The ifIndex value of the local interface."
	::= { snFdpCachedAddressEntry 1 }

snFdpCachedAddrDeviceIndex OBJECT-TYPE
	SYNTAX     Integer32
	MAX-ACCESS     not-accessible
	STATUS     current
	DESCRIPTION
			"A unique vlaue for each device from which FDP/CDP messages
			are being received."
	::= { snFdpCachedAddressEntry 2 }

snFdpCachedAddrDeviceAddrEntryIndex OBJECT-TYPE
	SYNTAX     Integer32
	MAX-ACCESS     not-accessible
	STATUS     current
	DESCRIPTION
			"A unique vlaue for address entry in device from which FDP/CDP messages
			are being received."
	::= { snFdpCachedAddressEntry 3 }

snFdpCachedAddrType OBJECT-TYPE
	SYNTAX     INTEGER { ip(1), ipx(2), appletalk(3) }
	MAX-ACCESS     read-only
	STATUS     current
	DESCRIPTION
			"An indication of the type of address contained in the
			corresponding instance of snFdpCacheAddrValue."
	::= { snFdpCachedAddressEntry 4 }

snFdpCachedAddrValue OBJECT-TYPE
	SYNTAX     OCTET STRING
	MAX-ACCESS     read-only
	STATUS     current
	DESCRIPTION
			"The network-layer address of the device
			SNMP-agent as reported in the most recent FDP/CDP message
			in the following format:
			  IP address:  4 octets, ip(1)
			  IPX address: 10 octets, ipx(2)
					 First 4-octet as the network number
					 Second 6-octet as the host number
			  Appletalk address: 3 octets, appletalk(3)
					 First 2-octet as the network number
					 Second 1-octet as the host number"
	::= { snFdpCachedAddressEntry 5 }


snMacSecurity   OBJECT IDENTIFIER ::= { snMac 1 }
snPortMacSecurity   		OBJECT IDENTIFIER ::= { snMacSecurity 1 }
snPortMacGlobalSecurity   	OBJECT IDENTIFIER ::= { snMacSecurity 2 }

--
-- Port MAC Security Table
--

snPortMacSecurityTable OBJECT-TYPE
	SYNTAX     SEQUENCE OF PortMacSecurityEntry
	MAX-ACCESS     not-accessible
	STATUS     current
	DESCRIPTION
			"Status of port MAC security on the device's interfaces."
	::= { snPortMacSecurity 1 }

snPortMacSecurityEntry OBJECT-TYPE
	SYNTAX     PortMacSecurityEntry
	MAX-ACCESS     not-accessible
	STATUS     current
	DESCRIPTION
			"An entry in the snPortMacSecurityTable"
	INDEX      { snPortMacSecurityIfIndex,
					 snPortMacSecurityResource,
					 snPortMacSecurityQueryIndex
				  }
	::= { snPortMacSecurityTable 1 }

PortMacSecurityEntry ::= SEQUENCE {
	snPortMacSecurityIfIndex                    Unsigned32,
	snPortMacSecurityResource                 INTEGER,
	snPortMacSecurityQueryIndex              Unsigned32,
	snPortMacSecurityMAC                       MacAddress,
	snPortMacSecurityAgeLeft                  Unsigned32,
	snPortMacSecurityShutdownStatus       INTEGER,
	snPortMacSecurityShutdownTimeLeft   Unsigned32,
	snPortMacSecurityVlanId                    Unsigned32
}

snPortMacSecurityIfIndex     OBJECT-TYPE
	SYNTAX     Unsigned32
	MAX-ACCESS     read-only
	STATUS     current
	DESCRIPTION
			"ifIndex value of the local Ethernet interface on 
			which MAC security is configured."
	::= {snPortMacSecurityEntry 1}

snPortMacSecurityResource OBJECT-TYPE
	SYNTAX     INTEGER { local(1), shared(2) }
	MAX-ACCESS     read-only
	STATUS     current
	DESCRIPTION
			"The MAC address was secured using local or shared resources."
	::= {snPortMacSecurityEntry 2}

snPortMacSecurityQueryIndex     OBJECT-TYPE
	SYNTAX     Unsigned32
	MAX-ACCESS     read-only
	STATUS     current
	DESCRIPTION
			"Entry index within the given resource of local Ethernet interface on 
			which MAC security is configured."
	::= {snPortMacSecurityEntry 3}

snPortMacSecurityMAC OBJECT-TYPE
	SYNTAX     MacAddress
	MAX-ACCESS     read-only
	STATUS     current
	DESCRIPTION
			"The secure MAC address for this interface."
	::= {snPortMacSecurityEntry 4}

snPortMacSecurityAgeLeft OBJECT-TYPE
	SYNTAX     Unsigned32
	MAX-ACCESS     read-only
	STATUS     current
	DESCRIPTION
			"The number of minutes the MAC address will remain secure
			before being aged out. 0 means no aging."
	::= {snPortMacSecurityEntry 5}

snPortMacSecurityShutdownStatus OBJECT-TYPE
	SYNTAX     INTEGER { up(1), down(2) }
	MAX-ACCESS     read-only
	STATUS     current
	DESCRIPTION
			"Interface up/down status."
	::= {snPortMacSecurityEntry 6}

snPortMacSecurityShutdownTimeLeft OBJECT-TYPE
	SYNTAX     Unsigned32
	MAX-ACCESS     read-only
	STATUS     current
	DESCRIPTION
			"If snPortMacSecurityShutdownStatus is up(1), this value will be 0.
			If snPortMacSecurityShutdownStatus is down(2), this gives
			the number of seconds before this interface is enabled again.
			In the later case, 0 means interface is permanently down."
	::= {snPortMacSecurityEntry 7}

snPortMacSecurityVlanId OBJECT-TYPE
	SYNTAX     Unsigned32 (1..65535)
	MAX-ACCESS     read-only
	STATUS     current
	DESCRIPTION
			"The vlan membership of this interface."
	::= {snPortMacSecurityEntry 8}



--
-- Port MAC Security Module Statistics Table
--

snPortMacSecurityModuleStatTable OBJECT-TYPE
	SYNTAX     SEQUENCE OF PortMacSecurityModuleStatEntry
	MAX-ACCESS     not-accessible
	STATUS     current
	DESCRIPTION
			"Port MAC security statistics on each module."
	::= { snPortMacSecurity 2 }

snPortMacSecurityModuleStatEntry OBJECT-TYPE
	SYNTAX     PortMacSecurityModuleStatEntry 
	MAX-ACCESS     not-accessible
	STATUS     current
	DESCRIPTION
			"An entry in the snPortMacSecurityModuleStatTable"
	INDEX      { snPortMacSecurityModuleStatSlotNum }
	::= { snPortMacSecurityModuleStatTable 1 }

PortMacSecurityModuleStatEntry ::= SEQUENCE {
	snPortMacSecurityModuleStatSlotNum					Integer32,
	snPortMacSecurityModuleStatTotalSecurityPorts		Unsigned32,
	snPortMacSecurityModuleStatTotalMACs				Unsigned32,
	snPortMacSecurityModuleStatViolationCounts			Unsigned32,
	snPortMacSecurityModuleStatTotalShutdownPorts		Unsigned32
}

snPortMacSecurityModuleStatSlotNum 		OBJECT-TYPE
	SYNTAX     Integer32   
	MAX-ACCESS     read-only
	STATUS     current
	DESCRIPTION
			"The slot number of the port security device module."
	::= {snPortMacSecurityModuleStatEntry 1}

snPortMacSecurityModuleStatTotalSecurityPorts     OBJECT-TYPE
	SYNTAX     Unsigned32
	MAX-ACCESS     read-only
	STATUS     current
	DESCRIPTION
			"The totol number of Ethernet interfaces on which MAC security is configured in this module."
	::= {snPortMacSecurityModuleStatEntry 2}

snPortMacSecurityModuleStatTotalMACs     OBJECT-TYPE
	SYNTAX     Unsigned32
	MAX-ACCESS     read-only
	STATUS     current
	DESCRIPTION
			"The totol number of port MAC security MAC addresses are learned or configured in this module."
	::= {snPortMacSecurityModuleStatEntry 3}

snPortMacSecurityModuleStatViolationCounts     OBJECT-TYPE
	SYNTAX     Unsigned32
	MAX-ACCESS     read-only
	STATUS     current
	DESCRIPTION
			"The totol number of counts of violation are collected in this module."
	::= {snPortMacSecurityModuleStatEntry 4}

snPortMacSecurityModuleStatTotalShutdownPorts     OBJECT-TYPE
	SYNTAX     Unsigned32
	MAX-ACCESS     read-only
	STATUS     current
	DESCRIPTION
			"The totol number of Ethernet interfaces are shutted down due to security violation in this module."
	::= {snPortMacSecurityModuleStatEntry 5}

--
-- Port MAC Security Interface Table
--

snPortMacSecurityIntfContentTable OBJECT-TYPE
	SYNTAX     SEQUENCE OF PortMacSecurityIntfContentEntry
	MAX-ACCESS     not-accessible
	STATUS     current
	DESCRIPTION
			"Port MAC security statistics on each Ethernet Interface."
	::= { snPortMacSecurity 3 }

snPortMacSecurityIntfContentEntry OBJECT-TYPE
	SYNTAX     PortMacSecurityIntfContentEntry 
	MAX-ACCESS     not-accessible
	STATUS     current
	DESCRIPTION
			"An entry in the snPortMacSecurityIntfContentTable"
	INDEX      { snPortMacSecurityIntfContentIfIndex }
	::= { snPortMacSecurityIntfContentTable 1 }

PortMacSecurityIntfContentEntry ::= SEQUENCE {
	snPortMacSecurityIntfContentIfIndex					InterfaceIndex,
	snPortMacSecurityIntfContentSecurity   				INTEGER,
	snPortMacSecurityIntfContentViolationType			INTEGER,
	snPortMacSecurityIntfContentShutdownTime			Unsigned32,
	snPortMacSecurityIntfContentShutdownTimeLeft		Unsigned32,
	snPortMacSecurityIntfContentAgeOutTime				Unsigned32,
	snPortMacSecurityIntfContentMaxLockedMacAllowed		Unsigned32,
	snPortMacSecurityIntfContentTotalMACs				Unsigned32,
	snPortMacSecurityIntfContentViolationCounts			Unsigned32
}

snPortMacSecurityIntfContentIfIndex OBJECT-TYPE
	SYNTAX  InterfaceIndex
	MAX-ACCESS  not-accessible
	STATUS  current
	DESCRIPTION
		"In order to identify a particular interface, this
		object shall identify the instance of the ifIndex
		object, defined in RFC 2863."
	::= { snPortMacSecurityIntfContentEntry 1 }

snPortMacSecurityIntfContentSecurity OBJECT-TYPE
	SYNTAX     INTEGER { disable(0), enable(1) }
	MAX-ACCESS     read-write
	STATUS     current
	DESCRIPTION
			"Port security for this interface can be either disabled or enabled."
	::= {snPortMacSecurityIntfContentEntry 2}

snPortMacSecurityIntfContentViolationType OBJECT-TYPE
	SYNTAX     INTEGER { shutdown(0), restrict(1) }
	MAX-ACCESS     read-write
	STATUS     current
	DESCRIPTION
			"Port security violation type for this interface is shutdown or restrict."
	::= {snPortMacSecurityIntfContentEntry 3}

snPortMacSecurityIntfContentShutdownTime OBJECT-TYPE
	SYNTAX     Unsigned32 (0..1440)
	MAX-ACCESS     read-write
	STATUS     current
	DESCRIPTION
			"If snPortMacSecurityIntfContentViolationType is shutdown(1),
			this value gives the number of seconds this interface is shut down when violation occurs.
			In the shutdown(1) case, 0 means interface is permanently down.
			If snPortMacSecurityIntfContentViolationType is restrict(2), this value will be always 0."
	::= {snPortMacSecurityIntfContentEntry 4}

snPortMacSecurityIntfContentShutdownTimeLeft OBJECT-TYPE
	SYNTAX     Unsigned32
	MAX-ACCESS     read-only
	STATUS     current
	DESCRIPTION
			"If snPortMacSecurityIntfContentViolationType is shutdown(1), 
			whether this interface has been shut down due to a security violation 
			and the value gives the number of seconds before this interface is enabled again.
			If snPortMacSecurityIntfContentViolationType is restrict(2), this value will be always 0."
	::= {snPortMacSecurityIntfContentEntry 5}

snPortMacSecurityIntfContentAgeOutTime OBJECT-TYPE
	SYNTAX     Unsigned32 (0..1440)
	MAX-ACCESS     read-write
	STATUS     current
	DESCRIPTION
			"The amount of time, in minutes, MAC addresses learned on this interface will remain secure.
			It allows configurable values 0-1440.  0 means no aging permanently."
	::= {snPortMacSecurityIntfContentEntry 6}

snPortMacSecurityIntfContentMaxLockedMacAllowed OBJECT-TYPE
	SYNTAX     Unsigned32
	MAX-ACCESS     read-write
	STATUS     current
	DESCRIPTION
			"Maximum number of security MAC addresses can be locked to this interface."
	::= {snPortMacSecurityIntfContentEntry 7}

snPortMacSecurityIntfContentTotalMACs     OBJECT-TYPE
	SYNTAX     Unsigned32
	MAX-ACCESS     read-only
	STATUS     current
	DESCRIPTION
			"The totol number of port MAC security MAC addresses are locked in this interface."
	::= {snPortMacSecurityIntfContentEntry 8}

snPortMacSecurityIntfContentViolationCounts     OBJECT-TYPE
	SYNTAX     Unsigned32
	MAX-ACCESS     read-only
	STATUS     current
	DESCRIPTION
			"The totol number of counts of violation are collected in this interface."
	::= {snPortMacSecurityIntfContentEntry 9}

--
-- Port MAC Security Interface MAC Table
--

snPortMacSecurityIntfMacTable OBJECT-TYPE
	SYNTAX     SEQUENCE OF PortMacSecurityIntfMacEntry
	MAX-ACCESS     not-accessible
	STATUS     current
	DESCRIPTION
			"Status of port MAC security on the device's interfaces."
	::= { snPortMacSecurity 4 }

snPortMacSecurityIntfMacEntry OBJECT-TYPE
	SYNTAX     PortMacSecurityIntfMacEntry
	MAX-ACCESS     not-accessible
	STATUS     current
	DESCRIPTION
			"An entry in the snPortMacSecurityIntfMacTable"
	INDEX      { snPortMacSecurityIntfMacIfIndex,
					snPortMacSecurityIntfMacAddress 
					}
	::= { snPortMacSecurityIntfMacTable 1 }

PortMacSecurityIntfMacEntry ::= SEQUENCE {
	snPortMacSecurityIntfMacIfIndex			Integer32,
	snPortMacSecurityIntfMacAddress			MacAddress,
	snPortMacSecurityIntfMacVlanId			Unsigned32,
	snPortMacSecurityIntfMacRowStatus 		INTEGER
}

snPortMacSecurityIntfMacIfIndex     OBJECT-TYPE
	SYNTAX     Integer32
	MAX-ACCESS     read-only
	STATUS     current
	DESCRIPTION
			"ifIndex value of the local Ethernet interface on 
			which MAC security is configured."
	::= {snPortMacSecurityIntfMacEntry 1}

snPortMacSecurityIntfMacAddress OBJECT-TYPE
	SYNTAX     MacAddress
	MAX-ACCESS     read-only
	STATUS     current
	DESCRIPTION
			"The secure MAC address for this local Ethernet interface on 
			which the secure MAC Address is configured and/or learned.  
			The maximum number of the secure MAC Addresses is restricted 
			by the snPortMacSecurityIntfContentMaxLockedMacAllowed."
	::= {snPortMacSecurityIntfMacEntry 2}

snPortMacSecurityIntfMacVlanId OBJECT-TYPE
	SYNTAX     Unsigned32 (0..65535)
	MAX-ACCESS     read-write
	STATUS     current
	DESCRIPTION
			"The vlan membership of this interface, zero means don't care."
	::= {snPortMacSecurityIntfMacEntry 3}

snPortMacSecurityIntfMacRowStatus OBJECT-TYPE
	SYNTAX  INTEGER {
		other(1),
		valid(2),
		delete(3),
		create(4)
		}
	MAX-ACCESS  read-write
	STATUS  current
	DESCRIPTION
		"This object is used to create and
		delete row in the table and control
		if they are used. The values
		that can be written are:
		  delete(3)...deletes the row
		  create(4)...creates a new row

		If the row exists, then a SET with
		value of create(4) returns error
		'badValue'. Deleted rows go away
		immediately. The following values
		can be returned on reads:
		  noSuch(0)...no such row
		  other(1)....some other case
		  valid(2)....the row exists and is valid"
	::= {snPortMacSecurityIntfMacEntry 4}


--
-- Port MAC Security Autosave MAC Table
--

snPortMacSecurityAutosaveMacTable OBJECT-TYPE
	SYNTAX     SEQUENCE OF PortMacSecurityAutosaveMacEntry
	MAX-ACCESS     not-accessible
	STATUS     current
	DESCRIPTION
			"Autosave MAC addresses of port MAC security on the device's interfaces."
	::= { snPortMacSecurity 5 }

snPortMacSecurityAutosaveMacEntry OBJECT-TYPE
	SYNTAX     PortMacSecurityAutosaveMacEntry
	MAX-ACCESS     not-accessible
	STATUS     current
	DESCRIPTION
			"An entry in the snPortMacSecurityAutosaveMacTable"
	INDEX      { snPortMacSecurityAutosaveMacIfIndex,
				 snPortMacSecurityAutosaveMacResource,
				 snPortMacSecurityAutosaveMacQueryIndex
					}
	::= { snPortMacSecurityAutosaveMacTable 1 }

PortMacSecurityAutosaveMacEntry ::= SEQUENCE {
	snPortMacSecurityAutosaveMacIfIndex		Integer32,
	snPortMacSecurityAutosaveMacResource	INTEGER,
	snPortMacSecurityAutosaveMacQueryIndex	Unsigned32,
	snPortMacSecurityAutosaveMacAddress		MacAddress
}

snPortMacSecurityAutosaveMacIfIndex     OBJECT-TYPE
	SYNTAX     Integer32
	MAX-ACCESS     read-only
	STATUS     current
	DESCRIPTION
			"ifIndex value of the local Ethernet interface on 
			which MAC security is configured."
	::= {snPortMacSecurityAutosaveMacEntry 1}

snPortMacSecurityAutosaveMacResource OBJECT-TYPE
	SYNTAX     INTEGER { local(1), shared(2) }
	MAX-ACCESS     read-only
	STATUS     current
	DESCRIPTION
			"The MAC address was autosaved using local or shared resources."
	::= {snPortMacSecurityAutosaveMacEntry 2}

snPortMacSecurityAutosaveMacQueryIndex     OBJECT-TYPE
	SYNTAX     Unsigned32
	MAX-ACCESS     read-only
	STATUS     current
	DESCRIPTION
			"Entry index within the given resource of local Ethernet interface on 
			which MAC security is autosaved."
	::= {snPortMacSecurityAutosaveMacEntry 3}

snPortMacSecurityAutosaveMacAddress OBJECT-TYPE
	SYNTAX     MacAddress
	MAX-ACCESS     read-only
	STATUS     current
	DESCRIPTION
			"The secure MAC address for this local Ethernet interface on 
			which the secure MAC Address is autosaved."
	::= {snPortMacSecurityAutosaveMacEntry 4}



-- Port MAC Global Security MIB Group 

snPortMacGlobalSecurityFeature OBJECT-TYPE
	SYNTAX     INTEGER { disable(0), enable(1) }
	MAX-ACCESS     read-write
	STATUS     current
	DESCRIPTION
			"Port security for this device can be either disabled or enabled."
	::= { snPortMacGlobalSecurity 1 }

snPortMacGlobalSecurityAgeOutTime OBJECT-TYPE
	SYNTAX     Unsigned32 (0..1440)
	MAX-ACCESS     read-write
	STATUS     current
	DESCRIPTION
			"The amount of time, in minutes, MAC addresses learned on this device will remain secure.
			It allows configurable values in the range of 0-1440.  0 means no aging permanently."
	::= { snPortMacGlobalSecurity 2 }

snPortMacGlobalSecurityAutosave OBJECT-TYPE
	SYNTAX     Unsigned32
	MAX-ACCESS     read-write
	STATUS     current
	DESCRIPTION
			"The port security autosave value for this device. It allows
	configurable values 0 and also in the range of 15-1440. The value 0 means no autosave."
	::= { snPortMacGlobalSecurity 3 }


--
-- Port Monitor Table
--

snPortMonitorTable OBJECT-TYPE
	SYNTAX     SEQUENCE OF PortMonitorEntry
	MAX-ACCESS     not-accessible
	STATUS     current
	DESCRIPTION
			"Status of port monitoring on the device's interfaces."
	::= { snPortMonitor 1 }

snPortMonitorEntry OBJECT-TYPE
	SYNTAX     PortMonitorEntry
	MAX-ACCESS     not-accessible
	STATUS     current
	DESCRIPTION
			"An entry in the snPortMonitorTable"
	INDEX      { snPortMonitorIfIndex }
	::= { snPortMonitorTable 1 }

PortMonitorEntry ::= SEQUENCE {
	snPortMonitorIfIndex                    InterfaceIndex,
	snPortMonitorMirrorList                 DisplayString
}

snPortMonitorIfIndex OBJECT-TYPE
	SYNTAX     InterfaceIndex
	MAX-ACCESS     not-accessible
	STATUS     current
	DESCRIPTION
			"ifIndex value of the local interface on which
			monitoring is configuerd."
	::= { snPortMonitorEntry 1 }

snPortMonitorMirrorList OBJECT-TYPE
	 SYNTAX  DisplayString
	 MAX-ACCESS  read-write
	 STATUS  current
	 DESCRIPTION
			 "Lists the monitoring configuration of this port.
			 The value is a space delimited sequence of ifIndex of mirror port
			 and monitor mode. The values for mode can be -
			 0 -  off, 1 - input, 2 - output, 3 - both
			 Eg. '65 2 66 1' means send the output traffic to port 2/1 and
			 input traffic to port 2/2.
			  To turn off a mirror use monitor mode of 0 (off) in the list."
	 ::= { snPortMonitorEntry 2 }

END
FOUNDRY-SN-VSRP-MIB DEFINITIONS ::= BEGIN

IMPORTS

	MODULE-IDENTITY, OBJECT-TYPE,IpAddress, Counter32,Integer32
		FROM SNMPv2-SMI 
	TEXTUAL-CONVENTION
		FROM SNMPv2-TC
	snSwitch
		FROM FOUNDRY-SN-SWITCH-GROUP-MIB
	;

snVsrp MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"            
	REVISION     "200909300000Z" -- September 30, 2009
	DESCRIPTION
			"convert from SMIv1 to SMIv2"
   ::= { snSwitch 21}
		
	MacAddress ::= TEXTUAL-CONVENTION
		STATUS	  current
		DESCRIPTION
			"
			   This data type is used to model media addresses.  For many
			   types of media, this will be in a binary representation.
			   For example, an ethernet address would be represented as
			   a string of 6 octets.			
			"
		SYNTAX	OCTET STRING (SIZE(6))		

snVsrpGlobal 	OBJECT IDENTIFIER ::= { snVsrp 1 } 
snVsrpIfIntf 	OBJECT IDENTIFIER ::= { snVsrp 2 }
snVsrpVirRtr 	OBJECT IDENTIFIER ::= { snVsrp 3 }

--  Section 1:	VSRP Global Variables

snVsrpGroupOperModeVsrp OBJECT-TYPE 
	SYNTAX  INTEGER 
		{   disabled(0),             
			enabled(1)
		} 
	MAX-ACCESS  read-write
	STATUS  current
	DESCRIPTION "The VSRP is configured on this system either enabled or 
		disabled and thedefault is disabled mode.
		 disabled(0)..........disable VSRP   
		 enabled(1)...........activate VSRP" 
	::= { snVsrpGlobal 1 } 
	
snVsrpIfStateChangeTrap OBJECT-TYPE
	SYNTAX	INTEGER { disabled(0), enabled(1) }
	MAX-ACCESS	read-write
	STATUS	current
	DESCRIPTION
		"Indicates whether the SNMP agent process is
		permitted to generate VSRP interface state change
		traps."
	DEFVAL { enabled }
	::= { snVsrpGlobal 2 }

snVsrpIfMaxNumVridPerIntf OBJECT-TYPE
	SYNTAX   Integer32
	MAX-ACCESS	read-only
	STATUS	current
	DESCRIPTION
		"Indicates the maximum number of VRID per interface."
	::= { snVsrpGlobal 3 }

snVsrpIfMaxNumVridPerSystem OBJECT-TYPE
	SYNTAX   Integer32
	MAX-ACCESS	read-only
	STATUS	current
	DESCRIPTION
		"Indicates the maximum number of VRID per system."
	::= { snVsrpGlobal 4 }

snVsrpClearVrrpStat OBJECT-TYPE
	SYNTAX	INTEGER { normal(0), clear(1) }
	MAX-ACCESS	read-write
	STATUS	current
	DESCRIPTION
		"Clear VSRP statistics command."
	::= { snVsrpGlobal 5 }

	 
--  Section 2:	VSRP  Interface Table, new table with vlan_id as an index, 

snVsrpIfTable OBJECT-TYPE
	SYNTAX   SEQUENCE OF SnVsrpIfEntry
	MAX-ACCESS   not-accessible
	STATUS   current
	DESCRIPTION
	   "The VSRP Interface Table describes the interfaces from
		the viewpoint of VSRP."
	::= { snVsrpIfIntf 1 }

	 snVsrpIfEntry OBJECT-TYPE
		 SYNTAX   SnVsrpIfEntry
		 MAX-ACCESS   not-accessible
		 STATUS   current
		 DESCRIPTION
			"The VSRP Interface Entry describes one interface from
			the viewpoint of VSRP."
		 INDEX { snVsrpIfVlanId}
		 ::= { snVsrpIfTable 1 }

	 SnVsrpIfEntry ::=
		 SEQUENCE {
			 snVsrpIfVlanId
				Integer32,
			 snVsrpIfAuthType
				 INTEGER,
			 snVsrpIfAuthPassword
				 OCTET STRING
		 }

	 snVsrpIfVlanId OBJECT-TYPE
		 SYNTAX  Integer32
		 MAX-ACCESS  read-only
		 STATUS  current
		 DESCRIPTION
			"Vlan index."
		 ::= { snVsrpIfEntry 1 }

	snVsrpIfAuthType OBJECT-TYPE
		 SYNTAX   INTEGER { 
						noAuth(0), 
						simpleTextPasswd(1), 
						ipAuthHeader(2)
						}
		 MAX-ACCESS   read-write
		 STATUS   current
		 DESCRIPTION
			"The authentication type of this interface."
		 ::= { snVsrpIfEntry 2 }

	snVsrpIfAuthPassword OBJECT-TYPE
		 SYNTAX	  OCTET STRING (SIZE (0..8))
		 MAX-ACCESS   read-write
		 STATUS   current
		 DESCRIPTION
			"The simple text password is allowed if only if 
			the snVsrpIfAuthType type is simpleTextPasswd."
		 ::= { snVsrpIfEntry 3 }

	 
--  Section 3: VSRP Virtual Router Configuration Table
--  The vsrp Virtual Router Table augments with vsrp specific information.

snVsrpVirRtrTable OBJECT-TYPE
	SYNTAX   SEQUENCE OF SnVsrpVirRtrEntry
	MAX-ACCESS   not-accessible
	STATUS   current
	DESCRIPTION
	   "The vsrp virtual router Entry describes one virtual router from
		the viewpoint of vsrp."
	::= { snVsrpVirRtr 1 }

	 snVsrpVirRtrEntry OBJECT-TYPE
		 SYNTAX   SnVsrpVirRtrEntry
		 MAX-ACCESS   not-accessible
		 STATUS   current
		 DESCRIPTION
			"The vsrp virtual router Entry describes one virtual router from
			the viewpoint of vsrp."
		 INDEX { snVsrpVirRtrVlanId, snVsrpVirRtrId }
		 ::= { snVsrpVirRtrTable 1 }

	 SnVsrpVirRtrEntry ::=
		 SEQUENCE {
			  snVsrpVirRtrVlanId
			Integer32,
			 snVsrpVirRtrId
				 INTEGER,
			 snVsrpVirRtrOwnership
				 INTEGER,
			 snVsrpVirRtrCfgPriority
				 INTEGER,
			 snVsrpVirRtrTrackPriority
				 INTEGER,
			 snVsrpVirRtrCurrPriority
				 INTEGER,
			 snVsrpVirRtrHelloInt 
				 INTEGER,
			 snVsrpVirRtrDeadInt 
				 INTEGER,
			 snVsrpVirRtrPreemptMode 
				 INTEGER,
			 snVsrpVirRtrState
				 INTEGER,
			snVsrpVirRtrIpAddrMask
				OCTET STRING,
			 snVsrpVirRtrActivate 
				 INTEGER,
			 snVsrpVirRtrTrackPortList
				 OCTET STRING,
			 snVsrpVirRtrAdvertiseBackup 
				 INTEGER,
			 snVsrpVirRtrHoldDownInt 
				 INTEGER,
			 snVsrpVirRtrInitTtl
				 INTEGER,
			 snVsrpVirRtrIncPortList
				 OCTET STRING,
			 snVsrpVirRtrSave
				 INTEGER,
			 snVsrpVirRtrBackupInt
				 INTEGER,
			 snVsrpVirRtrRowStatus 
				 INTEGER,
			 snVsrpVirRtrRxArpPktDropCnts 
				 Counter32,
			 snVsrpVirRtrRxIpPktDropCnts 
				 Counter32,
			 snVsrpVirRtrRxPortMismatchCnts 
				 Counter32,
			 snVsrpVirRtrRxNumOfIpMismatchCnts 
				 Counter32,				 
			 snVsrpVirRtrRxIpMismatchCnts 
				 Counter32,
			 snVsrpVirRtrRxHelloIntMismatchCnts 
				 Counter32,
			 snVsrpVirRtrRxPriorityZeroFromMasterCnts 
				 Counter32,
			 snVsrpVirRtrRxHigherPriorityCnts 
				 Counter32,
			 snVsrpVirRtrTransToMasterStateCnts 
				 Counter32,
			 snVsrpVirRtrTransToBackupStateCnts 
				 Counter32,
			 snVsrpVirRtrCurrDeadInt 
				 Integer32,
			 snVsrpVirRtrCurHelloInt 
				 INTEGER,
			 snVsrpVirRtrCurHoldDownInt 
				 INTEGER,
			 snVsrpVirRtrCurInitTtl
				 INTEGER,
			snVsrpVirRtrHelloMacAddress
				MacAddress,
			snVsrpVirRtrMasterIpAddr
				 IpAddress
	   }
	   
	 snVsrpVirRtrVlanId OBJECT-TYPE
		 SYNTAX  Integer32
		 MAX-ACCESS  read-only
		 STATUS  current
		 DESCRIPTION
			"Vlan index."
		 ::= { snVsrpVirRtrEntry 1 }
		 
	snVsrpVirRtrId OBJECT-TYPE
		 SYNTAX   INTEGER (1..255)
		 MAX-ACCESS   read-only
		 STATUS   current
		 DESCRIPTION
			"One of the virtual router ID of this vsrp interface."
		 ::= { snVsrpVirRtrEntry 2 }

	snVsrpVirRtrOwnership OBJECT-TYPE
		 SYNTAX   INTEGER {
					incomplete(0),
					owner(1),
					backup(2)
					}
		 MAX-ACCESS   read-write
		 STATUS   current
		 DESCRIPTION
			"The ownership of this vsrp router interface 
			can be set to backup(2).  
			VirRtr SNMP-GET returns incomplete(0), it means 
			no IP address has assigned to this vsrp router interface."
		 ::= { snVsrpVirRtrEntry 3 }

	 snVsrpVirRtrCfgPriority OBJECT-TYPE
		 SYNTAX   INTEGER (1..255)
		 MAX-ACCESS   read-write
		 STATUS   current
		 DESCRIPTION
			"The higher the number the higher the priority is.
			This parameter decides which backup router should becomes
			the Active Router for the interface.  A backup Router with
			higher priority selected to becomes the Active Router.
			Therefore, this Object can be set if only if snVsrpVirRtrOwnership
			is set to backup(2)."
		 DEFVAL { 100 }
		 ::= { snVsrpVirRtrEntry 4 }

	 snVsrpVirRtrTrackPriority OBJECT-TYPE
		 SYNTAX   INTEGER (1..254)
		 MAX-ACCESS   read-write
		 STATUS   current
		 DESCRIPTION
			"The higher the number the higher the priority is.
			after this object is configured, the snVsrpVirRtrCurrPriority 
			of this interface will be adjusted dynamically with this
			track priority when the Track Port states first
			changes from UP to DOWN."
		 ::= { snVsrpVirRtrEntry 5 }

	 snVsrpVirRtrCurrPriority OBJECT-TYPE
		 SYNTAX   INTEGER (1..254)
		 MAX-ACCESS   read-only
		 STATUS   current
		 DESCRIPTION
			"The higher the number the higher the priority is.
			This object will be adjusted dynamically with the
			track priority when the Track Port states first
			changes from UP to DOWN."
		 ::= { snVsrpVirRtrEntry 6 }

	 snVsrpVirRtrHelloInt OBJECT-TYPE
		 SYNTAX   INTEGER (1..84)
		 MAX-ACCESS   read-write
		 STATUS   current
		 DESCRIPTION
			"Time interval between advertisements (seconds)."
		 DEFVAL { 1 }
		 ::= { snVsrpVirRtrEntry 7 }

	 snVsrpVirRtrDeadInt OBJECT-TYPE
		 SYNTAX   INTEGER (0..84)
		 MAX-ACCESS   read-write
		 STATUS   current
		 DESCRIPTION
			"Dead interval (seconds)."
		 ::= { snVsrpVirRtrEntry 8 }

	 snVsrpVirRtrPreemptMode OBJECT-TYPE
		 SYNTAX   INTEGER { disabled(0), enabled(1) }
		 MAX-ACCESS   read-write
		 STATUS   current
		 DESCRIPTION
			"This mode controls whether a higher priority Backup router
			preempts a lower priority Master.  The mode with enabled(1)
			allow preemption and disabled(0) prohibit preemption."
		 DEFVAL { enabled }
		 ::= { snVsrpVirRtrEntry 9 }

	 snVsrpVirRtrState OBJECT-TYPE
		 SYNTAX   INTEGER {
					init(0),
					master(1),
					backup(2)
				  }
		 MAX-ACCESS   read-only
		 STATUS   current
		 DESCRIPTION
			"This object specifies the vsrp Router's interface state as:
			init(0)...initialization state.
			master(1)...master state.
			backup(2)...backup state."
		 ::= { snVsrpVirRtrEntry 10 }

	snVsrpVirRtrIpAddrMask OBJECT-TYPE
		 SYNTAX  OCTET STRING (SIZE(64))
		 MAX-ACCESS   read-write
		 STATUS   current
		 DESCRIPTION
			"The numbers of IP Addresses of this virtual router of this 
			interface, this holds good for L3 vsrp."
		 ::= { snVsrpVirRtrEntry 11 }

	 snVsrpVirRtrActivate OBJECT-TYPE
		 SYNTAX   INTEGER {
					disabled(0),
					enabled(1)
				  }
		 MAX-ACCESS   read-write
		 STATUS   current
		 DESCRIPTION
			"This object specifies the vsrp Router's activate command as:
			disabled(0)...deactivate this vsrp Router.
			enabled(1)....activate this vsrp Router."
		 ::= { snVsrpVirRtrEntry 12 }

	 snVsrpVirRtrTrackPortList OBJECT-TYPE
		 SYNTAX  OCTET STRING
		 MAX-ACCESS   read-write
		 STATUS   current
		 DESCRIPTION
			"This object specifies the identity of the physical port and virtual ports
			whose state is to be monitored.  Each port index is 
			an ifIndex, if there are consecutive 4 or more ifIndex then
			they will be encoded like below. 
			Encoding and decoding scheme is range based:
			Each range prefix with 0000 (2 octets) where 0000 is not valid 
			ifIndex. Next 2 octets indicates lower range ifIndex, followed by 2 
			octets of higher range ifIndex. Individual(non range) ones will be displayed as it is.
			Ex:
			port list: 0001..0005 0015 0032..0047
			Port list in PDU:  0000 0001 0005 000f 0000 0020 002f.
			If this object is configured
			then the Preference Level of this interface will be adjusted
			dynamically depending on the state of the Track Port.
			The interface's Preference Level is reduced by value of 
			Preference Level parameter when the Track Port states first
			changes from UP to DOWN.  When the Track Port next comes up
			the interface's Preference Level is increased by the amount
			specified by the Preference Level.
			The router VSRP physical track port membership."
		 ::= { snVsrpVirRtrEntry 13 }

	 snVsrpVirRtrAdvertiseBackup OBJECT-TYPE
		 SYNTAX   INTEGER { disabled(0), enabled(1) }
		 MAX-ACCESS   read-write
		 STATUS   current
		 DESCRIPTION
			"Set Advertise this backup router to master "
		 DEFVAL { disabled }
		 ::= { snVsrpVirRtrEntry 14 }			  
		 
	snVsrpVirRtrHoldDownInt OBJECT-TYPE
		 SYNTAX   INTEGER (1..84)
		 MAX-ACCESS   read-write
		 STATUS   current
		 DESCRIPTION
			"VSRP protection mechanism, an extra delay for a switch in
			backup mode to upgrade itself to master mode"
		 DEFVAL { 2 }
		 ::= { snVsrpVirRtrEntry 15 }

	 snVsrpVirRtrInitTtl OBJECT-TYPE
		 SYNTAX   INTEGER (1..255)
		 MAX-ACCESS   read-write
		 STATUS   current
		 DESCRIPTION
			"VSRP:TTL in the hello packet to regulate the distance that a hello packet 
			can travel. It prevents the flooding of VSRP hello packets in the network"
		 DEFVAL { 2 }
		 ::= { snVsrpVirRtrEntry 16 }

	 snVsrpVirRtrIncPortList OBJECT-TYPE
		 SYNTAX  OCTET STRING
		 MAX-ACCESS   read-write
		 STATUS   current
		 DESCRIPTION
			"Include all free ports of the VLAN into its control ports"
		 ::= { snVsrpVirRtrEntry 17 }

	 snVsrpVirRtrSave OBJECT-TYPE
		 SYNTAX   INTEGER { disabled(0), enabled(1) }
		 MAX-ACCESS   read-write
		 STATUS   current
		 DESCRIPTION
			"Set VSRP to save current parameters value"
		 DEFVAL { disabled }
		 ::= { snVsrpVirRtrEntry 18 }

	 snVsrpVirRtrBackupInt OBJECT-TYPE
		 SYNTAX   INTEGER (60..3600)
		 MAX-ACCESS   read-write
		 STATUS   current
		 DESCRIPTION
			"Time interval between backup routers hello message advertisements (seconds)."
		 DEFVAL { 60 }
		 ::= { snVsrpVirRtrEntry 19 }
		 
	snVsrpVirRtrRowStatus OBJECT-TYPE
		 SYNTAX   INTEGER {
					invalid(1),
					valid(2),
					delete(3),
					create(4),
					modify(5)
				  }
		 MAX-ACCESS   read-write
		 STATUS   current
		 DESCRIPTION
			"This object is used to create and
			 delete row in the table and control
			 if they are used. The values
			 that can be written are:
			 delete(3)...deletes the row
			 create(4)...creates a new row
			 modify(5)...modifies an existing row

			 VirRtr the row exists, then a SET with
			 value of create(4) returns error
			 'badValue'. Deleted rows go away
			 immediately. The following values
			 can be returned on reads:
			 noSuch(0)...no such row
			 invalid(1)...Setting it to 'invalid' has the effect of
						  rendering it inoperative..
			 valid(2)....the row exists and is valid"
		 ::= { snVsrpVirRtrEntry 20}

	 snVsrpVirRtrRxArpPktDropCnts OBJECT-TYPE
		 SYNTAX   Counter32
		 MAX-ACCESS   read-only
		 STATUS   current
		 DESCRIPTION
			"The received vsrp ARP Packet Drop Counts."
		 ::= { snVsrpVirRtrEntry 21 }

	 snVsrpVirRtrRxIpPktDropCnts OBJECT-TYPE
		 SYNTAX   Counter32
		 MAX-ACCESS   read-only
		 STATUS   current
		 DESCRIPTION
			"The received VSRP IP Packet Drop Counts."
		 ::= { snVsrpVirRtrEntry 22 }

	 snVsrpVirRtrRxPortMismatchCnts OBJECT-TYPE
		 SYNTAX   Counter32
		 MAX-ACCESS   read-only
		 STATUS   current
		 DESCRIPTION
			"The received vsrp Port mismatching Counts."
		 ::= { snVsrpVirRtrEntry 23 }

	 snVsrpVirRtrRxNumOfIpMismatchCnts OBJECT-TYPE
		 SYNTAX   Counter32
		 MAX-ACCESS   read-only
		 STATUS   current
		 DESCRIPTION
			"The received VSRP Number of IP Addresses mismatching Counts."
		 ::= { snVsrpVirRtrEntry 24 }

	 snVsrpVirRtrRxIpMismatchCnts OBJECT-TYPE
		 SYNTAX   Counter32
		 MAX-ACCESS   read-only
		 STATUS   current
		 DESCRIPTION
			"The received vsrp IP Address mismatching Counts."
		 ::= { snVsrpVirRtrEntry 25 }

	 snVsrpVirRtrRxHelloIntMismatchCnts OBJECT-TYPE
		 SYNTAX   Counter32
		 MAX-ACCESS   read-only
		 STATUS   current
		 DESCRIPTION
			"The counts of the virtual router interface with hello interval mismatch counts."
		 ::= { snVsrpVirRtrEntry 26 }

	 snVsrpVirRtrRxPriorityZeroFromMasterCnts OBJECT-TYPE
		 SYNTAX   Counter32
		 MAX-ACCESS   read-only
		 STATUS   current
		 DESCRIPTION
			"The counts of the virtual router interface with Priority zero from the master."
		 ::= { snVsrpVirRtrEntry 27 }

	 snVsrpVirRtrRxHigherPriorityCnts OBJECT-TYPE
		 SYNTAX   Counter32
		 MAX-ACCESS   read-only
		 STATUS   current
		 DESCRIPTION
			"The counts of the virtual router interface with higher Priority."
		 ::= { snVsrpVirRtrEntry 28 }

	 snVsrpVirRtrTransToMasterStateCnts OBJECT-TYPE
		 SYNTAX   Counter32
		 MAX-ACCESS   read-only
		 STATUS   current
		 DESCRIPTION
			"The counts of the virtual router interface transition to master state."
		 ::= { snVsrpVirRtrEntry 29 }

	 snVsrpVirRtrTransToBackupStateCnts OBJECT-TYPE
		 SYNTAX   Counter32
		 MAX-ACCESS   read-only
		 STATUS   current
		 DESCRIPTION
			"The counts of the virtual router interface transition to backup state."
		 ::= { snVsrpVirRtrEntry 30 }

	 snVsrpVirRtrCurrDeadInt OBJECT-TYPE
		 SYNTAX   Integer32 
		 MAX-ACCESS   read-only
		 STATUS   current
		 DESCRIPTION
			"Current Dead interval (in 100 milliseconds)."
		 ::= { snVsrpVirRtrEntry 31 }

	snVsrpVirRtrCurHelloInt OBJECT-TYPE
		 SYNTAX   INTEGER (1..84)
		 MAX-ACCESS   read-only
		 STATUS   current
		 DESCRIPTION
			"Set backup router hello interval"
		 ::= { snVsrpVirRtrEntry 32 }

	snVsrpVirRtrCurHoldDownInt OBJECT-TYPE
		 SYNTAX   INTEGER (1..84)
		 MAX-ACCESS   read-only
		 STATUS   current
		 DESCRIPTION
			"VSRP protection mechanism, an extra delay for a switch in
			backup mode to upgrade itself to master mode"
		 ::= { snVsrpVirRtrEntry 33 }

	 snVsrpVirRtrCurInitTtl OBJECT-TYPE
		 SYNTAX   INTEGER (1..255)
		 MAX-ACCESS   read-only
		 STATUS   current
		 DESCRIPTION
			"VSRP:TTL in the hello packet to regulate the distance that a hello packet 
			can travel. It prevents the flooding of VSRP hello packets in the network"
		 ::= { snVsrpVirRtrEntry 34 }

	snVsrpVirRtrHelloMacAddress    OBJECT-TYPE
		SYNTAX  MacAddress
		MAX-ACCESS  read-only
		STATUS  current
		DESCRIPTION
			"Hello MAC address."
		::= { snVsrpVirRtrEntry 35 }

	 snVsrpVirRtrMasterIpAddr OBJECT-TYPE
		 SYNTAX       IpAddress
		 MAX-ACCESS       read-only
		 STATUS       current
		 DESCRIPTION
			 "The master router's real/virtual (primary) IP address. This is
			 the IP address listed as the source in vsrp advertisement
			 last received by this virtual router."
		 ::= { snVsrpVirRtrEntry 36 }

		
END		
FOUNDRY-SN-ARP-GROUP-MIB DEFINITIONS ::= BEGIN
-- Foundry ARP MIB Release 1.0.0
-- Revision 1 2/9/04
-- Copyright 2003 Foundry Networks, Inc.
-- All rights reserved.
-- This Foundry Networks SNMP Management Information Base 
-- Specification embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.

-- SECTION 1: Top Level Definitions
-- Imports

IMPORTS

MODULE-IDENTITY, OBJECT-TYPE, Counter32
		FROM SNMPv2-SMI
snSwitch
		FROM FOUNDRY-SN-ROOT-MIB;

snArpInfo MODULE-IDENTITY
    LAST-UPDATED "200402090000Z"
    ORGANIZATION "Foundry Network"
    CONTACT-INFO "support@foundrynet.com"
    DESCRIPTION  "The Enterprise MIB for ARP support in SNMP.
               This Foundry Networks SNMP Management Information Base 
               Specification embodies Foundry Networks' confidential and
               proprietary intellectual property. Foundry Networks retains all
               title and ownership in the Specification, including any
               revisions.
               This Specification is supplied AS IS, and Foundry Networks makes
               no warranty, either express or implied, as to the use,
               operation, condition, or performance of the Specification.
               "
       ::= { snSwitch 22 }

snArpStats                    OBJECT IDENTIFIER ::= { snArpInfo 1 }

snArpStatsTotalReceived OBJECT-TYPE
    SYNTAX         Counter32
    MAX-ACCESS  read-only
    STATUS         current
    DESCRIPTION
            "The total number of ARP packets received from
            interfaces, including those received in error."
              ::= { snArpStats 1 }

snArpStatsRequestReceived OBJECT-TYPE
    SYNTAX         Counter32
    MAX-ACCESS  read-only
    STATUS         current
    DESCRIPTION
            "The total number of input ARP Request packets received from
            interfaces."
              ::= { snArpStats 2 }

snArpStatsRequestSent OBJECT-TYPE
    SYNTAX         Counter32
    MAX-ACCESS  read-only
    STATUS         current
    DESCRIPTION
            "The total number of output ARP Request packets sent from
            interfaces."
              ::= { snArpStats 3 }

snArpStatsRepliesSent OBJECT-TYPE
    SYNTAX         Counter32
    MAX-ACCESS  read-only
    STATUS         current
    DESCRIPTION
            "The total number of output ARP Reply packets sent from
            interfaces."
              ::= { snArpStats 4 }

snArpStatsPendingDrop OBJECT-TYPE
    SYNTAX         Counter32
    MAX-ACCESS  read-only
    STATUS         current
    DESCRIPTION
            "The total number of ARP pending packets discarded."
              ::= { snArpStats 5 }

snArpStatsInvalidSource OBJECT-TYPE
    SYNTAX         Counter32
    MAX-ACCESS  read-only
    STATUS         current
    DESCRIPTION
            "The total number of ARP packets received with invalid
            sender protocol address."
              ::= { snArpStats 6 }

snArpStatsInvalidDestination OBJECT-TYPE
    SYNTAX         Counter32
    MAX-ACCESS  read-only
    STATUS         current
    DESCRIPTION
            "The total number of ARP packets received with invalid
            destination protocol address."
              ::= { snArpStats 7 }

		
END		
FOUNDRY-SN-IPX-MIB DEFINITIONS ::= BEGIN

IMPORTS
	MODULE-IDENTITY, OBJECT-TYPE,Counter32,Integer32 
		FROM SNMPv2-SMI
	TEXTUAL-CONVENTION
		FROM SNMPv2-TC		
	router
		FROM FOUNDRY-SN-ROOT-MIB
	PhysAddress
		FROM FOUNDRY-SN-SWITCH-GROUP-MIB;

snIpx MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"        
	REVISION     "200909300000Z" -- September 30, 2009
	DESCRIPTION
			"convert from SMIv1 to SMIv2"
   ::= { router 1 }
	-- textual conventions

	RtrStatus ::= TEXTUAL-CONVENTION
		STATUS	  current
		DESCRIPTION
			"
			RtrStatus Values
			"
		SYNTAX	INTEGER { disabled(0), enabled (1) }
		


	ClearStatus ::= TEXTUAL-CONVENTION
		STATUS	  current
		DESCRIPTION
			"
			Clear Status Values
			"
		SYNTAX	INTEGER { normal(0), clear(1) }


	PortIndex ::= TEXTUAL-CONVENTION
		STATUS	  current
		DESCRIPTION
			"
			The bits 0-7 = port number. 
			The bits 8-15 = slot number (slot for chassis only).
			ve port format         bits 16-24 = 0x01, bits 0-15 = ve number
			loopback port format bits 16-24 = 0x02, bits 0-15= lb number	
			"
		SYNTAX	Integer32(1..3900)


	Action ::= TEXTUAL-CONVENTION
		STATUS	  current
		DESCRIPTION
			"
			Represents a action value such as deny or permit.
			"
		SYNTAX	INTEGER { deny(0), permit(1) }

	 NetNumber::= TEXTUAL-CONVENTION
		STATUS	  current
		DESCRIPTION
			"
			"
		SYNTAX	OCTET STRING (SIZE(4))

-- SECTION 2: MIB 

-- Router IPX MIB

snIpxGen			OBJECT IDENTIFIER ::= { snIpx 1 }
snIpxCache			OBJECT IDENTIFIER ::= { snIpx 2 }
snIpxRoute			OBJECT IDENTIFIER ::= { snIpx 3 }
snIpxServer			OBJECT IDENTIFIER ::= { snIpx 4 }
snIpxFwdFilter		OBJECT IDENTIFIER ::= { snIpx 5 }
snIpxRipFilter		OBJECT IDENTIFIER ::= { snIpx 6 }
snIpxSapFilter		OBJECT IDENTIFIER ::= { snIpx 7 }
snIpxIfFwdAccess	OBJECT IDENTIFIER ::= { snIpx 8 }
snIpxIfRipAccess	OBJECT IDENTIFIER ::= { snIpx 9 }
snIpxIfSapAccess	OBJECT IDENTIFIER ::= { snIpx 10 }
snIpxPortAddr		OBJECT IDENTIFIER ::= { snIpx 11 }
snIpxPortCounters	OBJECT IDENTIFIER ::= { snIpx 12 }

-- IPX General MIBs

snIpxRoutingMode 	     OBJECT-TYPE
	SYNTAX	RtrStatus
	MAX-ACCESS  read-write
	STATUS  current
	DESCRIPTION
		"Enabled/Disabled System IPX Routing Mode status."
	::= { snIpxGen 1 }

snIpxNetBiosFilterMode		    OBJECT-TYPE
	SYNTAX	RtrStatus
	MAX-ACCESS  read-write
	STATUS  current
	DESCRIPTION
		"Enabled/Disabled NetBios Filter Mode status."
	::= { snIpxGen 2 }

				
snIpxClearCache 		OBJECT-TYPE
	SYNTAX  ClearStatus
	MAX-ACCESS  read-write
	STATUS  current
	DESCRIPTION
		"clear(1) will clear cache table."
	::= { snIpxGen 3 }

snIpxClearRoute 		OBJECT-TYPE
	SYNTAX  ClearStatus
	MAX-ACCESS  read-write
	STATUS  current
	DESCRIPTION
		"clear(1) will clear ipx route table."
	::= { snIpxGen 4 }

snIpxClearTrafficCnts		OBJECT-TYPE
	SYNTAX  ClearStatus
	MAX-ACCESS  read-write
	STATUS  current
	DESCRIPTION
		"clear(1) will clear ipx all traffic counters.
		 - snIpxRcvPktsCnt, snIpxFwdPktsCnt,
		   snIpxRcvDropPktsCnt, snIpxTxDropPktsCnt,
		   snIpxRcvFiltPktsCnt, snIpxTxFiltPktsCnt."
	::= { snIpxGen 5 }


snIpxRcvPktsCnt 		OBJECT-TYPE
	SYNTAX	Counter32
	MAX-ACCESS	read-only
	STATUS  current
	DESCRIPTION
		"IPX incoming packets counter."
	::= { snIpxGen 6 }


snIpxTxPktsCnt 		OBJECT-TYPE
	SYNTAX	Counter32
	MAX-ACCESS	read-only
	STATUS  current
	DESCRIPTION
		"IPX Outgoing packets counter."
	::= { snIpxGen 7 }


snIpxFwdPktsCnt 		OBJECT-TYPE
	SYNTAX	Counter32
	MAX-ACCESS	read-only
	STATUS  current
	DESCRIPTION
		"IPX forwarding packets counter."
	::= { snIpxGen 8 }

snIpxRcvDropPktsCnt		OBJECT-TYPE
	SYNTAX	Counter32
	MAX-ACCESS	read-only
	STATUS  current
	DESCRIPTION
		"IPX receiving drop packets counter."
	::= { snIpxGen 9 }

snIpxRcvFiltPktsCnt		OBJECT-TYPE
	SYNTAX	Counter32
	MAX-ACCESS	read-only
	STATUS  current
	DESCRIPTION
		"IPX receiving filter packets counter."
	::= { snIpxGen 10 }

snIpxRipGblFiltList    OBJECT-TYPE
	SYNTAX	OCTET STRING(SIZE(0..32))
	MAX-ACCESS  read-write
	STATUS  current
	DESCRIPTION
		"An IPX RIP Global Filter List. Null value indicates no filter list."
	::= { snIpxGen 11 }

snIpxRipFiltOnAllPort		OBJECT-TYPE
	SYNTAX	 INTEGER {
		valid(1),
		deleteAllInBound(2),
		deleteAllOutBound(3),
		addAllInBound(4),
		addAllOutBound(5)
	}
	MAX-ACCESS	read-write
	STATUS  current
	DESCRIPTION
	"Apply the IPX RIP Global filter list snIpxRipGblFiltList to 
	 all interfaces. This object is used to add all RIP filter 
	 lists and delete all RIP filter lists to/from all ports.
	 Prior to sending this command, snIpxRipGblFiltList must be ready.
	 The values that can be written are:
	 deleteAllInBound(2)...delete all in-bound filter lists from all ports. 
	 deleteAllOutBound(3)..delete all out-bound filter lists from all ports.
	 addAllInBound(4)......add all in-bound filter lists to all ports.
	 addAllOutBound(5).....add all out-bound filter lists to all ports.

	 If set operation is failed, then a SET with
	 value of (2)or(3) returns error 'GenError'. 
	 Deleted(2)&(3) go away immediately. 
	 The following values can be returned on reads:
	 noSuch(0)...no such operation yet.
	 valid(1)....set operation is done and is valid"

	::= { snIpxGen 12 }

snIpxSapGblFiltList    OBJECT-TYPE
	SYNTAX	OCTET STRING(SIZE(0..32))
	MAX-ACCESS  read-write
	STATUS  current
	DESCRIPTION
		"An IPX SAP Global Filter List. Null value indicates no filter list"
	::= { snIpxGen 13 }


snIpxSapFiltOnAllPort		OBJECT-TYPE
	SYNTAX	 INTEGER {
		valid(1),
		deleteAllInBound(2),
		deleteAllOutBound(3),
		addAllInBound(4),
		addAllOutBound(5)
	}
	MAX-ACCESS	read-write
	STATUS  current
	DESCRIPTION
	"Apply the IPX SAP Global filter list snIpxSapGblFiltList to 
	 all interfaces. This object is used to add all RIP filter 
	 lists and delete all SAP filter lists to/from all ports.
	 Prior to sending this command, snIpxSapGblFiltList must be ready.
	 The values that can be written are:
	 deleteAllInBound(2)...delete all in-bound filter lists from all ports. 
	 deleteAllOutBound(3)..delete all out-bound filter lists from all ports.
	 addAllInBound(4)......add all in-bound filter lists to all ports.
	 addAllOutBound(5).....add all out-bound filter lists to all ports.

	 If set operation is failed, then a SET with
	 value of (2)or(3) returns error 'GenError'. 
	 Deleted(2)&(3) go away immediately. 
	 The following values can be returned on reads:
	 noSuch(0)...no such operation yet.
	 valid(1)....set operation is done and is valid"
	::= { snIpxGen 14 }

snIpxTxDropPktsCnt		OBJECT-TYPE
	SYNTAX	Counter32
	MAX-ACCESS	read-only
	STATUS  current
	DESCRIPTION
		"IPX transmitting drop packets counter."
	::= { snIpxGen 15 }

snIpxTxFiltPktsCnt		OBJECT-TYPE
	SYNTAX	Counter32
	MAX-ACCESS	read-only
	STATUS  current
	DESCRIPTION
		"IPX transmitting filter packets counter."
	::= { snIpxGen 16 }


-- IPX Cache table

snIpxCacheTable  OBJECT-TYPE
	SYNTAX	SEQUENCE OF SnIpxCacheEntry
	MAX-ACCESS  not-accessible
	STATUS  current
	DESCRIPTION
		"IPX Cache table."
	::= { snIpxCache 1 }

snIpxCacheEntry  OBJECT-TYPE
	SYNTAX	SnIpxCacheEntry
	MAX-ACCESS  not-accessible
	STATUS  current
	DESCRIPTION
		"An entry in the IPX Cache table."
	INDEX	{ snIpxCacheIndex }
	::= { snIpxCacheTable 1 }

SnIpxCacheEntry ::= SEQUENCE {
	snIpxCacheIndex
		Integer32,
	snIpxCacheNetNum
		NetNumber,
	snIpxCacheNode
		PhysAddress,
	snIpxCacheOutFilter
		RtrStatus,
	snIpxCacheEncap  
		INTEGER,
	snIpxCachePort
		PortIndex
	}

snIpxCacheIndex  OBJECT-TYPE
	SYNTAX   Integer32
	MAX-ACCESS  read-only
	STATUS  current
	DESCRIPTION
		"The table index for a IPX Cache entry."
	::= { snIpxCacheEntry 1 }


snIpxCacheNetNum  OBJECT-TYPE
	SYNTAX	NetNumber
	MAX-ACCESS	read-only
	STATUS  current
	DESCRIPTION
		"Cache Network number."
	::= { snIpxCacheEntry 2 }

snIpxCacheNode  OBJECT-TYPE
	SYNTAX	PhysAddress
	MAX-ACCESS  read-only
	STATUS  current
	DESCRIPTION
		"Cache Node Number."
	::= { snIpxCacheEntry 3 }

snIpxCacheOutFilter	OBJECT-TYPE
	SYNTAX	RtrStatus
	MAX-ACCESS  read-only
	STATUS  current
	DESCRIPTION
		"Cache Outbound Filter is ether disabled(0) or enabled(1)."
	::= { snIpxCacheEntry 4 }

snIpxCacheEncap  OBJECT-TYPE
	SYNTAX	 INTEGER {
		ethernetII(1),
		ethernet8022(2),
		ethernet8023(3),
		ethernetSnap(4)
	}
	MAX-ACCESS	read-only
	STATUS  current
	DESCRIPTION
		"The IPX encapsulation frame type."
	::= { snIpxCacheEntry 5 }


snIpxCachePort  OBJECT-TYPE
	SYNTAX	PortIndex
	MAX-ACCESS	read-only
	STATUS  current
	DESCRIPTION
		"IPX Router Port number." 
	::= { snIpxCacheEntry 6 }




-- IPX route table

snIpxRouteTable  OBJECT-TYPE
	SYNTAX	SEQUENCE OF SnIpxRouteEntry
	MAX-ACCESS  not-accessible
	STATUS  current
	DESCRIPTION
		"IPX route table."
	::= { snIpxRoute 1 }

snIpxRouteEntry  OBJECT-TYPE
	SYNTAX	SnIpxRouteEntry
	MAX-ACCESS  not-accessible
	STATUS  current
	DESCRIPTION
		"An entry in the IPX route table."
	INDEX	{ snIpxRouteIndex }
	::= { snIpxRouteTable 1 }

SnIpxRouteEntry ::= SEQUENCE {
	snIpxRouteIndex
		Integer32,
	snIpxDestNetNum
		NetNumber,
	snIpxFwdRouterNode
		PhysAddress,
	snIpxDestHopCnts
		Integer32,
	snIpxRouteMetric
		Integer32,
	snIpxDestPort
		Integer32
	}

snIpxRouteIndex  OBJECT-TYPE
	SYNTAX   Integer32
	MAX-ACCESS  read-only
	STATUS  current
	DESCRIPTION
		"The table index for a IPX route entry."
	::= { snIpxRouteEntry 1 }

snIpxDestNetNum  OBJECT-TYPE
	SYNTAX	NetNumber
	MAX-ACCESS	read-only
	STATUS  current
	DESCRIPTION
		"Destination Network number."
	::= { snIpxRouteEntry 2 }

snIpxFwdRouterNode  OBJECT-TYPE
	SYNTAX	PhysAddress
	MAX-ACCESS  read-only
	STATUS  current
	DESCRIPTION
		"Forward Router Node Number."
	::= { snIpxRouteEntry 3 }

snIpxDestHopCnts  OBJECT-TYPE
	SYNTAX   Integer32
	MAX-ACCESS	read-only
	STATUS  current
	DESCRIPTION
		"Number of hops to reach the
		 destination."
	::= { snIpxRouteEntry 4 }

snIpxRouteMetric  OBJECT-TYPE
	SYNTAX Integer32
	MAX-ACCESS	read-only
	STATUS  current
	DESCRIPTION
		"The metrics to next hop router."
	::= { snIpxRouteEntry 5 }

snIpxDestPort  OBJECT-TYPE
	SYNTAX Integer32
	MAX-ACCESS	read-only
	STATUS  current
	DESCRIPTION
		"The destination port."
	::= { snIpxRouteEntry 6 }


-- IPX Server table

snIpxServerTable  OBJECT-TYPE
	SYNTAX	SEQUENCE OF SnIpxServerEntry
	MAX-ACCESS  not-accessible
	STATUS  current
	DESCRIPTION
		"IPX Server table."
	::= { snIpxServer 1 }

snIpxServerEntry  OBJECT-TYPE
	SYNTAX	SnIpxServerEntry
	MAX-ACCESS  not-accessible
	STATUS  current
	DESCRIPTION
		"An entry in the IPX Server table."
	INDEX	{ snIpxServerIndex }
	::= { snIpxServerTable 1 }

SnIpxServerEntry ::= SEQUENCE {
	snIpxServerIndex
		Integer32,
	snIpxServerType
		Integer32,
	snIpxServerNetNum
		NetNumber,
	snIpxServerNode
		PhysAddress,
	snIpxServerSocket
		Integer32,
	snIpxServerHopCnts  
		Integer32,
	snIpxServerName
		OCTET STRING
	}

snIpxServerIndex  OBJECT-TYPE
	SYNTAX   Integer32
	MAX-ACCESS  read-only
	STATUS  current
	DESCRIPTION
		"The table index for a IPX Server entry."
	::= { snIpxServerEntry 1 }


snIpxServerType  OBJECT-TYPE
	SYNTAX   Integer32
	MAX-ACCESS	read-only
	STATUS  current
	DESCRIPTION
		"IPX Server Type."
	::= { snIpxServerEntry 2 }

snIpxServerNetNum  OBJECT-TYPE
	SYNTAX	NetNumber
	MAX-ACCESS	read-only
	STATUS  current
	DESCRIPTION
		"Server Network number."
	::= { snIpxServerEntry 3 }

snIpxServerNode  OBJECT-TYPE
	SYNTAX	PhysAddress
	MAX-ACCESS  read-only
	STATUS  current
	DESCRIPTION
		"Server Node Number."
	::= { snIpxServerEntry 4 }

snIpxServerSocket	OBJECT-TYPE
	SYNTAX   Integer32
	MAX-ACCESS  read-only
	STATUS  current
	DESCRIPTION
		"Server Socket Number."
	::= { snIpxServerEntry 5 }

snIpxServerHopCnts  OBJECT-TYPE
	SYNTAX   Integer32
	MAX-ACCESS	read-only
	STATUS  current
	DESCRIPTION
		"Number of intervening networks to reach the
		 server."
	::= { snIpxServerEntry 6 }


snIpxServerName  OBJECT-TYPE
	SYNTAX	OCTET STRING(SIZE(0..47))
	MAX-ACCESS	read-only
	STATUS  current
	DESCRIPTION
		"IPX Server Name."
	::= { snIpxServerEntry 7 }



-- IPX Forward Filter table

snIpxFwdFilterTable	  OBJECT-TYPE
	SYNTAX	SEQUENCE OF SnIpxFwdFilterEntry
	MAX-ACCESS  not-accessible
	STATUS  current
	DESCRIPTION
		"IPX Forward Filter table."
	::= { snIpxFwdFilter 1 }

snIpxFwdFilterEntry	  OBJECT-TYPE
	SYNTAX	SnIpxFwdFilterEntry
	MAX-ACCESS  not-accessible
	STATUS  current
	DESCRIPTION
		"An entry in the IPX Forward Filter table."
	INDEX	{ snIpxFwdFilterIdx }
	::= { snIpxFwdFilterTable 1 }

SnIpxFwdFilterEntry ::= SEQUENCE {
	snIpxFwdFilterIdx
		Integer32,
	snIpxFwdFilterAction
		Action,
	snIpxFwdFilterSocket
		Integer32,
	snIpxFwdFilterSrcNet
		NetNumber,
	snIpxFwdFilterSrcNode
		PhysAddress,
	snIpxFwdFilterDestNet
		NetNumber,
	snIpxFwdFilterDestNode
		PhysAddress,
	snIpxFwdFilterRowStatus
		INTEGER
	}

snIpxFwdFilterIdx       OBJECT-TYPE
	SYNTAX   Integer32 
	MAX-ACCESS  read-only
	STATUS  current
	DESCRIPTION
		"The filter ID for a filter entry."
	::= { snIpxFwdFilterEntry 1 }

snIpxFwdFilterAction	  OBJECT-TYPE
	SYNTAX  Action 
	MAX-ACCESS  read-write
	STATUS  current
	DESCRIPTION
		"Action to take if the ipx packet match
		with this filter."
	::= { snIpxFwdFilterEntry 2 }

snIpxFwdFilterSocket	OBJECT-TYPE
	SYNTAX   Integer32
	MAX-ACCESS  read-write
	STATUS  current
	DESCRIPTION
		"IPX Forward Filter Socket Number."
	::= { snIpxFwdFilterEntry 3 }

snIpxFwdFilterSrcNet	OBJECT-TYPE
	SYNTAX	NetNumber
	MAX-ACCESS  read-write
	STATUS  current
	DESCRIPTION
		"Source Network Number."
	::= { snIpxFwdFilterEntry 4 }

snIpxFwdFilterSrcNode  OBJECT-TYPE
	SYNTAX	PhysAddress
	MAX-ACCESS  read-write
	STATUS  current
	DESCRIPTION
		"Source Node Number."
	::= { snIpxFwdFilterEntry 5 }

snIpxFwdFilterDestNet	 OBJECT-TYPE
	SYNTAX	NetNumber
	MAX-ACCESS  read-write
	STATUS  current
	DESCRIPTION
		"Destination Network Number."
	::= { snIpxFwdFilterEntry 6 }

snIpxFwdFilterDestNode	OBJECT-TYPE
	SYNTAX	PhysAddress
	MAX-ACCESS  read-write
	STATUS  current
	DESCRIPTION
		"Destination Node Number."
	::= { snIpxFwdFilterEntry 7 }

snIpxFwdFilterRowStatus OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpxFwdFilterEntry 8 }



-- IPX RIP Filter table

snIpxRipFilterTable	  OBJECT-TYPE
	SYNTAX	SEQUENCE OF SnIpxRipFilterEntry
	MAX-ACCESS  not-accessible
	STATUS  current
	DESCRIPTION
		"IPX RIP Filter table."
	::= { snIpxRipFilter 1 }

snIpxRipFilterEntry	  OBJECT-TYPE
	SYNTAX	SnIpxRipFilterEntry
	MAX-ACCESS  not-accessible
	STATUS  current
	DESCRIPTION
		"An entry in the IPX RIP Filter table."
	INDEX	{ snIpxRipFilterId }
	::= { snIpxRipFilterTable 1 }

SnIpxRipFilterEntry ::= SEQUENCE {
	snIpxRipFilterId
		Integer32,
	snIpxRipFilterAction
		Action,
	snIpxRipFilterNet
		NetNumber,
	snIpxRipFilterMask
		NetNumber,
	snIpxRipFilterRowStatus
		INTEGER
	}

snIpxRipFilterId       OBJECT-TYPE
	SYNTAX   Integer32
	MAX-ACCESS  read-only
	STATUS  current
	DESCRIPTION
		"The filter ID for a filter entry."
	::= { snIpxRipFilterEntry 1 }

snIpxRipFilterAction	  OBJECT-TYPE
	SYNTAX  Action 
	MAX-ACCESS  read-write
	STATUS  current
	DESCRIPTION
		"Action to take if the ipx packet match
		with this filter."
	::= { snIpxRipFilterEntry 2 }

snIpxRipFilterNet    OBJECT-TYPE
	SYNTAX	NetNumber
	MAX-ACCESS  read-write
	STATUS  current
	DESCRIPTION
		"IPX RIP Filter Network number."
	::= { snIpxRipFilterEntry 3 }

snIpxRipFilterMask    OBJECT-TYPE
	SYNTAX	NetNumber
	MAX-ACCESS  read-write
	STATUS  current
	DESCRIPTION
		"IPX RIP Filter Network/Subnet Mask."
	::= { snIpxRipFilterEntry 4 }


snIpxRipFilterRowStatus OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpxRipFilterEntry 5 }



-- IPX SAP Filter table

snIpxSapFilterTable	  OBJECT-TYPE
	SYNTAX	SEQUENCE OF SnIpxSapFilterEntry
	MAX-ACCESS  not-accessible
	STATUS  current
	DESCRIPTION
		"IPX SAP Filter table."
	::= { snIpxSapFilter 1 }

snIpxSapFilterEntry	  OBJECT-TYPE
	SYNTAX	SnIpxSapFilterEntry
	MAX-ACCESS  not-accessible
	STATUS  current
	DESCRIPTION
		"An entry in the IPX SAP Filter table."
	INDEX	{ snIpxSapFilterId }
	::= { snIpxSapFilterTable 1 }

SnIpxSapFilterEntry ::= SEQUENCE {
	snIpxSapFilterId
		Integer32,
	snIpxSapFilterAction
		Action,
	snIpxSapFilterType
		Integer32,
	snIpxSapFilterName
		OCTET STRING,
	snIpxSapFilterRowStatus
		INTEGER
	}

snIpxSapFilterId       OBJECT-TYPE
	SYNTAX   Integer32
	MAX-ACCESS  read-only
	STATUS  current
	DESCRIPTION
		"The filter ID for a filter entry."
	::= { snIpxSapFilterEntry 1 }

snIpxSapFilterAction	  OBJECT-TYPE
	SYNTAX  Action 
	MAX-ACCESS  read-write
	STATUS  current
	DESCRIPTION
		"Action to take if the ipx packet match
		with this filter."
	::= { snIpxSapFilterEntry 2 }

snIpxSapFilterType    OBJECT-TYPE
	SYNTAX   Integer32
	MAX-ACCESS  read-write
	STATUS  current
	DESCRIPTION
		"IPX SAP Filter type to be matched."
	::= { snIpxSapFilterEntry 3 }

snIpxSapFilterName    OBJECT-TYPE
	SYNTAX	OCTET STRING(SIZE(0..47))
	MAX-ACCESS  read-write
	STATUS  current
	DESCRIPTION
		"IPX SAP Filter Name."  
	::= { snIpxSapFilterEntry 4 }


snIpxSapFilterRowStatus OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpxSapFilterEntry 5 }


-- IPX IF Forward Access table

snIpxIfFwdAccessTable	    OBJECT-TYPE
	SYNTAX	SEQUENCE OF SnIpxIfFwdAccessEntry
	MAX-ACCESS  not-accessible
	STATUS  current
	DESCRIPTION
		"IPX IF Forward Access table."
	::= { snIpxIfFwdAccess 1 }

snIpxIfFwdAccessEntry	    OBJECT-TYPE
	SYNTAX	SnIpxIfFwdAccessEntry
	MAX-ACCESS  not-accessible
	STATUS  current
	DESCRIPTION
		"An entry in the IPX Forward Access table."
	INDEX	{ snIpxIfFwdAccessPort, snIpxIfFwdAccessDir }
	::= { snIpxIfFwdAccessTable 1 }

SnIpxIfFwdAccessEntry ::= SEQUENCE {
	snIpxIfFwdAccessPort
		Integer32,
	snIpxIfFwdAccessDir
		INTEGER,
	snIpxIfFwdAccessFilterList
		OCTET STRING,
	snIpxIfFwdAccessRowStatus
		INTEGER
	}

snIpxIfFwdAccessPort	   OBJECT-TYPE
	SYNTAX   Integer32
	MAX-ACCESS  read-only
	STATUS  current
	DESCRIPTION
		"The IPX interface to which the Forward Filter applies."
	::= { snIpxIfFwdAccessEntry 1 }

snIpxIfFwdAccessDir	 OBJECT-TYPE
	SYNTAX  INTEGER { in(1), out(2) }
	MAX-ACCESS	read-only
	STATUS  current
	DESCRIPTION
		"The access direction of incoming packet filter
		or outgoing packet filter."
	::= { snIpxIfFwdAccessEntry 2 }

snIpxIfFwdAccessFilterList    OBJECT-TYPE
	SYNTAX	OCTET STRING(SIZE(1..32))
	MAX-ACCESS  read-write
	STATUS  current
	DESCRIPTION
		"An IPX IF Forward Filter List."
	::= { snIpxIfFwdAccessEntry 3 }


snIpxIfFwdAccessRowStatus OBJECT-TYPE
	SYNTAX	 INTEGER {
		invalid(1),
		valid(2),
		delete(3),
		create(4),
			modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpxIfFwdAccessEntry 4 }



-- IPX IF RIP Access table

snIpxIfRipAccessTable	    OBJECT-TYPE
	SYNTAX	SEQUENCE OF SnIpxIfRipAccessEntry
	MAX-ACCESS  not-accessible
	STATUS  current
	DESCRIPTION
		"IPX IF RIP Access table."
	::= { snIpxIfRipAccess 1 }

snIpxIfRipAccessEntry	    OBJECT-TYPE
	SYNTAX	SnIpxIfRipAccessEntry
	MAX-ACCESS  not-accessible
	STATUS  current
	DESCRIPTION
		"An entry in the IPX Forward Access table."
	INDEX	{ snIpxIfRipAccessPort, snIpxIfRipAccessDir }
	::= { snIpxIfRipAccessTable 1 }

SnIpxIfRipAccessEntry ::= SEQUENCE {
	snIpxIfRipAccessPort
		Integer32,
	snIpxIfRipAccessDir
		INTEGER,
	snIpxIfRipAccessFilterList
		OCTET STRING,
	snIpxIfRipAccessRowStatus
		INTEGER
	}

snIpxIfRipAccessPort	   OBJECT-TYPE
	SYNTAX   Integer32
	MAX-ACCESS  read-only
	STATUS  current
	DESCRIPTION
		"The IPX interface to which the RIP Filter applies."
	::= { snIpxIfRipAccessEntry 1 }

snIpxIfRipAccessDir	 OBJECT-TYPE
	SYNTAX  INTEGER { in(1), out(2) }
	MAX-ACCESS	read-only
	STATUS  current
	DESCRIPTION
		"The access direction of incoming packet filter
		or outgoing packet filter."
	::= { snIpxIfRipAccessEntry 2 }

snIpxIfRipAccessFilterList    OBJECT-TYPE
	SYNTAX	OCTET STRING(SIZE(1..32))
	MAX-ACCESS  read-write
	STATUS  current
	DESCRIPTION
		"An IPX IF RIP Access Filter List."
	::= { snIpxIfRipAccessEntry 3 }


snIpxIfRipAccessRowStatus OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpxIfRipAccessEntry 4 }


-- IPX IF SAP Access table

snIpxIfSapAccessTable	    OBJECT-TYPE
	SYNTAX	SEQUENCE OF SnIpxIfSapAccessEntry
	MAX-ACCESS  not-accessible
	STATUS  current
	DESCRIPTION
		"IPX IF RIP Access table."
	::= { snIpxIfSapAccess 1 }

snIpxIfSapAccessEntry	    OBJECT-TYPE
	SYNTAX	SnIpxIfSapAccessEntry
	MAX-ACCESS  not-accessible
	STATUS  current
	DESCRIPTION
		"An entry in the IPX Forward Access table."
	INDEX	{ snIpxIfSapAccessPort, snIpxIfSapAccessDir }
	::= { snIpxIfSapAccessTable 1 }

SnIpxIfSapAccessEntry ::= SEQUENCE {
	snIpxIfSapAccessPort
		Integer32,
	snIpxIfSapAccessDir
		INTEGER,
	snIpxIfSapAccessFilterList
		OCTET STRING,
	snIpxIfSapAccessRowStatus
		INTEGER
	}

snIpxIfSapAccessPort	   OBJECT-TYPE
	SYNTAX   Integer32
	MAX-ACCESS  read-only
	STATUS  current
	DESCRIPTION
		"The IPX interface to which the SAP Filter applies."
	::= { snIpxIfSapAccessEntry 1 }

snIpxIfSapAccessDir	 OBJECT-TYPE
	SYNTAX  INTEGER { in(1), out(2) }
	MAX-ACCESS	read-only
	STATUS  current
	DESCRIPTION
		"The access direction of incoming packet filter
		or outgoing packet filter."
	::= { snIpxIfSapAccessEntry 2 }

snIpxIfSapAccessFilterList    OBJECT-TYPE
	SYNTAX	OCTET STRING(SIZE(1..32))
	MAX-ACCESS  read-write
	STATUS  current
	DESCRIPTION
		"An IPX IF SAP Access Filter List."
	::= { snIpxIfSapAccessEntry 3 }


snIpxIfSapAccessRowStatus OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpxIfSapAccessEntry 4 }


-- ipx interface address table

snIpxPortAddrTable	       OBJECT-TYPE
	SYNTAX	SEQUENCE OF SnIpxPortAddrEntry
	MAX-ACCESS  not-accessible
	STATUS  current
	DESCRIPTION
		"IPX port address table."
	::= { snIpxPortAddr 1 }

snIpxPortAddrEntry	       OBJECT-TYPE
	SYNTAX	SnIpxPortAddrEntry
	MAX-ACCESS  not-accessible
	STATUS  current
	DESCRIPTION
		"An entry in the IPX Port Address table."
	INDEX	{ snIpxPortAddrPort, snIpxPortAddrEncap }
	::= { snIpxPortAddrTable 1 }

SnIpxPortAddrEntry ::= SEQUENCE {
	snIpxPortAddrPort
		PortIndex,
	snIpxPortAddrEncap
		INTEGER,
	snIpxPortAddrNetNum
		NetNumber,
	snIpxPortAddrRowStatus
		INTEGER,
	snIpxPortAddrNetBiosFilterMode
		RtrStatus
	}


snIpxPortAddrPort	       OBJECT-TYPE
	SYNTAX  PortIndex
	MAX-ACCESS  read-only
	STATUS  current
	DESCRIPTION
		"The port index for port address entry."
	::= { snIpxPortAddrEntry 1 }

snIpxPortAddrEncap	      OBJECT-TYPE
	SYNTAX	 INTEGER {
		ethernet8022(1),
		ethernet8023(2),
		ethernetII(3),
		ethernetSnap(4)
	}
	MAX-ACCESS  read-only
	STATUS  current
	DESCRIPTION
		"The IPX encapsulation type.
		ethernet8022(1), ethernet8023(2),
		ethernetII(3),  ethernetSnap(4)  
		Note: Each Network Number can be assigned with one unique Frame type; Otherwise,
		a SNMP-SET error will be returned."
	::= { snIpxPortAddrEntry 2 }

snIpxPortAddrNetNum	       OBJECT-TYPE
	SYNTAX	NetNumber
	MAX-ACCESS	read-write
	STATUS  current
	DESCRIPTION
		"An unique Network number for the IPX interface port."
	::= { snIpxPortAddrEntry 3 }

snIpxPortAddrRowStatus OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpxPortAddrEntry 4 }

snIpxPortAddrNetBiosFilterMode		    OBJECT-TYPE
	SYNTAX	RtrStatus
	MAX-ACCESS  read-write
	STATUS  current
	DESCRIPTION
		"Enabled/Disabled NetBios Filter Mode status per Port Address entry."
	::= { snIpxPortAddrEntry 5 }


-- ipx port counters table

snIpxPortCountersTable	       OBJECT-TYPE
	SYNTAX	SEQUENCE OF SnIpxPortCountersEntry
	MAX-ACCESS  not-accessible
	STATUS  current
	DESCRIPTION
		"IPX port Counters table."
	::= { snIpxPortCounters 1 }

snIpxPortCountersEntry	       OBJECT-TYPE
	SYNTAX	SnIpxPortCountersEntry
	MAX-ACCESS  not-accessible
	STATUS  current
	DESCRIPTION
		"An entry in the IPX Port Counters table."
	INDEX	{ snIpxPortCountersPort }
	::= { snIpxPortCountersTable 1 }

SnIpxPortCountersEntry ::= SEQUENCE {
	snIpxPortCountersPort
		PortIndex,
	snIpxPortCountersRcvPktsCnt
		Counter32,
	snIpxPortCountersTxPktsCnt
		Counter32,
	snIpxPortCountersFwdPktsCnt
		Counter32,
	snIpxPortCountersRcvDropPktsCnt
		Counter32,
	snIpxPortCountersTxDropPktsCnt
		Counter32,
	snIpxPortCountersRcvFiltPktsCnt
		Counter32,
	snIpxPortCountersTxFiltPktsCnt
		Counter32
	}


snIpxPortCountersPort	       OBJECT-TYPE
	SYNTAX  PortIndex
	MAX-ACCESS  read-only
	STATUS  current
	DESCRIPTION
		"The port index for port Counters entry."
	::= { snIpxPortCountersEntry 1 }

snIpxPortCountersRcvPktsCnt 		OBJECT-TYPE
	SYNTAX	Counter32
	MAX-ACCESS	read-only
	STATUS  current
	DESCRIPTION
		"IPX incoming packets counter for the interface."
	::= { snIpxPortCountersEntry 2 }


snIpxPortCountersTxPktsCnt 		OBJECT-TYPE
	SYNTAX	Counter32
	MAX-ACCESS	read-only
	STATUS  current
	DESCRIPTION
		"IPX Outgoing packets counter for the interface."
	::= { snIpxPortCountersEntry 3 }


snIpxPortCountersFwdPktsCnt 		OBJECT-TYPE
	SYNTAX	Counter32
	MAX-ACCESS	read-only
	STATUS  current
	DESCRIPTION
		"IPX forwarding packets counter for the interface."
	::= { snIpxPortCountersEntry 4 }

snIpxPortCountersRcvDropPktsCnt		OBJECT-TYPE
	SYNTAX	Counter32
	MAX-ACCESS	read-only
	STATUS  current
	DESCRIPTION
		"IPX receiving drop packets counter for the interface."
	::= { snIpxPortCountersEntry 5 }

snIpxPortCountersTxDropPktsCnt		OBJECT-TYPE
	SYNTAX	Counter32
	MAX-ACCESS	read-only
	STATUS  current
	DESCRIPTION
		"IPX transmitting drop packets counter for the interface."
	::= { snIpxPortCountersEntry 6 }

snIpxPortCountersRcvFiltPktsCnt		OBJECT-TYPE
	SYNTAX	Counter32
	MAX-ACCESS	read-only
	STATUS  current
	DESCRIPTION
		"IPX receiving filter packets counter for the interface."
	::= { snIpxPortCountersEntry 7 }

snIpxPortCountersTxFiltPktsCnt		OBJECT-TYPE
	SYNTAX	Counter32
	MAX-ACCESS	read-only
	STATUS  current
	DESCRIPTION
		"IPX transmitting filter packets counter for the interface."
	::= { snIpxPortCountersEntry 8 }



END

FOUNDRY-SN-OSPF-GROUP-MIB DEFINITIONS ::= BEGIN

IMPORTS
	MODULE-IDENTITY, OBJECT-TYPE,Counter32, Gauge32, IpAddress,Integer32 
					 FROM SNMPv2-SMI
	router
		FROM FOUNDRY-SN-ROOT-MIB
	TEXTUAL-CONVENTION
		FROM SNMPv2-TC;
	 
snOspf MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"    
	REVISION     "200909300000Z" -- September 30, 2009
	DESCRIPTION
			"convert from SMIv1 to SMIv2"
   ::= {router 4}	                  

	--  Textual Conventions

	AreaID::= TEXTUAL-CONVENTION 
	STATUS      current 
	DESCRIPTION 
		"
		The Area ID, in OSPF, has the same format as an IP Address,
		but has the function of defining a summarization point for
		Link State Advertisements
		"
	SYNTAX  IpAddress

	RouterID::= TEXTUAL-CONVENTION 
	STATUS      current 
	DESCRIPTION 
		"
		   The Router ID, in OSPF, has the same format as an IP Address,
		   but identifies the router independent of its IP Address.		
		"
	SYNTAX  IpAddress

	Metric::= TEXTUAL-CONVENTION 
	STATUS      current 
	DESCRIPTION 
		"
		The OSPF Metric is defined as an unsigned value in the range
		0..'FFFF'h
		"
	SYNTAX  INTEGER (0..65535)
	
	BigMetric::= TEXTUAL-CONVENTION 
	STATUS      current 
	DESCRIPTION 
		"
			0..'FFFFFF'h
		"
	SYNTAX      INTEGER (0..16777215)

	TruthVal::= TEXTUAL-CONVENTION 
	STATUS      current 
	DESCRIPTION 
		"
		Boolean Values
		"
	SYNTAX  INTEGER { false (0), true (1)  }

	RtrStatus::= TEXTUAL-CONVENTION 
	STATUS      current 
	DESCRIPTION 
		"
			RtrStatus Values
		"
	SYNTAX  INTEGER { disabled (0), enabled (1) }

	 --  Time Durations measured in seconds

	PositiveInteger::= TEXTUAL-CONVENTION 
	STATUS      current 
	DESCRIPTION 
		"
			0..'7FFFFFFF'h
		"
	SYNTAX  INTEGER (0..2147483647)
	
	HelloRange::= TEXTUAL-CONVENTION 
	STATUS      current 
	DESCRIPTION 
		"
		1..'FFFF'h
		"
	SYNTAX   INTEGER (1..65535)
	
	UpToMaxAge::= TEXTUAL-CONVENTION 
	STATUS      current 
	DESCRIPTION 
		"
		"
	SYNTAX  INTEGER (0..3600)

	DesignatedRouterPriority::= TEXTUAL-CONVENTION 
	STATUS      current 
	DESCRIPTION 
		"
		The range of ifIndex, i.e. (1..ifNumber)
		Potential Priorities for the Designated Router Election		
		"
	SYNTAX  INTEGER (0..255)


	TOSType::= TEXTUAL-CONVENTION 
	STATUS      current 
	DESCRIPTION 
		"
		 Type of Service is defined as a mapping to the IP Type of
		 Service Flags as defined in the Router Requirements
		 Document:
		 
		 Type of Service is defined as a mapping to the IP Type of
		 Service Flags as defined in the IP Forwarding Table MIB
	
		  +-----+-----+-----+-----+-----+-----+-----+-----+
		  |                 |                       |     |
		  |   PRECEDENCE    |    TYPE OF SERVICE    |  0  |
		  |                 |                       |     |
		  +-----+-----+-----+-----+-----+-----+-----+-----+
	
				   IP TOS                IP TOS
			  Field     Policy      Field     Policy
	
			  Contents    Code      Contents    Code
			  0 0 0 0  ==>   0      0 0 0 1  ==>   2
			  0 0 1 0  ==>   4      0 0 1 1  ==>   6
			  0 1 0 0  ==>   8      0 1 0 1  ==>  10
			  0 1 1 0  ==>  12      0 1 1 1  ==>  14
			  1 0 0 0  ==>  16      1 0 0 1  ==>  18
			  1 0 1 0  ==>  20      1 0 1 1  ==>  22
			  1 1 0 0  ==>  24      1 1 0 1  ==>  26
			  1 1 1 0  ==>  28      1 1 1 1  ==>  30
	
		   The remaining values are left for future definition.		
		"
	SYNTAX  INTEGER (0..30)


-- Groups

snOspfGen 	        OBJECT IDENTIFIER ::= { snOspf 1 }
snOspfArea		    OBJECT IDENTIFIER ::= { snOspf 2 }
snOspfAddrRange		OBJECT IDENTIFIER ::= { snOspf 3 }
snOspfIntf		    OBJECT IDENTIFIER ::= { snOspf 4 }
snOspfVirtIf		OBJECT IDENTIFIER ::= { snOspf 5 }
snOspfRedis		    OBJECT IDENTIFIER ::= { snOspf 6 }
snOspfNbr		    OBJECT IDENTIFIER ::= { snOspf 7 }
snOspfVirtNbr		OBJECT IDENTIFIER ::= { snOspf 8 }
snOspfLsdb		    OBJECT IDENTIFIER ::= { snOspf 9 }
snOspfExtLsdb 		OBJECT IDENTIFIER ::= { snOspf 10 }
snOspfAreaStatus	OBJECT IDENTIFIER ::= { snOspf 11 }
snOspfIfStatus		OBJECT IDENTIFIER ::= { snOspf 12 }
snOspfVirtIfStatus	OBJECT IDENTIFIER ::= { snOspf 13 }
snOspfRoutingInfo	OBJECT IDENTIFIER ::= { snOspf 14 }
snOspfTrapControl 	OBJECT IDENTIFIER ::= { snOspf 15 }
 
	

--  Section 1:	OSPF General Variables

--      These parameters apply globally to the Router's
--      OSPF Process.


	 snOspfRouterId OBJECT-TYPE
		 SYNTAX   RouterID
		 MAX-ACCESS   read-write
		 STATUS   current
		 DESCRIPTION
			"A 32-bit integer uniquely identifying the router in
			the Autonomous System.

			By convention, to ensure uniqueness, this should
			default to the value of one of the router's IP
			interface addresses."
		 REFERENCE
			"OSPF Version 2, C.1 Global parameters"
		 ::= { snOspfGen 1 }

	 snOspfAdminStat OBJECT-TYPE
		 SYNTAX   RtrStatus
		 MAX-ACCESS   read-write
		 STATUS   current
		 DESCRIPTION
			"The administrative status of OSPF in the router.  The
			value 'enabled' denotes that the OSPF Process is active
			on at least one interface; 'disabled' disables it on
			all interfaces."
		 ::= { snOspfGen 2 }

	 snOspfASBdrRtrStatus OBJECT-TYPE
		 SYNTAX   TruthVal
		 MAX-ACCESS   read-write
		 STATUS   current
		 DESCRIPTION
			"A flag to note whether this router is an Autonomous
			System border router."
		 REFERENCE
			"OSPF Version 2, Section 3.3 Classification of routers"
		 ::= { snOspfGen 3 }


	 snOspfRedisMode OBJECT-TYPE
		 SYNTAX   RtrStatus
		 MAX-ACCESS   read-write
		 STATUS   current
		 DESCRIPTION
			"The Redistribution status of OSPF in the router.  The
			value 'enabled' denotes that the OSPF Redistribution is 
			active; 'disabled' disables it on the router."
		 ::= { snOspfGen 4 }


	 snOspfDefaultOspfMetricValue OBJECT-TYPE
		 SYNTAX   INTEGER (1..65535)
		 MAX-ACCESS   read-write
		 STATUS   current 
		 DESCRIPTION
			"The metric of using a default OSPF Metric value on this route."
		 ::= { snOspfGen 5 }

	 snOspfExternLSACount OBJECT-TYPE
		 SYNTAX   Gauge32
		 MAX-ACCESS   read-only
		 STATUS   current
		 DESCRIPTION
			"The number of external (LS type 5) link-state
			advertisements in the link-state database."
		 REFERENCE
			"OSPF Version 2, Appendix A.4.5 AS external link
			advertisements"
		 ::= { snOspfGen 6 }

	 snOspfExternLSACksumSum OBJECT-TYPE
		 SYNTAX   Integer32
		 MAX-ACCESS   read-only
		 STATUS   current
		 DESCRIPTION
			"The 32-bit unsigned sum of the LS checksums of the
			external link-state advertisements contained in the
			link-state database.  This sum can be used to determine
			if there has been a change in a router's link state
			database, and to compare the link-state database of two
			routers."
		 ::= { snOspfGen 7 }

	 snOspfOriginateNewLSAs OBJECT-TYPE
		 SYNTAX   Counter32
		 MAX-ACCESS   read-only
		 STATUS   current
		 DESCRIPTION
			"The number of new link-state advertisements that have
			been originated.  This number is incremented each time
			the router originates a new LSA."
		 ::= { snOspfGen 8 }

	 snOspfRxNewLSAs OBJECT-TYPE
		 SYNTAX   Counter32
		 MAX-ACCESS   read-only
		 STATUS   current
		 DESCRIPTION
			"The number of link-state advertisements received
			determined to be new instantiations.  This number does
			not include newer instantiations of self-originated
			link-state advertisements."
		 ::= { snOspfGen 9 }

	 snOspfOspfRedisMetricType OBJECT-TYPE
		 SYNTAX   INTEGER {
					type1(1),
					type2(2)
				  }
		 MAX-ACCESS   read-write
		 STATUS   current 
		 DESCRIPTION
			"type1: For External Type 1 (comparable value) the 
					intra-area and inter-area routes, 
					it is an OSPF metric plus the External Metric.
			 type2: For external Type 2 (non-comparable value) routes, 
					it is the external metric."
		 ::= { snOspfGen 10 }

	 snOspfExtLsdbLimit OBJECT-TYPE
		 SYNTAX   Integer32
		 MAX-ACCESS   read-write
		 STATUS   current 
		 DESCRIPTION
		   "The  maximum   number   of   non-default   AS-
		   external-LSAs entries that can be stored in the
		   link-state database. 

		   When the number of non-default AS-external-LSAs
		   in   a  router's  link-state  database  reaches
		   ospfExtLsdbLimit, the router  enters  Overflow-
		   State.   The   router  never  holds  more  than
		   ospfExtLsdbLimit  non-default  AS-external-LSAs
		   in  its  database. OspfExtLsdbLimit MUST be set
		   identically in all routers attached to the OSPF
		   backbone  and/or  any regular OSPF area. (i.e.,
		   OSPF stub areas and NSSAs are excluded)."
	   ::= { snOspfGen 11 }


	snOspfExitOverflowInterval OBJECT-TYPE
		 SYNTAX   INTEGER (0..86400)
		 MAX-ACCESS   read-write
		 STATUS   current 
		 DESCRIPTION
		   "The number of  seconds  that,  after  entering
		   OverflowState,  a  router will attempt to leave
		   OverflowState. This allows the router to  again
		   originate  non-default  AS-external-LSAs.  When
		   set to 0, the router will not  leave  Overflow-
		   State until restarted."
	   ::= { snOspfGen 12 }

	snOspfRfc1583Compatibility OBJECT-TYPE
		SYNTAX  INTEGER {
			disabled(0),             
			enabled(1)
			}
		MAX-ACCESS  read-write
		STATUS  current
		DESCRIPTION
			"This allows the ospf routing either compatible with
			RFC1583 or RFC2178.
			enabled(1)........activate RFC1583 compatibility rather than RFC2178
			disabled(0).......disable RFC1583 compatibility and compatible to RFC2178."  
	   ::= { snOspfGen 13 }

	 snOspfRouterIdFormat OBJECT-TYPE
		 SYNTAX   INTEGER {
					integer(0),
					ipAddress(1)
				  }
		 MAX-ACCESS   read-write
		 STATUS   current
		 DESCRIPTION
			"This object is used to specify whether
			 RouterId is represented as IP Address or 
			 an Integer. The values
			 that can be written are:
			 integer(0).....as an integer.
			 ipAddress(1)...as IP Address."
		 ::= { snOspfGen 14 }

	 snOspfDistance OBJECT-TYPE
		 SYNTAX   INTEGER (0..255)
		 MAX-ACCESS   read-write
		 STATUS   obsolete
		 DESCRIPTION
			"OSPF Adminitrative distance. 0 if distance is not set."
		 ::= { snOspfGen 15 }

	 snOspfDistanceIntra OBJECT-TYPE
		 SYNTAX   INTEGER (1..255)
		 MAX-ACCESS   read-write
		 STATUS   current
		 DESCRIPTION
			"OSPF Adminitrative distance - Intra Area."
		 ::= { snOspfGen 16 }

	 snOspfDistanceInter OBJECT-TYPE
		 SYNTAX   INTEGER (1..255)
		 MAX-ACCESS   read-write
		 STATUS   current
		 DESCRIPTION
			"OSPF Adminitrative distance - Inter Area."
		 ::= { snOspfGen 17 }

	 snOspfDistanceExternal OBJECT-TYPE
		 SYNTAX   INTEGER (1..255)
		 MAX-ACCESS   read-write
		 STATUS   current
		 DESCRIPTION
			"OSPF Adminitrative distance - External."
		 ::= { snOspfGen 18 }

--		Section 2:	OSPF Area Table

--      The OSPF Area Data Structure contains information
--      regarding the various areas. The interfaces and
--      virtual links are configured as part of these areas.
--      Area 0.0.0.0, by definition, is the Backbone Area

	 snOspfAreaTable OBJECT-TYPE
		 SYNTAX   SEQUENCE OF SnOspfAreaEntry
		 MAX-ACCESS   not-accessible
		 STATUS   current
		 DESCRIPTION
			"Information describing the configured parameters and
			cumulative statistics of the router's attached areas."
		 REFERENCE
			"OSPF Version 2, Section 6  The Area Data Structure"
		 ::= { snOspfArea 1 }

	 snOspfAreaEntry OBJECT-TYPE
		 SYNTAX   SnOspfAreaEntry
		 MAX-ACCESS   not-accessible
		 STATUS   current
		 DESCRIPTION
			"Information describing the configured parameters and
			cumulative statistics of one of the router's attached
			areas."
		 INDEX { snOspfAreaId }
		 ::= { snOspfAreaTable 1 }

	 SnOspfAreaEntry ::=
		 SEQUENCE {
			 snOspfAreaId
				 AreaID,
			 snOspfImportASExtern
				 Integer32,
			 snOspfStubMetric
				 BigMetric,
			 snOspfAreaRowStatus 
				 INTEGER,
			 snOspfAreaIdFormat 
				 INTEGER
		 }

	 snOspfAreaId OBJECT-TYPE
		 SYNTAX   AreaID
		 MAX-ACCESS   read-only
		 STATUS   current
		 DESCRIPTION
			"A 32-bit integer uniquely identifying an area.  Area
			ID 0.0.0.0 is used for the OSPF backbone."
		 REFERENCE
			"OSPF Version 2, Appendix C.2 Area parameters"
		 ::= { snOspfAreaEntry 1 }

	 snOspfImportASExtern OBJECT-TYPE
		 SYNTAX   Integer32
		 MAX-ACCESS   read-write
		 STATUS   current
		 DESCRIPTION
			"The area's support for importing AS external link-
			state advertisements. 
			0: 	Stub Area Type
			1: 	Normal Area Type
			2: 	NSSA Area Type"
		 REFERENCE
			"OSPF Version 2, Appendix C.2 Area parameters"
		 DEFVAL { 1}
		 ::= { snOspfAreaEntry 2 }


	 snOspfStubMetric OBJECT-TYPE
		 SYNTAX   BigMetric
		 MAX-ACCESS   read-write
		 STATUS   current
		 DESCRIPTION
			"The metric value applied at the default type of
			service(ospfMetric).  By default, this equals the 
			least metric at the type of service among the 
			interfaces to other areas.  This Object exist if
			only if the value of snOspfAreaSummary is 
			snOspfAreaSummary(2); Otherwise, an SNMP_GET/GET_NEXT 
			attempt of this Object will return NO_SUCH_NAME."
		 ::= { snOspfAreaEntry 3 }


	 snOspfAreaRowStatus OBJECT-TYPE
		 SYNTAX   INTEGER {
					invalid(1),
					valid(2),
					delete(3),
					create(4),
					modify(5)
				  }
		 MAX-ACCESS   read-write
		 STATUS   current
		 DESCRIPTION
			"This object is used to create and
			 delete row in the table and control
			 if they are used. The values
			 that can be written are:
			 delete(3)...deletes the row
			 create(4)...creates a new row
			 modify(5)...modifies an exsisting row

			 If the row exists, then a SET with
			 value of create(4) returns error
			 'badValue'. Deleted rows go away
			 immediately. The following values
			 can be returned on reads:
			 noSuch(0)...no such row
			 invalid(1)...Setting it to 'invalid' has the effect of
						  rendering it inoperative..
			 valid(2)....the row exists and is valid"
		 ::= { snOspfAreaEntry 4 }

	 snOspfAreaIdFormat OBJECT-TYPE
		 SYNTAX   INTEGER {
					integer(0),
					ipAddress(1)
				  }
		 MAX-ACCESS   read-write
		 STATUS   current
		 DESCRIPTION
			"This object is used to specify whether
			 AreaId is represented as IP Address or 
			 an Integer. The values
			 that can be written are:
			 integer(0).....as an integer.
			 ipAddress(1)...as IP Address."
		 ::= { snOspfAreaEntry 5 }


--  Section 3:		Area Range Table (Address Range Table)

--      The Address Range Table acts as an adjunct to the Area
--      Table; It describes those Address Range Summaries that
--      are configured to be propagated from an Area to reduce
--      the amount of information about it which is known beyond
--      its borders.



	 snOspfAreaRangeTable OBJECT-TYPE
		 SYNTAX   SEQUENCE OF SnOspfAreaRangeEntry
		 MAX-ACCESS   not-accessible
		 STATUS   current
		 DESCRIPTION
			"A range if IP addresses specified by an IP address/IP
			network mask pair.  For example, class B address range
			of X.X.X.X with a network mask of 255.255.0.0 includes
			all IP addresses from X.X.0.0 to X.X.255.255"
		 REFERENCE
			"OSPF Version 2, Appendix C.2  Area parameters"
		 ::= { snOspfAddrRange 1 }

	 snOspfAreaRangeEntry OBJECT-TYPE
		 SYNTAX   SnOspfAreaRangeEntry
		 MAX-ACCESS   not-accessible
		 STATUS   current
		 DESCRIPTION
			"A range if IP addresses specified by an IP address/IP
			network mask pair.  For example, class B address range
			of X.X.X.X with a network mask of 255.255.0.0 includes
			all IP addresses from X.X.0.0 to X.X.255.255"
		 REFERENCE
			"OSPF Version 2, Appendix C.2  Area parameters"
		 INDEX { snOspfAreaRangeAreaID, snOspfAreaRangeNet }
		 ::= { snOspfAreaRangeTable 1 }

	 SnOspfAreaRangeEntry ::=
		 SEQUENCE {
			 snOspfAreaRangeAreaID
				 AreaID,
			 snOspfAreaRangeNet
				 IpAddress,
			 snOspfAreaRangeMask
				 IpAddress,
			 snOspfAreaRangeRowStatus
				 INTEGER,
			 snOspfAreaRangeAreaIdFormat 
				 INTEGER
		 }

	 snOspfAreaRangeAreaID OBJECT-TYPE
		 SYNTAX   AreaID
		 MAX-ACCESS   read-only
		 STATUS   current
		 DESCRIPTION
			"The Area the Address Range is to be found within."
		 REFERENCE
			"OSPF Version 2, Appendix C.2 Area parameters"
		 ::= { snOspfAreaRangeEntry 1 }

	 snOspfAreaRangeNet OBJECT-TYPE
		 SYNTAX   IpAddress
		 MAX-ACCESS   read-only
		 STATUS   current
		 DESCRIPTION
			"The IP Address of the Net or Subnet indicated by the
			range."
		 REFERENCE
			"OSPF Version 2, Appendix C.2 Area parameters"
		 ::= { snOspfAreaRangeEntry 2 }

	 snOspfAreaRangeMask OBJECT-TYPE
		 SYNTAX   IpAddress
		 MAX-ACCESS   read-write
		 STATUS   current
		 DESCRIPTION
			"The Subnet Mask that pertains to the Net or Subnet."
		 REFERENCE
			"OSPF Version 2, Appendix C.2 Area parameters"
		 ::= { snOspfAreaRangeEntry 3 }


	 snOspfAreaRangeRowStatus OBJECT-TYPE
		 SYNTAX   INTEGER {
					invalid(1),
					valid(2),
					delete(3),
					create(4),
					modify(5)
				  }
		 MAX-ACCESS   read-write
		 STATUS   current
		 DESCRIPTION
			"This object is used to create and
			 delete row in the table and control
			 if they are used. The values
			 that can be written are:
			 delete(3)...deletes the row
			 create(4)...creates a new row
			 modify(5)...modifies an exsisting row

			 If the row exists, then a SET with
			 value of create(4) returns error
			 'badValue'. Deleted rows go away
			 immediately. The following values
			 can be returned on reads:
			 noSuch(0)...no such row
			 invalid(1)...Setting it to 'invalid' has the effect of
						  rendering it inoperative..
			 valid(2)....the row exists and is valid"
		 ::= { snOspfAreaRangeEntry 4 }

	 snOspfAreaRangeAreaIdFormat OBJECT-TYPE
		 SYNTAX   INTEGER {
					integer(0),
					ipAddress(1)
				  }
		 MAX-ACCESS   read-only
		 STATUS   current
		 DESCRIPTION
			"This object is used to specify whether
			 AreaId is represented as IP Address or 
			 an Integer. The values
			 that can be written are:
			 integer(0).....as an integer.
			 ipAddress(1)...as IP Address."
		 ::= { snOspfAreaRangeEntry 5 }



 

--  Section 4:		OSPF Interface Configuration Table

--      The OSPF Interface Table augments the ifTable with OSPF
--      specific information.
--  snOspfIfTable was replaced by snOspfIf2Table. The snOspfIfPort
--  was not an ifIndex, and the snOspfIf2Port is an ifIndex.


	 snOspfIfTable OBJECT-TYPE
		 SYNTAX   SEQUENCE OF SnOspfIfEntry
		 MAX-ACCESS   not-accessible
		 STATUS   deprecated
		 DESCRIPTION
			"The OSPF Interface Table describes the interfaces from
			the viewpoint of OSPF."
		 REFERENCE
			"OSPF Version 2, Appendix C.3  Router interface
			parameters"
		 ::= { snOspfIntf 1 }

	 snOspfIfEntry OBJECT-TYPE
		 SYNTAX   SnOspfIfEntry
		 MAX-ACCESS   not-accessible
		 STATUS   deprecated
		 DESCRIPTION
			"The OSPF Interface Entry describes one interface from
			the viewpoint of OSPF."
		 INDEX { snOspfIfPort }
		 ::= { snOspfIfTable 1 }

	 SnOspfIfEntry ::=
		 SEQUENCE {
			 snOspfIfPort
				 Integer32,
			 snOspfIfAreaId
				 AreaID,
			 snOspfIfAdminStat
				 RtrStatus,
			 snOspfIfRtrPriority
				 DesignatedRouterPriority,
			 snOspfIfTransitDelay
				 UpToMaxAge,
			 snOspfIfRetransInterval
				 UpToMaxAge,
			 snOspfIfHelloInterval
				 HelloRange,
			 snOspfIfRtrDeadInterval
				 PositiveInteger,
			 snOspfIfAuthType
				 INTEGER,
			 snOspfIfAuthKey
				 OCTET STRING,
			 snOspfIfMetricValue
				 INTEGER,
			 snOspfIfRowStatus 
				 INTEGER, 
			 snOspfIfMd5AuthKeyId
				 INTEGER,
			 snOspfIfMd5AuthKey
				 OCTET STRING,
			 snOspfIfMd5ActivationWaitTime
				 INTEGER,
			 snOspfIfAreaIdFormat 
				 INTEGER,
			 snOspfIfPassiveMode
				 INTEGER,
			 snOspfIfDatabaseFilterAllOut
				 INTEGER,
			 snOspfIfMtuIgnore
				 INTEGER,
			 snOspfIfNetworkP2mp
				 INTEGER
		 }


	snOspfIfPort OBJECT-TYPE
		 SYNTAX   Integer32
		 MAX-ACCESS   read-only
		 STATUS   deprecated
		 DESCRIPTION
			"The physical router port of this OSPF interface."
		 ::= { snOspfIfEntry 1 }


	 snOspfIfAreaId OBJECT-TYPE
		 SYNTAX   AreaID
		 MAX-ACCESS   read-write
		 STATUS   deprecated
		 DESCRIPTION
			"A 32-bit integer uniquely identifying the area to
			which the interface connects.  Area ID 0.0.0.0 is used
			for the OSPF backbone."
		 DEFVAL   { '00000000'h }    -- 0.0.0.0
		 ::= { snOspfIfEntry 2 }


	 snOspfIfAdminStat OBJECT-TYPE
		 SYNTAX   RtrStatus
		 MAX-ACCESS   read-write
		 STATUS   deprecated
		 DESCRIPTION
			"The OSPF interface's administrative status.  The value
			'enabled' denotes that neighbor relationships may be
			formed on the interface, and the interface will be
			advertised as an internal route to some area.  The
			value 'disabled' denotes that the interface is external
			to OSPF."
		 DEFVAL { enabled }
		 ::= { snOspfIfEntry 3 }

	 snOspfIfRtrPriority OBJECT-TYPE
		 SYNTAX   DesignatedRouterPriority
		 MAX-ACCESS   read-write
		 STATUS   deprecated
		 DESCRIPTION
			"The priority of this interface.  Used in multi-access
			networks, this field is used in the designated router
			election algorithm.  The value 0 signifies that the
			router is not eligible to become the designated router
			on this particular network.  In the event of a tie in
			this value, routers will use their router id as a tie
			breaker."
		 DEFVAL { 1 }
		 ::= { snOspfIfEntry 4 }

	 snOspfIfTransitDelay OBJECT-TYPE
		 SYNTAX   UpToMaxAge
		 MAX-ACCESS   read-write
		 STATUS   deprecated
		 DESCRIPTION
			"The estimated number of seconds it takes to transmit a
			link- state update packet over this interface."
		 DEFVAL { 1 }
		 ::= { snOspfIfEntry 5 }

	 snOspfIfRetransInterval OBJECT-TYPE
		 SYNTAX   UpToMaxAge
		 MAX-ACCESS   read-write
		 STATUS   deprecated
		 DESCRIPTION
			"The number of seconds between link-state advertisement
			retransmissions, for adjacencies belonging to this
			interface.  This value is also used when retransmitting
			database description and link-state request packets."
		 DEFVAL { 5 }
		 ::= { snOspfIfEntry 6 }

	 snOspfIfHelloInterval OBJECT-TYPE
		 SYNTAX   HelloRange
		 MAX-ACCESS   read-write
		 STATUS   deprecated
		 DESCRIPTION
			"The length of time, in seconds, between the Hello
			packets that the router sends on the interface.  This
			value must be the same for all routers attached to a
			common network."
		 DEFVAL { 10 }
		 ::= { snOspfIfEntry 7 }

	 snOspfIfRtrDeadInterval OBJECT-TYPE
		 SYNTAX   PositiveInteger
		 MAX-ACCESS   read-write
		 STATUS   deprecated
		 DESCRIPTION
			"The number of seconds that a router's Hello packets
			have not been seen before it's neighbors declare the
			router down.  This should be some multiple of the Hello
			interval.  This value must be the same for all routers
			attached to a common network."
		 DEFVAL { 40 }
		 ::= { snOspfIfEntry 8 }


	 snOspfIfAuthType OBJECT-TYPE
		 SYNTAX   INTEGER (0..255)
					 -- none (0),
					 -- simplePassword (1)
					 -- md5 (2)
					 -- reserved for specification by IANA (> 2)
		 MAX-ACCESS   read-write
		 STATUS   deprecated
		 DESCRIPTION
			"The authentication type specified for an interface.
			Additional authentication types may be assigned locally
			on a per interface basis."
		 REFERENCE
			"OSPF Version 2, Appendix E Authentication"
		 DEFVAL { 0 }        -- no authentication, by default
		 ::= { snOspfIfEntry 9 }


	 snOspfIfAuthKey OBJECT-TYPE
		 SYNTAX   OCTET STRING (SIZE (0..8))
		 MAX-ACCESS   read-write
		 STATUS   deprecated
		 DESCRIPTION
			"The Authentication Key.  If the Area's Authorization
			Type is simplePassword, and the key length is shorter
			than 8 octets, the agent will left adjust and zero fill
			to 8 octets.

			When read, snOspfIfAuthKey always returns an Octet String
			of length zero."
		 REFERENCE
			"OSPF Version 2, Section 9 The Interface Data
			Structure"
		 DEFVAL   { '0000000000000000'h }    -- 0.0.0.0.0.0.0.0
		 ::= { snOspfIfEntry 10 }


	 snOspfIfMetricValue OBJECT-TYPE
		 SYNTAX   INTEGER (1..65535)
		 MAX-ACCESS   read-write
		 STATUS   deprecated
		 DESCRIPTION
			"The metric of using this type  of  service  on
			 this interface.  The default value of the TOS 0
			 Metric is 10^8 / ifSpeed."
		 ::= { snOspfIfEntry 11 }

	 snOspfIfRowStatus OBJECT-TYPE
		 SYNTAX   INTEGER {
					invalid(1),
					valid(2),
					delete(3),
					create(4),
					modify(5)
				  }
		 MAX-ACCESS   read-write
		 STATUS   deprecated
		 DESCRIPTION
			"This object is used to create and
			 delete row in the table and control
			 if they are used. The values
			 that can be written are:
			 delete(3)...deletes the row
			 create(4)...creates a new row
			 modify(5)...modifies an exsisting row

			 If the row exists, then a SET with
			 value of create(4) returns error
			 'badValue'. Deleted rows go away
			 immediately. The following values
			 can be returned on reads:
			 noSuch(0)...no such row
			 invalid(1)...Setting it to 'invalid' has the effect of
						  rendering it inoperative..
			 valid(2)....the row exists and is valid"
		 ::= { snOspfIfEntry 12 }
	 
	 snOspfIfMd5AuthKeyId OBJECT-TYPE
		 SYNTAX   INTEGER (0..255)
		 MAX-ACCESS   read-write
		 STATUS   deprecated
		 DESCRIPTION
			"The md5 authentication key ID.  If the snOspfVirtIfAuthType
			is set to md5, the value of snOspfIfMd5AuthKeyId must be
			(1 to 255). This field identifies the algorithm and secret 
			key used to create the message digest appended to the OSPF 
			packet.  Key Identifiers are unique per-interface 
			(or equivalently, per-subnet)."
		 ::= { snOspfIfEntry 13 }


	 snOspfIfMd5AuthKey OBJECT-TYPE
		 SYNTAX   OCTET STRING (SIZE (0..16))
		 MAX-ACCESS   read-write
		 STATUS   deprecated
		 DESCRIPTION
			"The MD5 Authentication Key.  If the Area's Authorization
			Type is md5, and the key length is shorter than 16 octets, 
			the agent will left adjust and zero fill to 16 octets.
			When read, snOspfIfMd5AuthKey always returns an Octet String
			of length zero."
		 ::= { snOspfIfEntry 14 }


	 snOspfIfMd5ActivationWaitTime OBJECT-TYPE
		 SYNTAX   INTEGER (0..14400)
		 MAX-ACCESS   read-write
		 STATUS   deprecated
		 DESCRIPTION
			"The md5 authentication key activation wait time is specified in second
			and the maximum wait time is 14400 seconds (4 hours)."
		 ::= { snOspfIfEntry 15 }

	 snOspfIfAreaIdFormat OBJECT-TYPE
		 SYNTAX   INTEGER {
					integer(0),
					ipAddress(1)
				  }
		 MAX-ACCESS   read-only
		 STATUS   deprecated
		 DESCRIPTION
			"This object is used to specify whether
			 AreaId is represented as IP Address or 
			 an Integer. The values
			 that can be written are:
			 integer(0).....as an integer.
			 ipAddress(1)...as IP Address."
		 ::= { snOspfIfEntry 16 }

	 snOspfIfPassiveMode OBJECT-TYPE
		 SYNTAX   INTEGER {
			disabled(0),
			enabled(1)
			}
		 MAX-ACCESS   read-write
		 STATUS   deprecated
		 DESCRIPTION
			"This object control the passive mode of this interface."
		 ::= { snOspfIfEntry 17 }

	 snOspfIfDatabaseFilterAllOut OBJECT-TYPE
		 SYNTAX   INTEGER {
			disabled(0),
			enabled(1)
			}
		 MAX-ACCESS   read-write
		 STATUS   deprecated
		 DESCRIPTION
			"This object control the filtering of outgoing OSPF LSA on this interface."
		 ::= { snOspfIfEntry 18 }

	 snOspfIfMtuIgnore OBJECT-TYPE
		 SYNTAX   INTEGER {
			disabled(0),
			enabled(1)
			}
		 MAX-ACCESS   read-write
		 STATUS   deprecated
		 DESCRIPTION
			"This object control MTU detection mode of this interface."
		 ::= { snOspfIfEntry 19 }

	 snOspfIfNetworkP2mp OBJECT-TYPE
		 SYNTAX   INTEGER {
			disabled(0),
			enabled(1)
			}
		 MAX-ACCESS   read-write
		 STATUS   deprecated
		 DESCRIPTION
			"This object enable/disable P2MP mode of this interface."
		 ::= { snOspfIfEntry 20 }


--  Section 4:		OSPF Interface Configuration Table

--      The OSPF Interface Table augments the ifTable with OSPF
--      specific information.
--  snOspfIf2Table replaced snOspfIfTable. The snOspfIf2Port
--  is an ifIndex, and the snOspfIfPort is not an ifIndex.


	 snOspfIf2Table OBJECT-TYPE
		 SYNTAX   SEQUENCE OF SnOspfIf2Entry
		 MAX-ACCESS   not-accessible
		 STATUS   current
		 DESCRIPTION
			"The OSPF Interface Table describes the interfaces from
			the viewpoint of OSPF."
		 REFERENCE
			"OSPF Version 2, Appendix C.3  Router interface
			parameters"
		 ::= { snOspfIntf 2 }

	 snOspfIf2Entry OBJECT-TYPE
		 SYNTAX   SnOspfIf2Entry
		 MAX-ACCESS   not-accessible
		 STATUS   current
		 DESCRIPTION
			"The OSPF Interface Entry describes one interface from
			the viewpoint of OSPF."
		 INDEX { snOspfIf2Port }
		 ::= { snOspfIf2Table 1 }

	 SnOspfIf2Entry ::=
		 SEQUENCE {
			 snOspfIf2Port
				 Integer32,
			 snOspfIf2AreaId
				 AreaID,
			 snOspfIf2AdminStat
				 RtrStatus,
			 snOspfIf2RtrPriority
				 DesignatedRouterPriority,
			 snOspfIf2TransitDelay
				 UpToMaxAge,
			 snOspfIf2RetransInterval
				 UpToMaxAge,
			 snOspfIf2HelloInterval
				 HelloRange,
			 snOspfIf2RtrDeadInterval
				 PositiveInteger,
			 snOspfIf2AuthType
				 INTEGER,
			 snOspfIf2AuthKey
				 OCTET STRING,
			 snOspfIf2MetricValue
				 INTEGER,
			 snOspfIf2RowStatus 
				 INTEGER, 
			 snOspfIf2Md5AuthKeyId
				 INTEGER,
			 snOspfIf2Md5AuthKey
				 OCTET STRING,
			 snOspfIf2Md5ActivationWaitTime
				 INTEGER,
			 snOspfIf2AreaIdFormat 
				 INTEGER,
			 snOspfIf2PassiveMode
				 INTEGER,
			 snOspfIf2DatabaseFilterAllOut
				 INTEGER,
			 snOspfIf2MtuIgnore
				 INTEGER,
			 snOspfIf2NetworkP2mp
				 INTEGER,
			 snOspfIf2NetworkP2pt
				 INTEGER,
			 snOspfIf2NetworkNonBroadcast
				 INTEGER
		 }


	snOspfIf2Port OBJECT-TYPE
		 SYNTAX   Integer32
		 MAX-ACCESS   read-only
		 STATUS   current
		 DESCRIPTION
			"The physical router port of this OSPF interface."
		 ::= { snOspfIf2Entry 1 }


	 snOspfIf2AreaId OBJECT-TYPE
		 SYNTAX   AreaID
		 MAX-ACCESS   read-write
		 STATUS   current
		 DESCRIPTION
			"A 32-bit integer uniquely identifying the area to
			which the interface connects.  Area ID 0.0.0.0 is used
			for the OSPF backbone."
		 DEFVAL   { '00000000'h }    -- 0.0.0.0
		 ::= { snOspfIf2Entry 2 }


	 snOspfIf2AdminStat OBJECT-TYPE
		 SYNTAX   RtrStatus
		 MAX-ACCESS   read-write
		 STATUS   current
		 DESCRIPTION
			"The OSPF interface's administrative status.  The value
			'enabled' denotes that neighbor relationships may be
			formed on the interface, and the interface will be
			advertised as an internal route to some area.  The
			value 'disabled' denotes that the interface is external
			to OSPF."
		 DEFVAL { enabled }
		 ::= { snOspfIf2Entry 3 }

	 snOspfIf2RtrPriority OBJECT-TYPE
		 SYNTAX   DesignatedRouterPriority
		 MAX-ACCESS   read-write
		 STATUS   current
		 DESCRIPTION
			"The priority of this interface.  Used in multi-access
			networks, this field is used in the designated router
			election algorithm.  The value 0 signifies that the
			router is not eligible to become the designated router
			on this particular network.  In the event of a tie in
			this value, routers will use their router id as a tie
			breaker."
		 DEFVAL { 1 }
		 ::= { snOspfIf2Entry 4 }

	 snOspfIf2TransitDelay OBJECT-TYPE
		 SYNTAX   UpToMaxAge
		 MAX-ACCESS   read-write
		 STATUS   current
		 DESCRIPTION
			"The estimated number of seconds it takes to transmit a
			link- state update packet over this interface."
		 DEFVAL { 1 }
		 ::= { snOspfIf2Entry 5 }

	 snOspfIf2RetransInterval OBJECT-TYPE
		 SYNTAX   UpToMaxAge
		 MAX-ACCESS   read-write
		 STATUS   current
		 DESCRIPTION
			"The number of seconds between link-state advertisement
			retransmissions, for adjacencies belonging to this
			interface.  This value is also used when retransmitting
			database description and link-state request packets."
		 DEFVAL { 5 }
		 ::= { snOspfIf2Entry 6 }

	 snOspfIf2HelloInterval OBJECT-TYPE
		 SYNTAX   HelloRange
		 MAX-ACCESS   read-write
		 STATUS   current
		 DESCRIPTION
			"The length of time, in seconds, between the Hello
			packets that the router sends on the interface.  This
			value must be the same for all routers attached to a
			common network."
		 DEFVAL { 10 }
		 ::= { snOspfIf2Entry 7 }

	 snOspfIf2RtrDeadInterval OBJECT-TYPE
		 SYNTAX   PositiveInteger
		 MAX-ACCESS   read-write
		 STATUS   current
		 DESCRIPTION
			"The number of seconds that a router's Hello packets
			have not been seen before it's neighbors declare the
			router down.  This should be some multiple of the Hello
			interval.  This value must be the same for all routers
			attached to a common network."
		 DEFVAL { 40 }
		 ::= { snOspfIf2Entry 8 }


	 snOspfIf2AuthType OBJECT-TYPE
		 SYNTAX   INTEGER (0..255)
					 -- none (0),
					 -- simplePassword (1)
					 -- md5 (2)
					 -- reserved for specification by IANA (> 2)
		 MAX-ACCESS   read-write
		 STATUS   current
		 DESCRIPTION
			"The authentication type specified for an interface.
			Additional authentication types may be assigned locally
			on a per interface basis."
		 REFERENCE
			"OSPF Version 2, Appendix E Authentication"
		 DEFVAL { 0 }        -- no authentication, by default
		 ::= { snOspfIf2Entry 9 }


	 snOspfIf2AuthKey OBJECT-TYPE
		 SYNTAX   OCTET STRING (SIZE (0..8))
		 MAX-ACCESS   read-write
		 STATUS   current
		 DESCRIPTION
			"The Authentication Key.  If the Area's Authorization
			Type is simplePassword, and the key length is shorter
			than 8 octets, the agent will left adjust and zero fill
			to 8 octets.

			When read, snOspfIf2AuthKey always returns an Octet String
			of length zero."
		 REFERENCE
			"OSPF Version 2, Section 9 The Interface Data
			Structure"
		 DEFVAL   { '0000000000000000'h }    -- 0.0.0.0.0.0.0.0
		 ::= { snOspfIf2Entry 10 }


	 snOspfIf2MetricValue OBJECT-TYPE
		 SYNTAX   INTEGER (1..65535)
		 MAX-ACCESS   read-write
		 STATUS   current 
		 DESCRIPTION
			"The metric of using this type  of  service  on
			 this interface.  The default value of the TOS 0
			 Metric is 10^8 / ifSpeed."
		 ::= { snOspfIf2Entry 11 }

	 snOspfIf2RowStatus OBJECT-TYPE
		 SYNTAX   INTEGER {
					invalid(1),
					valid(2),
					delete(3),
					create(4),
					modify(5)
				  }
		 MAX-ACCESS   read-write
		 STATUS   current
		 DESCRIPTION
			"This object is used to create and
			 delete row in the table and control
			 if they are used. The values
			 that can be written are:
			 delete(3)...deletes the row
			 create(4)...creates a new row
			 modify(5)...modifies an exsisting row

			 If the row exists, then a SET with
			 value of create(4) returns error
			 'badValue'. Deleted rows go away
			 immediately. The following values
			 can be returned on reads:
			 noSuch(0)...no such row
			 invalid(1)...Setting it to 'invalid' has the effect of
						  rendering it inoperative..
			 valid(2)....the row exists and is valid"
		 ::= { snOspfIf2Entry 12 }
	 
	 snOspfIf2Md5AuthKeyId OBJECT-TYPE
		 SYNTAX   INTEGER (0..255)
		 MAX-ACCESS   read-write
		 STATUS   current
		 DESCRIPTION
			"The md5 authentication key ID.  If the snOspfVirtIfAuthType
			is set to md5, the value of snOspfIf2Md5AuthKeyId must be
			(1 to 255). This field identifies the algorithm and secret 
			key used to create the message digest appended to the OSPF 
			packet.  Key Identifiers are unique per-interface 
			(or equivalently, per-subnet)."
		 ::= { snOspfIf2Entry 13 }


	 snOspfIf2Md5AuthKey OBJECT-TYPE
		 SYNTAX   OCTET STRING (SIZE (0..16))
		 MAX-ACCESS   read-write
		 STATUS   current
		 DESCRIPTION
			"The MD5 Authentication Key.  If the Area's Authorization
			Type is md5, and the key length is shorter than 16 octets, 
			the agent will left adjust and zero fill to 16 octets.
			When read, snOspfIf2Md5AuthKey always returns an Octet String
			of length zero."
		 ::= { snOspfIf2Entry 14 }


	 snOspfIf2Md5ActivationWaitTime OBJECT-TYPE
		 SYNTAX   INTEGER (0..14400)
		 MAX-ACCESS   read-write
		 STATUS   current 
		 DESCRIPTION
			"The md5 authentication key activation wait time is specified in second
			and the maximum wait time is 14400 seconds (4 hours)."
		 ::= { snOspfIf2Entry 15 }

	 snOspfIf2AreaIdFormat OBJECT-TYPE
		 SYNTAX   INTEGER {
					integer(0),
					ipAddress(1)
				  }
		 MAX-ACCESS   read-only
		 STATUS   current
		 DESCRIPTION
			"This object is used to specify whether
			 AreaId is represented as IP Address or 
			 an Integer. The values
			 that can be written are:
			 integer(0).....as an integer.
			 ipAddress(1)...as IP Address."
		 ::= { snOspfIf2Entry 16 }

	 snOspfIf2PassiveMode OBJECT-TYPE
		 SYNTAX   INTEGER {
			disabled(0),
			enabled(1)
			}
		 MAX-ACCESS   read-write
		 STATUS   current
		 DESCRIPTION
			"This object control the passive mode of this interface."
		 ::= { snOspfIf2Entry 17 }

	 snOspfIf2DatabaseFilterAllOut OBJECT-TYPE
		 SYNTAX   INTEGER {
			disabled(0),
			enabled(1)
			}
		 MAX-ACCESS   read-write
		 STATUS   current
		 DESCRIPTION
			"This object control the filtering of outgoing OSPF LSA on this interface."
		 ::= { snOspfIf2Entry 18 }

	 snOspfIf2MtuIgnore OBJECT-TYPE
		 SYNTAX   INTEGER {
			disabled(0),
			enabled(1)
			}
		 MAX-ACCESS   read-write
		 STATUS   current
		 DESCRIPTION
			"This object control MTU detection mode of this interface."
		 ::= { snOspfIf2Entry 19 }

	 snOspfIf2NetworkP2mp OBJECT-TYPE
		 SYNTAX   INTEGER {
			disabled(0),
			enabled(1)
			}
		 MAX-ACCESS   read-write
		 STATUS   current
		 DESCRIPTION
			"This object enable/disable P2MP mode of this interface."
		 ::= { snOspfIf2Entry 20 }

	 snOspfIf2NetworkP2pt OBJECT-TYPE
		   SYNTAX   INTEGER {
				disabled(0),
				enabled(1)
				}
		   MAX-ACCESS   read-write
		   STATUS   current
		   DESCRIPTION
				"This object enable/disable Point-to-Point mode of this interface."
		  ::= { snOspfIf2Entry 21 }

	 snOspfIf2NetworkNonBroadcast OBJECT-TYPE
		   SYNTAX   INTEGER {
				disabled(0),
				enabled(1)
				}
		   MAX-ACCESS   read-write
		   STATUS   current
		   DESCRIPTION
				"This object enable/disable non broadcast mode of this interface."
		  ::= { snOspfIf2Entry 22 }


--  Section 5:		OSPF Virtual Interface Table

--      The Virtual Interface Table describes the virtual
--      links that the OSPF Process is configured to
--      carry on.



	 snOspfVirtIfTable OBJECT-TYPE
		 SYNTAX   SEQUENCE OF SnOspfVirtIfEntry
		 MAX-ACCESS   not-accessible
		 STATUS   current
		 DESCRIPTION
			"Information about this router's virtual interfaces."
		 REFERENCE
			"OSPF Version 2, Appendix C.4  Virtual link parameters"
		 ::= { snOspfVirtIf 1 }

	 snOspfVirtIfEntry OBJECT-TYPE
		 SYNTAX   SnOspfVirtIfEntry
		 MAX-ACCESS   not-accessible
		 STATUS   current
		 DESCRIPTION
			"Information about a single Virtual Interface."
		 INDEX { snOspfVirtIfAreaID, snOspfVirtIfNeighbor }
		 ::= { snOspfVirtIfTable 1 }

	 SnOspfVirtIfEntry ::=
		 SEQUENCE {
			 snOspfVirtIfAreaID
				 AreaID,
			 snOspfVirtIfNeighbor
				 RouterID,
			 snOspfVirtIfTransitDelay
				 UpToMaxAge,
			 snOspfVirtIfRetransInterval
				 UpToMaxAge,
			 snOspfVirtIfHelloInterval
				 HelloRange,
			 snOspfVirtIfRtrDeadInterval
				 PositiveInteger,
			 snOspfVirtIfAuthType
				 INTEGER,
			 snOspfVirtIfAuthKey
				 OCTET STRING,
			 snOspfVirtIfRowStatus
				 INTEGER, 
			 snOspfVirtIfMd5AuthKeyId
				 INTEGER,
			 snOspfVirtIfMd5AuthKey
				 OCTET STRING,
			 snOspfVirtIfMd5ActivationWaitTime
				 INTEGER,
			 snOspfVirtIfAreaIdFormat 
				 INTEGER
		 }

	 snOspfVirtIfAreaID OBJECT-TYPE
		 SYNTAX   AreaID
		 MAX-ACCESS   read-only
		 STATUS   current
		 DESCRIPTION
			"The Transit Area that the Virtual Link traverses.  By
			definition, this is not 0.0.0.0"
		 ::= { snOspfVirtIfEntry 1 }

	 snOspfVirtIfNeighbor OBJECT-TYPE
		 SYNTAX   RouterID
		 MAX-ACCESS   read-only
		 STATUS   current
		 DESCRIPTION
			"The Router ID of the Virtual Neighbor."
		 ::= { snOspfVirtIfEntry 2 }

	 snOspfVirtIfTransitDelay OBJECT-TYPE
		 SYNTAX   UpToMaxAge
		 MAX-ACCESS   read-write
		 STATUS   current
		 DESCRIPTION
			"The estimated number of seconds it takes to transmit a
			link- state update packet over this interface."
		 DEFVAL { 1 }
		 ::= { snOspfVirtIfEntry 3 }

	 snOspfVirtIfRetransInterval OBJECT-TYPE
		 SYNTAX   UpToMaxAge
		 MAX-ACCESS   read-write
		 STATUS   current
		 DESCRIPTION
			"The number of seconds between link-state advertisement
			retransmissions, for adjacencies belonging to this
			interface.  This value is also used when retransmitting
			database description and link-state request packets.
			This value should be well over the expected round-trip
			time."
		 DEFVAL { 5 }
		 ::= { snOspfVirtIfEntry 4 }

	 snOspfVirtIfHelloInterval OBJECT-TYPE
		 SYNTAX   HelloRange
		 MAX-ACCESS   read-write
		 STATUS   current
		 DESCRIPTION
			"The length of time, in seconds, between the Hello
			packets that the router sends on the interface.  This
			value must be the same for the virtual neighbor."
		 DEFVAL { 10 }
		 ::= { snOspfVirtIfEntry 5 }

	 snOspfVirtIfRtrDeadInterval OBJECT-TYPE
		 SYNTAX   PositiveInteger
		 MAX-ACCESS   read-write
		 STATUS   current
		 DESCRIPTION
			"The number of seconds that a router's Hello packets
			have not been seen before it's neighbors declare the
			router down.  This should be some multiple of the Hello
			interval.  This value must be the same for the virtual
			neighbor."
		 DEFVAL { 60 }
		 ::= { snOspfVirtIfEntry 6 }

	 snOspfVirtIfAuthType OBJECT-TYPE
		 SYNTAX   INTEGER (0..255)
					 -- none (0),
					 -- simplePassword (1)
					 -- md5 (2)
					 -- reserved for specification by IANA (> 2)
		 MAX-ACCESS   read-write
		 STATUS   current
		 DESCRIPTION
			"The authentication type specified for an interface.
			Additional authentication types may be assigned locally
			on a per interface basis."
		 REFERENCE
			"OSPF Version 2, Appendix E Authentication"
		 DEFVAL { 0 }        -- no authentication, by default
		 ::= { snOspfVirtIfEntry 7 }

	 snOspfVirtIfAuthKey OBJECT-TYPE
		 SYNTAX   OCTET STRING (SIZE (0..8)) 
		 MAX-ACCESS   read-write
		 STATUS   current
		 DESCRIPTION
			"If Authentication Type is simplePassword, the device
			will left adjust and zero fill to 8 octets.

			When read, snOspfVifAuthKey always returns a string of
			length zero."
		 REFERENCE
			"OSPF Version 2, Section 9 The Interface Data
			Structure"
		 DEFVAL   { '0000000000000000'h }    -- 0.0.0.0.0.0.0.0
		 ::= { snOspfVirtIfEntry 8 }

	 snOspfVirtIfRowStatus OBJECT-TYPE
		 SYNTAX   INTEGER {
					invalid(1),
					valid(2),
					delete(3),
					create(4),
					modify(5)
				  }
		 MAX-ACCESS   read-write
		 STATUS   current
		 DESCRIPTION
			"This object is used to create and
			 delete row in the table and control
			 if they are used. The values
			 that can be written are:
			 delete(3)...deletes the row
			 create(4)...creates a new row
			 modify(5)...modifies an exsisting row

			 If the row exists, then a SET with
			 value of create(4) returns error
			 'badValue'. Deleted rows go away
			 immediately. The following values
			 can be returned on reads:
			 noSuch(0)...no such row
			 invalid(1)...Setting it to 'invalid' has the effect of
						  rendering it inoperative..
			 valid(2)....the row exists and is valid"
		 ::= { snOspfVirtIfEntry 9 } 

	 snOspfVirtIfMd5AuthKeyId OBJECT-TYPE
		 SYNTAX   INTEGER (0..255)
		 MAX-ACCESS   read-write
		 STATUS   current
		 DESCRIPTION
			"The md5 authentication key ID.  If the snOspfVirtIfAuthType
			is set to md5, the value of snOspfVirtIfMd5AuthKeyId must be
			(1 to 255). This field identifies the algorithm and secret 
			key used to create the message digest appended to the OSPF 
			packet.  Key Identifiers are unique per-interface 
			(or equivalently, per-subnet)."
		 ::= { snOspfVirtIfEntry 10 }


	 snOspfVirtIfMd5AuthKey OBJECT-TYPE
		 SYNTAX   OCTET STRING (SIZE (0..16))
		 MAX-ACCESS   read-write
		 STATUS   current
		 DESCRIPTION
			"The MD5 Authentication Key.  If the Area's Authorization
			Type is md5, and the key length is shorter than 16 octets, 
			the agent will left adjust and zero fill to 16 octets.

			When read, snOspfIfMd5AuthKey always returns an Octet String
			of length zero."
		 REFERENCE
			"OSPF Version 2, Section 9 The Interface Data
			Structure"
		 DEFVAL   { '0000000000000000'h }    -- 0.0.0.0.0.0.0.0
		 ::= { snOspfVirtIfEntry 11 }


	 snOspfVirtIfMd5ActivationWaitTime OBJECT-TYPE
		 SYNTAX   INTEGER (0..14400)
		 MAX-ACCESS   read-write
		 STATUS   current 
		 DESCRIPTION
			"The md5 authentication key activation wait time is specified in second
			and the maximum wait time is 14400 seconds (4 hours)."
		 ::= { snOspfVirtIfEntry 12 }


	 snOspfVirtIfAreaIdFormat OBJECT-TYPE
		 SYNTAX   INTEGER {
					integer(0),
					ipAddress(1)
				  }
		 MAX-ACCESS   read-only
		 STATUS   current
		 DESCRIPTION
			"This object is used to specify whether
			 AreaId is represented as IP Address or 
			 an Integer. The values
			 that can be written are:
			 integer(0).....as an integer.
			 ipAddress(1)...as IP Address."
		 ::= { snOspfVirtIfEntry 13 }






--  Section 6:		OSPF Redistribution of Routes Table

--      The OSPF Redistribution of Routes Table contains list of routes
--      that will be used to decide whether a particular RIP or Static
--      route is to be imported into OSPF domain as external type 2
--      route when parameter Import Route into OSPF is Enabled.


	 snOspfRedisTable OBJECT-TYPE
		 SYNTAX   SEQUENCE OF SnOspfRedisEntry
		 MAX-ACCESS   not-accessible
		 STATUS   current
		 DESCRIPTION
			"The OSPF Redistribution Table contains a list of routes
			that could be imported into the OSPF domain."
		 ::= { snOspfRedis 1 }

	 snOspfRedisEntry OBJECT-TYPE
		 SYNTAX   SnOspfRedisEntry
		 MAX-ACCESS   not-accessible
		 STATUS   current
		 DESCRIPTION
			"The OSPF Redistribution Entry specifies a particular RIP 
			or Static route to be imported into the OSPF domain."
		 INDEX { snOspfRedisIndex }
		 ::= { snOspfRedisTable 1 }

	 SnOspfRedisEntry ::=
		 SEQUENCE {
			 snOspfRedisIndex
				 INTEGER,
			 snOspfRedisIpAddress
				 IpAddress,
			 snOspfRedisMask
				 IpAddress,
			 snOspfRedisAction
				 INTEGER,
			 snOspfRedisProtocol
				 INTEGER,
			 snOspfRedisSetOspfMetric
				 INTEGER,
			 snOspfRedisOspfMetricValue
				 Metric,
			 snOspfRedisMatchRipMetric
				 INTEGER,
			 snOspfRedisRipMetricValue
				 INTEGER,
			 snOspfRedisRowStatus
				 INTEGER
		 }


	snOspfRedisIndex OBJECT-TYPE
		 SYNTAX   INTEGER (1..64)
		 MAX-ACCESS   read-only
		 STATUS   current
		 DESCRIPTION
			"The destination IP address that associates with 
			this particular route."
		 ::= { snOspfRedisEntry 1 }

	snOspfRedisIpAddress OBJECT-TYPE
		 SYNTAX   IpAddress
		 MAX-ACCESS   read-write
		 STATUS   current
		 DESCRIPTION
			"The destination IP address that associates with 
			this particular route."
		 ::= { snOspfRedisEntry 2 }

	snOspfRedisMask OBJECT-TYPE
		 SYNTAX   IpAddress
		 MAX-ACCESS   read-write
		 STATUS   current
		 DESCRIPTION
			"The Subnet Mask that pertains to this route."
		 ::= { snOspfRedisEntry 3 }

	snOspfRedisAction OBJECT-TYPE
		 SYNTAX   INTEGER {
					noImport(0),
					import(1)
				  }
		 MAX-ACCESS   read-write
		 STATUS   current
		 DESCRIPTION
			"The action to be taken if the route match this entry. 
				noImport(0):	- the route is NOT imported into OSPF
								  Domain. 
				import(1):		- the route is imported into OSPF
								  Domain as external type 2 route."
		 ::= { snOspfRedisEntry 4 }

	snOspfRedisProtocol OBJECT-TYPE
		 SYNTAX   INTEGER {
			rip(1),
			all(2),
			static(3),
			bgp(4),
			connected(5),
			isis(6)
				  }
		 MAX-ACCESS   read-write
		 STATUS   current
		 DESCRIPTION
			"The imported routes into OSPF domain is set in the following: 
				rip(1):		- the RIP route.
				all(2):		- all protocol route.
				static(3):	- the static route.
				bgp(4):		- the BGP route.
				connected(5):		- the connected route.
				isis(6):		- the ISIS route."
		 ::= { snOspfRedisEntry 5 }

	snOspfRedisSetOspfMetric OBJECT-TYPE
		 SYNTAX   INTEGER {
					disabled(0),
					enabled(1)
				  }
		 MAX-ACCESS   read-write
		 STATUS   current
		 DESCRIPTION
			"The value indicates to which the route metric should match: 
				disabled(0):	- the route metric does NOT match the 
								  OSPF metric field.
				enabled(1):		- the route metric matches the OSPF 
								  metric field."
		 ::= { snOspfRedisEntry 6 }


	snOspfRedisOspfMetricValue OBJECT-TYPE
		 SYNTAX   Metric
		 MAX-ACCESS   read-write
		 STATUS   current 
		 DESCRIPTION
			"The metric of using OSPF Metric value on this route."
		 ::= { snOspfRedisEntry 7 }


	snOspfRedisMatchRipMetric OBJECT-TYPE
		 SYNTAX   INTEGER {
					disabled(0),
					enabled(1)
				  }
		 MAX-ACCESS   read-write
		 STATUS   current
		 DESCRIPTION
			"The value indicates to which the route metric should match: 
				disabled(0):	- the route metric does NOT match the 
								  RIP metric field.
				enabled(1):		- the route metric matches the RIP 
								  metric field."
		 ::= { snOspfRedisEntry 8 }


	 snOspfRedisRipMetricValue OBJECT-TYPE
		 SYNTAX   INTEGER (1..15)
		 MAX-ACCESS   read-write
		 STATUS   current 
		 DESCRIPTION
			"The metric of using RIP Metric value (1 to 15 hops) on this route."
		 ::= { snOspfRedisEntry 9 }


	 snOspfRedisRowStatus OBJECT-TYPE
		 SYNTAX   INTEGER {
					invalid(1),
					valid(2),
					delete(3),
					create(4),
					modify(5)
				  }
		 MAX-ACCESS   read-write
		 STATUS   current
		 DESCRIPTION
			"This object is used to create and
			 delete row in the table and control
			 if they are used. The values
			 that can be written are:
			 delete(3)...deletes the row
			 create(4)...creates a new row
			 modify(5)...modifies an exsisting row

			 If the row exists, then a SET with
			 value of create(4) returns error
			 'badValue'. Deleted rows go away
			 immediately. The following values
			 can be returned on reads:
			 noSuch(0)...no such row
			 invalid(1)...Setting it to 'invalid' has the effect of
						  rendering it inoperative..
			 valid(2)....the row exists and is valid"
		 ::= { snOspfRedisEntry 10 }



--  Section 7:		OSPF Neighbor Table

--      The OSPF Neighbor Table describes all neighbors in
--      the locality of the subject router.


	 snOspfNbrTable OBJECT-TYPE
		 SYNTAX   SEQUENCE OF SnOspfNbrEntry
		 MAX-ACCESS   not-accessible
		 STATUS   current
		 DESCRIPTION
			"A table of non-virtual neighbor information."
		 REFERENCE
			"OSPF Version 2, Section 10 The Neighbor Data
			Structure"
		 ::= { snOspfNbr 1 }

	 snOspfNbrEntry OBJECT-TYPE
		 SYNTAX   SnOspfNbrEntry
		 MAX-ACCESS   not-accessible
		 STATUS   current
		 DESCRIPTION
			"The information regarding a single neighbor."
		 REFERENCE
			"OSPF Version 2, Section 10 The Neighbor Data
			Structure"
		 INDEX { snOspfNbrEntryIndex }
		 ::= { snOspfNbrTable 1 }

	 SnOspfNbrEntry ::=
		 SEQUENCE {
			 snOspfNbrEntryIndex
				 Integer32,
			 snOspfNbrPort
				 Integer32,
			 snOspfNbrIpAddr
				 IpAddress,
			 snOspfNbrIndex
				 Integer32,
			 snOspfNbrRtrId
				 RouterID,
			 snOspfNbrOptions
				 Integer32,
			 snOspfNbrPriority
				 DesignatedRouterPriority,
			 snOspfNbrState
				 INTEGER,
			 snOspfNbrEvents
				 Counter32,
			 snOspfNbrLsRetransQLen
				 Gauge32
		 }

	 snOspfNbrEntryIndex  OBJECT-TYPE
		 SYNTAX   Integer32
		 MAX-ACCESS   read-only
		 STATUS   current
		 DESCRIPTION
			"The table entry index of this neighbor."
		 ::= { snOspfNbrEntry 1 }
	 
	 snOspfNbrPort OBJECT-TYPE
		 SYNTAX   Integer32
		 MAX-ACCESS   read-only
		 STATUS   current
		 DESCRIPTION
			"The physical port of this neighbor."
		 ::= { snOspfNbrEntry 2 }
	 

	 snOspfNbrIpAddr OBJECT-TYPE
		 SYNTAX   IpAddress
		 MAX-ACCESS   read-only
		 STATUS   current
		 DESCRIPTION
			"The IP address of this neighbor."
		 ::= { snOspfNbrEntry 3 }


	 snOspfNbrIndex OBJECT-TYPE
		 SYNTAX   Integer32
		 MAX-ACCESS   read-only
		 STATUS   current
		 DESCRIPTION
			"The neighbor index of each port and each IP address."
		 ::= { snOspfNbrEntry 4 }
	 
	 snOspfNbrRtrId OBJECT-TYPE
		 SYNTAX   RouterID
		 MAX-ACCESS   read-only
		 STATUS   current
		 DESCRIPTION
			"A 32-bit integer (represented as a type IpAddress)
			uniquely identifying the neighboring router in the
			Autonomous System."
		 DEFVAL   { '00000000'h }    -- 0.0.0.0
		 ::= { snOspfNbrEntry 5 }


	snOspfNbrOptions OBJECT-TYPE
		SYNTAX   Integer32
		MAX-ACCESS   read-only
		STATUS   current
		DESCRIPTION
		   "A Bit Mask corresponding to the neighbor's op-
		   tions field.

		   Bit 0, if set, indicates that the  system  will
		   operate  on  Type of Service metrics other than
		   TOS 0.  If zero, the neighbor will  ignore  all
		   metrics except the TOS 0 metric.

		   Bit 1, if set, indicates  that  the  associated
		   area  accepts and operates on external informa-
		   tion; if zero, it is a stub area.

		   Bit 2, if set, indicates that the system is ca-
		   pable  of routing IP Multicast datagrams; i.e.,
		   that it implements the Multicast Extensions  to
		   OSPF.

		   Bit 3, if set, indicates  that  the  associated
		   area  is  an  NSSA.  These areas are capable of
		   carrying type 7 external advertisements,  which
		   are  translated into type 5 external advertise-
		   ments at NSSA borders."
	   REFERENCE
		  "OSPF Version 2, Section 12.1.2 Options"
	  DEFVAL { 0 }
	  ::= { snOspfNbrEntry 6 }


	snOspfNbrPriority OBJECT-TYPE
		SYNTAX   DesignatedRouterPriority
		MAX-ACCESS   read-only
		STATUS   current
		DESCRIPTION
		   "The priority of this neighbor in the designat-
		   ed router election algorithm.  The value 0 sig-
		   nifies that the neighbor is not eligible to be-
		   come  the  designated router on this particular
		   network."
	   DEFVAL { 1 }
	   ::= { snOspfNbrEntry 7 }


	snOspfNbrState OBJECT-TYPE
		SYNTAX   INTEGER    {
					down (1),
					attempt (2),
					init (3),
					twoWay (4),
					exchangeStart (5),
					exchange (6),
					loading (7),
					full (8)
				  }
		MAX-ACCESS   read-only
		STATUS   current
		DESCRIPTION
		   "The State of the relationship with this Neigh-
		   bor."
	   REFERENCE
		  "OSPF Version 2, Section 10.1 Neighbor States"
	  DEFVAL   { down }
	  ::= { snOspfNbrEntry 8 }


	snOspfNbrEvents OBJECT-TYPE
		SYNTAX   Counter32
		MAX-ACCESS   read-only
		STATUS   current
		DESCRIPTION
		   "The number of times this neighbor relationship
		   has changed state, or an error has occurred."
	   ::= { snOspfNbrEntry 9 }


	snOspfNbrLsRetransQLen OBJECT-TYPE
		SYNTAX   Gauge32
		MAX-ACCESS   read-only
		STATUS   current
		DESCRIPTION
		   "The  current  length  of  the   retransmission
		   queue."
	   ::= { snOspfNbrEntry 10 }



	 --  Section 8: OSPF Virtual Neighbor Table

	 --      This table describes all virtual neighbors.
	 --      Since Virtual Links are configured in the
	 --      virtual interface table, this table is read-only.

	 snOspfVirtNbrTable OBJECT-TYPE
		 SYNTAX   SEQUENCE OF SnOspfVirtNbrEntry
		 MAX-ACCESS   not-accessible
		 STATUS   current
		 DESCRIPTION
			"A table of virtual neighbor information."
		 REFERENCE
			"OSPF Version 2, Section 15  Virtual Links"
		 ::= { snOspfVirtNbr 1 }

	 snOspfVirtNbrEntry OBJECT-TYPE
		 SYNTAX   SnOspfVirtNbrEntry
		 MAX-ACCESS   not-accessible
		 STATUS   current
		 DESCRIPTION
			"Virtual neighbor information."
		 INDEX { snOspfVirtNbrEntryIndex }
		 ::= { snOspfVirtNbrTable 1 }

	 SnOspfVirtNbrEntry ::=
		 SEQUENCE {
			 snOspfVirtNbrEntryIndex
				 Integer32,
			 snOspfVirtNbrArea
				 AreaID,
			 snOspfVirtNbrRtrId
				 RouterID,
			 snOspfVirtNbrIpAddr
				 IpAddress,
			 snOspfVirtNbrOptions
				 Integer32,
			 snOspfVirtNbrState
				 INTEGER,
			 snOspfVirtNbrEvents
				 Counter32,
			 snOspfVirtNbrLSRetransQLen
				 Gauge32,
			 snOspfVirtNbrAreaIdFormat 
				 INTEGER
		 }

	 snOspfVirtNbrEntryIndex  OBJECT-TYPE
		 SYNTAX   Integer32
		 MAX-ACCESS   read-only
		 STATUS   current
		 DESCRIPTION
			"The table entry index of this virtual neighbor."
		 ::= { snOspfVirtNbrEntry 1 }

	 snOspfVirtNbrArea OBJECT-TYPE
		 SYNTAX   AreaID
		 MAX-ACCESS   read-only
		 STATUS   current
		 DESCRIPTION
			"The Transit Area Identifier."
		 ::= { snOspfVirtNbrEntry 2 }

	 snOspfVirtNbrRtrId OBJECT-TYPE
		 SYNTAX   RouterID
		 MAX-ACCESS   read-only
		 STATUS   current
		 DESCRIPTION
			"A 32-bit integer uniquely identifying the neighboring
			router in the Autonomous System."
		 ::= { snOspfVirtNbrEntry 3 }

	 snOspfVirtNbrIpAddr OBJECT-TYPE
		 SYNTAX   IpAddress
		 MAX-ACCESS   read-only
		 STATUS   current
		 DESCRIPTION
			"The IP address this Virtual Neighbor is using."
		 ::= { snOspfVirtNbrEntry 4 }

	 snOspfVirtNbrOptions OBJECT-TYPE
		 SYNTAX   Integer32
		 MAX-ACCESS   read-only
		 STATUS   current
		 DESCRIPTION
			"A bit map corresponding to the neighbor's options
			field.  Thus, Bit 1, if set, indicates that the
			neighbor supports Type of Service Routing; if zero, no
			metrics other than TOS 0 are in use by the neighbor."
		 ::= { snOspfVirtNbrEntry 5 }

	 snOspfVirtNbrState OBJECT-TYPE
		 SYNTAX   INTEGER {
					 down (1),
					 attempt (2),
					 init (3),
					 twoWay (4),
					 exchangeStart (5),
					 exchange (6),
					 loading (7),
					 full (8)
				  }
		 MAX-ACCESS   read-only
		 STATUS   current
		 DESCRIPTION
			"The state of the Virtual Neighbor Relationship."
		 ::= { snOspfVirtNbrEntry 6 }

	 snOspfVirtNbrEvents OBJECT-TYPE
		 SYNTAX   Counter32
		 MAX-ACCESS   read-only
		 STATUS   current
		 DESCRIPTION
			"The number of times this virtual link has changed its
			state, or an error has occurred."
		 ::= { snOspfVirtNbrEntry 7 }

	 snOspfVirtNbrLSRetransQLen OBJECT-TYPE
		 SYNTAX   Gauge32
		 MAX-ACCESS   read-only
		 STATUS   current
		 DESCRIPTION
			"The current length of the retransmission queue."
		 ::= { snOspfVirtNbrEntry 8 }

	 snOspfVirtNbrAreaIdFormat OBJECT-TYPE
		 SYNTAX   INTEGER {
					integer(0),
					ipAddress(1)
				  }
		 MAX-ACCESS   read-only
		 STATUS   current
		 DESCRIPTION
			"This object is used to specify whether
			 AreaId is represented as IP Address or 
			 an Integer. The values
			 that can be written are:
			 integer(0).....as an integer.
			 ipAddress(1)...as IP Address."
		 ::= { snOspfVirtNbrEntry 9 }


	 --  Section 9: OSPF Link State Database

	 --      The Link State Database contains the Link State
	 --      Advertisements from throughout the areas that the
	 --      device is attached to.

	 snOspfLsdbTable OBJECT-TYPE
		 SYNTAX   SEQUENCE OF SnOspfLsdbEntry
		 MAX-ACCESS   not-accessible
		 STATUS   current
		 DESCRIPTION
			"The OSPF Process's Links State Database."
		 REFERENCE
			"OSPF Version 2, Section 12 Link State Advertisements"
		 ::= { snOspfLsdb 1 }

	 snOspfLsdbEntry OBJECT-TYPE
		 SYNTAX   SnOspfLsdbEntry
		 MAX-ACCESS   not-accessible
		 STATUS   current
		 DESCRIPTION
			"A single Link State Advertisement."
		 INDEX { snOspfLsdbEntryIndex }
		 ::= { snOspfLsdbTable 1 }

	 SnOspfLsdbEntry ::=
		 SEQUENCE {
			 snOspfLsdbEntryIndex
				 Integer32,
			 snOspfLsdbAreaId
				 AreaID,
			 snOspfLsdbType
				 INTEGER,
			 snOspfLsdbLsId
				 IpAddress,
			 snOspfLsdbRouterId
				 RouterID,
			 snOspfLsdbSequence
				 Integer32,
			 snOspfLsdbAge
				 Integer32,
			 snOspfLsdbChecksum
				 Integer32,
			 snOspfLsdbAdvertisement
				 OCTET STRING,
			 snOspfLsdbAreaIdFormat 
				 INTEGER
		 }

	 snOspfLsdbEntryIndex  OBJECT-TYPE
		 SYNTAX   Integer32
		 MAX-ACCESS   read-only
		 STATUS   current
		 DESCRIPTION
			"The table entry index of this Link State Database."
		 ::= { snOspfLsdbEntry 1 }


	 snOspfLsdbAreaId OBJECT-TYPE
		 SYNTAX   AreaID
		 MAX-ACCESS   read-only
		 STATUS   current
		 DESCRIPTION
			"The 32 bit identifier of the Area from which the LSA
			was received."
		 REFERENCE
			"OSPF Version 2, Appendix C.2 Area parameters"
		 ::= { snOspfLsdbEntry 2 }

	 snOspfLsdbType OBJECT-TYPE
		 SYNTAX   INTEGER {
					 routerLink (1),
					 networkLink (2),
					 summaryLink (3),
					 asSummaryLink (4),
					 asExternalLink (5),
					 multicastLink (6),
					 nssaExternalLink (7),
					 opaqueLink (9),
					 opaqueAreaLink (10),
					 opaqueAsLink (11)
				  }
		 MAX-ACCESS   read-only
		 STATUS   current
		 DESCRIPTION
			"The type of the link state advertisement.  Each link
			state type has a separate advertisement format."
		 REFERENCE
			"OSPF Version 2, Appendix A.4.1 The Link State
			Advertisement header"
		 ::= { snOspfLsdbEntry 3 }

	 snOspfLsdbLsId OBJECT-TYPE
		 SYNTAX   IpAddress
		 MAX-ACCESS   read-only
		 STATUS   current
		 DESCRIPTION
			"The Link State ID is an LS Type Specific field
			containing either a Router ID or an IP Address; it
			identifies the piece of the routing domain that is
			being described by the advertisement."
		 REFERENCE
			"OSPF Version 2, Section 12.1.4 Link State ID"
		 ::= { snOspfLsdbEntry 4 }

	 snOspfLsdbRouterId OBJECT-TYPE
		 SYNTAX   RouterID
		 MAX-ACCESS   read-only
		 STATUS   current
		 DESCRIPTION
			"The 32 bit number that uniquely identifies the
			originating router in the Autonomous System."
		 REFERENCE
			"OSPF Version 2, Appendix C.1 Global parameters"
		 ::= { snOspfLsdbEntry 5 }

	 --  Note that the OSPF Sequence Number is a 32 bit signed
	 --  integer.  It starts with the value '80000001'h,
	 --  or -'7FFFFFFF'h, and increments until '7FFFFFFF'h
	 --  Thus, a typical sequence number will be very negative.

	 snOspfLsdbSequence OBJECT-TYPE
		 SYNTAX   Integer32
		 MAX-ACCESS   read-only
		 STATUS   current
		 DESCRIPTION
			"The sequence number field is a signed 32-bit integer.
			It is used to detect old and duplicate link state
			advertisements.  The space of sequence numbers is
			linearly ordered.  The larger the sequence number the
			more recent the advertisement."
		 REFERENCE
			"OSPF Version 2, Section 12.1.6 LS sequence number"
		 ::= { snOspfLsdbEntry 6 }

	 snOspfLsdbAge OBJECT-TYPE
		 SYNTAX   Integer32    -- Should be 0..MaxAge
		 MAX-ACCESS   read-only
		 STATUS   current
		 DESCRIPTION
			"This field is the age of the link state advertisement
			in seconds."
		 REFERENCE
			"OSPF Version 2, Section 12.1.1 LS age"
		 ::= { snOspfLsdbEntry 7 }

	 snOspfLsdbChecksum OBJECT-TYPE
		 SYNTAX   Integer32
		 MAX-ACCESS   read-only
		 STATUS   current
		 DESCRIPTION
			"This field is the checksum of the complete contents of
			the advertisement, excepting the age field.  The age
			field is excepted so that an advertisement's age can be
			incremented without updating the checksum.  The
			checksum used is the same that is used for ISO
			connectionless datagrams; it is commonly referred to as
			the Fletcher checksum."
		 REFERENCE
			"OSPF Version 2, Section 12.1.7 LS checksum"
		 ::= { snOspfLsdbEntry 8 }

	 snOspfLsdbAdvertisement OBJECT-TYPE
		 SYNTAX   OCTET STRING (SIZE (1..65535))
		 MAX-ACCESS   read-only
		 STATUS   current
		 DESCRIPTION
			"The entire Link State Advertisement, including its
			header."
		 REFERENCE
			"OSPF Version 2, Section 12 Link State Advertisements"
		 ::= { snOspfLsdbEntry 9 }


	 snOspfLsdbAreaIdFormat OBJECT-TYPE
		 SYNTAX   INTEGER {
					integer(0),
					ipAddress(1)
				  }
		 MAX-ACCESS   read-only
		 STATUS   current
		 DESCRIPTION
			"This object is used to specify whether
			 AreaId is represented as IP Address or 
			 an Integer. The values
			 that can be written are:
			 integer(0).....as an integer.
			 ipAddress(1)...as IP Address."
		 ::= { snOspfLsdbEntry 10 }


--  Section 10: OSPF Link State Database, External

--      The Link State Database contains the Link State
--      Advertisements from throughout the areas that the
--      device is attached to.

--             This table is identical to the OSPF LSDB Table in
--      format, but contains only External Link State
--             Advertisements.  The purpose is to allow external
--      LSAs to be displayed once for the router rather
--      than once in each non-stub area.

	snOspfExtLsdbTable OBJECT-TYPE
		SYNTAX   SEQUENCE OF SnOspfExtLsdbEntry
		MAX-ACCESS   not-accessible
		STATUS   current
		DESCRIPTION
		   "The OSPF Process's Links State Database."
	   REFERENCE
		  "OSPF Version 2, Section 12  Link  State  Adver-
		  tisements"
	  ::= { snOspfExtLsdb 1 }


	snOspfExtLsdbEntry OBJECT-TYPE
		SYNTAX   SnOspfExtLsdbEntry
		MAX-ACCESS   not-accessible
		STATUS   current
		DESCRIPTION
		   "A single Link State Advertisement."
	   INDEX { snOspfExtLsdbEntryIndex }
	   ::= { snOspfExtLsdbTable 1 }

SnOspfExtLsdbEntry ::=
	SEQUENCE {
	   snOspfExtLsdbEntryIndex 
			Integer32,
		snOspfExtLsdbType
			INTEGER,
		snOspfExtLsdbLsId
			IpAddress,
		snOspfExtLsdbRouterId
			RouterID,
		snOspfExtLsdbSequence
			Integer32,
		snOspfExtLsdbAge
			Integer32,
		snOspfExtLsdbChecksum
			Integer32,
		snOspfExtLsdbAdvertisement
			OCTET STRING
			  }

	snOspfExtLsdbEntryIndex  OBJECT-TYPE
		 SYNTAX   Integer32
		 MAX-ACCESS   read-only
		 STATUS   current
		 DESCRIPTION
			"The table entry index of this Link State Database."
		 ::= { snOspfExtLsdbEntry 1 }


	snOspfExtLsdbType OBJECT-TYPE
		SYNTAX   INTEGER    {
					asExternalLink (5)
				  }
		MAX-ACCESS   read-only
		STATUS   current
		DESCRIPTION
		   "The type  of  the  link  state  advertisement.
		   Each  link state type has a separate advertise-
		   ment format."
	   REFERENCE
		  "OSPF Version 2, Appendix A.4.1 The  Link  State
		  Advertisement header"
	  ::= { snOspfExtLsdbEntry 2 }


	snOspfExtLsdbLsId OBJECT-TYPE
		SYNTAX   IpAddress
		MAX-ACCESS   read-only
		STATUS   current
		DESCRIPTION
		   "The Link State ID is an LS Type Specific field
		   containing either a Router ID or an IP Address;
		   it identifies the piece of the  routing  domain
		   that is being described by the advertisement."
	   REFERENCE
		  "OSPF Version 2, Section 12.1.4 Link State ID"
	  ::= { snOspfExtLsdbEntry 3 }


	snOspfExtLsdbRouterId OBJECT-TYPE
		SYNTAX   RouterID
		MAX-ACCESS   read-only
		STATUS   current
		DESCRIPTION
		   "The 32 bit number that uniquely identifies the
		   originating router in the Autonomous System."
	   REFERENCE
		  "OSPF Version 2, Appendix C.1 Global parameters"
	  ::= { snOspfExtLsdbEntry 4 }

--  Note that the OSPF Sequence Number is a 32 bit signed
--  integer.  It starts with the value '80000001'h,
--  or -'7FFFFFFF'h, and increments until '7FFFFFFF'h
--  Thus, a typical sequence number will be very negative.


	snOspfExtLsdbSequence OBJECT-TYPE
		SYNTAX   Integer32
		MAX-ACCESS   read-only
		STATUS   current
		DESCRIPTION
		   "The sequence number field is a  signed  32-bit
		   integer.   It  is used to detect old and dupli-
		   cate link state advertisements.  The  space  of
		   sequence  numbers  is  linearly  ordered.   The
		   larger the sequence number the more recent  the
		   advertisement."
	   REFERENCE
		  "OSPF Version  2,  Section  12.1.6  LS  sequence
		  number"
	  ::= { snOspfExtLsdbEntry 5 }


	snOspfExtLsdbAge OBJECT-TYPE
		SYNTAX   Integer32    -- Should be 0..MaxAge
		MAX-ACCESS   read-only
		STATUS   current
		DESCRIPTION
		   "This field is the age of the link state adver-
		   tisement in seconds."
	   REFERENCE
		  "OSPF Version 2, Section 12.1.1 LS age"
	  ::= { snOspfExtLsdbEntry 6 }


	snOspfExtLsdbChecksum OBJECT-TYPE
		SYNTAX   Integer32
		MAX-ACCESS   read-only
		STATUS   current
		DESCRIPTION
		   "This field is the  checksum  of  the  complete
		   contents  of  the  advertisement, excepting the
		   age field.  The age field is excepted  so  that
		   an   advertisement's  age  can  be  incremented
		   without updating the  checksum.   The  checksum
		   used  is  the same that is used for ISO connec-
		   tionless datagrams; it is commonly referred  to
		   as the Fletcher checksum."
	   REFERENCE
		  "OSPF Version 2, Section 12.1.7 LS checksum"
	  ::= { snOspfExtLsdbEntry 7 }


	snOspfExtLsdbAdvertisement OBJECT-TYPE
		SYNTAX   OCTET STRING (SIZE(36))
		MAX-ACCESS   read-only
		STATUS   current
		DESCRIPTION
		   "The entire Link State Advertisement, including
		   its header."
	   REFERENCE
		  "OSPF Version 2, Section 12  Link  State  Adver-
		  tisements"
	  ::= { snOspfExtLsdbEntry 8 }



--		Section 11:	OSPF Area Status Table

--      The OSPF Area Status Data Structure contains information
--      regarding the various areas. The interfaces and
--      virtual links are configured as part of these areas.
--      Area 0.0.0.0, by definition, is the Backbone Area

	 snOspfAreaStatusTable OBJECT-TYPE
		 SYNTAX   SEQUENCE OF SnOspfAreaStatusEntry
		 MAX-ACCESS   not-accessible
		 STATUS   current
		 DESCRIPTION
			"Information describing the configured parameters and
			cumulative statistics of the router's attached areas."
		 REFERENCE
			"OSPF Version 2, Section 6  The Area Data Structure"
		 ::= { snOspfAreaStatus 1 }

	 snOspfAreaStatusEntry OBJECT-TYPE
		 SYNTAX   SnOspfAreaStatusEntry
		 MAX-ACCESS   not-accessible
		 STATUS   current
		 DESCRIPTION
			"Information describing the configured parameters and
			cumulative statistics of one of the router's attached
			areas."
		 INDEX { snOspfAreaStatusEntryIndex }
		 ::= { snOspfAreaStatusTable 1 }

	 SnOspfAreaStatusEntry ::=
		 SEQUENCE {
			 snOspfAreaStatusEntryIndex 
				 Integer32,
			 snOspfAreaStatusAreaId 
				 AreaID,
			 snOspfAreaStatusImportASExtern
				 Integer32,
			 snOspfAreaStatusStubMetric
				 BigMetric,
			 snOspfAreaStatusSpfRuns
				 Counter32,
			 snOspfAreaStatusAreaBdrRtrCount
				 Gauge32,
			 snOspfAreaStatusASBdrRtrCount
				 Gauge32,
			 snOspfAreaStatusLSACount
				 Gauge32,
			 snOspfAreaStatusLSACksumSum
				 Integer32,
			 snOspfAreaStatusAreaIdFormat 
				 INTEGER
		 }

	 snOspfAreaStatusEntryIndex  OBJECT-TYPE
		 SYNTAX   Integer32
		 MAX-ACCESS   read-only
		 STATUS   current
		 DESCRIPTION
			"The table entry index of this Area."
		 ::= { snOspfAreaStatusEntry 1 }


	 snOspfAreaStatusAreaId OBJECT-TYPE
		 SYNTAX   AreaID
		 MAX-ACCESS   read-only
		 STATUS   current
		 DESCRIPTION
			"A 32-bit integer uniquely identifying an area.  Area
			ID 0.0.0.0 is used for the OSPF backbone."
		 REFERENCE
			"OSPF Version 2, Appendix C.2 Area parameters"
		 ::= { snOspfAreaStatusEntry 2 }

	 snOspfAreaStatusImportASExtern OBJECT-TYPE
		 SYNTAX   Integer32
		 MAX-ACCESS   read-only
		 STATUS   current
		 DESCRIPTION
			"The area's support for importing AS external link-
			state advertisements."
		 REFERENCE
			"OSPF Version 2, Appendix C.2 Area parameters"
		 DEFVAL { 1 }
		 ::= { snOspfAreaStatusEntry 3 }

	 snOspfAreaStatusStubMetric OBJECT-TYPE
		 SYNTAX   BigMetric
		 MAX-ACCESS   read-only
		 STATUS   current
		 DESCRIPTION
			"The metric value applied at the default type of
			service(ospfMetric).  By default, this equals the 
			least metric at the type of service among the 
			interfaces to other areas.  This Object exist if
			only if the value of snOspfAreaSummary is 
			snOspfAreaSummary(2); Otherwise, an SNMP_GET/GET_NEXT 
			attempt of this Object will return NO_SUCH_NAME."
		 ::= { snOspfAreaStatusEntry 4 }

	 snOspfAreaStatusSpfRuns OBJECT-TYPE
		 SYNTAX   Counter32
		 MAX-ACCESS   read-only
		 STATUS   current
		 DESCRIPTION
			"The number of times that the intra-area route table
			has been calculated using this area's link-state
			database.  This is typically done using Dijkstra's
			algorithm."
		 ::= { snOspfAreaStatusEntry 5 }

	 snOspfAreaStatusAreaBdrRtrCount OBJECT-TYPE
		 SYNTAX   Gauge32
		 MAX-ACCESS   read-only
		 STATUS   current
		 DESCRIPTION
			"The total number of area border routers reachable
			within this area.  This is initially zero, and is
			calculated in each SPF Pass."
		 DEFVAL   { 0 }
		 ::= { snOspfAreaStatusEntry 6 }

	 snOspfAreaStatusASBdrRtrCount OBJECT-TYPE
		 SYNTAX   Gauge32
		 MAX-ACCESS   read-only
		 STATUS   current
		 DESCRIPTION
			"The total number of Autonomous System border routers
			reachable within this area.  This is initially zero,
			and is calculated in each SPF Pass."
		 DEFVAL   { 0 }
		 ::= { snOspfAreaStatusEntry 7 }

	 snOspfAreaStatusLSACount OBJECT-TYPE
		 SYNTAX   Gauge32
		 MAX-ACCESS   read-only
		 STATUS   current
		 DESCRIPTION
			"The total number of link-state advertisements in this
			area's link-state database, excluding AS External
			LSA's."
		 DEFVAL   { 0 }
		 ::= { snOspfAreaStatusEntry 8 }

	 snOspfAreaStatusLSACksumSum OBJECT-TYPE
		 SYNTAX   Integer32
		 MAX-ACCESS   read-only
		 STATUS   current
		 DESCRIPTION
			"The 32-bit unsigned sum of the link-state
			advertisements' LS checksums contained in this area's
			link-state database.  This sum excludes external (LS
			type 5) link-state advertisements.  The sum can be used
			to determine if there has been a change in a router's
			link state database, and to compare the link-state
			database of two routers."
		 DEFVAL   { 0 }
		 ::= { snOspfAreaStatusEntry 9 }


	 snOspfAreaStatusAreaIdFormat OBJECT-TYPE
		 SYNTAX   INTEGER {
					integer(0),
					ipAddress(1)
				  }
		 MAX-ACCESS   read-only
		 STATUS   current
		 DESCRIPTION
			"This object is used to specify whether
			 AreaId is represented as IP Address or 
			 an Integer. The values
			 that can be written are:
			 integer(0).....as an integer.
			 ipAddress(1)...as IP Address."
		 ::= { snOspfAreaStatusEntry 10 }
	 


--  Section 12:		OSPF Interface Status Table

--      The OSPF Interface Status Table augments the ifStatusTable with OSPF
--      specific information.


	 snOspfIfStatusTable OBJECT-TYPE
		 SYNTAX   SEQUENCE OF SnOspfIfStatusEntry
		 MAX-ACCESS   not-accessible
		 STATUS   current
		 DESCRIPTION
			"The OSPF Interface Status Table describes the interfaces from
			the viewpoint of OSPF."
		 ::= { snOspfIfStatus 1 }

	 snOspfIfStatusEntry OBJECT-TYPE
		 SYNTAX   SnOspfIfStatusEntry
		 MAX-ACCESS   not-accessible
		 STATUS   current
		 DESCRIPTION
			"The OSPF Interface Entry describes one interface from
			the viewpoint of OSPF."
		 INDEX { snOspfIfStatusEntryIndex }
		 ::= { snOspfIfStatusTable 1 }

	 SnOspfIfStatusEntry ::=
		 SEQUENCE {
			 snOspfIfStatusEntryIndex 
				 Integer32,
			 snOspfIfStatusPort
				 Integer32,
			 snOspfIfStatusIpAddress
				 IpAddress,
			 snOspfIfStatusAreaId
				 AreaID,
			 snOspfIfStatusType
				 INTEGER,
			 snOspfIfStatusAdminStat
				 RtrStatus,
			 snOspfIfStatusRtrPriority
				 DesignatedRouterPriority,
			 snOspfIfStatusTransitDelay
				 UpToMaxAge,
			 snOspfIfStatusRetransInterval
				 UpToMaxAge,
			 snOspfIfStatusHelloInterval
				 HelloRange,
			 snOspfIfStatusRtrDeadInterval
				 PositiveInteger,
			 snOspfIfStatusState
				 INTEGER,
			 snOspfIfStatusDesignatedRouter
				 IpAddress,
			 snOspfIfStatusBackupDesignatedRouter
				 IpAddress,
			 snOspfIfStatusEvents
				 Counter32,
			 snOspfIfStatusAuthType
				 Integer32,
			 snOspfIfStatusAuthKey
				 OCTET STRING,
			 snOspfIfStatusMetricValue
				 Metric,
			 snOspfIfStatusMd5AuthKeyId
				 INTEGER,
			 snOspfIfStatusMd5AuthKey
				 OCTET STRING,
			 snOspfIfStatusMd5ActivationWaitTime
				 INTEGER,
			 snOspfIfStatusAreaIdFormat 
				 INTEGER
		 }

	 snOspfIfStatusEntryIndex  OBJECT-TYPE
		 SYNTAX   Integer32
		 MAX-ACCESS   read-only
		 STATUS   current
		 DESCRIPTION
			"The table entry index of this Area."
		 ::= { snOspfIfStatusEntry 1 }

	 snOspfIfStatusPort OBJECT-TYPE
		 SYNTAX   Integer32
		 MAX-ACCESS   read-only
		 STATUS   current
		 DESCRIPTION
			"The physical router port of this OSPF interface."
		 ::= { snOspfIfStatusEntry 2 }

	 snOspfIfStatusIpAddress OBJECT-TYPE
		 SYNTAX   IpAddress
		 MAX-ACCESS   read-only
		 STATUS   current
		 DESCRIPTION
			"The IP address of this OSPF interface."
		 ::= { snOspfIfStatusEntry 3 }


	 snOspfIfStatusAreaId OBJECT-TYPE
		 SYNTAX   AreaID
		 MAX-ACCESS   read-only
		 STATUS   current
		 DESCRIPTION
			"A 32-bit integer uniquely identifying the area to
			which the interface connects.  Area ID 0.0.0.0 is used
			for the OSPF backbone."
		 DEFVAL   { '00000000'h }    -- 0.0.0.0
		 ::= { snOspfIfStatusEntry 4 }


	 snOspfIfStatusType OBJECT-TYPE
		 SYNTAX   INTEGER {
					 broadcast (1),
					 nbma (2),
					 pointToPoint (3)
				  }
		 MAX-ACCESS   read-only
		 STATUS   current
		 DESCRIPTION
			"The OSPF interface type.

			By way of a default, this field may be intuited from
			the corresponding value of ifType.  Broadcast LANs,
			such as Ethernet and IEEE 802.5, take the value
			'broadcast', X.25, Frame Relay, and similar
			technologies take the value 'nbma', and links that are
			definitively point to point take the value
			'pointToPoint'."
		 ::= { snOspfIfStatusEntry 5 }


	 snOspfIfStatusAdminStat OBJECT-TYPE
		 SYNTAX   RtrStatus
		 MAX-ACCESS   read-only
		 STATUS   current
		 DESCRIPTION
			"The OSPF interface's administrative status.  The value
			'enabled' denotes that neighbor relationships may be
			formed on the interface, and the interface will be
			advertised as an internal route to some area.  The
			value 'disabled' denotes that the interface is external
			to OSPF."
		 ::= { snOspfIfStatusEntry 6 }

	 snOspfIfStatusRtrPriority OBJECT-TYPE
		 SYNTAX   DesignatedRouterPriority
		 MAX-ACCESS   read-only
		 STATUS   current
		 DESCRIPTION
			"The priority of this interface.  Used in multi-access
			networks, this field is used in the designated router
			election algorithm.  The value 0 signifies that the
			router is not eligible to become the designated router
			on this particular network.  In the event of a tie in
			this value, routers will use their router id as a tie
			breaker."
		 DEFVAL { 1 }
		 ::= { snOspfIfStatusEntry 7 }

	 snOspfIfStatusTransitDelay OBJECT-TYPE
		 SYNTAX   UpToMaxAge
		 MAX-ACCESS   read-only
		 STATUS   current
		 DESCRIPTION
			"The estimated number of seconds it takes to transmit a
			link- state update packet over this interface."
		 DEFVAL { 1 }
		 ::= { snOspfIfStatusEntry 8 }

	 snOspfIfStatusRetransInterval OBJECT-TYPE
		 SYNTAX   UpToMaxAge
		 MAX-ACCESS   read-only
		 STATUS   current
		 DESCRIPTION
			"The number of seconds between link-state advertisement
			retransmissions, for adjacencies belonging to this
			interface.  This value is also used when retransmitting
			database description and link-state request packets."
		 DEFVAL { 5 }
		 ::= { snOspfIfStatusEntry 9 }

	 snOspfIfStatusHelloInterval OBJECT-TYPE
		 SYNTAX   HelloRange
		 MAX-ACCESS   read-only
		 STATUS   current
		 DESCRIPTION
			"The length of time, in seconds, between the Hello
			packets that the router sends on the interface.  This
			value must be the same for all routers attached to a
			common network."
		 DEFVAL { 10 }
		 ::= { snOspfIfStatusEntry 10 }

	 snOspfIfStatusRtrDeadInterval OBJECT-TYPE
		 SYNTAX   PositiveInteger
		 MAX-ACCESS   read-only
		 STATUS   current
		 DESCRIPTION
			"The number of seconds that a router's Hello packets
			have not been seen before it's neighbors declare the
			router down.  This should be some multiple of the Hello
			interval.  This value must be the same for all routers
			attached to a common network."
		 DEFVAL { 40 }
		 ::= { snOspfIfStatusEntry 11 }

	 snOspfIfStatusState OBJECT-TYPE
		 SYNTAX   INTEGER {
					 down (1),
					 loopback (2),
					 waiting (3),
					 pointToPoint (4),
					 designatedRouter (5),
					 backupDesignatedRouter (6),
					 otherDesignatedRouter (7)
				  }
		 MAX-ACCESS   read-only
		 STATUS   current
		 DESCRIPTION
			"The OSPF Interface State."
		 DEFVAL { down }
		 ::= { snOspfIfStatusEntry 12 }

	 snOspfIfStatusDesignatedRouter OBJECT-TYPE
		 SYNTAX   IpAddress
		 MAX-ACCESS   read-only
		 STATUS   current
		 DESCRIPTION
			"The IP Address of the Designated Router."
		 DEFVAL   { '00000000'h }    -- 0.0.0.0
		 ::= { snOspfIfStatusEntry 13 }

	 snOspfIfStatusBackupDesignatedRouter OBJECT-TYPE
		 SYNTAX   IpAddress
		 MAX-ACCESS   read-only
		 STATUS   current
		 DESCRIPTION
			"The IP Address of the Backup Designated Router."
		 DEFVAL   { '00000000'h }    -- 0.0.0.0
		 ::= { snOspfIfStatusEntry 14 }

	 snOspfIfStatusEvents OBJECT-TYPE
		 SYNTAX   Counter32
		 MAX-ACCESS   read-only
		 STATUS   current
		 DESCRIPTION
			"The number of times this OSPF interface has changed
			its state, or an error has occurred."
		 ::= { snOspfIfStatusEntry 15 }


	 snOspfIfStatusAuthType OBJECT-TYPE
		 SYNTAX   Integer32
					 -- none (0),
					 -- simplePassword (1)
					 -- reserved for specification by IANA (> 1)
		 MAX-ACCESS   read-only
		 STATUS   current
		 DESCRIPTION
			"The authentication type specified for an interface.
			Additional authentication types may be assigned locally
			on a per interface basis."
		 REFERENCE
			"OSPF Version 2, Appendix E Authentication"
		 DEFVAL { 0 }        -- no authentication, by default
		 ::= { snOspfIfStatusEntry 16 }


	 snOspfIfStatusAuthKey OBJECT-TYPE
		 SYNTAX   OCTET STRING (SIZE (0..8))
		 MAX-ACCESS   read-only
		 STATUS   current
		 DESCRIPTION
			"The Authentication Key.  If the Area's Authorization
			Type is simplePassword, and the key length is shorter
			than 8 octets, the agent will left adjust and zero fill
			to 8 octets.

			When read, snOspfIfStatusAuthKey always returns an Octet String
			of length zero."
		 REFERENCE
			"OSPF Version 2, Section 9 The Interface Data
			Structure"
		 DEFVAL   { '0000000000000000'h }    -- 0.0.0.0.0.0.0.0
		 ::= { snOspfIfStatusEntry 17 }


	 snOspfIfStatusMetricValue OBJECT-TYPE
		 SYNTAX   Metric
		 MAX-ACCESS   read-only
		 STATUS   current 
		 DESCRIPTION
			"The metric of using this type  of  service  on
			 this interface.  The default value of the TOS 0
			 Metric is 10^8 / ifSpeed."
		 ::= { snOspfIfStatusEntry 18 }

	 snOspfIfStatusMd5AuthKeyId OBJECT-TYPE
		 SYNTAX   INTEGER (0..255)
		 MAX-ACCESS   read-only
		 STATUS   current
		 DESCRIPTION
			"The md5 authentication key ID.  If the snOspfVirtIfAuthType
			is set to md5, the value of snOspfIfMd5AuthKeyId must be
			(1 to 255). This field identifies the algorithm and secret 
			key used to create the message digest appended to the OSPF 
			packet.  Key Identifiers are unique per-interface 
			(or equivalently, per-subnet)."
		 ::= { snOspfIfStatusEntry 19 }


	 snOspfIfStatusMd5AuthKey OBJECT-TYPE
		 SYNTAX   OCTET STRING (SIZE (0..16))
		 MAX-ACCESS   read-only
		 STATUS   current
		 DESCRIPTION
			"The MD5 Authentication Key.  If the Area's Authorization
			Type is md5, and the key length is shorter than 16 octets, 
			the agent will left adjust and zero fill to 16 octets.
			When read, snOspfIfMd5AuthKey always returns an Octet String
			of length zero."
		 ::= { snOspfIfStatusEntry 20 }


	 snOspfIfStatusMd5ActivationWaitTime OBJECT-TYPE
		 SYNTAX   INTEGER (0..14400)
		 MAX-ACCESS   read-only
		 STATUS   current 
		 DESCRIPTION
			"The md5 authentication key activation wait time is specified in second
			and the maximum wait time is 14400 seconds (4 hours)."
		 ::= { snOspfIfStatusEntry 21 }

	 snOspfIfStatusAreaIdFormat OBJECT-TYPE
		 SYNTAX   INTEGER {
					integer(0),
					ipAddress(1)
				  }
		 MAX-ACCESS   read-only
		 STATUS   current
		 DESCRIPTION
			"This object is used to specify whether
			 AreaId is represented as IP Address or 
			 an Integer. The values
			 that can be written are:
			 integer(0).....as an integer.
			 ipAddress(1)...as IP Address."
		 ::= { snOspfIfStatusEntry 22 }


--  Section 13:		OSPF Virtual Interface Status Table

--      The Virtual Interface Status Table describes the virtual
--      links status data. 



	 snOspfVirtIfStatusTable OBJECT-TYPE
		 SYNTAX   SEQUENCE OF SnOspfVirtIfStatusEntry
		 MAX-ACCESS   not-accessible
		 STATUS   current
		 DESCRIPTION
			"Information about this router's virtual interfaces."
		 REFERENCE
			"OSPF Version 2, Appendix C.4  Virtual link parameters"
		 ::= { snOspfVirtIfStatus 1 }

	 snOspfVirtIfStatusEntry OBJECT-TYPE
		 SYNTAX   SnOspfVirtIfStatusEntry
		 MAX-ACCESS   not-accessible
		 STATUS   current
		 DESCRIPTION
			"Information about a single Virtual Interface."
		 INDEX { snOspfVirtIfStatusEntryIndex }
		 ::= { snOspfVirtIfStatusTable 1 }

	 SnOspfVirtIfStatusEntry ::=
		 SEQUENCE {
			 snOspfVirtIfStatusEntryIndex 
				 Integer32,
			 snOspfVirtIfStatusAreaID
				 AreaID,
			 snOspfVirtIfStatusNeighbor
				 RouterID,
			 snOspfVirtIfStatusTransitDelay
				 UpToMaxAge,
			 snOspfVirtIfStatusRetransInterval
				 UpToMaxAge,
			 snOspfVirtIfStatusHelloInterval
				 HelloRange,
			 snOspfVirtIfStatusRtrDeadInterval
				 PositiveInteger,
			 snOspfVirtIfStatusState
				 INTEGER,
			 snOspfVirtIfStatusEvents
				 Counter32,
			 snOspfVirtIfStatusAuthType
				 Integer32,
			 snOspfVirtIfStatusAuthKey
				 OCTET STRING,
			 snOspfVirtIfStatusMd5AuthKeyId
				 INTEGER,
			 snOspfVirtIfStatusMd5AuthKey
				 OCTET STRING,
			 snOspfVirtIfStatusMd5ActivationWaitTime
				 INTEGER,
			 snOspfVirtIfStatusAreaIdFormat 
				 INTEGER
		 }

	 snOspfVirtIfStatusEntryIndex  OBJECT-TYPE
		 SYNTAX   Integer32
		 MAX-ACCESS   read-only
		 STATUS   current
		 DESCRIPTION
			"The table entry index of this Area."
		 ::= { snOspfVirtIfStatusEntry 1 }


	 snOspfVirtIfStatusAreaID 	OBJECT-TYPE
		 SYNTAX   AreaID
		 MAX-ACCESS   read-only
		 STATUS   current
		 DESCRIPTION
			"The Transit Area that the Virtual Link traverses.  By
			definition, this is not 0.0.0.0 "
		 ::= { snOspfVirtIfStatusEntry 2 }

	 snOspfVirtIfStatusNeighbor OBJECT-TYPE
		 SYNTAX   RouterID
		 MAX-ACCESS   read-only
		 STATUS   current
		 DESCRIPTION
			"The Router ID of the Virtual Neighbor."
		 ::= { snOspfVirtIfStatusEntry 3 }

	 snOspfVirtIfStatusTransitDelay OBJECT-TYPE
		 SYNTAX   UpToMaxAge
		 MAX-ACCESS   read-only
		 STATUS   current
		 DESCRIPTION
			"The estimated number of seconds it takes to transmit a
			link- state update packet over this interface."
		 DEFVAL { 1 }
		 ::= { snOspfVirtIfStatusEntry 4 }

	 snOspfVirtIfStatusRetransInterval OBJECT-TYPE
		 SYNTAX   UpToMaxAge
		 MAX-ACCESS   read-only
		 STATUS   current
		 DESCRIPTION
			"The number of seconds between link-state advertisement
			retransmissions, for adjacencies belonging to this
			interface.  This value is also used when retransmitting
			database description and link-state request packets.
			This value should be well over the expected round-trip
			time."
		 DEFVAL { 5 }
		 ::= { snOspfVirtIfStatusEntry 5 }

	 snOspfVirtIfStatusHelloInterval OBJECT-TYPE
		 SYNTAX   HelloRange
		 MAX-ACCESS   read-only
		 STATUS   current
		 DESCRIPTION
			"The length of time, in seconds, between the Hello
			packets that the router sends on the interface.  This
			value must be the same for the virtual neighbor."
		 DEFVAL { 10 }
		 ::= { snOspfVirtIfStatusEntry 6 }

	 snOspfVirtIfStatusRtrDeadInterval OBJECT-TYPE
		 SYNTAX   PositiveInteger
		 MAX-ACCESS   read-only
		 STATUS   current
		 DESCRIPTION
			"The number of seconds that a router's Hello packets
			have not been seen before it's neighbors declare the
			router down.  This should be some multiple of the Hello
			interval.  This value must be the same for the virtual
			neighbor."
		 DEFVAL { 60 }
		 ::= { snOspfVirtIfStatusEntry 7 }


	 snOspfVirtIfStatusState OBJECT-TYPE
		 SYNTAX   INTEGER {
					 down (1),
					 pointToPoint (4)
				  }
		 MAX-ACCESS   read-only
		 STATUS   current
		 DESCRIPTION
			"The OSPF virtual interfaces states."
		 DEFVAL { down }
		 ::= { snOspfVirtIfStatusEntry 8 }


	 snOspfVirtIfStatusEvents OBJECT-TYPE
		 SYNTAX   Counter32
		 MAX-ACCESS   read-only
		 STATUS   current
		 DESCRIPTION
			"The number of state changes or error events on 
			this Virtual Link."
		 ::= { snOspfVirtIfStatusEntry 9 }


	 snOspfVirtIfStatusAuthType OBJECT-TYPE
		 SYNTAX   Integer32
					 -- none (0),
					 -- simplePassword (1)
					 -- reserved for specification by IANA (> 1)
		 MAX-ACCESS   read-only
		 STATUS   current
		 DESCRIPTION
			"The authentication type specified for an interface.
			Additional authentication types may be assigned locally
			on a per interface basis."
		 REFERENCE
			"OSPF Version 2, Appendix E Authentication"
		 DEFVAL { 0 }        -- no authentication, by default
		 ::= { snOspfVirtIfStatusEntry 10 }

	 snOspfVirtIfStatusAuthKey OBJECT-TYPE
		 SYNTAX   OCTET STRING (SIZE (0..8)) 
		 MAX-ACCESS   read-only
		 STATUS   current
		 DESCRIPTION
			"If Authentication Type is simplePassword, the device
			will left adjust and zero fill to 8 octets.

			When read, snOspfVifAuthKey always returns a string of
			length zero."
		 REFERENCE
			"OSPF Version 2, Section 9 The Interface Data
			Structure"
		 DEFVAL   { '0000000000000000'h }    -- 0.0.0.0.0.0.0.0
		 ::= { snOspfVirtIfStatusEntry 11 }

	 snOspfVirtIfStatusMd5AuthKeyId OBJECT-TYPE
		 SYNTAX   INTEGER (0..255)
		 MAX-ACCESS   read-only
		 STATUS   current
		 DESCRIPTION
			"The md5 authentication key ID.  If the snOspfVirtIfAuthType
			is set to md5, the value of snOspfVirtIfMd5AuthKeyId must be
			(1 to 255). This field identifies the algorithm and secret 
			key used to create the message digest appended to the OSPF 
			packet.  Key Identifiers are unique per-interface 
			(or equivalently, per-subnet)."
		 ::= { snOspfVirtIfStatusEntry 12 }


	 snOspfVirtIfStatusMd5AuthKey OBJECT-TYPE
		 SYNTAX   OCTET STRING (SIZE (0..16))
		 MAX-ACCESS   read-only
		 STATUS   current
		 DESCRIPTION
			"The MD5 Authentication Key.  If the Area's Authorization
			Type is md5, and the key length is shorter than 16 octets, 
			the agent will left adjust and zero fill to 16 octets.

			When read, snOspfIfMd5AuthKey always returns an Octet String
			of length zero."
		 REFERENCE
			"OSPF Version 2, Section 9 The Interface Data
			Structure"
		 DEFVAL   { '0000000000000000'h }    -- 0.0.0.0.0.0.0.0
		 ::= { snOspfVirtIfStatusEntry 13 }


	 snOspfVirtIfStatusMd5ActivationWaitTime OBJECT-TYPE
		 SYNTAX   INTEGER (0..14400)
		 MAX-ACCESS   read-only
		 STATUS   current 
		 DESCRIPTION
			"The md5 authentication key activation wait time is specified in second
			and the maximum wait time is 14400 seconds (4 hours)."
		 ::= { snOspfVirtIfStatusEntry 14 }


	 snOspfVirtIfStatusAreaIdFormat OBJECT-TYPE
		 SYNTAX   INTEGER {
					integer(0),
					ipAddress(1)
				  }
		 MAX-ACCESS   read-only
		 STATUS   current
		 DESCRIPTION
			"This object is used to specify whether
			 AreaId is represented as IP Address or 
			 an Integer. The values
			 that can be written are:
			 integer(0).....as an integer.
			 ipAddress(1)...as IP Address."
		 ::= { snOspfVirtIfStatusEntry 15 }


--  Section 14:		OSPF Routing Information Table

--      The OSPF Routing Information Table describes the OSPF ABR/ASBR
--      routing information. 



	 snOspfRoutingInfoTable OBJECT-TYPE
		 SYNTAX   SEQUENCE OF SnOspfRoutingInfoEntry
		 MAX-ACCESS   not-accessible
		 STATUS   current
		 DESCRIPTION
			"Information about this router's routing information."
		 ::= { snOspfRoutingInfo 1 }

	 snOspfRoutingInfoEntry OBJECT-TYPE
		 SYNTAX   SnOspfRoutingInfoEntry
		 MAX-ACCESS   not-accessible
		 STATUS   current
		 DESCRIPTION
			"Information about a single ABR/ASBR Routing entry."
		 INDEX { snOspfRoutingInfoIndex }
		 ::= { snOspfRoutingInfoTable 1 }

	 SnOspfRoutingInfoEntry ::=
		 SEQUENCE {
			 snOspfRoutingInfoIndex 
				 Integer32,
			 snOspfRoutingInfoRouterID
				 RouterID,
			 snOspfRoutingInfoRouterType
				 INTEGER,
			 snOspfRoutingInfoNextHopRouterID
				 RouterID,
			 snOspfRoutingInfoOutgoingInterface
				 Integer32
		 }

	 snOspfRoutingInfoIndex  OBJECT-TYPE
		 SYNTAX   Integer32
		 MAX-ACCESS   read-only
		 STATUS   current
		 DESCRIPTION
			"The table entry index of this Routing entry."
		 ::= { snOspfRoutingInfoEntry 1 }


	 snOspfRoutingInfoRouterID 	OBJECT-TYPE
		 SYNTAX   RouterID
		 MAX-ACCESS   read-only
		 STATUS   current
		 DESCRIPTION
			"The Router ID of the destination router." 
		 ::= { snOspfRoutingInfoEntry 2 }

	 snOspfRoutingInfoRouterType OBJECT-TYPE
		 SYNTAX   INTEGER {
					 abr  (1),
					 asbr (2),
					 abrANDasbr(3)
				  }
		 MAX-ACCESS   read-only
		 STATUS   current
		 DESCRIPTION
			"The Router type of the destination router as the following:
					 abr  (1) -- area border router.
					 asbr (2) -- autonomous sytem border router.
					 abrANDasbr(3) -- area border and autonomous system border router."
		 ::= { snOspfRoutingInfoEntry 3 }

	 snOspfRoutingInfoNextHopRouterID OBJECT-TYPE
		 SYNTAX   RouterID
		 MAX-ACCESS   read-only
		 STATUS   current
		 DESCRIPTION
			"The router ID of the next hop destination router."
		 ::= { snOspfRoutingInfoEntry 4 }

	 snOspfRoutingInfoOutgoingInterface OBJECT-TYPE
		 SYNTAX   Integer32
		 MAX-ACCESS   read-only
		 STATUS   current
		 DESCRIPTION
			"The outgoing interface of the destination router."
		 ::= { snOspfRoutingInfoEntry 5 }

--  Section 15:		Trap Support Objects

--         The following are support objects for the OSPF traps.


		snOspfSetTrap OBJECT-TYPE
			SYNTAX   OCTET STRING (SIZE(4))
			MAX-ACCESS   read-write
			STATUS   current
			DESCRIPTION
			   "A four-octet string serving as a bit  map  for
			   the trap events defined by the OSPF traps. This
			   object is used to enable and  disable  specific
			   OSPF   traps   where  a  1  in  the  bit  field
			   represents enabled.  The right-most bit  (least
			   significant) represents trap 0."
		   ::= { snOspfTrapControl 1 }


		snOspfConfigErrorType OBJECT-TYPE
			SYNTAX   INTEGER   {
						unUsed (0),
						badVersion (1),
						areaMismatch (2),
						unknownNbmaNbr (3), -- Router is Dr eligible
						unknownVirtualNbr (4),
						authTypeMismatch(5),
						authFailure (6),
						netMaskMismatch (7),
						helloIntervalMismatch (8),
						deadIntervalMismatch (9),
						optionMismatch (10) }
			MAX-ACCESS   read-only
			STATUS   current
			DESCRIPTION
			   "Potential types  of  configuration  conflicts.
			   Used  by the ospfConfigError and ospfConfigVir-
			   tError traps."
	   ::= { snOspfTrapControl 2 }


		snOspfPacketType OBJECT-TYPE
			SYNTAX   INTEGER   {
						unUsed (0),
						hello (1),
						dbDescript (2),
						lsReq (3),
						lsUpdate (4),
						lsAck (5) }
			MAX-ACCESS   read-only
			STATUS   current
			DESCRIPTION

			   "OSPF packet types."
	   ::= { snOspfTrapControl 3 }


		snOspfPacketSrc OBJECT-TYPE
			SYNTAX   IpAddress
			MAX-ACCESS   read-only
			STATUS   current
			DESCRIPTION
			   "The IP address of an inbound packet that  can-
			   not be identified by a neighbor instance."
		   ::= { snOspfTrapControl 4 }

		snOspfTrapsGenerationMode OBJECT-TYPE
			SYNTAX   RtrStatus
			MAX-ACCESS   read-write
			STATUS   current
			DESCRIPTION
			   "Indicates if the generation of any OSPF traps is permitted on the router. 
				The value 'enabled' denotes that the OSPF Traps can be generated by the 
				router; 'disabled' denotes that the OSPF Traps can not be generated by the
				router even when snOspfSetTrap indicates the generation of specific OSPF Traps.
				This object provides global control on the generation of ospf traps."
		   ::= { snOspfTrapControl 5 }


END
FOUNDRY-SN-IP-MIB DEFINITIONS ::= BEGIN

IMPORTS
	MODULE-IDENTITY, OBJECT-TYPE,IpAddress, Counter32, TimeTicks,Counter64,Integer32
		FROM SNMPv2-SMI
		
	TEXTUAL-CONVENTION
		FROM SNMPv2-TC

	router,snRip, snDvmrp, snFsrp,snGblRt, snPim, snLoopbackIf
		FROM FOUNDRY-SN-ROOT-MIB
		
	InterfaceIndex, ifIndex
		FROM IF-MIB

	InetAddressType
		FROM INET-ADDRESS-MIB
		
	DisplayString
		FROM FOUNDRY-SN-AGENT-MIB
		
	PortMask
		FROM FOUNDRY-SN-SWITCH-GROUP-MIB;

		
snIp MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"        	
	REVISION     "200909300000Z" -- September 30, 2009
	DESCRIPTION
			"convert from SMIv1 to SMIv2"
   ::= { router 2 }

	-- textual conventions

	RtrStatus ::= TEXTUAL-CONVENTION
		STATUS	  current
		DESCRIPTION
			"
			RtrStatus Values
			"
		SYNTAX	INTEGER { disabled(0), enabled (1) }
		


	ClearStatus ::= TEXTUAL-CONVENTION
		STATUS	  current
		DESCRIPTION
			"
			Clear Status Values
			"
		SYNTAX	INTEGER { normal(0), clear(1) }


	RowSts ::= TEXTUAL-CONVENTION
		STATUS	  current
		DESCRIPTION
			"
			Row Creation/Deletion Values
			"
		SYNTAX	INTEGER { other(1),
						valid(2),
						delete(3),
						create(4)
						}		

	PortIndex ::= TEXTUAL-CONVENTION
		STATUS	  current
		DESCRIPTION
			"
			The bits 0-7 = port number. 
			The bits 8-15 = slot number (slot for chassis only).
			ve port format         bits 16-24 = 0x01, bits 0-15 = ve number
			loopback port format bits 16-24 = 0x02, bits 0-15= lb number	
			"
		SYNTAX	Integer32


	Action ::= TEXTUAL-CONVENTION
		STATUS	  current
		DESCRIPTION
			"
			Represents a action value such as deny or permit.
			"
		SYNTAX	INTEGER { deny(0), permit(1) }


	Metric ::= TEXTUAL-CONVENTION
		STATUS	  current
		DESCRIPTION
			"
			The OSPF Metric is defined as an unsigned value in the range
			"
		SYNTAX	INTEGER (0..65535) 


-- SECTION 2: MIB 

-- Global Router MIB
-- This section contains global MIB object definitions applicable to the
-- switching router. These objects should be independent to any routing
-- protocol.

snGblRtGeneral              OBJECT IDENTIFIER ::= { snGblRt 1 }

snGblRtRouteOnly        OBJECT-TYPE
	SYNTAX  RtrStatus
	MAX-ACCESS  read-write
	STATUS  current
	DESCRIPTION
		"If this object is 'enabled', this switching router will only
		route packets. If this object is 'disabled', this switching
		router will first route packets. If route cannot perform,
		it will switch packets."
	::= { snGblRtGeneral 1 }

-- Router IP MIB
-- This section contains IP specific router MIB object definitions.

-- IP general group

snRtIpGeneral               OBJECT IDENTIFIER ::= { snIp 1 }
		
snRtClearArpCache       OBJECT-TYPE
	SYNTAX  ClearStatus
	MAX-ACCESS  read-write
	STATUS  current
	DESCRIPTION
		"clear(1) will clear arp cache table."
	::= { snRtIpGeneral 1 }

snRtClearIpCache                OBJECT-TYPE
	SYNTAX  ClearStatus
	MAX-ACCESS  read-write
	STATUS  current
	DESCRIPTION
		"clear(1) will clear ip route cache table."
	::= { snRtIpGeneral 2 }

snRtClearIpRoute                OBJECT-TYPE
	SYNTAX  ClearStatus
	MAX-ACCESS  read-write
	STATUS  current
	DESCRIPTION
		"clear(1) will clear ip route table."
	::= { snRtIpGeneral 3 }

snRtBootpServer                 OBJECT-TYPE
	SYNTAX  IpAddress
	MAX-ACCESS  read-write
	STATUS  deprecated
	DESCRIPTION
		"IP address of bootp server to
		which bootp packet need to be relayed."
	::= { snRtIpGeneral 4 }

snRtBootpRelayMax               OBJECT-TYPE
	SYNTAX  INTEGER (1..15)
	MAX-ACCESS  read-write
	STATUS  current
	DESCRIPTION
		"Maximum number of hop the bootp packet 
		should travel."
	::= { snRtIpGeneral 5 } 

snRtArpAge                      OBJECT-TYPE
	SYNTAX  INTEGER (0..240)
	MAX-ACCESS  read-write
	STATUS  current
	DESCRIPTION
		"The time in minutes an ARP entry can
		be valid without relearning. 
		0 - Don't not age."
	::= { snRtIpGeneral 6 }

snRtIpIrdpEnable                OBJECT-TYPE
	SYNTAX  RtrStatus
	MAX-ACCESS  read-write
	STATUS  current
	DESCRIPTION
		"Perform router advertisement on this box."
	::= { snRtIpGeneral 7 }

snRtIpLoadShare         OBJECT-TYPE
	SYNTAX  RtrStatus
	MAX-ACCESS  read-write
	STATUS  current
	DESCRIPTION
		"If more than one route available,
		use them to share load."
	::= { snRtIpGeneral 8 }

snRtIpProxyArp          OBJECT-TYPE
	SYNTAX  RtrStatus
	MAX-ACCESS  read-write
	STATUS  current
	DESCRIPTION
		"Enable/disable proxy arp function 
		in the box."
	::= { snRtIpGeneral 9 }

snRtIpRarp                      OBJECT-TYPE
	SYNTAX  RtrStatus
	MAX-ACCESS  read-write
	STATUS  current
	DESCRIPTION
		"Enable/disable RARP server."
	::= { snRtIpGeneral 10 }

snRtIpTtl                       OBJECT-TYPE
	SYNTAX  INTEGER (1..255)
	MAX-ACCESS  read-write
	STATUS  current
	DESCRIPTION
		"The time to live value to be used
		in IP header of IP packet generated
		by the box."
	::= { snRtIpGeneral 11 }

snRtIpSetAllPortConfig          OBJECT-TYPE
	SYNTAX Integer32
	MAX-ACCESS  read-write
	STATUS  current
	DESCRIPTION
		"The value of this object is an index number of a
		snRtIpPortConfigTable row (i.e. snRtIpPortConfigPortIndex),
		which is the selected row to copy all of its read-writable
		data (i.e. snRtIpPortMtu and snRtIpPortEncap) to the rest
		of the rows in snRtIpPortConfigTable.
		Note: prior setting this object, all the intended data of
		the given row of the table must be set. Otherwise, the
		current data of the row will be used to set the entire ip
		interface configuration table. The previous setting will
		be overwritten by the new one."
	::= { snRtIpGeneral 12 }

snRtIpFwdCacheMaxEntries        OBJECT-TYPE
	SYNTAX Integer32
	MAX-ACCESS  read-only
	STATUS  current
	DESCRIPTION
		"The maximum number of ip forwarding table entries."
	::= { snRtIpGeneral 13 }

snRtIpFwdCacheCurEntries        OBJECT-TYPE
	SYNTAX Integer32
	MAX-ACCESS  read-only
	STATUS  current
	DESCRIPTION
		"The current number of ip forwarding table entries."
	::= { snRtIpGeneral 14 }

snRtIpMaxStaticRouteEntries     OBJECT-TYPE
	SYNTAX Integer32
	MAX-ACCESS  read-only
	STATUS  current
	DESCRIPTION
		"The maximum number of static route entries in the static route table."
	::= { snRtIpGeneral 15 }

snRtIpDirBcastFwd               OBJECT-TYPE
	SYNTAX  RtrStatus
	MAX-ACCESS  read-write
	STATUS  current
	DESCRIPTION
		"Enable/Disable directed broadcast forwarding."
	DEFVAL  { enabled }
	::= { snRtIpGeneral 16 }

snRtIpLoadShareNumOfPaths	OBJECT-TYPE
	SYNTAX Integer32
	MAX-ACCESS  read-write
	STATUS  current
	DESCRIPTION
		"Number of routes are used to share load."
	::= { snRtIpGeneral 17 }

snRtIpLoadShareMaxPaths	OBJECT-TYPE
	SYNTAX Integer32
	MAX-ACCESS  read-only
	STATUS  current
	DESCRIPTION
		"Maximum number of routes can be configured to share load."
	::= { snRtIpGeneral 18 }

snRtIpLoadShareMinPaths	OBJECT-TYPE
	SYNTAX Integer32
	MAX-ACCESS  read-only
	STATUS  current
	DESCRIPTION
		"Minimum number of routes can be configured to share load."
	::= { snRtIpGeneral 19 }

snRtIpProtocolRouterId OBJECT-TYPE
	SYNTAX   IpAddress
	MAX-ACCESS   read-write
	STATUS   current
	DESCRIPTION
		"Router Id for all IP Protocols."
	::= { snRtIpGeneral 20 }

snRtIpSourceRoute OBJECT-TYPE
	SYNTAX   RtrStatus
	MAX-ACCESS   read-write
	STATUS   current
	DESCRIPTION
		"Enable/Disable source routing support, ability to drop the
		source routing packets."
	DEFVAL { enabled }
	::= { snRtIpGeneral 21 }


-- IP static route table

snRtIpStaticRouteTable  OBJECT-TYPE
	SYNTAX  SEQUENCE OF SnRtIpStaticRouteEntry
	MAX-ACCESS  not-accessible
	STATUS  current
	DESCRIPTION
		"IP static/default route table."
	::= { snIp 2 }

snRtIpStaticRouteEntry  OBJECT-TYPE
	SYNTAX  SnRtIpStaticRouteEntry
	MAX-ACCESS  not-accessible
	STATUS  current
	DESCRIPTION
		"An entry in the IP static route table."
	INDEX   { snRtIpStaticRouteIndex }
	::= { snRtIpStaticRouteTable 1 }

SnRtIpStaticRouteEntry ::= SEQUENCE {
	snRtIpStaticRouteIndex
		Integer32,
	snRtIpStaticRouteDest
		IpAddress,
	snRtIpStaticRouteMask
		IpAddress,
	snRtIpStaticRouteNextHop
		IpAddress,
	snRtIpStaticRouteMetric
		Integer32,
	snRtIpStaticRouteRowStatus
		RowSts,
	snRtIpStaticRouteDistance
		INTEGER
	}

snRtIpStaticRouteIndex  OBJECT-TYPE
	SYNTAX  Integer32
	MAX-ACCESS  read-only
	STATUS  current
	DESCRIPTION
		"The table index for a static route entry."
	::= { snRtIpStaticRouteEntry 1 }

snRtIpStaticRouteDest           OBJECT-TYPE
	SYNTAX  IpAddress
	MAX-ACCESS  read-write
	STATUS  current
	DESCRIPTION
		"Destination IP address.
		0.0.0.0 for default route."
	::= { snRtIpStaticRouteEntry 2 }

snRtIpStaticRouteMask           OBJECT-TYPE
	SYNTAX  IpAddress
	MAX-ACCESS  read-write
	STATUS  current
	DESCRIPTION
		"Subnet mask associated with 
		the destination IP address.
		0.0.0.0 for default route mask."
	::= { snRtIpStaticRouteEntry 3 }

snRtIpStaticRouteNextHop        OBJECT-TYPE
	SYNTAX  IpAddress
	MAX-ACCESS  read-write
	STATUS  current
	DESCRIPTION
		"IP address of next hop router that
		is located on one of the directly
		attached IP subnet."
	::= { snRtIpStaticRouteEntry 4 }

snRtIpStaticRouteMetric         OBJECT-TYPE
	SYNTAX Integer32
	MAX-ACCESS  read-write
	STATUS  current
	DESCRIPTION
		"The metrics to next hop router."
	::= { snRtIpStaticRouteEntry 5 }

snRtIpStaticRouteRowStatus      OBJECT-TYPE
	SYNTAX  RowSts
	MAX-ACCESS  read-write
	STATUS  current
	DESCRIPTION
		"To create or delete a static route
		entry."
	::= { snRtIpStaticRouteEntry 6 }

snRtIpStaticRouteDistance		OBJECT-TYPE
	SYNTAX  INTEGER (1..255)
	MAX-ACCESS  read-write
	STATUS  current
	DESCRIPTION
		"Administration distance."
	::= { snRtIpStaticRouteEntry 7 }

-- ip filter table

snRtIpFilterTable       OBJECT-TYPE
	SYNTAX  SEQUENCE OF SnRtIpFilterEntry
	MAX-ACCESS  not-accessible
	STATUS  current
	DESCRIPTION
		"IP filter table."
	::= { snIp 3 }

snRtIpFilterEntry       OBJECT-TYPE
	SYNTAX  SnRtIpFilterEntry
	MAX-ACCESS  not-accessible
	STATUS  current
	DESCRIPTION
		"An entry in the IP filter table."
	INDEX   { snRtIpFilterIndex }
	::= { snRtIpFilterTable 1 }

SnRtIpFilterEntry ::= SEQUENCE {
	snRtIpFilterIndex
		Integer32,
	snRtIpFilterAction              
		INTEGER,
	snRtIpFilterProtocol            
		INTEGER,
	snRtIpFilterSourceIp
		IpAddress,
	snRtIpFilterSourceMask
		IpAddress,
	snRtIpFilterDestIp
		IpAddress,
	snRtIpFilterDestMask
		IpAddress,
	snRtIpFilterOperator
		INTEGER,
	snRtIpFilterOperand
		INTEGER,
	snRtIpFilterRowStatus
		RowSts,
	snRtIpFilterEstablished
		RtrStatus,
	snRtIpFilterQosPriority
		INTEGER
	}

snRtIpFilterIndex       OBJECT-TYPE
	SYNTAX  Integer32
	MAX-ACCESS  read-only
	STATUS  current
	DESCRIPTION
		"The table index for a filter entry."
	::= { snRtIpFilterEntry 1 }

snRtIpFilterAction      OBJECT-TYPE
	SYNTAX  INTEGER { deny(0), permit(1), qosEnabled(2) } 
	MAX-ACCESS  read-write
	STATUS  current
	DESCRIPTION
		"Action to take if the ip packet match
		with this filter."
	::= { snRtIpFilterEntry 2 }

snRtIpFilterProtocol    OBJECT-TYPE
	SYNTAX  INTEGER (0..255)
	MAX-ACCESS  read-write
	STATUS  current
	DESCRIPTION
		"Transport protocol. 0 means don't care"
	::= { snRtIpFilterEntry 3 }

snRtIpFilterSourceIp    OBJECT-TYPE
	SYNTAX  IpAddress
	MAX-ACCESS  read-write
	STATUS  current
	DESCRIPTION
		"Source IP address."
	::= { snRtIpFilterEntry 4 }

snRtIpFilterSourceMask  OBJECT-TYPE
	SYNTAX  IpAddress
	MAX-ACCESS  read-write
	STATUS  current
	DESCRIPTION
		"Source IP subnet mask."
	::= { snRtIpFilterEntry 5 }

snRtIpFilterDestIp      OBJECT-TYPE
	SYNTAX  IpAddress
	MAX-ACCESS  read-write
	STATUS  current
	DESCRIPTION
		"Destination IP address."
	::= { snRtIpFilterEntry 6 }

snRtIpFilterDestMask    OBJECT-TYPE
	SYNTAX  IpAddress
	MAX-ACCESS  read-write
	STATUS  current
	DESCRIPTION
		"Destination IP subnet mask."
	::= { snRtIpFilterEntry 7 }

snRtIpFilterOperator    OBJECT-TYPE
	SYNTAX  INTEGER { greater(1), equal(2), less(3), notEqual(4) }
	MAX-ACCESS  read-write
	STATUS  current
	DESCRIPTION
		"Type of comparison to perform.
		for now, this only applys to tcp or udp
		to compare the port number"
	::= { snRtIpFilterEntry 8 }

snRtIpFilterOperand     OBJECT-TYPE
	SYNTAX  INTEGER(0..65535)
	MAX-ACCESS  read-write
	STATUS  current
	DESCRIPTION
		"For now this only refers to transport 
		protocol port number. 0 means NA"
	::= { snRtIpFilterEntry 9 }

snRtIpFilterRowStatus   OBJECT-TYPE
	SYNTAX  RowSts
	MAX-ACCESS  read-write
	STATUS  current
	DESCRIPTION
		"To create or delete a filter
		entry."
	::= { snRtIpFilterEntry 10 }

snRtIpFilterEstablished OBJECT-TYPE
	SYNTAX  RtrStatus
	MAX-ACCESS  read-write
	STATUS  current
	DESCRIPTION
		"Enable/Disable the filtering of established TCP
		packets of which the ACK or RESET flag is on. This
		additional filter only applies to TCP transport
		protocol."
	::= { snRtIpFilterEntry 11 }

snRtIpFilterQosPriority OBJECT-TYPE
	SYNTAX  INTEGER {
		level0(0),
		level1(1),
		level2(2),
		level3(3),
		level4(4),
		level5(5),
		level6(6),
		level7(7)
		}
	MAX-ACCESS  read-write
	STATUS  current
	DESCRIPTION
		"The router L4 Qos Priority values are:
		 low(0)   -- low prority
		 high(1) -- high prority.
		 The Priority values are:
		level0(0), level1(1), level2(2), level3(3),
		level4(4), level5(5), level6(6), level7(7) "
	::= { snRtIpFilterEntry 12 }

-- RARP table

snRtIpRarpTable         OBJECT-TYPE
	SYNTAX  SEQUENCE OF SnRtIpRarpEntry
	MAX-ACCESS  not-accessible
	STATUS  current
	DESCRIPTION
		"IP RARP table."
	::= { snIp 4 }

snRtIpRarpEntry         OBJECT-TYPE
	SYNTAX  SnRtIpRarpEntry
	MAX-ACCESS  not-accessible
	STATUS  current
	DESCRIPTION
		"An entry in the IP Rarp table."
	INDEX   { snRtIpRarpIndex }
	::= { snRtIpRarpTable 1 }

SnRtIpRarpEntry ::= SEQUENCE {
	snRtIpRarpIndex
		INTEGER,
	snRtIpRarpMac
		OCTET STRING,
	snRtIpRarpIp
		IpAddress,
	snRtIpRarpRowStatus
		RowSts
	}

snRtIpRarpIndex                 OBJECT-TYPE
	SYNTAX  INTEGER (1..16)
	MAX-ACCESS  read-only
	STATUS  current
	DESCRIPTION
		"The table index for a Rarp entry."
	::= { snRtIpRarpEntry 1 }

snRtIpRarpMac           OBJECT-TYPE
	SYNTAX  OCTET STRING (SIZE (6))
	MAX-ACCESS  read-write
	STATUS  current
	DESCRIPTION
		"The Mac address for a Rarp entry."
	::= { snRtIpRarpEntry 2 }

snRtIpRarpIp            OBJECT-TYPE
	SYNTAX  IpAddress
	MAX-ACCESS  read-write
	STATUS  current
	DESCRIPTION
		"The IP address for a Rarp entry."
	::= { snRtIpRarpEntry 3 }

snRtIpRarpRowStatus     OBJECT-TYPE
	SYNTAX  RowSts
	MAX-ACCESS  read-write
	STATUS  current
	DESCRIPTION
		"To create or delete a Rarp
		entry."
	::= { snRtIpRarpEntry 4 }

-- Static ARP table

snRtStaticArpTable              OBJECT-TYPE
	SYNTAX  SEQUENCE OF SnRtStaticArpEntry
	MAX-ACCESS  not-accessible
	STATUS  current
	DESCRIPTION
		"IP static arp table."
	::= { snIp 5 }

snRtStaticArpEntry              OBJECT-TYPE
	SYNTAX  SnRtStaticArpEntry
	MAX-ACCESS  not-accessible
	STATUS  current
	DESCRIPTION
		"An entry in the IP static arp table."
	INDEX   { snRtStaticArpIndex }
	::= { snRtStaticArpTable 1 }

SnRtStaticArpEntry ::= SEQUENCE {
	snRtStaticArpIndex
		INTEGER,
	snRtStaticArpIp
		IpAddress,
	snRtStaticArpMac
		OCTET STRING,
	snRtStaticArpPort
		PortIndex,
	snRtStaticArpRowStatus
		RowSts
	}

snRtStaticArpIndex              OBJECT-TYPE
	SYNTAX  INTEGER (1..16)
	MAX-ACCESS  read-only
	STATUS  current
	DESCRIPTION
		"The table index for a static arp entry."
	::= { snRtStaticArpEntry 1 }

snRtStaticArpIp                 OBJECT-TYPE
	SYNTAX  IpAddress
	MAX-ACCESS  read-write
	STATUS  current
	DESCRIPTION
		"The IP address for a static arp entry."
	::= { snRtStaticArpEntry 2 }

snRtStaticArpMac                OBJECT-TYPE
	SYNTAX  OCTET STRING (SIZE (6))
	MAX-ACCESS  read-write
	STATUS  current
	DESCRIPTION
		"The Mac address for a static arp entry."
	::= { snRtStaticArpEntry 3 }

snRtStaticArpPort               OBJECT-TYPE
	SYNTAX  PortIndex
	MAX-ACCESS  read-write
	STATUS  current
	DESCRIPTION
		"The port index for a static arp entry."
	::= { snRtStaticArpEntry 4 }

snRtStaticArpRowStatus  OBJECT-TYPE
	SYNTAX  RowSts
	MAX-ACCESS  read-write
	STATUS  current
	DESCRIPTION
		"To create or delete a Static Arp
		entry."
	::= { snRtStaticArpEntry 5 }

-- ip interface address table
-- this table was replaced by the snRtIpPortIfAddrTable,
-- of which the index was changed to ifIndex, not another
-- indexing method used by this table

snRtIpPortAddrTable             OBJECT-TYPE
	SYNTAX  SEQUENCE OF SnRtIpPortAddrEntry
	MAX-ACCESS  not-accessible
	STATUS  deprecated
	DESCRIPTION
		"IP port address table."
	::= { snIp 6 }

snRtIpPortAddrEntry             OBJECT-TYPE
	SYNTAX  SnRtIpPortAddrEntry
	MAX-ACCESS  not-accessible
	STATUS  deprecated
	DESCRIPTION
		"An entry in the IP Port Address table."
	INDEX   { snRtIpPortAddrPortIndex, snRtIpPortAddress }
	::= { snRtIpPortAddrTable 1 }

SnRtIpPortAddrEntry ::= SEQUENCE {
	snRtIpPortAddrPortIndex
		PortIndex,
	snRtIpPortAddress
		IpAddress,
	snRtIpPortSubnetMask
		IpAddress,
	snRtIpPortAddrType
		INTEGER,
	snRtIpPortRowStatus
		RowSts
	}


snRtIpPortAddrPortIndex                 OBJECT-TYPE
	SYNTAX  PortIndex
	MAX-ACCESS  read-only
	STATUS  deprecated
	DESCRIPTION
		"The port index for port address entry."
	::= { snRtIpPortAddrEntry 1 }

snRtIpPortAddress               OBJECT-TYPE
	SYNTAX  IpAddress
	MAX-ACCESS  read-only
	STATUS  deprecated
	DESCRIPTION
		"The port IP address."
	::= { snRtIpPortAddrEntry 2 }

snRtIpPortSubnetMask            OBJECT-TYPE
	SYNTAX  IpAddress
	MAX-ACCESS  read-write
	STATUS  deprecated
	DESCRIPTION
		"The port IP address subnet mask."
	::= { snRtIpPortAddrEntry 3 }

snRtIpPortAddrType              OBJECT-TYPE
	SYNTAX  INTEGER { primary(1), secondary(2) }
	MAX-ACCESS  read-write
	STATUS  deprecated
	DESCRIPTION
		"The port IP address type."
	DEFVAL  { primary }
	::= { snRtIpPortAddrEntry 4 }

snRtIpPortRowStatus     OBJECT-TYPE
	SYNTAX  RowSts
	MAX-ACCESS  read-write
	STATUS  deprecated
	DESCRIPTION
		"To create or delete a port address
		entry."
	::= { snRtIpPortAddrEntry 5 }

-- ip interface access table
-- this table was replaced by the snRtIpPortIfAccessTable,
-- of which the index was changed to ifIndex, not another
-- indexing method used by this table

snRtIpPortAccessTable           OBJECT-TYPE
	SYNTAX  SEQUENCE OF SnRtIpPortAccessEntry
	MAX-ACCESS  not-accessible
	STATUS  deprecated
	DESCRIPTION
		"IP port access table."
	::= { snIp 7 }

snRtIpPortAccessEntry           OBJECT-TYPE
	SYNTAX  SnRtIpPortAccessEntry
	MAX-ACCESS  not-accessible
	STATUS  deprecated
	DESCRIPTION
		"An entry in the IP Port access table."
	INDEX   { snRtIpPortAccessPortIndex, snRtIpPortAccessDirection }
	::= { snRtIpPortAccessTable 1 }

SnRtIpPortAccessEntry ::= SEQUENCE {
	snRtIpPortAccessPortIndex
		PortIndex,
	snRtIpPortAccessDirection
		INTEGER,
	snRtIpPortAccessFilters
		OCTET STRING,
	snRtIpPortAccessRowStatus
		RowSts
	}

snRtIpPortAccessPortIndex               OBJECT-TYPE
	SYNTAX  PortIndex
	MAX-ACCESS  read-only
	STATUS  deprecated
	DESCRIPTION
		"The port index for port access entry."
	::= { snRtIpPortAccessEntry 1 }

snRtIpPortAccessDirection               OBJECT-TYPE
	SYNTAX  INTEGER { in(1), out(2) }
	MAX-ACCESS  read-only
	STATUS  deprecated
	DESCRIPTION
		"The incoming or outgoing check
		for port access."
	::= { snRtIpPortAccessEntry 2 }

snRtIpPortAccessFilters                 OBJECT-TYPE
	SYNTAX  OCTET STRING
	MAX-ACCESS  read-write
	STATUS  deprecated
	DESCRIPTION
		"1st octet correspond to 1st  filter 
		number and so on."
	::= { snRtIpPortAccessEntry 3 }

snRtIpPortAccessRowStatus       OBJECT-TYPE
	SYNTAX  RowSts
	MAX-ACCESS  read-write
	STATUS  deprecated
	DESCRIPTION
		"To create or delete a port access
		entry."
	::= { snRtIpPortAccessEntry 4 }

-- ip interface configuration table
-- this table was replaced by the snRtIpPortIfConfigTable,
-- of which the index was changed to ifIndex, not another
-- indexing method used by this table

snRtIpPortConfigTable           OBJECT-TYPE
	SYNTAX  SEQUENCE OF SnRtIpPortConfigEntry
	MAX-ACCESS  not-accessible
	STATUS  deprecated
	DESCRIPTION
		"IP port Config table."
	::= { snIp 8 }

snRtIpPortConfigEntry           OBJECT-TYPE
	SYNTAX  SnRtIpPortConfigEntry
	MAX-ACCESS  not-accessible
	STATUS  deprecated
	DESCRIPTION
		"An entry in the IP Port Config table."
	INDEX   { snRtIpPortConfigPortIndex }
	::= { snRtIpPortConfigTable 1 }

SnRtIpPortConfigEntry ::= SEQUENCE {
	snRtIpPortConfigPortIndex
		PortIndex,
	snRtIpPortMtu
		INTEGER,
	snRtIpPortEncap
		INTEGER,
	snRtIpPortMetric
		INTEGER,
	snRtIpPortDirBcastFwd
		RtrStatus
	}

snRtIpPortConfigPortIndex       OBJECT-TYPE
	SYNTAX  PortIndex
	MAX-ACCESS  read-only
	STATUS  deprecated
	DESCRIPTION
		"The port index for port config entry."
	::= { snRtIpPortConfigEntry 1 }

snRtIpPortMtu                   OBJECT-TYPE
	SYNTAX  INTEGER (576..4470)
	MAX-ACCESS  read-write
	STATUS  deprecated
	DESCRIPTION
		"The maximun transfer unit."
	::= { snRtIpPortConfigEntry 2 }

snRtIpPortEncap                 OBJECT-TYPE
	SYNTAX  INTEGER { 
					 ethernet(1),
					 snap(2),
					 hdlc(3),
					 ppp(4)
					}
	MAX-ACCESS  read-write
	STATUS  deprecated
	DESCRIPTION
		"Data link encapsulation to be used
		on the IP frame transmitted on the
		port."
	::= { snRtIpPortConfigEntry 3 }

snRtIpPortMetric                OBJECT-TYPE
	SYNTAX  INTEGER (1..15)
	MAX-ACCESS  read-write
	STATUS  deprecated
	DESCRIPTION
		"The metric."
	DEFVAL  { 1 }
	::= { snRtIpPortConfigEntry 4 }

snRtIpPortDirBcastFwd           OBJECT-TYPE
	SYNTAX  RtrStatus
	MAX-ACCESS  read-write
	STATUS  deprecated
	DESCRIPTION
		"Enable/Disable directed broadcast forwarding on the port."
	DEFVAL  { enabled }
	::= { snRtIpPortConfigEntry 5 }

-- ip interface address table, PortIndex is changed to ifIndex

snRtIpPortIfAddrTable             OBJECT-TYPE
	SYNTAX  SEQUENCE OF SnRtIpPortIfAddrEntry
	MAX-ACCESS  not-accessible
	STATUS  current
	DESCRIPTION
		"IP port If address table."
	::= { snIp 18 }

snRtIpPortIfAddrEntry             OBJECT-TYPE
	SYNTAX  SnRtIpPortIfAddrEntry
	MAX-ACCESS  not-accessible
	STATUS  current
	DESCRIPTION
		"An entry in the IP Port Address table."
	INDEX   { snRtIpPortIfAddrInterfaceIndex, snRtIpPortIfAddress }
	::= { snRtIpPortIfAddrTable 1 }

SnRtIpPortIfAddrEntry ::= SEQUENCE {
	snRtIpPortIfAddrInterfaceIndex
		InterfaceIndex,
	snRtIpPortIfAddress
		IpAddress,
	snRtIpPortIfSubnetMask
		IpAddress,
	snRtIpPortIfAddrType
		INTEGER,
	snRtIpPortIfRowStatus
		RowSts
	}


snRtIpPortIfAddrInterfaceIndex                 OBJECT-TYPE
	SYNTAX  InterfaceIndex
	MAX-ACCESS  read-only
	STATUS  current
	DESCRIPTION
		"The InterfaceIndex for port address entry."
	::= { snRtIpPortIfAddrEntry 1 }

snRtIpPortIfAddress               OBJECT-TYPE
	SYNTAX  IpAddress
	MAX-ACCESS  read-only
	STATUS  current
	DESCRIPTION
		"The port IP address."
	::= { snRtIpPortIfAddrEntry 2 }

snRtIpPortIfSubnetMask            OBJECT-TYPE
	SYNTAX  IpAddress
	MAX-ACCESS  read-write
	STATUS  current
	DESCRIPTION
		"The port IP address subnet mask."
	::= { snRtIpPortIfAddrEntry 3 }

snRtIpPortIfAddrType              OBJECT-TYPE
	SYNTAX  INTEGER { primary(1), secondary(2) }
	MAX-ACCESS  read-write
	STATUS  current
	DESCRIPTION
		"The port IP address type."
	DEFVAL  { primary }
	::= { snRtIpPortIfAddrEntry 4 }

snRtIpPortIfRowStatus     OBJECT-TYPE
	SYNTAX  RowSts
	MAX-ACCESS  read-write
	STATUS  current
	DESCRIPTION
		"To create or delete a port address
		entry."
	::= { snRtIpPortIfAddrEntry 5 }

-- ip interface access table, PortIndex is changed to ifIndex

snRtIpPortIfAccessTable           OBJECT-TYPE
	SYNTAX  SEQUENCE OF SnRtIpPortIfAccessEntry
	MAX-ACCESS  not-accessible
	STATUS  current
	DESCRIPTION
		"IP port If access table."
	::= { snIp 19 }

snRtIpPortIfAccessEntry           OBJECT-TYPE
	SYNTAX  SnRtIpPortIfAccessEntry
	MAX-ACCESS  not-accessible
	STATUS  current
	DESCRIPTION
		"An entry in the IP Port access table."
	INDEX   { snRtIpPortIfAccessInterfaceIndex, snRtIpPortIfAccessDirection }
	::= { snRtIpPortIfAccessTable 1 }

SnRtIpPortIfAccessEntry ::= SEQUENCE {
	snRtIpPortIfAccessInterfaceIndex
		InterfaceIndex,
	snRtIpPortIfAccessDirection
		INTEGER,
	snRtIpPortIfAccessFilters
		OCTET STRING,
	snRtIpPortIfAccessRowStatus
		RowSts
	}

snRtIpPortIfAccessInterfaceIndex               OBJECT-TYPE
	SYNTAX  InterfaceIndex
	MAX-ACCESS  read-only
	STATUS  current
	DESCRIPTION
		"The InterfaceIndex for port access entry."
	::= { snRtIpPortIfAccessEntry 1 }

snRtIpPortIfAccessDirection               OBJECT-TYPE
	SYNTAX  INTEGER { in(1), out(2) }
	MAX-ACCESS  read-only
	STATUS  current
	DESCRIPTION
		"The incoming or outgoing check
		for port access."
	::= { snRtIpPortIfAccessEntry 2 }

snRtIpPortIfAccessFilters                 OBJECT-TYPE
	SYNTAX  OCTET STRING
	MAX-ACCESS  read-write
	STATUS  current
	DESCRIPTION
		"1st octet correspond to 1st  filter 
		number and so on."
	::= { snRtIpPortIfAccessEntry 3 }

snRtIpPortIfAccessRowStatus       OBJECT-TYPE
	SYNTAX  RowSts
	MAX-ACCESS  read-write
	STATUS  current
	DESCRIPTION
		"To create or delete a port access
		entry."
	::= { snRtIpPortIfAccessEntry 4 }

-- ip interface configuration table, PortIndex is changed to ifIndex

snRtIpPortIfConfigTable           OBJECT-TYPE
	SYNTAX  SEQUENCE OF SnRtIpPortIfConfigEntry
	MAX-ACCESS  not-accessible
	STATUS  current
	DESCRIPTION
		"IP port If Config table."
	::= { snIp 20 }

snRtIpPortIfConfigEntry           OBJECT-TYPE
	SYNTAX  SnRtIpPortIfConfigEntry
	MAX-ACCESS  not-accessible
	STATUS  current
	DESCRIPTION
		"An entry in the IP Port Config table."
	INDEX   { snRtIpPortIfConfigInterfaceIndex }
	::= { snRtIpPortIfConfigTable 1 }

SnRtIpPortIfConfigEntry ::= SEQUENCE {
	snRtIpPortIfConfigInterfaceIndex
		InterfaceIndex,
	snRtIpPortIfMtu
		Integer32,
	snRtIpPortIfEncap
		INTEGER,
	snRtIpPortIfMetric
		INTEGER,
	snRtIpPortIfDirBcastFwd
		RtrStatus
	}

snRtIpPortIfConfigInterfaceIndex      OBJECT-TYPE
	SYNTAX  InterfaceIndex
	MAX-ACCESS  read-only
	STATUS  current
	DESCRIPTION
		"The If index for port config entry."
	::= { snRtIpPortIfConfigEntry 1 }

snRtIpPortIfMtu                   OBJECT-TYPE
	SYNTAX Integer32
	MAX-ACCESS  read-write
	STATUS  current
	DESCRIPTION
		"The maximun transfer unit.
		Ethernet MTU Range: 46 to 1500
		POS       MTU Range: 60 to 4470
		ATM       MTU Range: 1500 to 9180
		ATM SubIf MTU Range: 1500 to 9180
		For jumbo support, MTU range could be higher."
	::= { snRtIpPortIfConfigEntry 2 }

snRtIpPortIfEncap                 OBJECT-TYPE
	SYNTAX  INTEGER { 
					 ethernet(1),
					 snap(2),
					 hdlc(3),
					 ppp(4),
					 other(5)
					}
	MAX-ACCESS  read-write
	STATUS  current
	DESCRIPTION
		"Data link encapsulation to be used
		on the IP frame transmitted on the
		port."
	::= { snRtIpPortIfConfigEntry 3 }

snRtIpPortIfMetric                OBJECT-TYPE
	SYNTAX  INTEGER (1..15)
	MAX-ACCESS  read-write
	STATUS  current
	DESCRIPTION
		"The metric."
	DEFVAL  { 1 }
	::= { snRtIpPortIfConfigEntry 4 }

snRtIpPortIfDirBcastFwd           OBJECT-TYPE
	SYNTAX  RtrStatus
	MAX-ACCESS  read-write
	STATUS  current
	DESCRIPTION
		"Enable/Disable directed broadcast forwarding on the port."
	DEFVAL  { enabled }
	::= { snRtIpPortIfConfigEntry 5 }

-- IP Interface Counter table

agIpPortCounterTable           OBJECT-TYPE
	SYNTAX		SEQUENCE OF AgIpPortCounterEntry
	MAX-ACCESS      not-accessible
	STATUS		current
	DESCRIPTION
		"IP port counter table to display IP traffic statistics.
		At present the system supports only IP statistics for Ethernet ports."
	::= { snIp 21 }

agIpPortCounterEntry           OBJECT-TYPE
	SYNTAX		AgIpPortCounterEntry
	MAX-ACCESS      not-accessible
	STATUS		current
	DESCRIPTION
		"An entry in the IP port counter table."
	INDEX   { ifIndex, agIpPortCounterIpVersion }
	::= { agIpPortCounterTable 1 }

AgIpPortCounterEntry ::= SEQUENCE {
	agIpPortCounterIpVersion
		InetAddressType,
	agIpPortCounterRxPacket
		Counter64,
	agIpPortCounterRxOctet
		Counter64,
	agIpPortCounterTxPacket
		Counter64,
	agIpPortCounterTxOctet
		Counter64
	}

agIpPortCounterIpVersion    OBJECT-TYPE
	SYNTAX		InetAddressType
	MAX-ACCESS	not-accessible
	STATUS		current
	DESCRIPTION
		"The version of IP protocol for which this counter entry is returned.
		This table supports ipv4(1) and ipv6(2) enumerations."
	::= { agIpPortCounterEntry 1 }

agIpPortCounterRxPacket    OBJECT-TYPE
	SYNTAX		Counter64
	MAX-ACCESS      read-only
	STATUS		current
	DESCRIPTION
		"Total IP packets received on a given interface."
	::= { agIpPortCounterEntry 2 }

agIpPortCounterRxOctet    OBJECT-TYPE
	SYNTAX		Counter64
	MAX-ACCESS      read-only
	STATUS		current
	DESCRIPTION
		"Total IP octets received on a given interface."
	::= { agIpPortCounterEntry 3 }

agIpPortCounterTxPacket    OBJECT-TYPE
	SYNTAX		Counter64
	MAX-ACCESS      read-only
	STATUS		current
	DESCRIPTION
		"Total IP packets transmitted out from a given interface."
	::= { agIpPortCounterEntry 4 }

agIpPortCounterTxOctet    OBJECT-TYPE
	SYNTAX		Counter64
	MAX-ACCESS      read-only
	STATUS		current
	DESCRIPTION
		"Total IP octets transmitted out from a given interface."
	::= { agIpPortCounterEntry 5 }


-- Broadcast forwarding group

snRtBcastFwd                OBJECT IDENTIFIER ::= { snIp 9 }
snRtBcastFwdGeneral         OBJECT IDENTIFIER ::= { snRtBcastFwd 1 }
snRtUdpBcastFwdPort         OBJECT IDENTIFIER ::= { snRtBcastFwd 2 }
snRtUdpHelper               OBJECT IDENTIFIER ::= { snRtBcastFwd 3 }

-- General UDP broadcast forwarding group

snRtUdpBcastFwdEnable         OBJECT-TYPE
	SYNTAX  RtrStatus
	MAX-ACCESS  read-write
	STATUS  current
	DESCRIPTION
		"Enable or disable UDP broadcast forwarding service.
		When UDP broadcast forwarding is enabled, default
		entries are added to the UDP broadcast forwarding
		port table. When it is disabled, UDP broadcast
		forwarding port table is flushed to empty."
	DEFVAL     { enabled }
	::= { snRtBcastFwdGeneral 1 }

-- UDP broadcast forwarding port table
-- snRtUdpBroadcastFwdPortTable replaces snRtUdpBcastFwdPortTable
-- Notice that index of these tables are different

snRtUdpBcastFwdPortTable  OBJECT-TYPE
	SYNTAX  SEQUENCE OF SnRtUdpBcastFwdPortEntry
	MAX-ACCESS  not-accessible
	STATUS  current
	DESCRIPTION
		"This table contains a list of UDP port numbers
		for which forwarding UDP broadcast is enabled."
	::= { snRtUdpBcastFwdPort 1 }

snRtUdpBcastFwdPortEntry  OBJECT-TYPE
	SYNTAX  SnRtUdpBcastFwdPortEntry
	MAX-ACCESS  not-accessible
	STATUS  current
	DESCRIPTION
		"An entry of the UDP broadcast forwarding
		port table."
	INDEX   { snRtUdpBcastFwdPortIndex }
	::= { snRtUdpBcastFwdPortTable 1 }

SnRtUdpBcastFwdPortEntry ::= SEQUENCE {
	snRtUdpBcastFwdPortIndex
		INTEGER,
	snRtUdpBcastFwdPortNumber
		INTEGER,
	snRtUdpBcastFwdPortRowStatus
		RowSts
	}

snRtUdpBcastFwdPortIndex      OBJECT-TYPE
	SYNTAX  INTEGER (1..20)
	MAX-ACCESS  read-only
	STATUS  current
	DESCRIPTION
		"The table index for a UDP broadcast forwarding
		port entry."
	::= { snRtUdpBcastFwdPortEntry 1 }

snRtUdpBcastFwdPortNumber     OBJECT-TYPE
	SYNTAX  INTEGER (1..65535)
	MAX-ACCESS  read-write
	STATUS  current
	DESCRIPTION
		"UDP port number for which UDP broadcast forwarding
		is enabled."
	::= { snRtUdpBcastFwdPortEntry 2 }

snRtUdpBcastFwdPortRowStatus  OBJECT-TYPE
	SYNTAX  RowSts
	MAX-ACCESS  read-write
	STATUS  current
	DESCRIPTION
		"To create or delete a UDP broadcast forwarding
		port entry."
	::= { snRtUdpBcastFwdPortEntry 3 }

-- UDP broadcast forwarding port table

snRtUdpBroadcastFwdPortTable  OBJECT-TYPE
	SYNTAX	SEQUENCE OF SnRtUdpBroadcastFwdPortEntry
	MAX-ACCESS  not-accessible
	STATUS  current
	DESCRIPTION
		"This table contains a list of UDP port numbers
		for which forwarding UDP broadcast is enabled."
	::= { snRtUdpBcastFwdPort 2 }

snRtUdpBroadcastFwdPortEntry  OBJECT-TYPE
	SYNTAX	SnRtUdpBroadcastFwdPortEntry
	MAX-ACCESS  not-accessible
	STATUS  current
	DESCRIPTION
		"An entry of the UDP broadcast forwarding
		port table."
	INDEX   { snRtUdpBroadcastFwdPortNumber }
	::= { snRtUdpBroadcastFwdPortTable 1 }

SnRtUdpBroadcastFwdPortEntry ::= SEQUENCE {
	snRtUdpBroadcastFwdPortNumber
		Integer32,
	snRtUdpBroadcastFwdPortRowStatus
		RowSts
	}

snRtUdpBroadcastFwdPortNumber     OBJECT-TYPE
	SYNTAX   Integer32
	MAX-ACCESS	not-accessible
	STATUS  current
	DESCRIPTION
		"UDP port number for which UDP broadcast forwarding
		is enabled."
	::= { snRtUdpBroadcastFwdPortEntry 1 }

snRtUdpBroadcastFwdPortRowStatus  OBJECT-TYPE
	SYNTAX	RowSts
	MAX-ACCESS  read-write
	STATUS  current
	DESCRIPTION
		"To create or delete a UDP broadcast forwarding
		port entry."
	::= { snRtUdpBroadcastFwdPortEntry 2 }

-- UDP helper table
-- snRtUdpIfHelperTable replaces snRtUdpHelperTable
-- Notice that index of these tables are different

snRtUdpHelperTable  OBJECT-TYPE
	SYNTAX  SEQUENCE OF SnRtUdpHelperEntry
	MAX-ACCESS  not-accessible
	STATUS  current
	DESCRIPTION
		"UDP helper table."
	::= { snRtUdpHelper 1 }

snRtUdpHelperEntry  OBJECT-TYPE
	SYNTAX  SnRtUdpHelperEntry
	MAX-ACCESS  not-accessible
	STATUS  current
	DESCRIPTION
		"An entry of the UDP helper table."
	INDEX   { snRtUdpHelperPortIndex, snRtUdpHelperIndex }
	::= { snRtUdpHelperTable 1 }

SnRtUdpHelperEntry ::= SEQUENCE {
	snRtUdpHelperPortIndex
		PortIndex,
	snRtUdpHelperIndex
		INTEGER,
	snRtUdpHelperAddr
		IpAddress,
	snRtUdpHelperRowStatus
		RowSts
	}

snRtUdpHelperPortIndex  OBJECT-TYPE
	SYNTAX  PortIndex
	MAX-ACCESS  read-only
	STATUS  current
	DESCRIPTION
		"The port index for a UDP helper entry."
	::= { snRtUdpHelperEntry 1 }

snRtUdpHelperIndex      OBJECT-TYPE
	SYNTAX  INTEGER (1..4)
	MAX-ACCESS  read-only
	STATUS  current
	DESCRIPTION
		"The table index for a UDP helper entry."
	::= { snRtUdpHelperEntry 2 }

snRtUdpHelperAddr       OBJECT-TYPE
	SYNTAX  IpAddress
	MAX-ACCESS  read-write
	STATUS  current
	DESCRIPTION
		"The UDP helper address. This is the address that
		UDP packets will be forwarded. It can be a helper
		address or a subnet broadcast address. But it
		cannot be 255.255.255.255 or 0.0.0.0."
	::= { snRtUdpHelperEntry 3 }

snRtUdpHelperRowStatus  OBJECT-TYPE
	SYNTAX  RowSts
	MAX-ACCESS  read-write
	STATUS  current
	DESCRIPTION
		"To create or delete a UDP helper entry."
	::= { snRtUdpHelperEntry 4 }

-- UDP helper table

snRtUdpIfHelperTable  OBJECT-TYPE
	SYNTAX	SEQUENCE OF SnRtUdpIfHelperEntry
	MAX-ACCESS  not-accessible
	STATUS  current
	DESCRIPTION
		"UDP helper table."
	::= { snRtUdpHelper 2 }

snRtUdpIfHelperEntry  OBJECT-TYPE
	SYNTAX	SnRtUdpIfHelperEntry
	MAX-ACCESS  not-accessible
	STATUS  current
	DESCRIPTION
		"An entry of the UDP helper table."
	INDEX   { snRtUdpIfHelperPortIndex, snRtUdpIfHelperAddr }
	::= { snRtUdpIfHelperTable 1 }
	
SnRtUdpIfHelperEntry ::= SEQUENCE {
	snRtUdpIfHelperPortIndex
		InterfaceIndex,
	snRtUdpIfHelperAddr
		IpAddress,
	snRtUdpIfHelperAddrType
		INTEGER,
	snRtUdpIfHelperRowStatus
		RowSts
	}

snRtUdpIfHelperPortIndex  OBJECT-TYPE
	SYNTAX	InterfaceIndex
	MAX-ACCESS	not-accessible
	STATUS  current
	DESCRIPTION
		"The port/interface index for a UDP helper entry."
	::= { snRtUdpIfHelperEntry 1 }

snRtUdpIfHelperAddr       OBJECT-TYPE
	SYNTAX	IpAddress
	MAX-ACCESS	not-accessible
	STATUS  current
	DESCRIPTION
		"The UDP helper address. This is the address that
		UDP packets will be forwarded. It can be a helper
		address or a subnet broadcast address. But it
		cannot be 255.255.255.255 or 0.0.0.0."
	::= { snRtUdpIfHelperEntry 2 }

snRtUdpIfHelperAddrType  OBJECT-TYPE
	SYNTAX	INTEGER {
					unicast(1),
					broabcast(2)
				}
	MAX-ACCESS  read-write
	STATUS  current
	DESCRIPTION
		"Type of the helper address. It can be unicast or subnet
		 brodcast address."
	::= { snRtUdpIfHelperEntry 3}

snRtUdpIfHelperRowStatus  OBJECT-TYPE
	SYNTAX	RowSts
	MAX-ACCESS  read-write
	STATUS  current
	DESCRIPTION
		"To create or delete a UDP helper entry."
	::= { snRtUdpIfHelperEntry 4 }

-- Trace route group
-- This group uses the following method to detect routes used to reach
-- a destination address. The originating router sends a probe packet
-- (a UDP packet) to the destination address with TTL of 1. The first
-- router that receives this packet decrements the TTL, then drops the
-- packet and returns a ICMP packet to the originator. The originating
-- router records the route in snRtIpTraceRouteResultTable. The ori-
-- ginating router sends a probe packet (a UDP packet) to the des-
-- tination address with TTL of 2. The second router that receives
-- this packet decrements the TTL, then drops the packet and returns
-- a ICMP packet to the originator. The originating router records the
-- route in snRtIpTraceRouteResultTable. This procedure is repeated
-- until the destination is reached, or the maximum TTL is reached.

snRtIpTraceRoute            OBJECT IDENTIFIER ::= { snIp 10 }
snRtIpTraceRouteGeneral     OBJECT IDENTIFIER ::= { snRtIpTraceRoute 1 }
snRtIpTraceRouteResult      OBJECT IDENTIFIER ::= { snRtIpTraceRoute 2 }

-- General trace route group

snRtIpTraceRouteTargetAddr  OBJECT-TYPE
	SYNTAX  IpAddress
	MAX-ACCESS  read-write
	STATUS  current
	DESCRIPTION
		"Target IP address of which trace route is performed."
	::= { snRtIpTraceRouteGeneral 1 }

snRtIpTraceRouteMinTtl      OBJECT-TYPE
	SYNTAX  INTEGER (0..255)
	MAX-ACCESS  read-write
	STATUS  current
	DESCRIPTION
		"Minimum TTL value carried in the first probe packet.
		Value 0 cannot be used for SET operations. This value
		is returned if traceroute is not running within the system."
	DEFVAL { 1 }
	::= { snRtIpTraceRouteGeneral 2 }

snRtIpTraceRouteMaxTtl      OBJECT-TYPE
	SYNTAX  INTEGER (0..255)
	MAX-ACCESS  read-write
	STATUS  current
	DESCRIPTION
		"Maximum TTL value carried in the last probe packet.
		Value 0 cannot be used for SET operations. This value
		is returned if traceroute is not running within the system."
	DEFVAL { 30 }
	::= { snRtIpTraceRouteGeneral 3 }

snRtIpTraceRouteTimeOut     OBJECT-TYPE
	SYNTAX  INTEGER (0..120)
	MAX-ACCESS  read-write
	STATUS  current
	DESCRIPTION
		"Time out period (in seconds) to wait for the response
		from the probe packet (i,e, the ICMP packet).
		Value 0 cannot be used for SET operations. This value
		is returned if traceroute is not running within the system."
	DEFVAL { 2 }
	::= { snRtIpTraceRouteGeneral 4 }

snRtIpTraceRouteControl     OBJECT-TYPE
	SYNTAX  INTEGER {
				start(1),
				abort(2),
				success(3),
				failure(4),
				inProgress(5)
			}
	MAX-ACCESS  read-write
	STATUS  current
	DESCRIPTION
		"Only 'start' and 'abort' are writable values; 'success',
		'failure' and 'inProgress' are readeable (or returned)
		values.
		
		Writing 'start' to this object to initiate the trace route
		operation. snRtIpTraceRouteDestAddr must have been init-
		ialized before 'start' is writen.

		This object will return 'inProgress' after trace route
		operation has started. During the 'inProgress' state,
		writing 'abort' to this object will stop the current
		trace route operation.

		If the destination address is reached, this object
		returned 'success'. snRtIpTraceRouteResultTable
		contains the routes (and the target address) to
		reach the destination address. If the destination
		address does not reach, timeout, or ending TTL
		reached, 'failure' is returned."
	::= { snRtIpTraceRouteGeneral 5 }

-- Trace route result table

snRtIpTraceRouteResultTable  OBJECT-TYPE
	SYNTAX  SEQUENCE OF SnRtIpTraceRouteResultEntry
	MAX-ACCESS  not-accessible
	STATUS  current
	DESCRIPTION
		"Trace route result table."
	::= { snRtIpTraceRouteResult 1 }

snRtIpTraceRouteResultEntry  OBJECT-TYPE
	SYNTAX  SnRtIpTraceRouteResultEntry
	MAX-ACCESS  not-accessible
	STATUS  current
	DESCRIPTION
		"An entry of the trace route result table."
	INDEX   { snRtIpTraceRouteResultIndex }
	::= { snRtIpTraceRouteResultTable 1 }

SnRtIpTraceRouteResultEntry ::= SEQUENCE {
	snRtIpTraceRouteResultIndex
		Integer32,
	snRtIpTraceRouteResultAddr
		IpAddress,
	snRtIpTraceRouteResultRoundTripTime1
		TimeTicks,
	snRtIpTraceRouteResultRoundTripTime2
		TimeTicks
	}

snRtIpTraceRouteResultIndex          OBJECT-TYPE
	SYNTAX  Integer32
	MAX-ACCESS  read-only
	STATUS  current
	DESCRIPTION
		"The table index for a trace route result entry."
	::= { snRtIpTraceRouteResultEntry 1 }

snRtIpTraceRouteResultAddr           OBJECT-TYPE
	SYNTAX  IpAddress
	MAX-ACCESS  read-only
	STATUS  current
	DESCRIPTION
		"The router or the target address of which forms
		part of the route to reach the destination address."
	::= { snRtIpTraceRouteResultEntry 2 }

snRtIpTraceRouteResultRoundTripTime1 OBJECT-TYPE
	SYNTAX  TimeTicks
	MAX-ACCESS  read-only
	STATUS  current
	DESCRIPTION
		"The round trip time between the first probe packet
		transmitted and the reponse ICMP packet received."
	::= { snRtIpTraceRouteResultEntry 3 }

snRtIpTraceRouteResultRoundTripTime2 OBJECT-TYPE
	SYNTAX  TimeTicks
	MAX-ACCESS  read-only
	STATUS  current
	DESCRIPTION
		"The round trip time between the second probe packet
		transmitted and the reponse ICMP packet received."
	::= { snRtIpTraceRouteResultEntry 4 }

-- IP forwarding cache table

snRtIpFwdCacheTable  OBJECT-TYPE
	SYNTAX  SEQUENCE OF SnRtIpFwdCacheEntry
	MAX-ACCESS  not-accessible
	STATUS  current
	DESCRIPTION
		"IP forwarding cache table."
	::= { snIp 11 }

snRtIpFwdCacheEntry  OBJECT-TYPE
	SYNTAX  SnRtIpFwdCacheEntry
	MAX-ACCESS  not-accessible
	STATUS  current
	DESCRIPTION
		"An entry in the IP forwarding cache table."
	INDEX   { snRtIpFwdCacheIndex }
	::= { snRtIpFwdCacheTable 1 }

SnRtIpFwdCacheEntry ::= SEQUENCE {
	snRtIpFwdCacheIndex
		Integer32,
	snRtIpFwdCacheIp
		IpAddress,
	snRtIpFwdCacheMac
		OCTET STRING,
	snRtIpFwdCacheNextHopIp
		IpAddress,
	snRtIpFwdCacheOutgoingPort
		INTEGER,
	snRtIpFwdCacheType
		INTEGER,
	snRtIpFwdCacheAction
		INTEGER,
	snRtIpFwdCacheFragCheck
		INTEGER,
	snRtIpFwdCacheSnapHdr
		INTEGER,
	snRtIpFwdCacheVLanId
		Integer32,
	snRtIpFwdCacheOutgoingIf
		Integer32
	}

snRtIpFwdCacheIndex         OBJECT-TYPE
	SYNTAX  Integer32
	MAX-ACCESS  read-only
	STATUS  current
	DESCRIPTION
		"The table index for a ip forwarding cache table entry."
	::= { snRtIpFwdCacheEntry 1 }

snRtIpFwdCacheIp            OBJECT-TYPE
	SYNTAX  IpAddress
	MAX-ACCESS  read-only
	STATUS  current
	DESCRIPTION
		"The IP address of a station."
	::= { snRtIpFwdCacheEntry 2 }

snRtIpFwdCacheMac           OBJECT-TYPE
	SYNTAX  OCTET STRING (SIZE (6))
	MAX-ACCESS  read-only
	STATUS  current
	DESCRIPTION
		"The Mac address of an IP station."
	::= { snRtIpFwdCacheEntry 3 }

snRtIpFwdCacheNextHopIp     OBJECT-TYPE
	SYNTAX  IpAddress
	MAX-ACCESS  read-only
	STATUS  current
	DESCRIPTION
		"The next hop router IP address."
	::= { snRtIpFwdCacheEntry 4 }

snRtIpFwdCacheOutgoingPort  OBJECT-TYPE
	SYNTAX  INTEGER (0..3900)
	MAX-ACCESS  read-only
	STATUS  current
	DESCRIPTION
		"The outgoing port of which packets will forward to.
		Return port value of zero to indicate no outgoing port
		associated to this entry. Non-zero value has the
		following meanings:
		The bit 0 to bit 7: port number.
		The bit 8 to bit 11: slot number.
		For virtual router interface, slot number is 15,
		port number is the virtual router port from 1 to 60."
	::= { snRtIpFwdCacheEntry 5 }

snRtIpFwdCacheType          OBJECT-TYPE
	SYNTAX  INTEGER { dynamic(1), permanent(2) }
	MAX-ACCESS  read-only
	STATUS  current
	DESCRIPTION
		"The 'dynamic' or 'permanent' type for a ip forwarding
		cache table entry."
	::= { snRtIpFwdCacheEntry 6 }

snRtIpFwdCacheAction        OBJECT-TYPE
	SYNTAX  INTEGER {
			other(1),
			forward(2),
			forUs(3),
			waitForArp(4),
			complexFilter(5),
			icmpDeny(6),
			dropPacket(7)
			}
	MAX-ACCESS  read-only
	STATUS  current
	DESCRIPTION
		"The action to take."
	::= { snRtIpFwdCacheEntry 7 }

snRtIpFwdCacheFragCheck     OBJECT-TYPE
	SYNTAX  INTEGER { disabled(0), enabled(1) }
	MAX-ACCESS  read-only
	STATUS  current
	DESCRIPTION
		"Check for fragmentation."
	::= { snRtIpFwdCacheEntry 8 }

snRtIpFwdCacheSnapHdr       OBJECT-TYPE
	SYNTAX  INTEGER { disabled(0), enabled(1) }
	MAX-ACCESS  read-only
	STATUS  current
	DESCRIPTION
		"Apply SNAP encapsulation."
	::= { snRtIpFwdCacheEntry 9 }

snRtIpFwdCacheVLanId        OBJECT-TYPE
	SYNTAX Integer32
	MAX-ACCESS  read-only
	STATUS  current
	DESCRIPTION
		"The VLAN ID for a ip forwarding cache table entry.
		Return VLAN ID value of zero to indicate no VLAN
		associated to this entry."
	::= { snRtIpFwdCacheEntry 10 }

snRtIpFwdCacheOutgoingIf  OBJECT-TYPE
	SYNTAX   Integer32
	MAX-ACCESS  read-only
	STATUS  current
	DESCRIPTION
		"The outgoing interface of which packets will forward to.
		Return port value of zero to indicate no outgoing port
		associated to this entry."
	::= { snRtIpFwdCacheEntry 11 }


-- Ip AS-Path Access List table

snIpAsPathAccessListTable       OBJECT-TYPE
	SYNTAX  SEQUENCE OF SnIpAsPathAccessListEntry
	MAX-ACCESS  not-accessible
	STATUS  current
	DESCRIPTION
		"Ip As-Path Access List table."
	::= { snIp 12 }

snIpAsPathAccessListEntry       OBJECT-TYPE
	SYNTAX  SnIpAsPathAccessListEntry
	MAX-ACCESS  not-accessible
	STATUS  current
	DESCRIPTION
		"An entry in the Ip As-Path Access List table."
	INDEX   { snIpAsPathAccessListIndex,  snIpAsPathAccessListSequence}
	::= { snIpAsPathAccessListTable 1 }

SnIpAsPathAccessListEntry ::= SEQUENCE {
	snIpAsPathAccessListIndex
		Integer32,
	snIpAsPathAccessListSequence
		Integer32,
	snIpAsPathAccessListAction              
		INTEGER,
	snIpAsPathAccessListRegExpression
		OCTET STRING,
	snIpAsPathAccessListRowStatus
		INTEGER
	}

snIpAsPathAccessListIndex       OBJECT-TYPE
	SYNTAX  Integer32
	MAX-ACCESS  read-only
	STATUS  current
	DESCRIPTION
		"The table index for a filter entry."
	::= { snIpAsPathAccessListEntry 1 }

snIpAsPathAccessListSequence       OBJECT-TYPE
	SYNTAX  Integer32
	MAX-ACCESS  read-only
	STATUS  current
	DESCRIPTION
		"The table sequence index for a filter entry."
	::= { snIpAsPathAccessListEntry 2 }

snIpAsPathAccessListAction      OBJECT-TYPE
	SYNTAX  INTEGER { deny(0), permit(1) } 
	MAX-ACCESS  read-write
	STATUS  current
	DESCRIPTION
		"Action to take if the bgp address match
		with this filter."
	::= { snIpAsPathAccessListEntry 3 }

snIpAsPathAccessListRegExpression    OBJECT-TYPE
	SYNTAX  OCTET STRING (SIZE(0..256))
	MAX-ACCESS  read-write
	STATUS  current
	DESCRIPTION
		"Autonomous system in the filter using a regular expression.
		Each character of the regular expression string is represented
		by one octet."
	::= { snIpAsPathAccessListEntry 4 }

snIpAsPathAccessListRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpAsPathAccessListEntry 5 }


-- Ip Community List table

snIpCommunityListTable       OBJECT-TYPE
	SYNTAX  SEQUENCE OF SnIpCommunityListEntry
	MAX-ACCESS  not-accessible
	STATUS  current
	DESCRIPTION
		"Ip Community List table."
	::= { snIp 13 }

snIpCommunityListEntry       OBJECT-TYPE
	SYNTAX  SnIpCommunityListEntry
	MAX-ACCESS  not-accessible
	STATUS  current
	DESCRIPTION
		"An entry in the Ip Community List table."
	INDEX   { snIpCommunityListIndex,  snIpCommunityListSequence}
	::= { snIpCommunityListTable 1 }

SnIpCommunityListEntry ::= SEQUENCE {
	snIpCommunityListIndex
		Integer32,
	snIpCommunityListSequence
		Integer32,
	snIpCommunityListAction              
		INTEGER,
	snIpCommunityListCommNum
		OCTET STRING,
	snIpCommunityListInternet
		INTEGER,
	snIpCommunityListNoAdvertise
		INTEGER,
	snIpCommunityListNoExport
		INTEGER,
	snIpCommunityListRowStatus
		INTEGER,
	snIpCommunityListLocalAs
		INTEGER
	}

snIpCommunityListIndex       OBJECT-TYPE
	SYNTAX  Integer32
	MAX-ACCESS  read-only
	STATUS  current
	DESCRIPTION
		"The table index for a filter entry."
	::= { snIpCommunityListEntry 1 }

snIpCommunityListSequence       OBJECT-TYPE
	SYNTAX  Integer32
	MAX-ACCESS  read-only
	STATUS  current
	DESCRIPTION
		"The table sequence index for a filter entry."
	::= { snIpCommunityListEntry 2 }

snIpCommunityListAction      OBJECT-TYPE
	SYNTAX  INTEGER { deny(0), permit(1) } 
	MAX-ACCESS  read-write
	STATUS  current
	DESCRIPTION
		"Action to take if the bgp address match
		with this filter."
	::= { snIpCommunityListEntry 3 }

snIpCommunityListCommNum    OBJECT-TYPE
	SYNTAX  OCTET STRING (SIZE(0..80))
	MAX-ACCESS  read-write
	STATUS  current
	DESCRIPTION
		"A number from 1 to 0xFFFFFFFF. There are 20 of them.  
		This integer number is represented by 4 OCTETs."
	::= { snIpCommunityListEntry 4 }

snIpCommunityListInternet OBJECT-TYPE
	SYNTAX  INTEGER { disabled(0), enabled(1) } 
	MAX-ACCESS  read-write
	STATUS  current
	DESCRIPTION
		"Disabled/Enabled the Internet Community."
	::= { snIpCommunityListEntry 5 }

snIpCommunityListNoAdvertise OBJECT-TYPE
	SYNTAX  INTEGER { false(0), true(1) } 
	MAX-ACCESS  read-write
	STATUS  current
	DESCRIPTION
		"Do not advertise this route to any peer (internal or external)."
	::= { snIpCommunityListEntry 6 }

snIpCommunityListNoExport OBJECT-TYPE
	SYNTAX  INTEGER { false(0), true(1) } 
	MAX-ACCESS  read-write
	STATUS  current
	DESCRIPTION
		"Do not advertise this route to an EBGP peer."
	::= { snIpCommunityListEntry 7 }

snIpCommunityListRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpCommunityListEntry 8 }

snIpCommunityListLocalAs OBJECT-TYPE
	SYNTAX  INTEGER { false(0), true(1) } 
	MAX-ACCESS  read-write
	STATUS  current
	DESCRIPTION
		"Send this route to peers in other sub-autonomous systems within
		the local confederation. Do not advertise this route to an 
		external system."
	::= { snIpCommunityListEntry 9 }


-- Ip Prefix List table

snIpPrefixListTable       OBJECT-TYPE
	SYNTAX  SEQUENCE OF SnIpPrefixListEntry
	MAX-ACCESS  not-accessible
	STATUS  current
	DESCRIPTION
		"Ip Prefix List table."
	::= { snIp 14 }

snIpPrefixListEntry       OBJECT-TYPE
	SYNTAX  SnIpPrefixListEntry
	MAX-ACCESS  not-accessible
	STATUS  current
	DESCRIPTION
		"An entry in the Ip Prefix List table."
	INDEX   { snIpPrefixListName,  snIpPrefixListSequence}
	::= { snIpPrefixListTable 1 }

SnIpPrefixListEntry ::= SEQUENCE {
	snIpPrefixListName
		OCTET STRING,
	snIpPrefixListSequence
		Integer32,
	snIpPrefixListDesc
		OCTET STRING,
	snIpPrefixListAction              
		INTEGER,
	snIpPrefixListAddr
		IpAddress,
	snIpPrefixListMask
		IpAddress, 
	snIpPrefixListGeValue
		INTEGER,
	snIpPrefixListLeValue
		INTEGER,
	snIpPrefixListRowStatus
		INTEGER,
	snIpPrefixListLength
		Integer32
	}

snIpPrefixListName    OBJECT-TYPE
	SYNTAX  OCTET STRING (SIZE(0..32))
	MAX-ACCESS  read-only
	STATUS  current
	DESCRIPTION
		"An octet string of the ip prefix list name, each character of the name
		 is represented by one octet."
	::= { snIpPrefixListEntry 1 }

snIpPrefixListSequence       OBJECT-TYPE
	SYNTAX  Integer32
	MAX-ACCESS  read-only
	STATUS  current
	DESCRIPTION
		"The table sequence index for a filter entry."
	::= { snIpPrefixListEntry 2 }

snIpPrefixListDesc    OBJECT-TYPE
	SYNTAX  OCTET STRING (SIZE(0..80))
	MAX-ACCESS  read-write
	STATUS  current
	DESCRIPTION
		"An octet string of the ip prefix list description, each character of the name
		 is represented by one octet."
	::= { snIpPrefixListEntry 3 }

snIpPrefixListAction      OBJECT-TYPE
	SYNTAX  INTEGER { deny(0), permit(1) } 
	MAX-ACCESS  read-write
	STATUS  current
	DESCRIPTION
		"Action to take if the ip prefix match
		with this filter."
	::= { snIpPrefixListEntry 4 }

snIpPrefixListAddr    OBJECT-TYPE
	SYNTAX  IpAddress
	MAX-ACCESS  read-write
	STATUS  current
	DESCRIPTION
		"Prefix IP address."
	::= { snIpPrefixListEntry 5 }

snIpPrefixListMask    OBJECT-TYPE
	SYNTAX  IpAddress
	MAX-ACCESS  read-write
	STATUS  current
	DESCRIPTION
		"Prefix IP mask."
	::= { snIpPrefixListEntry 6 }

snIpPrefixListGeValue OBJECT-TYPE
		 SYNTAX   INTEGER (0..32)
		 MAX-ACCESS   read-write
		 STATUS   current
		 DESCRIPTION
			"Greater than value."
	::= { snIpPrefixListEntry 7 }

snIpPrefixListLeValue OBJECT-TYPE
		 SYNTAX   INTEGER (0..32)
		 MAX-ACCESS   read-write
		 STATUS   current
		 DESCRIPTION
			"Less than value."
	::= { snIpPrefixListEntry 8 }

snIpPrefixListRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpPrefixListEntry 9 }

snIpPrefixListLength    OBJECT-TYPE
	SYNTAX   Integer32
	MAX-ACCESS	 read-write
	STATUS	 current
	DESCRIPTION
		"Prefix IP mask length."
	::= { snIpPrefixListEntry 10 }


-- ################################ new 2 tables ###################################
-- Ip AS-Path Access List table

snIpAsPathAccessListStringTable       OBJECT-TYPE
	SYNTAX  SEQUENCE OF SnIpAsPathAccessListStringEntry
	MAX-ACCESS  not-accessible
	STATUS  current
	DESCRIPTION
		"Ip As-Path Access List table, string version."
	::= { snIp 16 }

snIpAsPathAccessListStringEntry       OBJECT-TYPE
	SYNTAX  SnIpAsPathAccessListStringEntry
	MAX-ACCESS  not-accessible
	STATUS  current
	DESCRIPTION
		"An entry in the Ip As-Path Access List table."
	INDEX   { snIpAsPathAccessListStringName,  snIpAsPathAccessListStringSequence}
	::= { snIpAsPathAccessListStringTable 1 }

SnIpAsPathAccessListStringEntry ::= SEQUENCE {
	snIpAsPathAccessListStringName
		DisplayString,
	snIpAsPathAccessListStringSequence
		Integer32,
	snIpAsPathAccessListStringAction              
		INTEGER,
	snIpAsPathAccessListStringRegExpression
		DisplayString,
	snIpAsPathAccessListStringRowStatus
		INTEGER
	}

snIpAsPathAccessListStringName      OBJECT-TYPE
	SYNTAX  DisplayString (SIZE(0..32))
	MAX-ACCESS  read-only
	STATUS  current
	DESCRIPTION
		"The table index for a filter entry, string version."
	::= { snIpAsPathAccessListStringEntry 1 }

snIpAsPathAccessListStringSequence       OBJECT-TYPE
	SYNTAX  Integer32
	MAX-ACCESS  read-only
	STATUS  current
	DESCRIPTION
		"The table sequence index for a filter entry."
	::= { snIpAsPathAccessListStringEntry 2 }

snIpAsPathAccessListStringAction      OBJECT-TYPE
	SYNTAX  INTEGER { deny(0), permit(1) } 
	MAX-ACCESS  read-write
	STATUS  current
	DESCRIPTION
		"Action to take if the bgp address match
		with this filter."
	::= { snIpAsPathAccessListStringEntry 3 }

snIpAsPathAccessListStringRegExpression    OBJECT-TYPE
	SYNTAX  DisplayString (SIZE(0..256))
	MAX-ACCESS  read-write
	STATUS  current
	DESCRIPTION
		"Autonomous system in the filter using a regular expression.
		Each character of the regular expression string is represented
		by one octet."
	::= { snIpAsPathAccessListStringEntry 4 }

snIpAsPathAccessListStringRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpAsPathAccessListStringEntry 5 }


-- Ip Community List String table

snIpCommunityListStringTable       OBJECT-TYPE
	SYNTAX  SEQUENCE OF SnIpCommunityListStringEntry
	MAX-ACCESS  not-accessible
	STATUS  current
	DESCRIPTION
		"Ip Community ListString table, string version."
	::= { snIp 17 }

snIpCommunityListStringEntry       OBJECT-TYPE
	SYNTAX  SnIpCommunityListStringEntry
	MAX-ACCESS  not-accessible
	STATUS  current
	DESCRIPTION
		"An entry in the Ip Community ListString table."
	INDEX   { snIpCommunityListStringName,  snIpCommunityListStringSequence}
	::= { snIpCommunityListStringTable 1 }

SnIpCommunityListStringEntry ::= SEQUENCE {
	snIpCommunityListStringName
		DisplayString,
	snIpCommunityListStringSequence
		Integer32,
	snIpCommunityListStringAction              
		INTEGER,
	snIpCommunityListStringCommNum
		OCTET STRING,
	snIpCommunityListStringInternet
		INTEGER,
	snIpCommunityListStringNoAdvertise
		INTEGER,
	snIpCommunityListStringNoExport
		INTEGER,
	snIpCommunityListStringRowStatus
		INTEGER,
	snIpCommunityListStringLocalAs
		INTEGER,
	snIpCommunityListStringType
		INTEGER,
	snIpCommunityListStringRegExpr
		DisplayString
	}

snIpCommunityListStringName       OBJECT-TYPE
	SYNTAX  DisplayString (SIZE(0..32))
	MAX-ACCESS  read-only
	STATUS  current
	DESCRIPTION
		"The table index for a filter entry."
	::= { snIpCommunityListStringEntry 1 }

snIpCommunityListStringSequence       OBJECT-TYPE
	SYNTAX  Integer32
	MAX-ACCESS  read-only
	STATUS  current
	DESCRIPTION
		"The table sequence index for a filter entry."
	::= { snIpCommunityListStringEntry 2 }

snIpCommunityListStringAction      OBJECT-TYPE
	SYNTAX  INTEGER { deny(0), permit(1) } 
	MAX-ACCESS  read-write
	STATUS  current
	DESCRIPTION
		"Action to take if the bgp address match
		with this filter."
	::= { snIpCommunityListStringEntry 3 }

snIpCommunityListStringCommNum    OBJECT-TYPE
	SYNTAX  OCTET STRING (SIZE(0..80))
	MAX-ACCESS  read-write
	STATUS  current
	DESCRIPTION
		"A number from 1 to 0xFFFFFFFF. There are 20 of them.  
		This integer number is represented by 4 OCTETs.
		This object is valid for standard community list.
		For extended type, this will return NULL string.
		The regular expression string for extended type is available at
		object snIpCommunityListStringRegExpr"
	::= { snIpCommunityListStringEntry 4 }

snIpCommunityListStringInternet OBJECT-TYPE
	SYNTAX  INTEGER { disabled(0), enabled(1) } 
	MAX-ACCESS  read-write
	STATUS  current
	DESCRIPTION
		"Disabled/Enabled the Internet Community.
		Valid only for standard community list. For extended type, 0 is returned."
	::= { snIpCommunityListStringEntry 5 }

snIpCommunityListStringNoAdvertise OBJECT-TYPE
	SYNTAX  INTEGER { false(0), true(1) } 
	MAX-ACCESS  read-write
	STATUS  current
	DESCRIPTION
		"Do not advertise this route to any peer (internal or external).
		Valid only for standard community list. For extended type, 0 is returned."
	::= { snIpCommunityListStringEntry 6 }

snIpCommunityListStringNoExport OBJECT-TYPE
	SYNTAX  INTEGER { false(0), true(1) } 
	MAX-ACCESS  read-write
	STATUS  current
	DESCRIPTION
		"Do not advertise this route to an EBGP peer.
		Valid only for standard community list. For extended type, 0 is returned."
	::= { snIpCommunityListStringEntry 7 }

snIpCommunityListStringRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snIpCommunityListStringEntry 8 }

snIpCommunityListStringLocalAs OBJECT-TYPE
	SYNTAX  INTEGER { false(0), true(1) } 
	MAX-ACCESS  read-write
	STATUS  current
	DESCRIPTION
		"Send this route to peers in other sub-autonomous systems within
		the local confederation. Do not advertise this route to an 
		external system.
		Valid only for standard community list. For extended type, 0 is returned."
	::= { snIpCommunityListStringEntry 9 }

snIpCommunityListStringType OBJECT-TYPE
	SYNTAX	INTEGER { standard(0), extended(1) } 
	MAX-ACCESS  read-write
	STATUS  current
	DESCRIPTION
		"Type of the community list, whether standard or extended.
		Default value is standard."
	::= { snIpCommunityListStringEntry 10 }

snIpCommunityListStringRegExpr       OBJECT-TYPE
	SYNTAX	DisplayString (SIZE(0..255))
	MAX-ACCESS  read-write
	STATUS  current
	DESCRIPTION
		"The regular expression string for extended community list.
		This object will return NULL for standard community list."
	::= { snIpCommunityListStringEntry 11 }




-- SECTION 2: MIB 

-- Router IP RIP MIB

snRtIpRipGeneral                        OBJECT IDENTIFIER ::= { snRip 1 }

-- IP RIP general group

snRtIpRipEnable                 OBJECT-TYPE
	SYNTAX  RtrStatus
	MAX-ACCESS  read-write
	STATUS  current
	DESCRIPTION
		"Enable/disable ip rip routing."
	::= { snRtIpRipGeneral 1 }

snRtIpRipUpdateTime             OBJECT-TYPE
	SYNTAX  INTEGER (1..21845)
	MAX-ACCESS  read-write
	STATUS  current
	DESCRIPTION
		"Ip rip update interval in seconds."
	::= { snRtIpRipGeneral 2 }

snRtIpRipRedisEnable            OBJECT-TYPE
	SYNTAX  RtrStatus
	MAX-ACCESS  read-write
	STATUS  current
	DESCRIPTION
		"Enable/disable redistribution to rip."
	::= { snRtIpRipGeneral 3 }

snRtIpRipRedisDefMetric         OBJECT-TYPE
	SYNTAX  INTEGER (1..15)
	MAX-ACCESS  read-write
	STATUS  current
	DESCRIPTION
		"Default metric to be used when redistribute route to rip."
	::= { snRtIpRipGeneral 4 }

snRtIpRipSetAllPortConfig       OBJECT-TYPE
	SYNTAX Integer32
	MAX-ACCESS  read-write
	STATUS  current
	DESCRIPTION
		"The value of this object is an index number of a
		snRtIpRipPortConfigTable row (i.e. snRtIpRipPortConfigPortIndex),
		which is the selected row to copy all of its read-writable data
		(i.e. snRtIpRipPortVersion and snRtIpRipPortPoisonReverse) to the
		rest of the rows in snRtIpRipPortConfigTable.
		Note: prior setting this object, all the intended data of the
		given row of the table must be set. Otherwise, the current data
		of the row will be used to set the entire ip rip port configuration
		table. The previous setting will be overwritten by the new one."
	::= { snRtIpRipGeneral 5 }

snRtIpRipGblFiltList            OBJECT-TYPE
	SYNTAX	OCTET STRING (SIZE(0..64))
	MAX-ACCESS  read-write
	STATUS  current
	DESCRIPTION
		"An ip rip global filter list, of which each octet contains a
		filter ID number that forms a group of filters. A valid entry
		in the snRtIpRipRouteFilterTable with the corresponding filter
		ID number (i.e. snRtIpRipRouteFilterId) must have been created
		before a filter list is initialized.
		NULL string will be returned if there are  no entries of this kind."
	::= { snRtIpRipGeneral 6 }

snRtIpRipFiltOnAllPort          OBJECT-TYPE
	SYNTAX	INTEGER {
		valid(1),
		deleteAllInBound(2),
		deleteAllOutBound(3),
		addAllInBound(4),
		addAllOutBound(5)
	}
	MAX-ACCESS	read-write
	STATUS  current
	DESCRIPTION
		"Apply the ip rip global filter list snRtIpRipGblFiltList to
		all interfaces. This object is used to add all rip filter
		lists and delete all rip filter lists to/from all interfaces.
		Prior to sending this command, snRtIpRipGblFiltList must have
		been set to a proper filter list.

		The values that can be written are:
		deleteAllInBound(2)...delete all in-bound filter lists from all ports.
		deleteAllOutBound(3)..delete all out-bound filter lists from all ports.
		addAllInBound(4)......add all in-bound filter lists to all ports.
		addAllOutBound(5).....add all out-bound filter lists to all ports.

		If set operation failed, then a SET with value of (2) or (3)
		returns error code 'GenError'. If succeed, entries in the
		filter list are deleted immediately.

		The following values can be returned on reads:
		valid(1)....set operation is done and is valid."
	::= { snRtIpRipGeneral 7 }

snRtIpRipDistance         OBJECT-TYPE
	SYNTAX  INTEGER (1..255)
	MAX-ACCESS  read-write
	STATUS  current
	DESCRIPTION
		"Administration distance."
	::= { snRtIpRipGeneral 8 }

snRtIpRipEcmpEnable                 OBJECT-TYPE
	SYNTAX  RtrStatus
	MAX-ACCESS  read-write
	STATUS  current
	DESCRIPTION
		"Enable/disable ECMP for ip rip routing."
	::= { snRtIpRipGeneral 9 }

-- IP RIP port configuration table
-- this table was replaced by the snRtIpRipPortIfConfigTable,
-- of which the index was changed to ifIndex, not another
-- indexing method used by this table

snRtIpRipPortConfigTable        OBJECT-TYPE
	SYNTAX  SEQUENCE OF SnRtIpRipPortConfigEntry
	MAX-ACCESS  not-accessible
	STATUS  deprecated
	DESCRIPTION
		"IP Rip port Config table."
	::= { snRip 2 }

snRtIpRipPortConfigEntry        OBJECT-TYPE
	SYNTAX  SnRtIpRipPortConfigEntry
	MAX-ACCESS  not-accessible
	STATUS  deprecated
	DESCRIPTION
		"An entry in the IP Rip Port Config table."
	INDEX   { snRtIpRipPortConfigPortIndex }
	::= { snRtIpRipPortConfigTable 1 }

SnRtIpRipPortConfigEntry ::= SEQUENCE {
	snRtIpRipPortConfigPortIndex
		PortIndex,
	snRtIpRipPortVersion
		INTEGER,
	snRtIpRipPortPoisonReverse
		RtrStatus,
	snRtIpRipPortLearnDefault
		INTEGER
	}

snRtIpRipPortConfigPortIndex    OBJECT-TYPE
	SYNTAX  PortIndex
	MAX-ACCESS  read-only
	STATUS  deprecated
	DESCRIPTION
		"The port index for ip rip port config entry."
	::= { snRtIpRipPortConfigEntry 1 }

snRtIpRipPortVersion            OBJECT-TYPE
	SYNTAX  INTEGER { disabled(0), v1Only(1), v2Only(2), v1CompatibleV2(3) }
	MAX-ACCESS  read-write
	STATUS  deprecated
	DESCRIPTION
		"The ip rip version on this port."
	::= { snRtIpRipPortConfigEntry 2 }

snRtIpRipPortPoisonReverse      OBJECT-TYPE
	SYNTAX  RtrStatus
	MAX-ACCESS  read-write
	STATUS  deprecated
	DESCRIPTION
		"Enable/disable poison reverse."
	::= { snRtIpRipPortConfigEntry 3 }

snRtIpRipPortLearnDefault          OBJECT-TYPE
	SYNTAX	INTEGER {
		disabled(0),             
		enabled(1)
	}
	MAX-ACCESS	read-write
	STATUS  deprecated
	DESCRIPTION
		"Apply the RIP router protocol learn-default option to the
		interface.  The values that can be written are:
		disabled(0)...deleted the learn default option.
		enabled(1)....enabled the learn default option."
	::= { snRtIpRipPortConfigEntry 4 }

-- redistribution table

snRtIpRipRedisTable             OBJECT-TYPE
	SYNTAX  SEQUENCE OF SnRtIpRipRedisEntry
	MAX-ACCESS  not-accessible
	STATUS  current
	DESCRIPTION
		"IP Rip Redistribution table."
	::= { snRip 3 }

snRtIpRipRedisEntry             OBJECT-TYPE
	SYNTAX  SnRtIpRipRedisEntry
	MAX-ACCESS  not-accessible
	STATUS  current
	DESCRIPTION
		"An entry in the IP Rip Redistribution table."
	INDEX   { snRtIpRipRedisIndex }
	::= { snRtIpRipRedisTable 1 }

SnRtIpRipRedisEntry ::= SEQUENCE {
	snRtIpRipRedisIndex
		INTEGER,        
	snRtIpRipRedisAction
		Action,
	snRtIpRipRedisProtocol
		INTEGER,
	snRtIpRipRedisIp
		IpAddress,
	snRtIpRipRedisMask
		IpAddress,
	snRtIpRipRedisMatchMetric
		Metric,
	snRtIpRipRedisSetMetric
		INTEGER,
	snRtIpRipRedisRowStatus
		RowSts,
	snRtIpRipRedisRouteMapName
		DisplayString
	}
			
snRtIpRipRedisIndex             OBJECT-TYPE
	SYNTAX  INTEGER (1..64)
	MAX-ACCESS  read-only
	STATUS  current
	DESCRIPTION
		"The table index for a IP Rip Redistribution entry."
	::= { snRtIpRipRedisEntry 1 }

snRtIpRipRedisAction            OBJECT-TYPE
	SYNTAX  Action
	MAX-ACCESS  read-write
	STATUS  current
	DESCRIPTION
		"The action to take when match this 
		IP Rip Redistribution entry."
	::= { snRtIpRipRedisEntry 2 }

snRtIpRipRedisProtocol          OBJECT-TYPE
	SYNTAX  INTEGER { other(1), all(2), static(3), ospf(4), bgp(5), isis(6), connected(7) }
	MAX-ACCESS  read-write
	STATUS  current
	DESCRIPTION
		"The protocol to be distributed. other(1) cannot be 
				 used for SNMP-SET." 
	::= { snRtIpRipRedisEntry 3 }

snRtIpRipRedisIp        OBJECT-TYPE
	SYNTAX  IpAddress
	MAX-ACCESS  read-write
	STATUS  current
	DESCRIPTION
		"The ip address of the ip route to be distributed.
		0.0.0.0 - all routes" 
	::= { snRtIpRipRedisEntry 4 }

		
snRtIpRipRedisMask              OBJECT-TYPE
	SYNTAX  IpAddress
	MAX-ACCESS  read-write
	STATUS  current
	DESCRIPTION
		"The ip subnet mask of the ip route to be distributed." 
	::= { snRtIpRipRedisEntry 5 }

snRtIpRipRedisMatchMetric       OBJECT-TYPE
	SYNTAX  Metric
	MAX-ACCESS  read-write
	STATUS  current
	DESCRIPTION
		"The metric of the route to be matched
		to determine the redistribution.
		0 - any metric value" 
	::= { snRtIpRipRedisEntry 6 }

snRtIpRipRedisSetMetric         OBJECT-TYPE
	SYNTAX  INTEGER (0..15)
	MAX-ACCESS  read-write
	STATUS  current
	DESCRIPTION
		"The new metric of the route to be advertised.
		0 - use the default metric." 
	::= { snRtIpRipRedisEntry 7 }

snRtIpRipRedisRowStatus         OBJECT-TYPE
	SYNTAX  RowSts
	MAX-ACCESS  read-write
	STATUS  current
	DESCRIPTION
		"To create or delete a Redistribution entry."
	::= { snRtIpRipRedisEntry 8 }

snRtIpRipRedisRouteMapName      OBJECT-TYPE
	SYNTAX	DisplayString (SIZE(0..32))
	MAX-ACCESS  read-write
	STATUS  current
	DESCRIPTION
		"The route map reference for this Redistribution entry."
	::= { snRtIpRipRedisEntry 9 }

-- IP RIP route filter table

snRtIpRipRouteFilterTable	  OBJECT-TYPE
	SYNTAX	SEQUENCE OF SnRtIpRipRouteFilterEntry
	MAX-ACCESS  not-accessible
	STATUS  current
	DESCRIPTION
		"ip rip route filter table."
	::= { snRip 4 }

snRtIpRipRouteFilterEntry	  OBJECT-TYPE
	SYNTAX	SnRtIpRipRouteFilterEntry
	MAX-ACCESS  not-accessible
	STATUS  current
	DESCRIPTION
		"An entry of the ip rip route filter table."
	INDEX	{ snRtIpRipRouteFilterId }
	::= { snRtIpRipRouteFilterTable 1 }

SnRtIpRipRouteFilterEntry ::= SEQUENCE {
	snRtIpRipRouteFilterId
		INTEGER,
	snRtIpRipRouteFilterAction
		Action,
	snRtIpRipRouteFilterIpAddr
		IpAddress,
	snRtIpRipRouteFilterSubnetMask
		IpAddress,
	snRtIpRipRouteFilterRowStatus
		INTEGER
	}

snRtIpRipRouteFilterId         OBJECT-TYPE
	SYNTAX	INTEGER (1..64)
	MAX-ACCESS  read-only
	STATUS  current
	DESCRIPTION
		"The filter ID to identify a filter entry."
	::= { snRtIpRipRouteFilterEntry 1 }

snRtIpRipRouteFilterAction	   OBJECT-TYPE
	SYNTAX  Action 
	MAX-ACCESS  read-write
	STATUS  current
	DESCRIPTION
		"Action to take if the ip rip packet matched
		with this filter."
	::= { snRtIpRipRouteFilterEntry 2 }

snRtIpRipRouteFilterIpAddr     OBJECT-TYPE
	SYNTAX  IpAddress
	MAX-ACCESS  read-write
	STATUS  current
	DESCRIPTION
		"Route IP address to compare with any route IP addresses
		in a ip rip packet. IP address 0.0.0.0 always compare
		equals to any route IP addresses in any ip rip packets."
	::= { snRtIpRipRouteFilterEntry 3 }

snRtIpRipRouteFilterSubnetMask OBJECT-TYPE
	SYNTAX  IpAddress
	MAX-ACCESS  read-write
	STATUS  current
	DESCRIPTION
		"Subnet mask to apply to the route IP address in a ip rip
		packet, the result is compared to snRtIpRipRouteFilterIpAddr.
		If snRtIpRipRouteFilterIpAddr is 0.0.0.0, this subnet mask
		value is ignored."
	::= { snRtIpRipRouteFilterEntry 4 }

snRtIpRipRouteFilterRowStatus  OBJECT-TYPE
	SYNTAX	INTEGER {
		invalid(1),
		valid(2),
		delete(3),
		create(4),
		modify(5)
	}
	MAX-ACCESS	 read-write
	STATUS	 current
	DESCRIPTION
		"This object is used to create and
		delete row in the table and control
		if they are used. The values
		that can be written are:
		delete(3)...deletes the row
		create(4)...creates a new row
		modify(5)...modifies an exsisting row

		If the row exists, then a SET with
		value of create(4) returns error
		'badValue'. Deleted rows go away
		immediately. The following values
		can be returned on reads:
		invalid(1)...Setting it to 'invalid' has the effect of
					 rendering it inoperative.
		valid(2).....the row exists and is valid"
	::= { snRtIpRipRouteFilterEntry 5 }

-- IP RIP neighbor filter table

snRtIpRipNbrFilterTable	     OBJECT-TYPE
	SYNTAX	SEQUENCE OF SnRtIpRipNbrFilterEntry
	MAX-ACCESS  not-accessible
	STATUS  current
	DESCRIPTION
		"ip rip neighbor filter table."
	::= { snRip 5 }

snRtIpRipNbrFilterEntry	     OBJECT-TYPE
	SYNTAX	SnRtIpRipNbrFilterEntry
	MAX-ACCESS  not-accessible
	STATUS  current
	DESCRIPTION
		"An entry of the ip rip neighbor filter table."
	INDEX	{ snRtIpRipNbrFilterId }
	::= { snRtIpRipNbrFilterTable 1 }

SnRtIpRipNbrFilterEntry ::= SEQUENCE {
	snRtIpRipNbrFilterId
		INTEGER,
	snRtIpRipNbrFilterAction
		Action,
	snRtIpRipNbrFilterSourceIp
		IpAddress,
	snRtIpRipNbrFilterRowStatus
		INTEGER
	}

snRtIpRipNbrFilterId         OBJECT-TYPE
	SYNTAX	INTEGER (1..64)
	MAX-ACCESS  read-only
	STATUS  current
	DESCRIPTION
		"The filter ID to identify a filter entry."
	::= { snRtIpRipNbrFilterEntry 1 }

snRtIpRipNbrFilterAction	 OBJECT-TYPE
	SYNTAX  Action 
	MAX-ACCESS  read-write
	STATUS  current
	DESCRIPTION
		"Action to take if the ip rip packet source IP
		address compares equal to the source IP address
		in this filter."
	::= { snRtIpRipNbrFilterEntry 2 }

snRtIpRipNbrFilterSourceIp   OBJECT-TYPE
	SYNTAX  IpAddress
	MAX-ACCESS  read-write
	STATUS  current
	DESCRIPTION
		"Source IP address to compare with the source IP
		address in a ip rip packet. IP address 0.0.0.0
		always compares equal to any source IP addresses
		in any ip rip packets."
	::= { snRtIpRipNbrFilterEntry 3 }

snRtIpRipNbrFilterRowStatus  OBJECT-TYPE
	SYNTAX	INTEGER {
		invalid(1),
		valid(2),
		delete(3),
		create(4),
		modify(5)
	}
	MAX-ACCESS	 read-write
	STATUS	 current
	DESCRIPTION
		"This object is used to create and
		delete row in the table and control
		if they are used. The values
		that can be written are:
		delete(3)...deletes the row
		create(4)...creates a new row
		modify(5)...modifies an exsisting row

		If the row exists, then a SET with
		value of create(4) returns error
		'badValue'. Deleted rows go away
		immediately. The following values
		can be returned on reads:
		invalid(1)...Setting it to 'invalid' has the effect of
					 rendering it inoperative.
		valid(2).....the row exists and is valid"
	::= { snRtIpRipNbrFilterEntry 4 }

-- IP RIP port access table
-- this table was replaced by the snRtIpRipPortIfAccessTable,
-- of which the index was changed to ifIndex, not another
-- indexing method used by this table

snRtIpRipPortAccessTable	     OBJECT-TYPE
	SYNTAX	SEQUENCE OF SnRtIpRipPortAccessEntry
	MAX-ACCESS  not-accessible
	STATUS  deprecated
	DESCRIPTION
		"ip interface rip access table."
	::= { snRip 6 }

snRtIpRipPortAccessEntry	     OBJECT-TYPE
	SYNTAX	SnRtIpRipPortAccessEntry
	MAX-ACCESS  not-accessible
	STATUS  deprecated
	DESCRIPTION
		"An entry of the ip interface rip access table."
	INDEX	{ snRtIpRipPortAccessPort, snRtIpRipPortAccessDir }
	::= { snRtIpRipPortAccessTable 1 }

SnRtIpRipPortAccessEntry ::= SEQUENCE {
	snRtIpRipPortAccessPort
		PortIndex,
	snRtIpRipPortAccessDir
		INTEGER,
	snRtIpRipPortAccessFilterList
		OCTET STRING,
	snRtIpRipPortAccessRowStatus
		INTEGER
	}

snRtIpRipPortAccessPort	     OBJECT-TYPE
	SYNTAX  PortIndex
	MAX-ACCESS  read-only
	STATUS  deprecated
	DESCRIPTION
		"The ip interface to which the rip filter applies."
	::= { snRtIpRipPortAccessEntry 1 }

snRtIpRipPortAccessDir	     OBJECT-TYPE
	SYNTAX  INTEGER { in(1), out(2) }
	MAX-ACCESS	read-only
	STATUS  deprecated
	DESCRIPTION
		"The access direction of incoming packet filter
		or outgoing packet filter."
	::= { snRtIpRipPortAccessEntry 2 }

snRtIpRipPortAccessFilterList  OBJECT-TYPE
	SYNTAX	OCTET STRING (SIZE(1..64))
	MAX-ACCESS  read-write
	STATUS  deprecated
	DESCRIPTION
		"An ip rip filter list, of which each octet contains
		a filter ID number that forms a group of filters. A
		valid entry in the snRtIpRipRouteFilterTable with the
		corresponding filter ID number (i.e. snRtIpRipRouteFilterId)
		must have been created before a filter list is initialized."
	::= { snRtIpRipPortAccessEntry 3 }

snRtIpRipPortAccessRowStatus   OBJECT-TYPE
	SYNTAX	 INTEGER {
		invalid(1),
		valid(2),
		delete(3),
		create(4),
		modify(5)
	}
	MAX-ACCESS	read-write
	STATUS  deprecated
	DESCRIPTION
		"This object is used to create and
		delete row in the table and control
		if they are used. The values
		that can be written are:
		delete(3)...deletes the row
		create(4)...creates a new row
		modify(5)...modifies an exsisting row

		If the row exists, then a SET with
		value of create(4) returns error
		'badValue'. Deleted rows go away
		immediately. The following values
		can be returned on reads:
		invalid(1)...Setting it to 'invalid' has the effect of
					 rendering it inoperative.
		valid(2).....the row exists and is valid"
	::= { snRtIpRipPortAccessEntry 4 }

-- IP RIP port configuration table, PortIndex is changed to ifIndex

snRtIpRipPortIfConfigTable        OBJECT-TYPE
	SYNTAX  SEQUENCE OF SnRtIpRipPortIfConfigEntry
	MAX-ACCESS  not-accessible
	STATUS  current
	DESCRIPTION
		"IP Rip port If Config table."
	::= { snRip 7 }

snRtIpRipPortIfConfigEntry        OBJECT-TYPE
	SYNTAX  SnRtIpRipPortIfConfigEntry
	MAX-ACCESS  not-accessible
	STATUS  current
	DESCRIPTION
		"An entry in the IP Rip Port If Config table."
	INDEX   { snRtIpRipPortIfConfigInterfaceIndex }
	::= { snRtIpRipPortIfConfigTable 1 }

SnRtIpRipPortIfConfigEntry ::= SEQUENCE {
	snRtIpRipPortIfConfigInterfaceIndex
		InterfaceIndex,
	snRtIpRipPortIfVersion
		INTEGER,
	snRtIpRipPortIfPoisonReverse
		RtrStatus,
	snRtIpRipPortIfLearnDefault
		INTEGER
	}

snRtIpRipPortIfConfigInterfaceIndex    OBJECT-TYPE
	SYNTAX  InterfaceIndex
	MAX-ACCESS  read-only
	STATUS  current
	DESCRIPTION
		"The If index for ip rip port config entry."
	::= { snRtIpRipPortIfConfigEntry 1 }

snRtIpRipPortIfVersion            OBJECT-TYPE
	SYNTAX  INTEGER { disabled(0), v1Only(1), v2Only(2), v1CompatibleV2(3) }
	MAX-ACCESS  read-write
	STATUS  current
	DESCRIPTION
		"The ip rip version on this port."
	::= { snRtIpRipPortIfConfigEntry 2 }

snRtIpRipPortIfPoisonReverse      OBJECT-TYPE
	SYNTAX  RtrStatus
	MAX-ACCESS  read-write
	STATUS  current
	DESCRIPTION
		"Enable/disable poison reverse."
	::= { snRtIpRipPortIfConfigEntry 3 }

snRtIpRipPortIfLearnDefault          OBJECT-TYPE
	SYNTAX	INTEGER {
		disabled(0),             
		enabled(1)
	}
	MAX-ACCESS	read-write
	STATUS  current
	DESCRIPTION
		"Apply the RIP router protocol learn-default option to the
		interface.  The values that can be written are:
		disabled(0)...deleted the learn default option.
		enabled(1)....enabled the learn default option."
	::= { snRtIpRipPortIfConfigEntry 4 }

-- IP RIP port access table, PortIndex is changed to ifIndex

snRtIpRipPortIfAccessTable	     OBJECT-TYPE
	SYNTAX	SEQUENCE OF SnRtIpRipPortIfAccessEntry
	MAX-ACCESS  not-accessible
	STATUS  current
	DESCRIPTION
		"ip interface rip access table."
	::= { snRip 8 }

snRtIpRipPortIfAccessEntry	     OBJECT-TYPE
	SYNTAX	SnRtIpRipPortIfAccessEntry
	MAX-ACCESS  not-accessible
	STATUS  current
	DESCRIPTION
		"An entry of the ip interface rip access table."
	INDEX	{ snRtIpRipPortIfAccessPort, snRtIpRipPortIfAccessDir }
	::= { snRtIpRipPortIfAccessTable 1 }

SnRtIpRipPortIfAccessEntry ::= SEQUENCE {
	snRtIpRipPortIfAccessPort
		InterfaceIndex,
	snRtIpRipPortIfAccessDir
		INTEGER,
	snRtIpRipPortIfAccessFilterList
		OCTET STRING,
	snRtIpRipPortIfAccessRowStatus
		INTEGER
	}

snRtIpRipPortIfAccessPort	     OBJECT-TYPE
	SYNTAX  InterfaceIndex
	MAX-ACCESS  read-only
	STATUS  current
	DESCRIPTION
		"The ip interface to which the rip filter applies."
	::= { snRtIpRipPortIfAccessEntry 1 }

snRtIpRipPortIfAccessDir	     OBJECT-TYPE
	SYNTAX  INTEGER { in(1), out(2) }
	MAX-ACCESS	read-only
	STATUS  current
	DESCRIPTION
		"The access direction of incoming packet filter
		or outgoing packet filter."
	::= { snRtIpRipPortIfAccessEntry 2 }

snRtIpRipPortIfAccessFilterList  OBJECT-TYPE
	SYNTAX	OCTET STRING (SIZE(1..64))
	MAX-ACCESS  read-write
	STATUS  current
	DESCRIPTION
		"An ip rip filter list, of which each octet contains
		a filter ID number that forms a group of filters. A
		valid entry in the snRtIpRipRouteFilterTable with the
		corresponding filter ID number (i.e. snRtIpRipRouteFilterId)
		must have been created before a filter list is initialized."
	::= { snRtIpRipPortIfAccessEntry 3 }

snRtIpRipPortIfAccessRowStatus   OBJECT-TYPE
	SYNTAX	 INTEGER {
		invalid(1),
		valid(2),
		delete(3),
		create(4),
		modify(5)
	}
	MAX-ACCESS	 read-write
	STATUS	 current
	DESCRIPTION
		"This object is used to create and
		delete row in the table and control
		if they are used. The values
		that can be written are:
		delete(3)...deletes the row
		create(4)...creates a new row
		modify(5)...modifies an exsisting row

		If the row exists, then a SET with
		value of create(4) returns error
		'badValue'. Deleted rows go away
		immediately. The following values
		can be returned on reads:
		invalid(1)...Setting it to 'invalid' has the effect of
					 rendering it inoperative.
		valid(2).....the row exists and is valid"
	::= { snRtIpRipPortIfAccessEntry 4 }

-- RIP Global Statistics

snRtIpRipStats                        OBJECT IDENTIFIER ::= { snRip 9 }

snRtIpRipStatsOutRequest OBJECT-TYPE
	SYNTAX	Counter32
	MAX-ACCESS	read-only
	STATUS	current
	DESCRIPTION
		"Number of outgoing RIP requests."
	::= { snRtIpRipStats 1 }

snRtIpRipStatsOutResponse OBJECT-TYPE
	SYNTAX	Counter32
	MAX-ACCESS	read-only
	STATUS	current
	DESCRIPTION
		"Number of outgoing RIP responses."
	::= { snRtIpRipStats 2 }

snRtIpRipStatsInRequest OBJECT-TYPE
	SYNTAX	Counter32
	MAX-ACCESS	read-only
	STATUS	current
	DESCRIPTION
		"Number of incoming RIP requests."
	::= { snRtIpRipStats 3 }

snRtIpRipStatsInResponse OBJECT-TYPE
	SYNTAX	Counter32
	MAX-ACCESS	read-only
	STATUS	current
	DESCRIPTION
		"Number of incoming RIP responses."
	::= { snRtIpRipStats 4 }

snRtIpRipStatsUnrecognized OBJECT-TYPE
	SYNTAX	Counter32
	MAX-ACCESS	read-only
	STATUS	current
	DESCRIPTION
		"Number of unrecognized RIP packets."
	::= { snRtIpRipStats 5 }

snRtIpRipStatsBadVersion OBJECT-TYPE
	SYNTAX	Counter32
	MAX-ACCESS	read-only
	STATUS	current
	DESCRIPTION
		"Number of RIP packets with bad version number."
	::= { snRtIpRipStats 6 }

snRtIpRipStatsBadAddrFamily OBJECT-TYPE
	SYNTAX	Counter32
	MAX-ACCESS	read-only
	STATUS	current
	DESCRIPTION
		"Number of RIP packets with bad address family value."
	::= { snRtIpRipStats 7 }

snRtIpRipStatsBadRequestFormat OBJECT-TYPE
	SYNTAX	Counter32
	MAX-ACCESS	read-only
	STATUS	current
	DESCRIPTION
		"Number of RIP packets with bad request format."
	::= { snRtIpRipStats 8 }

snRtIpRipStatsBadMetrics OBJECT-TYPE
	SYNTAX	Counter32
	MAX-ACCESS	read-only
	STATUS	current
	DESCRIPTION
		"Number of RIP packets with bad metric value."
	::= { snRtIpRipStats 9 }

snRtIpRipStatsBadRespFormat OBJECT-TYPE
	SYNTAX	Counter32
	MAX-ACCESS	read-only
	STATUS	current
	DESCRIPTION
		"Number of RIP packets with bad response format."
	::= { snRtIpRipStats 10 }

snRtIpRipStatsRespFromNonRipPort OBJECT-TYPE
	SYNTAX	Counter32
	MAX-ACCESS	read-only
	STATUS	current
	DESCRIPTION
		"Number of RIP packet responses coming from non-RIP configured ports."
	::= { snRtIpRipStats 11 }

snRtIpRipStatsResponseFromLoopback OBJECT-TYPE
	SYNTAX	Counter32
	MAX-ACCESS	read-only
	STATUS	current
	DESCRIPTION
		"Number of RIP packet responses coming from loopback ports."
	::= { snRtIpRipStats 12 }

snRtIpRipStatsPacketRejected OBJECT-TYPE
	SYNTAX	Counter32
	MAX-ACCESS	read-only
	STATUS	current
	DESCRIPTION
		"Number of RIP packets rejected."
	::= { snRtIpRipStats 13 }

-- DVMRP MIB

snDvmrpMIBObjects OBJECT IDENTIFIER ::= { snDvmrp 1 }

snDvmrpVersion OBJECT-TYPE
	SYNTAX     DisplayString (SIZE(0..255))
	MAX-ACCESS     read-only
	STATUS     current
	DESCRIPTION
			"The router's DVMRP version information."
	::= { snDvmrpMIBObjects 1 }

snDvmrpEnable OBJECT-TYPE
	SYNTAX     RtrStatus
	MAX-ACCESS     read-write
	STATUS     current
	DESCRIPTION
			"Enable or disable DVMRP on this router."
	DEFVAL     { disabled }
	::= { snDvmrpMIBObjects 2 }

snDvmrpGenerationId OBJECT-TYPE
	SYNTAX Integer32
	MAX-ACCESS     read-only
	STATUS     current
	DESCRIPTION
			"The generation identifier for the routing process.  This is
			used by neighboring routers to detect whether pruning
			information should be resent."
	::= { snDvmrpMIBObjects 3 }

snDvmrpProbeInterval OBJECT-TYPE
	SYNTAX     INTEGER (5..30)
	MAX-ACCESS     read-write
	STATUS     current
	DESCRIPTION
			"This is the time interval at which the router sends out
			probe messages to discover neighbour routers. Value is
			in number of seconds. snDvmrpEnable must be 'enabled'
			before this object is writen."
	DEFVAL     { 10 }
	::= { snDvmrpMIBObjects 4 }

snDvmrpReportInterval OBJECT-TYPE
	SYNTAX     INTEGER (10..2000)
	MAX-ACCESS     read-write
	STATUS     current
	DESCRIPTION
			"This is the time interval at which the router sends out
			full report messages. Value is in number of seconds.
			snDvmrpEnable must be 'enabled' before this object is
			writen."
	DEFVAL     { 60 }
	::= { snDvmrpMIBObjects 5 }

snDvmrpTriggerInterval OBJECT-TYPE
	SYNTAX     INTEGER (5..30)
	MAX-ACCESS     read-write
	STATUS     current
	DESCRIPTION
			"This is the time interval at which triggered updates are
			sent out. Value is in number of seconds. snDvmrpEnable must
			be 'enabled' before this object is writen."
	DEFVAL     { 5 }
	::= { snDvmrpMIBObjects 6 }

snDvmrpNeighborRouterTimeout OBJECT-TYPE
	SYNTAX     INTEGER (60..8000)
	MAX-ACCESS     read-write
	STATUS     current
	DESCRIPTION
			"This is the time interval after which the neighbour router
			is considered down. Value is in number of seconds. snDvmrpEnable
			must be 'enabled' before this object is writen."
	DEFVAL     { 180 }
	::= { snDvmrpMIBObjects 7 }

snDvmrpRouteExpireTime OBJECT-TYPE
	SYNTAX     INTEGER (20..4000)
	MAX-ACCESS     read-write
	STATUS     current
	DESCRIPTION
			"This is the time interval after which the route expires
			and becomes unreachable. Value is in number of seconds.
			snDvmrpEnable must be 'enabled' before this object is writen."
	DEFVAL     { 200 }
	::= { snDvmrpMIBObjects 8 }

snDvmrpRouteDiscardTime OBJECT-TYPE
	SYNTAX     INTEGER (40..8000)
	MAX-ACCESS     read-write
	STATUS     current
	DESCRIPTION
			"This is the time interval after which a route is discarded
			from the route table. Value is in number of seconds.
			snDvmrpEnable must be 'enabled' before this object is writen."
	DEFVAL     { 340 }
	::= { snDvmrpMIBObjects 9 }

snDvmrpPruneAge OBJECT-TYPE
	SYNTAX     INTEGER (20..3600)
	MAX-ACCESS     read-write
	STATUS     current
	DESCRIPTION
			"This is the duration of time for which the prune state
			is stored. Value is in number of seconds. snDvmrpEnable
			must be 'enabled' before this object is writen."
	DEFVAL     { 180 }
	::= { snDvmrpMIBObjects 10 }

snDvmrpGraftRetransmitTime OBJECT-TYPE
	SYNTAX     INTEGER (2..3600)
	MAX-ACCESS     read-write
	STATUS     current
	DESCRIPTION
			"This is the time interval after which a graft message will
			be retransmitted if graft acknowledge message has not been
			received. Value is in number of seconds. snDvmrpEnable must
			be 'enabled' before this object is writen.
			For FastIron platforms, the default value is 3 and the range is 
			between 2 to 10."
	DEFVAL     { 10 }
	::= { snDvmrpMIBObjects 11 }

snDvmrpDefaultRoute OBJECT-TYPE
	SYNTAX     IpAddress
	MAX-ACCESS     read-write
	STATUS     current
	DESCRIPTION
			"This is the IP address of a router that is connected to one
			of the directly attached subnet. If a multicast route is not
			present on the local router, this default route will be used
			for multicast forwarding. snDvmrpEnable must be 'enabled'
			before this object is writen."
	::= { snDvmrpMIBObjects 12 }

-- The DVMRP Virtual Interface Table

snDvmrpVInterfaceTable OBJECT-TYPE
	SYNTAX     SEQUENCE OF SnDvmrpVInterfaceEntry
	MAX-ACCESS     not-accessible
	STATUS     current
	DESCRIPTION
			"The (conceptual) table listing the router's DVMRP virtual
			interfaces. snDvmrpEnable must be 'enabled' before this
			table is read or writen."
	::= { snDvmrpMIBObjects 13 }

snDvmrpVInterfaceEntry OBJECT-TYPE
	SYNTAX     SnDvmrpVInterfaceEntry
	MAX-ACCESS     not-accessible
	STATUS     current
	DESCRIPTION
			"An entry (conceptual row) in the snDvmrpVInterfaceTable.
			This row augments ipMRouteInterfaceEntry in the IP
			Multicast MIB, where the threshold object resides."
	INDEX      { snDvmrpVInterfaceVifIndex }
	::= { snDvmrpVInterfaceTable 1 }

SnDvmrpVInterfaceEntry ::= SEQUENCE {
	snDvmrpVInterfaceVifIndex              INTEGER,
	snDvmrpVInterfaceType                  INTEGER,
	snDvmrpVInterfaceOperState             INTEGER,
	snDvmrpVInterfaceLocalAddress          IpAddress,
	snDvmrpVInterfaceRemoteAddress         IpAddress,
	snDvmrpVInterfaceRemoteSubnetMask      IpAddress,
	snDvmrpVInterfaceMetric                INTEGER,
	snDvmrpVInterfaceTtlThreshold          INTEGER,
	snDvmrpVInterfaceAdvertiseLocal        RtrStatus,
	snDvmrpVInterfaceEncapsulation         RtrStatus,
	snDvmrpVInterfaceStatus                INTEGER }

snDvmrpVInterfaceVifIndex OBJECT-TYPE
	SYNTAX     INTEGER (1..48)
	MAX-ACCESS     read-only
	STATUS     current
	DESCRIPTION
			"The ifIndex value of this DVMRP virtual interface."
	::= { snDvmrpVInterfaceEntry 1 }

snDvmrpVInterfaceType OBJECT-TYPE
	SYNTAX     INTEGER { tunnel(1), querier(2), subnet(3) }
	MAX-ACCESS     read-write
	STATUS     current
	DESCRIPTION
			"The type of this DVMRP virtual interface, whether it uses
			a tunnel, a physical interface for which we are a querier,
			or a physical interface for which we are not a querier.
			For write operation, this object can only accept tunnel(1)
			to configure a tunnel interface or subnet(3) to configure
			a physical interface."
	::= { snDvmrpVInterfaceEntry 2 }

snDvmrpVInterfaceOperState OBJECT-TYPE
	SYNTAX     INTEGER { up(1), down(2) }
	MAX-ACCESS     read-only
	STATUS     current
	DESCRIPTION
			"The current operational state of this DVMRP virtual
			interface."
	::= { snDvmrpVInterfaceEntry 3 }

snDvmrpVInterfaceLocalAddress OBJECT-TYPE
	SYNTAX     IpAddress
	MAX-ACCESS     read-write
	STATUS     current
	DESCRIPTION
			"The IP address of the local end of this DVMRP virtual
			interface."
	::= { snDvmrpVInterfaceEntry 4 }

snDvmrpVInterfaceRemoteAddress OBJECT-TYPE
	SYNTAX     IpAddress
	MAX-ACCESS     read-write
	STATUS     current
	DESCRIPTION
			"The IP address of the remote end of this DVMRP virtual
			interface.  For a tunnel, this is the IP address of the
			neighboring router.  For a subnet, this is the subnet
			address."
	::= { snDvmrpVInterfaceEntry 5 }

snDvmrpVInterfaceRemoteSubnetMask OBJECT-TYPE
	SYNTAX     IpAddress
	MAX-ACCESS     read-only
	STATUS     current
	DESCRIPTION
			"The subnet mask for a directly connected subnet.  For
			a tunnel, this should be 0.0.0.0."
	::= { snDvmrpVInterfaceEntry 6 }

snDvmrpVInterfaceMetric OBJECT-TYPE
	SYNTAX     INTEGER (1..31)
	MAX-ACCESS     read-write
	STATUS     current
	DESCRIPTION
			"The distance metric for this DVMRP virtual interface which
			is used to calculate distance vectors."
	DEFVAL     { 1 }
	::= { snDvmrpVInterfaceEntry 7 }

snDvmrpVInterfaceTtlThreshold OBJECT-TYPE
	SYNTAX     INTEGER (1..254)
	MAX-ACCESS     read-write
	STATUS     current
	DESCRIPTION
			"This is the minimum time-to-live value to forward the packets
			out of this virtual interface."
	DEFVAL     { 1 }
	::= { snDvmrpVInterfaceEntry 8 }

snDvmrpVInterfaceAdvertiseLocal OBJECT-TYPE
	SYNTAX     RtrStatus
	MAX-ACCESS     read-write
	STATUS     current
	DESCRIPTION
			"Enable or disable the advertising of this local route."
	DEFVAL     { enabled }
	::= { snDvmrpVInterfaceEntry 9 }

snDvmrpVInterfaceEncapsulation OBJECT-TYPE
	SYNTAX     RtrStatus
	MAX-ACCESS     read-write
	STATUS     current
	DESCRIPTION
			"Enable or disable the encapsulation of the DVMRP control
			packets when using IPINIP encapsulation."
	DEFVAL     { disabled }
	::= { snDvmrpVInterfaceEntry 10 }


snDvmrpVInterfaceStatus OBJECT-TYPE
	SYNTAX     INTEGER {
					invalid(1),
					valid(2),
					delete(3),
					create(4),
					modify(5)
			   }
	MAX-ACCESS     read-write
	STATUS     current
	DESCRIPTION
			"This object is used to create and
			 delete row in the table and control
			 if they are used. The values
			 that can be written are:
			 delete(3)...deletes the row
			 create(4)...creates a new row
			 modify(5)...modifies an exsisting row

			 If the row exists, then a SET with
			 value of create(4) returns error
			 'badValue'. Deleted rows go away
			 immediately. The following values
			 can be returned on reads:
			 invalid(1)...Setting it to 'invalid' has the effect of
						  rendering it inoperative.
			 valid(2)....Setting it to 'valid' has the effect of
						 changing the row to operative."
	::= { snDvmrpVInterfaceEntry 11 }


-- The DVMRP Neighbor Table

snDvmrpNeighborTable OBJECT-TYPE
	SYNTAX     SEQUENCE OF SnDvmrpNeighborEntry
	MAX-ACCESS     not-accessible
	STATUS     current
	DESCRIPTION
			"The (conceptual) table listing the router's DVMRP
			neighbors, as discovered by receiving Neighbor Probe
			messages. snDvmrpEnable must be 'enabled' before this
			table is read."
	::= { snDvmrpMIBObjects 14 }

snDvmrpNeighborEntry OBJECT-TYPE
	SYNTAX     SnDvmrpNeighborEntry
	MAX-ACCESS     not-accessible
	STATUS     current
	DESCRIPTION
			"An entry (conceptual row) in the snDvmrpNeighborTable."
	INDEX      { snDvmrpNeighborEntryIndex }
	::= { snDvmrpNeighborTable 1 }

SnDvmrpNeighborEntry ::= SEQUENCE {
	snDvmrpNeighborEntryIndex      Integer32,
	snDvmrpNeighborVifIndex        Integer32,
	snDvmrpNeighborAddress         IpAddress,
	snDvmrpNeighborUpTime          TimeTicks,
	snDvmrpNeighborExpiryTime      TimeTicks,
	snDvmrpNeighborGenerationId    Integer32,
	snDvmrpNeighborMajorVersion    INTEGER,
	snDvmrpNeighborMinorVersion    INTEGER,
	snDvmrpNeighborCapabilities    Integer32}

snDvmrpNeighborEntryIndex OBJECT-TYPE
	SYNTAX     Integer32
	MAX-ACCESS     read-only
	STATUS     current
	DESCRIPTION
			"The table entry index."
	::= { snDvmrpNeighborEntry 1 }

snDvmrpNeighborVifIndex OBJECT-TYPE
	SYNTAX Integer32
	MAX-ACCESS     read-only
	STATUS     current
	DESCRIPTION
			"The value of VifIndex for the virtual interface used to
			reach this DVMRP neighbor."
	::= { snDvmrpNeighborEntry 2 }

snDvmrpNeighborAddress OBJECT-TYPE
	SYNTAX     IpAddress
	MAX-ACCESS     read-only
	STATUS     current
	DESCRIPTION
			"The IP address of the DVMRP neighbor for which this entry
			contains information."
	::= { snDvmrpNeighborEntry 3 }

snDvmrpNeighborUpTime OBJECT-TYPE
	SYNTAX     TimeTicks
	MAX-ACCESS     read-only
	STATUS     current
	DESCRIPTION
			"The time since this DVMRP neighbor (last) became a neighbor
			of the local router."
	::= { snDvmrpNeighborEntry 4 }

snDvmrpNeighborExpiryTime OBJECT-TYPE
	SYNTAX     TimeTicks
	MAX-ACCESS     read-only
	STATUS     current
	DESCRIPTION
			"The minimum time remaining before this DVMRP neighbor will
			be aged out."
	::= { snDvmrpNeighborEntry 5 }

snDvmrpNeighborGenerationId OBJECT-TYPE
	SYNTAX Integer32
	MAX-ACCESS     read-only
	STATUS     current
	DESCRIPTION
			"The neighboring router's generation identifier."
	::= { snDvmrpNeighborEntry 6 }

snDvmrpNeighborMajorVersion OBJECT-TYPE
	SYNTAX     INTEGER (0..255)
	MAX-ACCESS     read-only
	STATUS     current
	DESCRIPTION
			"The neighboring router's major DVMRP version number."
	::= { snDvmrpNeighborEntry 7 }

snDvmrpNeighborMinorVersion OBJECT-TYPE
	SYNTAX     INTEGER (0..255)
	MAX-ACCESS     read-only
	STATUS     current
	DESCRIPTION
			"The neighboring router's minor DVMRP version number."
	::= { snDvmrpNeighborEntry 8 }

snDvmrpNeighborCapabilities OBJECT-TYPE
	SYNTAX Integer32
	MAX-ACCESS     read-only
	STATUS     current
	DESCRIPTION
			"This object describes the neighboring router's
			 capabilities.  The following shows the position
			 of each bit:

			 bit position  meaning
			 -----------   ------
				 3         mtrace bit
				 2         generationID bit
				 1         prune bit
				 0         leaf bit

			 The leaf bit indicates that the neighbor has only
			 one interface with neighbors.  The prune bit indicates
			 that the neighbor supports pruning.  The generationID bit
			 indicates that the neighbor sends its generationID in Probe
			 messages.  The mtrace bit indicates that the neighbor can
			 handle mtrace requests."
	::= { snDvmrpNeighborEntry 9 }


-- The DVMRP Route Table

snDvmrpRouteTable OBJECT-TYPE
	SYNTAX     SEQUENCE OF SnDvmrpRouteEntry
	MAX-ACCESS     not-accessible
	STATUS     current
	DESCRIPTION
			"The routing table used by DVMRP in place of the unicast
			routing table. snDvmrpEnable must be 'enabled' before this
			table is read."
	::= { snDvmrpMIBObjects 15 }

snDvmrpRouteEntry OBJECT-TYPE
	SYNTAX     SnDvmrpRouteEntry
	MAX-ACCESS     not-accessible
	STATUS     current
	DESCRIPTION
			"An entry (conceptual row) containing the multicast routing
			information used by DVMRP in place of the unicast routing
			information."
	INDEX      { snDvmrpRouteEntryIndex }
	::= { snDvmrpRouteTable 1 }

SnDvmrpRouteEntry ::= SEQUENCE {
	snDvmrpRouteEntryIndex         Integer32,
	snDvmrpRouteSource             IpAddress,
	snDvmrpRouteSourceMask         IpAddress,
	snDvmrpRouteUpstreamNeighbor   IpAddress,
	snDvmrpRouteVifIndex           Integer32,
	snDvmrpRouteMetric             Integer32,
	snDvmrpRouteExpiryTime         TimeTicks }

snDvmrpRouteEntryIndex OBJECT-TYPE
	SYNTAX     Integer32
	MAX-ACCESS     read-only
	STATUS     current
	DESCRIPTION
			"The table entry index."
	::= { snDvmrpRouteEntry 1 }

snDvmrpRouteSource OBJECT-TYPE
	SYNTAX     IpAddress
	MAX-ACCESS     read-only
	STATUS     current
	DESCRIPTION
			"The network address which when combined with the
			corresponding value of snDvmrpRouteSourceMask identifies the
			sources for which this entry contains multicast routing
			information."
	::= { snDvmrpRouteEntry 2 }

snDvmrpRouteSourceMask OBJECT-TYPE
	SYNTAX     IpAddress
	MAX-ACCESS     read-only
	STATUS     current
	DESCRIPTION
			"The network mask which when combined with the corresponding
			value of snDvmrpRouteSource identifies the sources for which
			this entry contains multicast routing information."
	::= { snDvmrpRouteEntry 3 }

snDvmrpRouteUpstreamNeighbor OBJECT-TYPE
	SYNTAX     IpAddress
	MAX-ACCESS     read-only
	STATUS     current
	DESCRIPTION
			"The address of the upstream neighbor (e.g., RPF neighbor)
			from which IP datagrams from these sources are received."
	::= { snDvmrpRouteEntry 4 }

snDvmrpRouteVifIndex OBJECT-TYPE
	SYNTAX Integer32
	MAX-ACCESS     read-only
	STATUS     current
	DESCRIPTION
			"The value of snDvmrpVInterfaceVifIndex for the virtual
			interface on which IP datagrams sent by these sources are
			received."
	::= { snDvmrpRouteEntry 5 }

snDvmrpRouteMetric OBJECT-TYPE
	SYNTAX Integer32
	MAX-ACCESS     read-only
	STATUS     current
	DESCRIPTION
			"The distance in hops to the source subnet."
	::= { snDvmrpRouteEntry 6 }

snDvmrpRouteExpiryTime OBJECT-TYPE
	SYNTAX     TimeTicks
	MAX-ACCESS     read-only			  
	STATUS     current
	DESCRIPTION
			"The minimum amount of time remaining before this entry will
			be aged out."
	::= { snDvmrpRouteEntry 7 }

-- The DVMRP Routing Next Hop Table

snDvmrpRouteNextHopTable OBJECT-TYPE
	SYNTAX     SEQUENCE OF SnDvmrpRouteNextHopEntry
	MAX-ACCESS     not-accessible
	STATUS     current
	DESCRIPTION
			"The (conceptual) table containing information on the next
			hops on outgoing interfaces for routing IP multicast
			datagrams. snDvmrpEnable must be 'enabled' before this
			table is read."
	::= { snDvmrpMIBObjects 16 }

snDvmrpRouteNextHopEntry OBJECT-TYPE
	SYNTAX     SnDvmrpRouteNextHopEntry
	MAX-ACCESS     not-accessible
	STATUS     current
	DESCRIPTION
			"An entry (conceptual row) in the list of next hops on
			outgoing interfaces to which IP multicast datagrams from
			particular sources are routed."
	INDEX      { snDvmrpRouteNextHopSource, snDvmrpRouteNextHopSourceMask,
				 snDvmrpRouteNextHopVifIndex }
	::= { snDvmrpRouteNextHopTable 1 }

SnDvmrpRouteNextHopEntry ::= SEQUENCE {
	snDvmrpRouteNextHopSource             IpAddress,
	snDvmrpRouteNextHopSourceMask         IpAddress,
	snDvmrpRouteNextHopVifIndex           Integer32,
	snDvmrpRouteNextHopType               INTEGER }

snDvmrpRouteNextHopSource OBJECT-TYPE
	SYNTAX     IpAddress
	MAX-ACCESS     read-only
	STATUS     current
	DESCRIPTION
			"The network address which when combined with the
			corresponding value of snDvmrpRouteNextHopSourceMask
			identifies the sources for which this entry specifies
			a next hop on an outgoing interface."
	::= { snDvmrpRouteNextHopEntry 1 }

snDvmrpRouteNextHopSourceMask OBJECT-TYPE
	SYNTAX     IpAddress
	MAX-ACCESS     read-only
	STATUS     current
	DESCRIPTION
			"The network mask which when combined with the corresponding
			value of snDvmrpRouteNextHopSource identifies the sources for
			which this entry specifies a next hop on an outgoing
			interface."
	::= { snDvmrpRouteNextHopEntry 2 }

snDvmrpRouteNextHopVifIndex OBJECT-TYPE
	SYNTAX     Integer32
	MAX-ACCESS     read-only
	STATUS     current
	DESCRIPTION
			"The snDvmrpVInterfaceVifIndex value of the virtual interface
			for the outgoing interface for this next hop."
	::= { snDvmrpRouteNextHopEntry 3 }

snDvmrpRouteNextHopType OBJECT-TYPE
	SYNTAX     INTEGER { leaf(1), branch(2) }
	MAX-ACCESS     read-only
	STATUS     current
	DESCRIPTION
			"Type is leaf if no neighbors exist on the outgoing virtual
			interface.  Otherwise, type is branch."
	::= { snDvmrpRouteNextHopEntry 4 }

-- The DVMRP Virtual Interface Statistics Table

snDvmrpVIfStatTable OBJECT-TYPE
	SYNTAX     SEQUENCE OF SnDvmrpVIfStatEntry
	MAX-ACCESS     not-accessible
	STATUS     current
	DESCRIPTION
			"The (conceptual) table listing the router's DVMRP virtual interface
			statistical counters. snDvmrpEnable must be 'enabled' before this
			table is read."
	::= { snDvmrpMIBObjects 17 }

snDvmrpVIfStatEntry OBJECT-TYPE
	SYNTAX     SnDvmrpVIfStatEntry
	MAX-ACCESS     not-accessible
	STATUS     current
	DESCRIPTION
			"An entry (conceptual row) in the snDvmrpVIfStatTable."
	INDEX      { snDvmrpVIfStatVifIndex }
	::= { snDvmrpVIfStatTable 1 }

SnDvmrpVIfStatEntry ::= SEQUENCE {
	snDvmrpVIfStatVifIndex              INTEGER,
	snDvmrpVIfStatInPkts                Counter32,
	snDvmrpVIfStatOutPkts               Counter32,
	snDvmrpVIfStatInOctets              Counter32,
	snDvmrpVIfStatOutOctets             Counter32,
	snDvmrpVIfStatInProbePkts           Counter32,
	snDvmrpVIfStatOutProbePkts          Counter32,
	snDvmrpVIfStatDiscardProbePkts      Counter32,
	snDvmrpVIfStatInRtUpdatePkts        Counter32,
	snDvmrpVIfStatOutRtUpdatePkts       Counter32,
	snDvmrpVIfStatDiscardRtUpdatePkts   Counter32,
	snDvmrpVIfStatInGraftPkts           Counter32,
	snDvmrpVIfStatOutGraftPkts          Counter32,
	snDvmrpVIfStatDiscardGraftPkts      Counter32,
	snDvmrpVIfStatInGraftAckPkts        Counter32,
	snDvmrpVIfStatOutGraftAckPkts       Counter32,
	snDvmrpVIfStatDiscardGraftAckPkts   Counter32,
	snDvmrpVIfStatInPrunePkts           Counter32,
	snDvmrpVIfStatOutPrunePkts          Counter32,
	snDvmrpVIfStatDiscardPrunePkts      Counter32 }

snDvmrpVIfStatVifIndex OBJECT-TYPE
	SYNTAX     INTEGER (1..65535)
	MAX-ACCESS     read-only
	STATUS     current
	DESCRIPTION
			"The ifIndex value of this DVMRP virtual interface."
	::= { snDvmrpVIfStatEntry 1 }

snDvmrpVIfStatInPkts OBJECT-TYPE
	SYNTAX     Counter32
	MAX-ACCESS     read-only
	STATUS     current
	DESCRIPTION
			"The number of packets that have arrived on the DVMRP
			virtual interface."
	::= { snDvmrpVIfStatEntry 2 }

snDvmrpVIfStatOutPkts OBJECT-TYPE
	SYNTAX     Counter32
	MAX-ACCESS     read-only
	STATUS     current
	DESCRIPTION
			"The number of packets that have been sent on the DVMRP
			virtual interface."
	::= { snDvmrpVIfStatEntry 3 }

snDvmrpVIfStatInOctets OBJECT-TYPE
	SYNTAX     Counter32
	MAX-ACCESS     read-only
	STATUS     current
	DESCRIPTION
			"The number of octets that have arrived on the DVMRP
			virtual interface."
	::= { snDvmrpVIfStatEntry 4 }

snDvmrpVIfStatOutOctets OBJECT-TYPE
	SYNTAX     Counter32
	MAX-ACCESS     read-only
	STATUS     current
	DESCRIPTION
			"The number of octets that have been sent on the DVMRP
			virtual interface."
	::= { snDvmrpVIfStatEntry 5 }

snDvmrpVIfStatInProbePkts OBJECT-TYPE
	SYNTAX     Counter32
	MAX-ACCESS     read-only
	STATUS     current
	DESCRIPTION
			"The number of probe packets that have arrived
			on the DVMRP virtual interface."
	::= { snDvmrpVIfStatEntry 6 }

snDvmrpVIfStatOutProbePkts OBJECT-TYPE
	SYNTAX     Counter32
	MAX-ACCESS     read-only
	STATUS     current
	DESCRIPTION
			"The number of probe packets that have been sent
			on the DVMRP virtual interface."
	::= { snDvmrpVIfStatEntry 7 }

snDvmrpVIfStatDiscardProbePkts OBJECT-TYPE
	SYNTAX     Counter32
	MAX-ACCESS     read-only
	STATUS     current
	DESCRIPTION
			"The number of probe packets that have been discarded
			by the DVMRP virtual interface."
	::= { snDvmrpVIfStatEntry 8 }

snDvmrpVIfStatInRtUpdatePkts OBJECT-TYPE
	SYNTAX     Counter32
	MAX-ACCESS     read-only
	STATUS     current
	DESCRIPTION
			"The number of route update packets that have arrived
			on the DVMRP virtual interface."
	::= { snDvmrpVIfStatEntry 9 }

snDvmrpVIfStatOutRtUpdatePkts OBJECT-TYPE
	SYNTAX     Counter32
	MAX-ACCESS     read-only
	STATUS     current
	DESCRIPTION
			"The number of route update packets that have been sent
			on the DVMRP virtual interface."
	::= { snDvmrpVIfStatEntry 10 }

snDvmrpVIfStatDiscardRtUpdatePkts OBJECT-TYPE
	SYNTAX     Counter32
	MAX-ACCESS     read-only
	STATUS     current
	DESCRIPTION
			"The number of route update packets that have been
			discarded by the DVMRP virtual interface."
	::= { snDvmrpVIfStatEntry 11 }

snDvmrpVIfStatInGraftPkts OBJECT-TYPE
	SYNTAX     Counter32
	MAX-ACCESS     read-only
	STATUS     current
	DESCRIPTION
			"The number of graft packets that have arrived
			on the DVMRP virtual interface."
	::= { snDvmrpVIfStatEntry 12 }

snDvmrpVIfStatOutGraftPkts OBJECT-TYPE
	SYNTAX     Counter32
	MAX-ACCESS     read-only
	STATUS     current
	DESCRIPTION
			"The number of graft packets that have been sent
			on the DVMRP virtual interface."
	::= { snDvmrpVIfStatEntry 13 }

snDvmrpVIfStatDiscardGraftPkts OBJECT-TYPE
	SYNTAX     Counter32
	MAX-ACCESS     read-only
	STATUS     current
	DESCRIPTION
			"The number of graft packets that have been discarded
			by the DVMRP virtual interface."
	::= { snDvmrpVIfStatEntry 14 }

snDvmrpVIfStatInGraftAckPkts OBJECT-TYPE
	SYNTAX     Counter32
	MAX-ACCESS     read-only
	STATUS     current
	DESCRIPTION
			"The number of graft acknowledge packets that have arrived
			on the DVMRP virtual interface."
	::= { snDvmrpVIfStatEntry 15 }

snDvmrpVIfStatOutGraftAckPkts OBJECT-TYPE
	SYNTAX     Counter32
	MAX-ACCESS     read-only
	STATUS     current
	DESCRIPTION
			"The number of graft acknowledge packets that have been
			sent on the DVMRP virtual interface."
	::= { snDvmrpVIfStatEntry 16 }

snDvmrpVIfStatDiscardGraftAckPkts OBJECT-TYPE
	SYNTAX     Counter32
	MAX-ACCESS     read-only
	STATUS     current
	DESCRIPTION
			"The number of graft acknowledge packets that have been
			discarded by the DVMRP virtual interface."
	::= { snDvmrpVIfStatEntry 17 }

snDvmrpVIfStatInPrunePkts OBJECT-TYPE
	SYNTAX     Counter32
	MAX-ACCESS     read-only
	STATUS     current
	DESCRIPTION
			"The number of prune packets that have arrived on the DVMRP
			virtual interface."
	::= { snDvmrpVIfStatEntry 18 }

snDvmrpVIfStatOutPrunePkts OBJECT-TYPE
	SYNTAX     Counter32
	MAX-ACCESS     read-only
	STATUS     current
	DESCRIPTION
			"The number of prune packets that have been sent on the DVMRP
			virtual interface."
	::= { snDvmrpVIfStatEntry 19 }

snDvmrpVIfStatDiscardPrunePkts OBJECT-TYPE
	SYNTAX     Counter32
	MAX-ACCESS     read-only
	STATUS     current
	DESCRIPTION
			"The number of prune packets that have been discarded
			by the DVMRP virtual interface."
	::= { snDvmrpVIfStatEntry 20 }


-- FSRP MIB

snFsrpGlobal 	OBJECT IDENTIFIER ::= { snFsrp 1 }
snFsrpIntf 		OBJECT IDENTIFIER ::= { snFsrp 2 }

--  Section 1:	FSRP Global Variables

snFsrpGroupOperMode OBJECT-TYPE
	SYNTAX  INTEGER {
		disabled(0),             
		enabled(1)
		}
	MAX-ACCESS  read-write
	STATUS  current
	DESCRIPTION
		"The FSRP is configured on this system
		 either enabled or disabled and the
		 default is disabled mode.
		 disabled(0)..........disable FSRP   
		 enabled(1)...........activate FSRP"
	::= { snFsrpGlobal 1 }

snFsrpIfStateChangeTrap OBJECT-TYPE
	SYNTAX	INTEGER { disabled(0), enabled(1) }
	MAX-ACCESS	read-write
	STATUS	current
	DESCRIPTION
		"Indicates whether the SNMP agent process is
		permitted to generate FSRP interface state change
		traps."
	DEFVAL { enabled }
	::= { snFsrpGlobal 2 }


--  Section 2: FSRP Interface Configuration Table

--      The FSRP (Foundry Standby Routing Protocol) Interface Table augments 
--		the ifTable with FSRP specific information.


	 snFsrpIfTable OBJECT-TYPE
		 SYNTAX   SEQUENCE OF SnFsrpIfEntry
		 MAX-ACCESS   not-accessible
		 STATUS   current
		 DESCRIPTION
			"The FSRP Interface Table describes the interfaces from
			the viewpoint of FSRP."
		 ::= { snFsrpIntf 1 }

	 snFsrpIfEntry OBJECT-TYPE
		 SYNTAX   SnFsrpIfEntry
		 MAX-ACCESS   not-accessible
		 STATUS   current
		 DESCRIPTION
			"The FSRP Interface Entry describes one interface from
			the viewpoint of FSRP."
		 INDEX { snFsrpIfPort, snFsrpIfIpAddress }
		 ::= { snFsrpIfTable 1 }

	 SnFsrpIfEntry ::=
		 SEQUENCE {
			 snFsrpIfPort
				 Integer32,
			 snFsrpIfIpAddress
				 IpAddress,
			 snFsrpIfVirRtrIpAddr
				 IpAddress,
			 snFsrpIfOtherRtrIpAddr
				 IpAddress,
			 snFsrpIfPreferLevel
				 INTEGER,
			 snFsrpIfTrackPortMask
				 PortMask,
			 snFsrpIfRowStatus 
				 INTEGER,
			 snFsrpIfState
				 INTEGER,
			 snFsrpIfKeepAliveTime 
				 INTEGER,
			 snFsrpIfRouterDeadTime 
				 INTEGER,
			 snFsrpIfChassisTrackPortMask
				 OCTET STRING,
			 snFsrpIfTrackPortList
				 OCTET STRING
		 }


	snFsrpIfPort OBJECT-TYPE
		 SYNTAX   Integer32
		 MAX-ACCESS   read-only
		 STATUS   current
		 DESCRIPTION
			"The physical router port of this FSRP interface."
		 ::= { snFsrpIfEntry 1 }

	 snFsrpIfIpAddress OBJECT-TYPE
		 SYNTAX   IpAddress
		 MAX-ACCESS   read-only
		 STATUS   current
		 DESCRIPTION
			"The IP Address of the physical router port of this
			interface."
		 ::= { snFsrpIfEntry 2 }

	 snFsrpIfVirRtrIpAddr OBJECT-TYPE
		 SYNTAX   IpAddress
		 MAX-ACCESS   read-write
		 STATUS   current
		 DESCRIPTION
			"The IP Address of the Virtual Router for the interface.
			The Virtual Router IP address need to be configured on 
			the interface before Redundant Router Function can operate
			on the interface.  This address has to be same on all the
			routers that going to participate in the Redundant Router
			Function on a given subnet."
		 ::= { snFsrpIfEntry 3 }

	 snFsrpIfOtherRtrIpAddr OBJECT-TYPE
		 SYNTAX   IpAddress
		 MAX-ACCESS   read-write
		 STATUS   current
		 DESCRIPTION
			"The IP Address of the Other Router on this ip subnet
			that operates FSRP and to whom the Keep Alive message
			need to be sent by this router.  This object must be
			configured for FSRP to work correctly"
		 ::= { snFsrpIfEntry 4 }

	 snFsrpIfPreferLevel OBJECT-TYPE
		 SYNTAX   INTEGER (1..255)
		 MAX-ACCESS   read-write
		 STATUS   current
		 DESCRIPTION
			"The higher the number the higher the priority is.
			This parameter decides which router should becomes
			the Active Router for the interface.  A Router with
			higher priority selected to becomes the Active Router."
		 DEFVAL { 100 }
		 ::= { snFsrpIfEntry 5 }

	 snFsrpIfTrackPortMask OBJECT-TYPE
		 SYNTAX   PortMask
		 MAX-ACCESS   read-write
		 STATUS   deprecated
		 DESCRIPTION
			"This object specifies the identity of the physical port 
			whose state is to be monitored.  Each bit is a port of
			the system. Default value is 0.  If this object is configured
			then the Preference Level of this interface will be adjusted
			dynamically depending on the state of the Track Port.
			The interface's Preference Level is reduced by value of 
			Preference Level parameter when the Track Port states first
			changes from UP to DOWN.  When the Track Port next comes up
			the interface's Preference Level is increased by the amount
			specified by the Preference Level.
			The Standalone router FSRP Track port membership (Not used for Chassis Product)"
		 DEFVAL { 0 }
		 ::= { snFsrpIfEntry 6 }

	 snFsrpIfRowStatus OBJECT-TYPE
		 SYNTAX   INTEGER {
					invalid(1),
					valid(2),
					delete(3),
					create(4),
					modify(5)
				  }
		 MAX-ACCESS   read-write
		 STATUS   current
		 DESCRIPTION
			"This object is used to create and
			 delete row in the table and control
			 if they are used. The values
			 that can be written are:
			 delete(3)...deletes the row
			 create(4)...creates a new row
			 modify(5)...modifies an exsisting row

			 If the row exists, then a SET with
			 value of create(4) returns error
			 'badValue'. Deleted rows go away
			 immediately. The following values
			 can be returned on reads:
			 noSuch(0)...no such row
			 invalid(1)...Setting it to 'invalid' has the effect of
						  rendering it inoperative..
			 valid(2)....the row exists and is valid"
		 ::= { snFsrpIfEntry 7 }

	 snFsrpIfState OBJECT-TYPE
		 SYNTAX   INTEGER {
					init(0),
					negotiating(1),
					standby(2),
					active(3)
				  }
		 MAX-ACCESS   read-only
		 STATUS   current
		 DESCRIPTION
			"This object specifies the FSRP Router's interface state as:
			init(0)...initialization state.
			negotiating(1)...negotiating state.
			standby(2)...standby state.
			active(3)...active state." 
		 ::= { snFsrpIfEntry 8 }

	 snFsrpIfKeepAliveTime OBJECT-TYPE
		 SYNTAX   INTEGER (1..120)
		 MAX-ACCESS   read-write
		 STATUS   current
		 DESCRIPTION
			"The heart-beat is from 1 to 120 seconds." 
		 DEFVAL { 3 }
		 ::= { snFsrpIfEntry 9 }

	 snFsrpIfRouterDeadTime OBJECT-TYPE
		 SYNTAX   INTEGER (3..255)
		 MAX-ACCESS   read-write
		 STATUS   current
		 DESCRIPTION
			"The hold time of the Fsrp router is from 3 to 255 seconds." 
		 DEFVAL { 9 }
		 ::= { snFsrpIfEntry 10 }

	 snFsrpIfChassisTrackPortMask OBJECT-TYPE
		 SYNTAX  OCTET STRING (SIZE(32))
		 MAX-ACCESS   read-write
		 STATUS   deprecated
		 DESCRIPTION
			"This object specifies the identity of the physical port 
			whose state is to be monitored.  Each bit is a port of
			the system. Default value is 0.  If this object is configured
			then the Preference Level of this interface will be adjusted
			dynamically depending on the state of the Track Port.
			The interface's Preference Level is reduced by value of 
			Preference Level parameter when the Track Port states first
			changes from UP to DOWN.  When the Track Port next comes up
			the interface's Preference Level is increased by the amount
			specified by the Preference Level.
			The Chassis router FSRP Track port membership.
			(It was obsoleted after release 07100, replaced by snFsrpIfTrackPortList)"
		 ::= { snFsrpIfEntry 11 }

	 snFsrpIfTrackPortList OBJECT-TYPE
		 SYNTAX  OCTET STRING
		 MAX-ACCESS   read-write
		 STATUS   current
		 DESCRIPTION
			"This object specifies the identity of the physical port 
			whose state is to be monitored.  Each port index is a
			16-bit integer in big endian order. 8-bit is the slot
			number, the other 8-bit is the port number. Default value
			is 0 length octet string.  If this object is configured
			then the Preference Level of this interface will be adjusted
			dynamically depending on the state of the Track Port.
			The interface's Preference Level is reduced by value of 
			Preference Level parameter when the Track Port states first
			changes from UP to DOWN.  When the Track Port next comes up
			the interface's Preference Level is increased by the amount
			specified by the Preference Level.
			The router FSRP physical track port membership."
		 ::= { snFsrpIfEntry 12 }

-- PIM MIB

snPimMIBObjects OBJECT IDENTIFIER ::= { snPim 1 }
snPimSMMIBObjects OBJECT IDENTIFIER ::= { snPim 2 }

snPimEnable OBJECT-TYPE
	SYNTAX     RtrStatus
	MAX-ACCESS     read-write
	STATUS     current
	DESCRIPTION
			"Enable or disable PIM on this router."
	DEFVAL     { disabled }
	::= { snPimMIBObjects 1 }

snPimNeighborRouterTimeout OBJECT-TYPE
	SYNTAX     INTEGER (60..8000)
	MAX-ACCESS     read-write
	STATUS     current
	DESCRIPTION
			"This is the time interval after which the neighbour router
			is considered down. Value is in number of seconds. snPimEnable
			must be 'enabled' before this object is writen."
	DEFVAL     { 180 }
	::= { snPimMIBObjects 2 }

snPimHelloTime OBJECT-TYPE
	SYNTAX     INTEGER (10..3600)
	MAX-ACCESS     read-write
	STATUS     current
	DESCRIPTION
			"This is the interval at which hello message is sent out
			an interface to the neighbouring router. This is used to
			detect the presence or abscense of a neighbouring router.
			Value is in number of seconds. snPimEnable must be 'enabled'
			before this object is writen."
	DEFVAL     { 60 }
	::= { snPimMIBObjects 3 }

snPimPruneTime OBJECT-TYPE
	SYNTAX     INTEGER (10..3600)
	MAX-ACCESS     read-write
	STATUS     current
	DESCRIPTION
			"This is the duration of time for which the prune state
			is stored. Value is in number of seconds. snPimEnable
			must be 'enabled' before this object is writen.
			For FastIron platforms, the default value is 180."
	DEFVAL     { 60 }
	::= { snPimMIBObjects 4 }

snPimGraftRetransmitTime OBJECT-TYPE
	SYNTAX     INTEGER (2..3600)
	MAX-ACCESS     read-write
	STATUS     current
	DESCRIPTION
			"This is the time interval after which a graft message will
			be retransmitted if graft acknowledge message has not been
			received. Value is in number of seconds. snPimEnable must
			be 'enabled' before this object is writen.
			For FastIron platforms, the default value is 3 and the range is 
			between 2 to 10."
	DEFVAL     { 180 }
	::= { snPimMIBObjects 5 }

snPimInactivityTime OBJECT-TYPE
	SYNTAX     INTEGER (10..3600)
	MAX-ACCESS     read-write
	STATUS     current
	DESCRIPTION
			"This is the interval after which the forwarding entry is
			deleted. When a packet is received for a group entry, this
			time is reset. This is used to only keep the forwarding
			entries for the active sessions. Value is in number of
			seconds. snPimEnable must be 'enabled' before this object
			is writen."
	DEFVAL     { 180 }
	::= { snPimMIBObjects 6 }

-- The PIM Virtual Interface Table

snPimVInterfaceTable OBJECT-TYPE
	SYNTAX     SEQUENCE OF SnPimVInterfaceEntry
	MAX-ACCESS     not-accessible
	STATUS     current
	DESCRIPTION
			"The (conceptual) table listing the router's PIM virtual
			interfaces. snPimEnable must be 'enabled' before this
			table is read or writen."
	::= { snPimMIBObjects 7 }

snPimVInterfaceEntry OBJECT-TYPE
	SYNTAX     SnPimVInterfaceEntry
	MAX-ACCESS     not-accessible
	STATUS     current
	DESCRIPTION
			"An entry (conceptual row) in the snPimVInterfaceTable."
	INDEX      { snPimVInterfaceVifIndex }
	::= { snPimVInterfaceTable 1 }

SnPimVInterfaceEntry ::= SEQUENCE {
	snPimVInterfaceVifIndex              INTEGER,
	snPimVInterfaceType                  INTEGER,
	snPimVInterfaceLocalAddress          IpAddress,
	snPimVInterfaceLocalSubnetMask       IpAddress,
	snPimVInterfaceRemoteAddress         IpAddress,
	snPimVInterfaceDR                    IpAddress,
	snPimVInterfaceTtlThreshold          INTEGER,
	snPimVInterfaceStatus                INTEGER,
	snPimVInterfaceMode                  INTEGER }

snPimVInterfaceVifIndex OBJECT-TYPE
	SYNTAX     INTEGER (1..48)
	MAX-ACCESS     read-only
	STATUS     current
	DESCRIPTION
			"The ifIndex value of this PIM virtual interface."
	::= { snPimVInterfaceEntry 1 }

snPimVInterfaceType OBJECT-TYPE
	SYNTAX     INTEGER { tunnel(1), subnet(2) }
	MAX-ACCESS     read-write
	STATUS     current
	DESCRIPTION
			"The type of PIM virtual interface, whether it uses
			a tunnel or a physical interface."
	::= { snPimVInterfaceEntry 2 }

snPimVInterfaceLocalAddress OBJECT-TYPE
	SYNTAX     IpAddress
	MAX-ACCESS     read-write
	STATUS     current
	DESCRIPTION
			"The IP address of the local end of this PIM virtual
			interface."
	::= { snPimVInterfaceEntry 3 }

snPimVInterfaceLocalSubnetMask OBJECT-TYPE
	SYNTAX     IpAddress
	MAX-ACCESS     read-only
	STATUS     current
	DESCRIPTION
			"The network mask for the IP address of the PIM
			virtual interface. For a tunnel, this should be
			0.0.0.0."
	::= { snPimVInterfaceEntry 4 }

snPimVInterfaceRemoteAddress OBJECT-TYPE
	SYNTAX     IpAddress
	MAX-ACCESS     read-write
	STATUS     current
	DESCRIPTION
			"The IP address of the remote end of this PIM virtual
			interface."
	::= { snPimVInterfaceEntry 5 }

snPimVInterfaceDR OBJECT-TYPE
	SYNTAX     IpAddress
	MAX-ACCESS     read-only
	STATUS     current
	DESCRIPTION
			"The Designated Router on this PIM virtual interface.
			For point-to-point interfaces, this object has the
			value 0.0.0.0."
	::= { snPimVInterfaceEntry 6 }

snPimVInterfaceTtlThreshold OBJECT-TYPE
	SYNTAX     INTEGER (1..31)
	MAX-ACCESS     read-write
	STATUS     current
	DESCRIPTION
			"This is the minimum time-to-live value to forward the packets
			out of this interface."
	DEFVAL     { 1 }
	::= { snPimVInterfaceEntry 7 }

snPimVInterfaceStatus OBJECT-TYPE
	SYNTAX     INTEGER {
					invalid(1),
					valid(2),
					delete(3),
					create(4),
					modify(5)
			   }
	MAX-ACCESS     read-write
	STATUS     current
	DESCRIPTION
			"This object is used to create and
			 delete row in the table and control
			 if they are used. The values
			 that can be written are:
			 delete(3)...deletes the row
			 create(4)...creates a new row
			 modify(5)...modifies an exsisting row

			 If the row exists, then a SET with
			 value of create(4) returns error
			 'badValue'. Deleted rows go away
			 immediately. The following values
			 can be returned on reads:
			 invalid(1)...Setting it to 'invalid' has the effect of
						  rendering it inoperative.
			 valid(2)....Setting it to 'valid' has the effect of
						 changing the row to operative."
	::= { snPimVInterfaceEntry 8 }

snPimVInterfaceMode OBJECT-TYPE
	SYNTAX     INTEGER { dense(1), sparse(2) }
	MAX-ACCESS     read-write
	STATUS     current
	DESCRIPTION
			"The configured mode of this PIM interface."
	DEFVAL     { dense }
	::= { snPimVInterfaceEntry 9 }

-- The PIM Neighbor Table

snPimNeighborTable OBJECT-TYPE
	SYNTAX     SEQUENCE OF SnPimNeighborEntry
	MAX-ACCESS     not-accessible
	STATUS     current
	DESCRIPTION
			"The (conceptual) table listing the router's PIM
			neighbors. snPimEnable must be 'enabled' before this
			table is read."
	::= { snPimMIBObjects 8 }

snPimNeighborEntry OBJECT-TYPE
	SYNTAX     SnPimNeighborEntry
	MAX-ACCESS     not-accessible
	STATUS     current
	DESCRIPTION
			"An entry (conceptual row) in the snPimNeighborTable."
	INDEX      { snPimNeighborEntryIndex }
	::= { snPimNeighborTable 1 }

SnPimNeighborEntry ::= SEQUENCE {
	snPimNeighborEntryIndex      Integer32,
	snPimNeighborVifIndex        Integer32,
	snPimNeighborAddress         IpAddress,
	snPimNeighborUpTime          TimeTicks,
	snPimNeighborExpiryTime      TimeTicks }

snPimNeighborEntryIndex OBJECT-TYPE
	SYNTAX     Integer32
	MAX-ACCESS     read-only
	STATUS     current
	DESCRIPTION
			"The table entry index."
	::= { snPimNeighborEntry 1 }

snPimNeighborVifIndex OBJECT-TYPE
	SYNTAX Integer32
	MAX-ACCESS     read-only
	STATUS     current
	DESCRIPTION
			"The value of VifIndex for the virtual interface used to
			reach this PIM neighbor."
	::= { snPimNeighborEntry 2 }

snPimNeighborAddress OBJECT-TYPE
	SYNTAX     IpAddress
	MAX-ACCESS     read-only
	STATUS     current
	DESCRIPTION
			"The IP address of the PIM neighbor for which this entry
			contains information."
	::= { snPimNeighborEntry 3 }

snPimNeighborUpTime OBJECT-TYPE
	SYNTAX     TimeTicks
	MAX-ACCESS     read-only
	STATUS     current
	DESCRIPTION
			"The time since this PIM neighbor (last) became a neighbor
			of the local router."
	::= { snPimNeighborEntry 4 }

snPimNeighborExpiryTime OBJECT-TYPE
	SYNTAX     TimeTicks
	MAX-ACCESS     read-only
	STATUS     current
	DESCRIPTION
			"The minimum time remaining before this PIM neighbor will
			be aged out."
	::= { snPimNeighborEntry 5 }

-- The PIM Virtual Interface Statistics Table

snPimVIfStatTable OBJECT-TYPE
	SYNTAX     SEQUENCE OF SnPimVIfStatEntry
	MAX-ACCESS     not-accessible
	STATUS     current
	DESCRIPTION
			"The (conceptual) table listing the router's PIM virtual
			interface statistical counters. snPimEnable must be
			'enabled' before this table is read."
	::= { snPimMIBObjects 9 }

snPimVIfStatEntry OBJECT-TYPE
	SYNTAX     SnPimVIfStatEntry
	MAX-ACCESS     not-accessible
	STATUS     current
	DESCRIPTION
			"An entry (conceptual row) in the snPimVIfStatTable."
	INDEX      { snPimVIfStatVifIndex }
	::= { snPimVIfStatTable 1 }

SnPimVIfStatEntry ::= SEQUENCE {
	snPimVIfStatVifIndex              INTEGER,
	snPimVIfStatInJoinPkts            Counter32,
	snPimVIfStatOutJoinPkts           Counter32,
	snPimVIfStatDiscardJoinPkts       Counter32,
	snPimVIfStatInPrunePkts           Counter32,
	snPimVIfStatOutPrunePkts          Counter32,
	snPimVIfStatDiscardPrunePkts      Counter32,
	snPimVIfStatInAssertPkts          Counter32,
	snPimVIfStatOutAssertPkts         Counter32,
	snPimVIfStatDiscardAssertPkts     Counter32,
	snPimVIfStatInHelloPkts           Counter32,
	snPimVIfStatOutHelloPkts          Counter32,
	snPimVIfStatDiscardHelloPkts      Counter32,
	snPimVIfStatInGraftPkts           Counter32,
	snPimVIfStatOutGraftPkts          Counter32,
	snPimVIfStatDiscardGraftPkts      Counter32,
	snPimVIfStatInGraftAckPkts        Counter32,
	snPimVIfStatOutGraftAckPkts       Counter32,
	snPimVIfStatDiscardGraftAckPkts   Counter32 }

snPimVIfStatVifIndex OBJECT-TYPE
	SYNTAX     INTEGER (1..32)
	MAX-ACCESS     read-only
	STATUS     current
	DESCRIPTION
			"The ifIndex value of this PIM virtual interface."
	::= { snPimVIfStatEntry 1 }

snPimVIfStatInJoinPkts OBJECT-TYPE
	SYNTAX     Counter32
	MAX-ACCESS     read-only
	STATUS     current
	DESCRIPTION
			"The number of join packets that have arrived
			on the PIM virtual interface."
	::= { snPimVIfStatEntry 2 }

snPimVIfStatOutJoinPkts OBJECT-TYPE
	SYNTAX     Counter32
	MAX-ACCESS     read-only
	STATUS     current
	DESCRIPTION
			"The number of join packets that have been sent
			on the PIM virtual interface."
	::= { snPimVIfStatEntry 3 }

snPimVIfStatDiscardJoinPkts OBJECT-TYPE
	SYNTAX     Counter32
	MAX-ACCESS     read-only
	STATUS     current
	DESCRIPTION
			"The number of join packets that have been discarded
			by the PIM virtual interface."
	::= { snPimVIfStatEntry 4 }

snPimVIfStatInPrunePkts OBJECT-TYPE
	SYNTAX     Counter32
	MAX-ACCESS     read-only
	STATUS     current
	DESCRIPTION
			"The number of prune packets that have arrived on the PIM
			virtual interface."
	::= { snPimVIfStatEntry 5 }

snPimVIfStatOutPrunePkts OBJECT-TYPE
	SYNTAX     Counter32
	MAX-ACCESS     read-only
	STATUS     current
	DESCRIPTION
			"The number of prune packets that have been sent on the PIM
			virtual interface."
	::= { snPimVIfStatEntry 6 }

snPimVIfStatDiscardPrunePkts OBJECT-TYPE
	SYNTAX     Counter32
	MAX-ACCESS     read-only
	STATUS     current
	DESCRIPTION
			"The number of prune packets that have been discarded
			by the PIM virtual interface."
	::= { snPimVIfStatEntry 7 }

snPimVIfStatInAssertPkts OBJECT-TYPE
	SYNTAX     Counter32
	MAX-ACCESS     read-only
	STATUS     current
	DESCRIPTION
			"The number of assert packets that have arrived
			on the PIM virtual interface."
	::= { snPimVIfStatEntry 8 }

snPimVIfStatOutAssertPkts OBJECT-TYPE
	SYNTAX     Counter32
	MAX-ACCESS     read-only
	STATUS     current
	DESCRIPTION
			"The number of assert packets that have been sent
			on the PIM virtual interface."
	::= { snPimVIfStatEntry 9 }

snPimVIfStatDiscardAssertPkts OBJECT-TYPE
	SYNTAX     Counter32
	MAX-ACCESS     read-only
	STATUS     current
	DESCRIPTION
			"The number of assert packets that have been
			discarded by the PIM virtual interface."
	::= { snPimVIfStatEntry 10 }

snPimVIfStatInHelloPkts OBJECT-TYPE
	SYNTAX     Counter32
	MAX-ACCESS     read-only
	STATUS     current
	DESCRIPTION
			"The number of hello packets that have arrived on the PIM
			virtual interface."
	::= { snPimVIfStatEntry 11 }

snPimVIfStatOutHelloPkts OBJECT-TYPE
	SYNTAX     Counter32
	MAX-ACCESS     read-only
	STATUS     current
	DESCRIPTION
			"The number of hello packets that have been sent on the PIM
			virtual interface."
	::= { snPimVIfStatEntry 12 }

snPimVIfStatDiscardHelloPkts OBJECT-TYPE
	SYNTAX     Counter32
	MAX-ACCESS     read-only
	STATUS     current
	DESCRIPTION
			"The number of hello packets that have been discarded
			by the PIM virtual interface."
	::= { snPimVIfStatEntry 13 }

snPimVIfStatInGraftPkts OBJECT-TYPE
	SYNTAX     Counter32
	MAX-ACCESS     read-only
	STATUS     current
	DESCRIPTION
			"The number of graft packets that have arrived
			on the PIM virtual interface."
	::= { snPimVIfStatEntry 14 }

snPimVIfStatOutGraftPkts OBJECT-TYPE
	SYNTAX     Counter32
	MAX-ACCESS     read-only
	STATUS     current
	DESCRIPTION
			"The number of graft packets that have been sent
			on the PIM virtual interface."
	::= { snPimVIfStatEntry 15 }

snPimVIfStatDiscardGraftPkts OBJECT-TYPE
	SYNTAX     Counter32
	MAX-ACCESS     read-only
	STATUS     current
	DESCRIPTION
			"The number of graft packets that have been discarded
			by the PIM virtual interface."
	::= { snPimVIfStatEntry 16 }

snPimVIfStatInGraftAckPkts OBJECT-TYPE
	SYNTAX     Counter32
	MAX-ACCESS     read-only
	STATUS     current
	DESCRIPTION
			"The number of graft acknowledge packets that have arrived
			on the PIM virtual interface."
	::= { snPimVIfStatEntry 17 }

snPimVIfStatOutGraftAckPkts OBJECT-TYPE
	SYNTAX     Counter32
	MAX-ACCESS     read-only
	STATUS     current
	DESCRIPTION
			"The number of graft acknowledge packets that have been
			sent on the PIM virtual interface."
	::= { snPimVIfStatEntry 18 }

snPimVIfStatDiscardGraftAckPkts OBJECT-TYPE
	SYNTAX     Counter32
	MAX-ACCESS     read-only
	STATUS     current
	DESCRIPTION
			"The number of graft acknowledge packets that have been
			discarded by the PIM virtual interface."
	::= { snPimVIfStatEntry 19 }


-- PIM-SM MIB

snPimJoinPruneInterval OBJECT-TYPE
	SYNTAX     INTEGER (10..3600)
	MAX-ACCESS     read-write
	STATUS     current
	DESCRIPTION
			"The default interval in seconds at which periodic 
			PIM-SM Join/Prune messages are to be sent. snPimEnable must 
			be 'enabled' before this table is read or writen."
	::= { snPimSMMIBObjects 1 }

-- PIM Candidate-BSR Table

snPimCandidateBSRTable OBJECT-TYPE
	SYNTAX     SEQUENCE OF SnPimCandidateBSR
	MAX-ACCESS     not-accessible
	STATUS     current
	DESCRIPTION
			"Candidate Bootstrap Router information."
	::= { snPimSMMIBObjects 2 }

snPimCandidateBSREntry OBJECT-TYPE
	SYNTAX     SnPimCandidateBSR
	MAX-ACCESS     not-accessible
	STATUS     current
	DESCRIPTION
			"An entry (conceptual row) in the snPimCandidateBSRTable."
	INDEX      { snPimCandidateBSRPortID }
	::= { snPimCandidateBSRTable 1 }

SnPimCandidateBSR ::= SEQUENCE {
	snPimCandidateBSRPortID        Integer32,
	snPimCandidateBSRIPAddress     IpAddress,
	snPimCandidateBSRHashMaskLen   INTEGER,
	snPimCandidateBSRPreference    INTEGER
}

snPimCandidateBSRPortID OBJECT-TYPE
	SYNTAX     Integer32
	MAX-ACCESS     read-write
	STATUS     current
	DESCRIPTION
			"The IP address of the PIM interface.
		 The bit 0 to bit 7: port number. 
		 The bit 8 to bit 11: slot number."
	::= { snPimCandidateBSREntry 1 }

snPimCandidateBSRIPAddress OBJECT-TYPE
	SYNTAX     IpAddress
	MAX-ACCESS     read-only
	STATUS     current
	DESCRIPTION
			"The (unicast) address of the Candidate BSR."
	::= { snPimCandidateBSREntry 2 }

snPimCandidateBSRHashMaskLen OBJECT-TYPE
	SYNTAX     INTEGER (1..32)
	MAX-ACCESS     read-write
	STATUS     current
	DESCRIPTION
			"The hash mask value for this router as a candidate
			bootstrap router."
	::= { snPimCandidateBSREntry 3 }

snPimCandidateBSRPreference OBJECT-TYPE
	SYNTAX     INTEGER (0..255)
	MAX-ACCESS     read-write
	STATUS     current
	DESCRIPTION
			"The preference value for this router as a candidate
			bootstrap router."
	DEFVAL     { 100 }
	::= { snPimCandidateBSREntry 4 }



-- The PIM RP-Set Table

snPimRPSetTable OBJECT-TYPE
	SYNTAX     SEQUENCE OF SnPimRPSetEntry
	MAX-ACCESS     not-accessible
	STATUS     current
	DESCRIPTION
			"The (conceptual) table listing PIM information for
			candidate Rendezvous Points (RPs) for IP multicast groups.
			When the local router is the BSR, this information is
			obtained from received Candidate-RP-Advertisements.  When
			the local router is not the BSR, this information is
			obtained from received RP-Set messages.
			 snPimEnable must be 'enabled' before this
			table is read or writen."
	::= { snPimSMMIBObjects 3 }

snPimRPSetEntry OBJECT-TYPE
	SYNTAX     SnPimRPSetEntry
	MAX-ACCESS     not-accessible
	STATUS     current
	DESCRIPTION
			"An entry (conceptual row) in the snPimRPSetTable."
	INDEX    { snPimRPSetGroupAddress, snPimRPSetMask, snPimRPSetIPAddress }
	::= { snPimRPSetTable 1 }

SnPimRPSetEntry ::= SEQUENCE {
	snPimRPSetGroupAddress    IpAddress,
	snPimRPSetMask            IpAddress,
	snPimRPSetIPAddress       IpAddress,
	snPimRPSetHoldTime        INTEGER
}

snPimRPSetGroupAddress OBJECT-TYPE
	SYNTAX     IpAddress
	MAX-ACCESS     read-only
	STATUS     current
	DESCRIPTION
			"The IP multicast group address which, when combined with
			snPimRPSetGroupMask, gives the group prefix for which this
			entry contains information about the Candidate-RP."
	::= { snPimRPSetEntry 1 }

snPimRPSetMask OBJECT-TYPE
	SYNTAX     IpAddress
	MAX-ACCESS     read-only
	STATUS     current
	DESCRIPTION
			"The multicast group address mask which, when combined with
			snPimRPSetGroupAddress, gives the group prefix for which this
			entry contains information about the Candidate-RP."
	::= { snPimRPSetEntry 2 }

snPimRPSetIPAddress OBJECT-TYPE
	SYNTAX     IpAddress
	MAX-ACCESS     read-only
	STATUS     current
	DESCRIPTION
			"The IP address of the Candidate-RP."
	::= { snPimRPSetEntry 3 }

snPimRPSetHoldTime OBJECT-TYPE
	SYNTAX     INTEGER (0..255)
	MAX-ACCESS     read-only
	STATUS     current
	DESCRIPTION
			"The holdtime, in seconds, of a Candidate-RP.  If the 
			local router is not the BSR, this value is 0."
	::= { snPimRPSetEntry 4 }


-- The PIM Candidate-RP Table

snPimCandidateRPTable OBJECT-TYPE
	SYNTAX     SEQUENCE OF SnPimCandidateRPEntry
	MAX-ACCESS     not-accessible
	STATUS     current
	DESCRIPTION
			"The (conceptual) table listing the IP multicast groups for
			which the local router is to advertise itself as a
			Candidate-RP. If this table is empty, then the local router
			will advertise itself as a Candidate-RP for all groups
			 snPimEnable must be 'enabled' before this
			table is read or writen."
	::= { snPimSMMIBObjects 4 }

snPimCandidateRPEntry OBJECT-TYPE
	SYNTAX     SnPimCandidateRPEntry
	MAX-ACCESS     not-accessible
	STATUS     current
	DESCRIPTION
			"An entry (conceptual row) in the snPimCandidateRPTable."
	INDEX      { snPimCandidateRPGroupAddress,
				 snPimCandidateRPMask }
	::= { snPimCandidateRPTable 1 }

SnPimCandidateRPEntry ::= SEQUENCE {
	snPimCandidateRPGroupAddress    IpAddress,
	snPimCandidateRPMask            IpAddress,
	snPimCandidateRPIPAddress       IpAddress,
	snPimCandidateRPRowStatus       INTEGER
}

snPimCandidateRPGroupAddress OBJECT-TYPE
	SYNTAX     IpAddress
	MAX-ACCESS     read-only
	STATUS     current
	DESCRIPTION
			"The IP multicast group address which, when combined with
			snPimCandidateRPGroupMask, identifies a group prefix for which
			the local router will advertise itself as a Candidate-RP."
	::= { snPimCandidateRPEntry 1 }

snPimCandidateRPMask OBJECT-TYPE
	SYNTAX     IpAddress
	MAX-ACCESS     read-only
	STATUS     current
	DESCRIPTION
			"The multicast group address mask which, when combined with
			snPimCandidateRPGroupMask, identifies a group prefix for which
			the local router will advertise itself as a Candidate-RP."
	::= { snPimCandidateRPEntry 2 }

snPimCandidateRPIPAddress OBJECT-TYPE
	SYNTAX     IpAddress
	MAX-ACCESS     read-write
	STATUS     current
	DESCRIPTION
			"The (unicast) address of the interface which will be
			advertised as a Candidate-RP."
	::= { snPimCandidateRPEntry 3 }

snPimCandidateRPRowStatus OBJECT-TYPE
	SYNTAX	INTEGER {
		noSuch(0),
		other(1),
		valid(2),
		delete(3),
		create(4),
		modify(5)
		}
	MAX-ACCESS     read-write
	STATUS     current
	DESCRIPTION
			"The status of this row, by which new entries may be
			created, or old entries deleted from this table.
			  This object is used to create and delete row in the 
			table and control if they are used. The values that 
			can be written are:
			  delete(3)...deletes the row
			  create(4)...creates a new row
			  modify(5)...modifies an exsisting row
			If the row exists, then a SET with value of create(4) 
			returns error 'badValue'. Deleted rows go away
			immediately. The following values can be returned on reads:
			  noSuch(0)...no such row
			  other(1)....some other case
			  valid(2)....the row exists and is valid"			
	::= { snPimCandidateRPEntry 4 }


-- Loopback Interface configuration table

snLoopbackIntfConfigTable           OBJECT-TYPE
	SYNTAX  SEQUENCE OF SnLoopbackIntfConfigEntry
	MAX-ACCESS  not-accessible
	STATUS  current
	DESCRIPTION
		"Loopback Interface Config table."
	::= { snLoopbackIf 1 }

snLoopbackIntfConfigEntry           OBJECT-TYPE
	SYNTAX  SnLoopbackIntfConfigEntry
	MAX-ACCESS  not-accessible
	STATUS  current
	DESCRIPTION
		"An entry in the Loopback Interface Config table."
	INDEX   { snLoopbackIntfConfigPortIndex }
	::= { snLoopbackIntfConfigTable 1 }

SnLoopbackIntfConfigEntry ::= SEQUENCE {
	snLoopbackIntfConfigPortIndex
		INTEGER,
	snLoopbackIntfMode		
		INTEGER,
	snLoopbackIntfRowStatus
		INTEGER
	}

snLoopbackIntfConfigPortIndex       OBJECT-TYPE
	SYNTAX  INTEGER (1..8)
	MAX-ACCESS  read-only
	STATUS  current
	DESCRIPTION
		"The port index for Loopback Interface config entry."
	::= { snLoopbackIntfConfigEntry 1 }

snLoopbackIntfMode                   OBJECT-TYPE
	SYNTAX  INTEGER { disabled(0), enabled(1) }
	MAX-ACCESS  read-write
	STATUS  current
	DESCRIPTION
		"The Loopback Interface mode."
	::= { snLoopbackIntfConfigEntry 2 }

snLoopbackIntfRowStatus   			OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snLoopbackIntfConfigEntry 3 }
END
FOUNDRY-SN-IGMP-MIB DEFINITIONS ::= BEGIN

IMPORTS
	MODULE-IDENTITY, OBJECT-TYPE,IpAddress,Integer32
		FROM SNMPv2-SMI
	router
		FROM FOUNDRY-SN-ROOT-MIB
		;
		
snIgmp MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"            
	REVISION     "200909300000Z" -- September 30, 2009
	DESCRIPTION
			""
   ::= { router 6}


-- SECTION 2: MIB 

-- IGMP MIB

snIgmpMIBObjects OBJECT IDENTIFIER ::= { snIgmp 1 }

snIgmpQueryInterval OBJECT-TYPE
	SYNTAX     INTEGER (0..3600)
	MAX-ACCESS     read-write
	STATUS     current
	DESCRIPTION
			"This is the time interval at which this entity sends out
			IGMP host query packets. For a router, snDvmrpEnable must
			have been set to 'enabled' before this object is writen.
			For a switch, snSwGroupIpMcastMode must have been set to
			'enabled' and snSwIpMcastQuerierMode must have been set
			to 'querier' before this object is writen.
			Value 0 cannot be used for SET operations. This value
			is returned if IGMP is not configured within the system.
			For FI platform the configurable range for this object is 
			10 .. 3600"
	DEFVAL     { 60 }
	::= { snIgmpMIBObjects 1 }

snIgmpGroupMembershipTime OBJECT-TYPE
	SYNTAX     INTEGER (0..7200)
	MAX-ACCESS     read-write
	STATUS     current
	DESCRIPTION
			"This is the time interval after which a group is considered
			inactive. For a router, snDvmrpEnable must have been set to
			'enabled' before this object is writen. For a switch,
			snSwGroupIpMcastMode must have been set to 'enabled' before
			this object is writen.
			Value 0 cannot be used for SET operations. This value
			is returned if IGMP is not configured within the system.
			For FI platform the configurable range for this object is 
			20 .. 7200"
	DEFVAL     { 140 }
	::= { snIgmpMIBObjects 2 }

-- The IGMP Interface Table

snIgmpIfTable OBJECT-TYPE
	SYNTAX     SEQUENCE OF SnIgmpIfEntry
	MAX-ACCESS     not-accessible
	STATUS     current
	DESCRIPTION
			"This table comprises of a list of IGMP interface entries."
	::= { snIgmpMIBObjects 3 }

snIgmpIfEntry OBJECT-TYPE
	SYNTAX     SnIgmpIfEntry
	MAX-ACCESS     not-accessible
	STATUS     current
	DESCRIPTION
			"An entry (conceptual row) contains the group
			membership information for that port."
	INDEX      { snIgmpIfEntryIndex }
	::= { snIgmpIfTable 1 }

SnIgmpIfEntry ::= SEQUENCE {
	snIgmpIfEntryIndex         Integer32,
	snIgmpIfPortNumber         Integer32,
	snIgmpIfGroupAddress       IpAddress,
	snIgmpIfGroupAge           Integer32 }

snIgmpIfEntryIndex OBJECT-TYPE
	SYNTAX     Integer32
	MAX-ACCESS     read-only
	STATUS     current
	DESCRIPTION
			"The table entry index."
	::= { snIgmpIfEntry 1 }

snIgmpIfPortNumber OBJECT-TYPE
	SYNTAX     Integer32
	MAX-ACCESS     read-only
	STATUS     current
	DESCRIPTION
			"This is the interface on which the group was learnt."
	::= { snIgmpIfEntry 2 }

snIgmpIfGroupAddress OBJECT-TYPE
	SYNTAX     IpAddress
	MAX-ACCESS     read-only
	STATUS     current
	DESCRIPTION
			"The group address learnt from the interface."
	::= { snIgmpIfEntry 3 }

snIgmpIfGroupAge OBJECT-TYPE
	SYNTAX     Integer32
	MAX-ACCESS     read-only
	STATUS     current
	DESCRIPTION
			"This is the interval (seconds) after which the group
			information will be aged out."
	::= { snIgmpIfEntry 4 }

-- The IGMP Static Group Table

snIgmpStaticGroupTable OBJECT-TYPE
	SYNTAX     SEQUENCE OF SnIgmpStaticGroupEntry
	MAX-ACCESS     not-accessible
	STATUS     current
	DESCRIPTION
			"This table comprises of a list of IGMP static group entries."
	::= { snIgmpMIBObjects 4 }

snIgmpStaticGroupEntry OBJECT-TYPE
	SYNTAX     SnIgmpStaticGroupEntry
	MAX-ACCESS     not-accessible
	STATUS     current
	DESCRIPTION
			"An entry (conceptual row) contains the IGMP static group
			membership information."
	INDEX      { snIgmpStaticGroupIfIndex, snIgmpStaticGroupAddress }
	::= { snIgmpStaticGroupTable 1 }

SnIgmpStaticGroupEntry ::= SEQUENCE {
	snIgmpStaticGroupIfIndex    Integer32,
	snIgmpStaticGroupAddress    IpAddress,
	snIgmpStaticGroupPortList   OCTET STRING,
	snIgmpStaticGroupRowStatus  INTEGER }

snIgmpStaticGroupIfIndex OBJECT-TYPE
	SYNTAX     Integer32
	MAX-ACCESS     read-only
	STATUS     current
	DESCRIPTION
			"The interface of which the static group was configured."
	::= { snIgmpStaticGroupEntry 1 }

snIgmpStaticGroupAddress OBJECT-TYPE
	SYNTAX     IpAddress
	MAX-ACCESS     read-only
	STATUS     current
	DESCRIPTION
			"The group address of which the static group was configured."
	::= { snIgmpStaticGroupEntry 2 }

snIgmpStaticGroupPortList OBJECT-TYPE
	SYNTAX     OCTET STRING
	MAX-ACCESS     read-write
	STATUS     current
	DESCRIPTION
			"A list of ports which are the port membership of the
			static group. Each port is a 16-bit integer ifIndex."
	::= { snIgmpStaticGroupEntry 3 }

snIgmpStaticGroupRowStatus OBJECT-TYPE
	SYNTAX     INTEGER {
				 other(1),
				 valid(2),
				 delete(3),
				 create(4),
				 modify(5) }
	MAX-ACCESS     read-write
	STATUS     current
	DESCRIPTION
			"To create or delete a static group entry."
	::= { snIgmpStaticGroupEntry 4 }

END
FOUNDRY-SN-APPLETALK-MIB DEFINITIONS ::= BEGIN

IMPORTS
	MODULE-IDENTITY, OBJECT-TYPE,Counter32,Integer32 
		FROM SNMPv2-SMI
	router
		FROM FOUNDRY-SN-ROOT-MIB
	RtrStatus, ClearStatus, RowSts, PortIndex, Action
		FROM FOUNDRY-SN-IP-MIB;

snAppleTalk MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"        
	REVISION     "200909300000Z" -- September 30, 2009
	DESCRIPTION
			"convert from SMIv1 to SMIv2"
   ::= {router  10}

	ATNetworkNumber ::=         -- 2 octets of net number
								-- in network byte order
		OCTET STRING (SIZE (2))

	DdpNodeAddress ::=          -- 2 octets of net number
								-- in network byte order,
								-- 1 octet of node number
		OCTET STRING (SIZE (3))

	ATName ::=                  -- 0 to 32 octets of AppleTalk
								-- ASCII [Inside AppleTalk]
		OCTET STRING (SIZE (0..32))


-- SECTION 2: MIB 

-- Router AppleTalk MIB
-- This section contains AppleTalk specific router MIB object definitions.

-- AppleTalk general group

snRtATGeneral               OBJECT IDENTIFIER ::= { snAppleTalk 1 }

snRtATRoutingEnable            OBJECT-TYPE
	SYNTAX  RtrStatus
	MAX-ACCESS  read-write
	STATUS  current
	DESCRIPTION
		"Enable/disable AppleTalk routing function on this box."
	::= { snRtATGeneral 1 }

snRtATClearArpCache            OBJECT-TYPE
	SYNTAX  ClearStatus
	MAX-ACCESS  read-write
	STATUS  current
	DESCRIPTION
		"clear(1) will clear AppleTalk arp cache table."
	::= { snRtATGeneral 2 }

snRtATClearFwdCache            OBJECT-TYPE
	SYNTAX  ClearStatus
	MAX-ACCESS  read-write
	STATUS  current
	DESCRIPTION
		"clear(1) will clear AppleTalk forward cache table."
	::= { snRtATGeneral 3 }

snRtATClearRoute               OBJECT-TYPE
	SYNTAX  ClearStatus
	MAX-ACCESS  read-write
	STATUS  current
	DESCRIPTION
		"clear(1) will clear AppleTalk route table."
	::= { snRtATGeneral 4 }

snRtATClearTrafficCounters     OBJECT-TYPE
	SYNTAX  ClearStatus
	MAX-ACCESS  read-write
	STATUS  current
	DESCRIPTION
		"clear(1) will clear AppleTalk network statistics counters."
	::= { snRtATGeneral 5 }

snRtATArpRetransmitCount       OBJECT-TYPE
	SYNTAX  INTEGER (1..10)
	MAX-ACCESS  read-write
	STATUS  current
	DESCRIPTION
		"The number of AppleTalk ARP request retransmits if the
		first request timeouts."
	DEFVAL  { 2 }
	::= { snRtATGeneral 6 }

snRtATArpRetransmitInterval    OBJECT-TYPE
	SYNTAX  INTEGER (1..120)
	MAX-ACCESS  read-write
	STATUS  current
	DESCRIPTION
		"The waiting time interval for an AppleTalk ARP response
		before retransmission of an ARP request. Each unit value
		is one second."
	DEFVAL  { 1 }
	::= { snRtATGeneral 7 }

snRtATGleanPacketsEnable       OBJECT-TYPE
	SYNTAX  RtrStatus
	MAX-ACCESS  read-write
	STATUS  current
	DESCRIPTION
		"Enable/disable AppleTalk glean packets function on this box."
	DEFVAL  { disabled }
	::= { snRtATGeneral 8 }

snRtATRtmpUpdateInterval       OBJECT-TYPE
	SYNTAX  INTEGER (1..3600)
	MAX-ACCESS  read-write
	STATUS  current
	DESCRIPTION
		"The periodic time interval to transmit a RTMP
		update. Each unit value is one second."
	DEFVAL  { 10 }
	::= { snRtATGeneral 9 }

snRtATZipQueryInterval         OBJECT-TYPE
	SYNTAX  INTEGER (1..1000)
	MAX-ACCESS  read-write
	STATUS  current
	DESCRIPTION
		"The periodic time interval to transmit a ZIP
		query. Each unit value is one second."
	DEFVAL  { 10 }
	::= { snRtATGeneral 10 }

snRtATInRtmpPkts               OBJECT-TYPE
	SYNTAX  Counter32
	MAX-ACCESS  read-only
	STATUS  current
	DESCRIPTION
		"The total number of RTMP packets received by
		this entity."
	::= { snRtATGeneral 11 }

snRtATOutRtmpPkts              OBJECT-TYPE
	SYNTAX  Counter32
	MAX-ACCESS  read-only
	STATUS  current
	DESCRIPTION
		"The total number of RTMP packets which were
		transmitted from this entity."
	::= { snRtATGeneral 12 }

snRtATFilteredRtmpPkts         OBJECT-TYPE
	SYNTAX  Counter32
	MAX-ACCESS  read-only
	STATUS  current
	DESCRIPTION
		"The total number of RTMP packets which were
		filtered by this entity."
	::= { snRtATGeneral 13 }

snRtATInZipPkts                OBJECT-TYPE
	SYNTAX  Counter32
	MAX-ACCESS  read-only
	STATUS  current
	DESCRIPTION
		"The total number of ZIP packets received by
		this entity."
	::= { snRtATGeneral 14 }

snRtATOutZipPkts               OBJECT-TYPE
	SYNTAX  Counter32
	MAX-ACCESS  read-only
	STATUS  current
	DESCRIPTION
		"The total number of ZIP packets which were
		transmitted from this entity."
	::= { snRtATGeneral 15 }

snRtATInZipGZLPkts             OBJECT-TYPE
	SYNTAX  Counter32
	MAX-ACCESS  read-only
	STATUS  current
	DESCRIPTION
		"The total number of ZIP get zone list packets received by
		this entity."
	::= { snRtATGeneral 16 }

snRtATOutZipGZLPkts            OBJECT-TYPE
	SYNTAX  Counter32
	MAX-ACCESS  read-only
	STATUS  current
	DESCRIPTION
		"The total number of ZIP get zone list packets which were
		transmitted from this entity."
	::= { snRtATGeneral 17 }

snRtATInZipNetInfoPkts         OBJECT-TYPE
	SYNTAX  Counter32
	MAX-ACCESS  read-only
	STATUS  current
	DESCRIPTION
		"The total number of ZIP network information packets received by
		this entity."
	::= { snRtATGeneral 18 }

snRtATOutZipNetInfoPkts        OBJECT-TYPE
	SYNTAX  Counter32
	MAX-ACCESS  read-only
	STATUS  current
	DESCRIPTION
		"The total number of ZIP network information packets which were
		transmitted from this entity."
	::= { snRtATGeneral 19 }

snRtATInDdpPkts                OBJECT-TYPE
	SYNTAX  Counter32
	MAX-ACCESS  read-only
	STATUS  current
	DESCRIPTION
		"The total number of DDP datagrams received by
		this entity."
	::= { snRtATGeneral 20 }

snRtATOutDdpPkts               OBJECT-TYPE
	SYNTAX  Counter32
	MAX-ACCESS  read-only
	STATUS  current
	DESCRIPTION
		"The total number of DDP datagrams which were
		transmitted from this entity."
	::= { snRtATGeneral 21 }

snRtATForwardedDdpPkts         OBJECT-TYPE
	SYNTAX  Counter32
	MAX-ACCESS  read-only
	STATUS  current
	DESCRIPTION
		"The number of input DDP datagrams for which this entity
		was not their final DDP destination, as a result of
		which an attempt was made to find a route to forward
		them to that final destination."
	::= { snRtATGeneral 22 }

snRtATInDeliveredDdpPkts       OBJECT-TYPE
	SYNTAX  Counter32
	MAX-ACCESS  read-only
	STATUS  current
	DESCRIPTION
		"The total number of input DDP datagrams for which
		this entity was their final DDP destination."
	::= { snRtATGeneral 23 }

snRtATDroppedNoRouteDdpPkts    OBJECT-TYPE
	SYNTAX  Counter32
	MAX-ACCESS  read-only
	STATUS  current
	DESCRIPTION
		"The total number of DDP datagrams dropped because a
		route could not be found to their final destination."
	::= { snRtATGeneral 24 }

snRtATDroppedBadHopCountsDdpPkts OBJECT-TYPE
	SYNTAX  Counter32
	MAX-ACCESS  read-only
	STATUS  current
	DESCRIPTION
		"The total number of input DDP datagrams dropped
		because this entity was not their final destination
		and their hop count would exceed 15."
	::= { snRtATGeneral 25 }

snRtATDroppedOtherReasonsDdpPkts OBJECT-TYPE
	SYNTAX  Counter32
	MAX-ACCESS  read-only
	STATUS  current
	DESCRIPTION
		"The total number of DDP datagrams dropped because
		of other reasons, e.g. run out of resouces."
	::= { snRtATGeneral 26 }

snRtATInAarpPkts               OBJECT-TYPE
	SYNTAX  Counter32
	MAX-ACCESS  read-only
	STATUS  current
	DESCRIPTION
		"The total number of AppleTalk ARP packets received by
		this entity."
	::= { snRtATGeneral 27 }

snRtATOutAarpPkts              OBJECT-TYPE
	SYNTAX  Counter32
	MAX-ACCESS  read-only
	STATUS  current
	DESCRIPTION
		"The total number of AppleTalk ARP packets which were
		transmitted from this entity."
	::= { snRtATGeneral 28 }


-- AppleTalk socket priority table

snRtATSocketPriorityTable      OBJECT-TYPE
	SYNTAX  SEQUENCE OF SnRtATSocketPriorityEntry
	MAX-ACCESS  not-accessible
	STATUS  current
	DESCRIPTION
		"AppleTalk socket priority table."
	::= { snAppleTalk 2 }

snRtATSocketPriorityEntry      OBJECT-TYPE
	SYNTAX  SnRtATSocketPriorityEntry
	MAX-ACCESS  not-accessible
	STATUS  current
	DESCRIPTION
		"An entry in the AppleTalk socket priority table."
	INDEX   { snRtATSocketPrioritySocket }
	::= { snRtATSocketPriorityTable 1 }

SnRtATSocketPriorityEntry ::= SEQUENCE {
	snRtATSocketPrioritySocket
		INTEGER,
	snRtATSocketPriorityPriority
		INTEGER
	}

snRtATSocketPrioritySocket     OBJECT-TYPE
	SYNTAX  INTEGER (1..254)
	MAX-ACCESS  read-only
	STATUS  current
	DESCRIPTION
		"Socket number for a socket priority entry."
	::= { snRtATSocketPriorityEntry 1 }

snRtATSocketPriorityPriority OBJECT-TYPE
	SYNTAX  INTEGER {
		level0(0),
		level1(1),
		level2(2),
		level3(3),
		level4(4),
		level5(5),
		level6(6),
		level7(7)
		}
	MAX-ACCESS  read-write
	STATUS  current
	DESCRIPTION
		"The Standalone router Priority level applies to a socket number:
		 low(0)   -- low prority
		 high(1) -- high prority.
		 The BigIron Priority levels applies to a socket number are:
		level0(0), level1(1), level2(2), level3(3),
		level4(4), level5(5), level6(6), level7(7) "
	::= { snRtATSocketPriorityEntry 2 }


-- AppleTalk interface zone filter table

snRtATPortZoneFilterTable      OBJECT-TYPE
	SYNTAX  SEQUENCE OF SnRtATPortZoneFilterEntry
	MAX-ACCESS  not-accessible
	STATUS  current
	DESCRIPTION
		"AppleTalk interface zone filter table."
	::= { snAppleTalk 3 }

snRtATPortZoneFilterEntry      OBJECT-TYPE
	SYNTAX  SnRtATPortZoneFilterEntry
	MAX-ACCESS  not-accessible
	STATUS  current
	DESCRIPTION
		"An entry in the AppleTalk interface zone filter table."
	INDEX   { snRtATPortZoneFilterPortIndex, snRtATPortZoneFilterZone }
	::= { snRtATPortZoneFilterTable 1 }

SnRtATPortZoneFilterEntry ::= SEQUENCE {
	snRtATPortZoneFilterPortIndex
		PortIndex,
	snRtATPortZoneFilterZone
		ATName,
	snRtATPortZoneFilterAction
		Action,
	snRtATPortZoneFilterRtmpEnable
		RtrStatus,
	snRtATPortZoneFilterRowStatus
		RowSts
	}

snRtATPortZoneFilterPortIndex  OBJECT-TYPE
	SYNTAX  PortIndex
	MAX-ACCESS  read-only
	STATUS  current
	DESCRIPTION
		"The port index for a zone filter entry."
	::= { snRtATPortZoneFilterEntry 1 }

snRtATPortZoneFilterZone       OBJECT-TYPE
	SYNTAX  ATName
	MAX-ACCESS  read-only
	STATUS  current
	DESCRIPTION
		"The zone name granted for this filter."
	::= { snRtATPortZoneFilterEntry 2 }

snRtATPortZoneFilterAction     OBJECT-TYPE
	SYNTAX  Action
	MAX-ACCESS  read-write
	STATUS  current
	DESCRIPTION
		"Action to take if the AppleTalk packet match
		with this filter."
	::= { snRtATPortZoneFilterEntry 3 }

snRtATPortZoneFilterRtmpEnable OBJECT-TYPE
	SYNTAX  RtrStatus
	MAX-ACCESS  read-write
	STATUS  current
	DESCRIPTION
		"Enable/disable RTMP filtering."
	::= { snRtATPortZoneFilterEntry 4 }

snRtATPortZoneFilterRowStatus  OBJECT-TYPE
	SYNTAX  RowSts
	MAX-ACCESS  read-write
	STATUS  current
	DESCRIPTION
		"To create or delete a zone filter entry."
	::= { snRtATPortZoneFilterEntry 5 }


-- AppleTalk port table

snRtATPortTable                OBJECT-TYPE
	SYNTAX  SEQUENCE OF SnRtATPortEntry
	MAX-ACCESS  not-accessible
	STATUS  current
	DESCRIPTION
		"AppleTalk port table."
	::= { snAppleTalk 4 }

snRtATPortEntry                OBJECT-TYPE
	SYNTAX  SnRtATPortEntry
	MAX-ACCESS  not-accessible
	STATUS  current
	DESCRIPTION
		"An entry in the AppleTalk port table."
	INDEX   { snRtATPortIndex }
	::= { snRtATPortTable 1 }

SnRtATPortEntry ::= SEQUENCE {
	snRtATPortIndex
		PortIndex,
	snRtATPortArpAge
		INTEGER,
	snRtATPortState
		INTEGER,
	snRtATPortSeedRouter
		INTEGER,
	snRtATPortOperationMode
		INTEGER
	}

snRtATPortIndex                OBJECT-TYPE
	SYNTAX  PortIndex
	MAX-ACCESS  read-only
	STATUS  current
	DESCRIPTION
		"The port index for port table entry."
	::= { snRtATPortEntry 1 }

snRtATPortArpAge               OBJECT-TYPE
	SYNTAX  INTEGER (0..240)
	MAX-ACCESS  read-write
	STATUS  current
	DESCRIPTION
		"The time in minutes an ARP entry can
		be valid without relearning. 
		0 - Don't age."
	DEFVAL  { 10 }
	::= { snRtATPortEntry 2 }

snRtATPortState                OBJECT-TYPE
	SYNTAX  INTEGER {
			 other(1),
			 down(2),
			 up(3) }
	MAX-ACCESS  read-only
	STATUS  current
	DESCRIPTION
		"The up and down state of this port."
	::= { snRtATPortEntry 3 }

snRtATPortSeedRouter           OBJECT-TYPE
	SYNTAX  INTEGER {
			 other(1),
			 seedRouter(2),
			 nonSeedRouter(3) }
	MAX-ACCESS  read-only
	STATUS  current
	DESCRIPTION
		"This port was configured to seed or non-seed router."
	::= { snRtATPortEntry 4 }

snRtATPortOperationMode        OBJECT-TYPE
	SYNTAX  INTEGER {
			 other(1),
			 seedRouter(2),
			 nonSeedRouter(3),
			 notOperational(4),
			 routingDisabled(5) }
	MAX-ACCESS  read-only
	STATUS  current
	DESCRIPTION
		"The operation mode of this port."
	::= { snRtATPortEntry 5 }


-- AppleTalk forwarding cache table

snRtATFwdCacheTable            OBJECT-TYPE
	SYNTAX  SEQUENCE OF SnRtATFwdCacheEntry
	MAX-ACCESS  not-accessible
	STATUS  current
	DESCRIPTION
		"AppleTalk forwarding cache table."
	::= { snAppleTalk 5 }

snRtATFwdCacheEntry            OBJECT-TYPE
	SYNTAX  SnRtATFwdCacheEntry
	MAX-ACCESS  not-accessible
	STATUS  current
	DESCRIPTION
		"An entry in the AppleTalk forwarding cache table."
	INDEX   { snRtATFwdCacheIndex }
	::= { snRtATFwdCacheTable 1 }

SnRtATFwdCacheEntry ::= SEQUENCE {
	snRtATFwdCacheIndex
		Integer32,
	snRtATFwdCacheNetAddr
		DdpNodeAddress,
	snRtATFwdCacheMacAddr
		OCTET STRING,
	snRtATFwdCacheNextHop
		DdpNodeAddress,
	snRtATFwdCacheOutgoingPort
		Integer32,
	snRtATFwdCacheType
		INTEGER,
	snRtATFwdCacheAction
		INTEGER,
	snRtATFwdCacheVLanId
		Integer32
	}

snRtATFwdCacheIndex            OBJECT-TYPE
	SYNTAX  Integer32
	MAX-ACCESS  read-only
	STATUS  current
	DESCRIPTION
		"The table index for an AppleTalk forwarding cache table entry."
	::= { snRtATFwdCacheEntry 1 }

snRtATFwdCacheNetAddr          OBJECT-TYPE
	SYNTAX  DdpNodeAddress
	MAX-ACCESS  read-only
	STATUS  current
	DESCRIPTION
		"The AppleTalk network address of a station."
	::= { snRtATFwdCacheEntry 2 }

snRtATFwdCacheMacAddr          OBJECT-TYPE
	SYNTAX  OCTET STRING (SIZE (6))
	MAX-ACCESS  read-only
	STATUS  current
	DESCRIPTION
		"The Mac address of an AppleTalk station."
	::= { snRtATFwdCacheEntry 3 }

snRtATFwdCacheNextHop          OBJECT-TYPE
	SYNTAX  DdpNodeAddress
	MAX-ACCESS  read-only
	STATUS  current
	DESCRIPTION
		"The next hop router network address."
	::= { snRtATFwdCacheEntry 4 }

snRtATFwdCacheOutgoingPort     OBJECT-TYPE
	SYNTAX  Integer32
	MAX-ACCESS  read-only
	STATUS  current
	DESCRIPTION
		"The outgoing port of which packets will forward to.
		Return port value of zero to indicate no outgoing port
		associated to this entry."
	::= { snRtATFwdCacheEntry 5 }

snRtATFwdCacheType             OBJECT-TYPE
	SYNTAX  INTEGER { dynamic(1), permanent(2) }
	MAX-ACCESS  read-only
	STATUS  current
	DESCRIPTION
		"The 'dynamic' or 'permanent' type for an AppleTalk forwarding
		cache table entry."
	::= { snRtATFwdCacheEntry 6 }

snRtATFwdCacheAction           OBJECT-TYPE
	SYNTAX  INTEGER {
			other(1),
			forward(2),
			forUs(3),
			waitForArp(4),
			dropPacket(5)
			}
	MAX-ACCESS  read-only
	STATUS  current
	DESCRIPTION
		"The action to take."
	::= { snRtATFwdCacheEntry 7 }

snRtATFwdCacheVLanId        OBJECT-TYPE
	SYNTAX  Integer32
	MAX-ACCESS  read-only
	STATUS  current
	DESCRIPTION
		"The VLAN ID for an AppleTalk forwarding cache table entry.
		Return VLAN ID value of zero to indicate no VLAN associated
		to this entry."
	::= { snRtATFwdCacheEntry 8 }


-- AppleTalk zone table

snRtATZoneTable            OBJECT-TYPE
	SYNTAX  SEQUENCE OF SnRtATZoneEntry
	MAX-ACCESS  not-accessible
	STATUS  current
	DESCRIPTION
		"AppleTalk zone table."
	::= { snAppleTalk 6 }

snRtATZoneEntry            OBJECT-TYPE
	SYNTAX  SnRtATZoneEntry
	MAX-ACCESS  not-accessible
	STATUS  current
	DESCRIPTION
		"An entry in the AppleTalk zone table."
	INDEX   { snRtATZoneIndex }
	::= { snRtATZoneTable 1 }

SnRtATZoneEntry ::= SEQUENCE {
	snRtATZoneIndex
	Integer32,
	snRtATZoneNetStart
		ATNetworkNumber,
	snRtATZoneNetEnd
		ATNetworkNumber,
	snRtATZoneName
		ATName
	}

snRtATZoneIndex            OBJECT-TYPE
	SYNTAX  Integer32
	MAX-ACCESS  read-only
	STATUS  current
	DESCRIPTION
		"The table index for an AppleTalk zone table entry."
	::= { snRtATZoneEntry 1 }

snRtATZoneNetStart         OBJECT-TYPE
	SYNTAX  ATNetworkNumber
	MAX-ACCESS  read-only
	STATUS  current
	DESCRIPTION
		"The first AppleTalk network address in the range
		of this zone name."
	::= { snRtATZoneEntry 2 }

snRtATZoneNetEnd           OBJECT-TYPE
	SYNTAX  ATNetworkNumber
	MAX-ACCESS  read-only
	STATUS  current
	DESCRIPTION
		"The last AppleTalk network address in the range
		of this zone name."
	::= { snRtATZoneEntry 3 }

snRtATZoneName             OBJECT-TYPE
	SYNTAX  ATName
	MAX-ACCESS  read-only
	STATUS  current
	DESCRIPTION
		"The zone name."
	::= { snRtATZoneEntry 4 }


-- AppleTalk additional zone filter table

snRtATAddZoneFilterTable       OBJECT-TYPE
	SYNTAX  SEQUENCE OF SnRtATAddZoneFilterEntry
	MAX-ACCESS  not-accessible
	STATUS  current
	DESCRIPTION
		"AppleTalk additional zone filter table. Additional zones
		are those zones that do not match any zones defined in the
		zone filter table."
	::= { snAppleTalk 7 }

snRtATAddZoneFilterEntry       OBJECT-TYPE
	SYNTAX  SnRtATAddZoneFilterEntry
	MAX-ACCESS  not-accessible
	STATUS  current
	DESCRIPTION
		"An entry in the AppleTalk additional zone filter table."
	INDEX   { snRtATAddZoneFilterPortIndex }
	::= { snRtATAddZoneFilterTable 1 }

SnRtATAddZoneFilterEntry ::= SEQUENCE {
	snRtATAddZoneFilterPortIndex
		PortIndex,
	snRtATAddZoneFilterAction
		Action,
	snRtATAddZoneFilterRtmpEnable
		RtrStatus
	}

snRtATAddZoneFilterPortIndex   OBJECT-TYPE
	SYNTAX  PortIndex
	MAX-ACCESS  read-only
	STATUS  current
	DESCRIPTION
		"The port index for additional zone filter table entry."
	::= { snRtATAddZoneFilterEntry 1 }

snRtATAddZoneFilterAction      OBJECT-TYPE
	SYNTAX  Action
	MAX-ACCESS  read-write
	STATUS  current
	DESCRIPTION
		"Action to take if no zone filter match."
	::= { snRtATAddZoneFilterEntry 2 }

snRtATAddZoneFilterRtmpEnable  OBJECT-TYPE
	SYNTAX  RtrStatus
	MAX-ACCESS  read-write
	STATUS  current
	DESCRIPTION
		"Enable/disable RTMP filtering on additional zone."
	::= { snRtATAddZoneFilterEntry 3 }

END
FOUNDRY-SN-SW-L4-SWITCH-GROUP-MIB DEFINITIONS ::= BEGIN

IMPORTS
	MODULE-IDENTITY, OBJECT-TYPE,IpAddress, Counter32, TimeTicks,Counter64,Integer32
			FROM SNMPv2-SMI
			
	switch
		FROM FOUNDRY-SN-ROOT-MIB
			
	TEXTUAL-CONVENTION
		FROM SNMPv2-TC
			
	PhysAddress
		FROM FOUNDRY-SN-SWITCH-GROUP-MIB
	
	DisplayString
		FROM FOUNDRY-SN-AGENT-MIB;
			
snL4 MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"        
	REVISION     "200909300000Z" -- September 30, 2009
	DESCRIPTION
			"convert from SMIv1 to SMIv2"
   ::= { switch 4}

	-- textual conventions

	L4RowSts ::= TEXTUAL-CONVENTION
		STATUS	  current
		DESCRIPTION
			"
			Row Creation/Deletion Values
			"
		SYNTAX	INTEGER {	other(1),
							valid(2),
							delete(3),
							create(4),
							modify(5)
						}		

	L4Status ::= TEXTUAL-CONVENTION
		STATUS	  current
		DESCRIPTION
			"
			L4 Status Values
			"
		SYNTAX	INTEGER { disabled(0), enabled(1) }

	L4ServerName ::= TEXTUAL-CONVENTION
		STATUS	  current
		DESCRIPTION
			"
			L4 Server Name
			"
		SYNTAX	OCTET STRING (SIZE(1..32))
		
	L4Flag ::= TEXTUAL-CONVENTION
		STATUS	  current
		DESCRIPTION
			"
				L4 Flag Values
			"
		SYNTAX	INTEGER { false(0), true(1) }

	L4DeleteState ::= TEXTUAL-CONVENTION
		STATUS	  current
		DESCRIPTION
			"
			L4 Delete Sate
			"
		SYNTAX	INTEGER {	done(0),
							waitunbind(1),
							waitdelete(2)
						}

	WebCacheState ::= TEXTUAL-CONVENTION
		STATUS	  current
		DESCRIPTION
			"
			WebCacheSate
			"
		SYNTAX	INTEGER {	disabled(0),
							enabled(1),
							failed(2),
							testing(3),
							suspect(4),
							shutdown(5),
							active(6)
							}



snL4Gen						OBJECT IDENTIFIER	  ::= { snL4 1  }
snL4VirtualServer			OBJECT IDENTIFIER	  ::= { snL4 2  }
snL4RealServer				OBJECT IDENTIFIER	  ::= { snL4 3  }
snL4VirtualServerPort		OBJECT IDENTIFIER	  ::= { snL4 4  }
snL4RealServerPort			OBJECT IDENTIFIER	  ::= { snL4 5  }
snL4Bind					OBJECT IDENTIFIER	  ::= { snL4 6  }
snL4VirtualServerStatus		OBJECT IDENTIFIER	  ::= { snL4 7  }
snL4RealServerStatus		OBJECT IDENTIFIER	  ::= { snL4 8  }
snL4VirtualServerPortStatus	OBJECT IDENTIFIER	  ::= { snL4 9  }
snL4RealServerPortStatus	OBJECT IDENTIFIER	  ::= { snL4 10 }
snL4Policy					OBJECT IDENTIFIER	  ::= { snL4 11 }
snL4PolicyPortAccess		OBJECT IDENTIFIER	  ::= { snL4 12 }
snL4Trap					OBJECT IDENTIFIER	  ::= { snL4 13 }
snL4WebCache				OBJECT IDENTIFIER	  ::= { snL4 14 }
snL4WebCacheGroup			OBJECT IDENTIFIER	  ::= { snL4 15 }
snL4WebCacheTrafficStats	OBJECT IDENTIFIER	  ::= { snL4 16 }
snL4WebUncachedTrafficStats	OBJECT IDENTIFIER	  ::= { snL4 17 }
snL4WebCachePort			OBJECT IDENTIFIER	  ::= { snL4 18 }
snL4RealServerCfg			OBJECT IDENTIFIER	  ::= { snL4 19 }
snL4RealServerPortCfg		OBJECT IDENTIFIER	  ::= { snL4 20 }
snL4VirtualServerCfg		OBJECT IDENTIFIER	  ::= { snL4 21  }
snL4VirtualServerPortCfg	OBJECT IDENTIFIER	  ::= { snL4 22  }
snL4RealServerStatistic		OBJECT IDENTIFIER	  ::= { snL4 23 }
snL4RealServerPortStatistic	OBJECT IDENTIFIER	  ::= { snL4 24 }
snL4VirtualServerStatistic		OBJECT IDENTIFIER	  ::= { snL4 25 }
snL4VirtualServerPortStatistic	OBJECT IDENTIFIER	  ::= { snL4 26 }
snL4GslbSiteRemoteServerIrons	OBJECT IDENTIFIER 	  ::= { snL4 27 }
snL4History						OBJECT IDENTIFIER 	  ::= { snL4 28 }


-- L4 General MIBs
				
snL4MaxSessionLimit 		OBJECT-TYPE
	SYNTAX	INTEGER	(0..1000000)
	MAX-ACCESS  read-write
	STATUS  current
	DESCRIPTION
		"numbers of maximum session (L4 cache) entries"
	::= { snL4Gen 1 }

snL4TcpSynLimit 		OBJECT-TYPE
	SYNTAX	INTEGER	 (1..65535)
	MAX-ACCESS  read-write
	STATUS  current
	DESCRIPTION
		"Numbers of connection per second"
	::= { snL4Gen 2 }

--  Server load balancing
snL4slbGlobalSDAType	OBJECT-TYPE
	SYNTAX	 INTEGER {
		leastconnection(1),
		roundrobin(2),
		weighted(3)
	}
	MAX-ACCESS  read-write
	STATUS  current
	DESCRIPTION
		"Global Session Distribution Algorithm(SDA)"
	::= { snL4Gen 3 }

snL4slbTotalConnections 		OBJECT-TYPE
	SYNTAX	Counter32
	MAX-ACCESS  read-only
	STATUS  current
	DESCRIPTION
		"Total connections in this device"
	::= { snL4Gen 4 }

snL4slbLimitExceeds 		OBJECT-TYPE
	SYNTAX   Integer32
	MAX-ACCESS  read-only
	STATUS  current
	DESCRIPTION
		"exceeds snL4TCPSynLimit (numbers of connection per second)"
	::= { snL4Gen 5 }

-- Server load balancing traffic info

snL4slbForwardTraffic 		OBJECT-TYPE
	SYNTAX	Counter32
	MAX-ACCESS  read-only
	STATUS  current
	DESCRIPTION
		"Client->Server"
	::= { snL4Gen 6 }

snL4slbReverseTraffic 		OBJECT-TYPE
	SYNTAX	Counter32
	MAX-ACCESS  read-only
	STATUS  current
	DESCRIPTION
		"Server->Client"
	::= { snL4Gen 7 }

snL4slbDrops 		OBJECT-TYPE
	SYNTAX   Integer32
	MAX-ACCESS  read-only
	STATUS  current
	DESCRIPTION
		""
	::= { snL4Gen 8 }

snL4slbDangling 		OBJECT-TYPE
	SYNTAX   Integer32
	MAX-ACCESS  read-only
	STATUS  current
	DESCRIPTION
		""
	::= { snL4Gen 9 }

snL4slbDisableCount 		OBJECT-TYPE
	SYNTAX   Integer32
	MAX-ACCESS  read-only
	STATUS  current
	DESCRIPTION
		""
	::= { snL4Gen 10 }

snL4slbAged 		OBJECT-TYPE
	SYNTAX   Integer32
	MAX-ACCESS  read-only
	STATUS  current
	DESCRIPTION
		""
	::= { snL4Gen 11 }

snL4slbFinished 		OBJECT-TYPE
	SYNTAX   Integer32
	MAX-ACCESS  read-only
	STATUS  current
	DESCRIPTION
		"FIN_or_RST"
	::= { snL4Gen 12 }

--  Session

snL4FreeSessionCount 		OBJECT-TYPE
	SYNTAX   Integer32
	MAX-ACCESS  read-only
	STATUS  current
	DESCRIPTION
		"Maximum sessions - used sessions"
	::= { snL4Gen 13 }


--  Hot stand-by
snL4BackupInterface 		OBJECT-TYPE
	SYNTAX	INTEGER	  (0..26)
	MAX-ACCESS  read-write
	STATUS  current
	DESCRIPTION
		"backup monitoring port"
	::= { snL4Gen 14 }

snL4BackupMacAddr 		OBJECT-TYPE
	SYNTAX	PhysAddress
	MAX-ACCESS  read-write
	STATUS  current
	DESCRIPTION
		"Associated MAC address for backup monitoring port"
	::= { snL4Gen 15 }

snL4Active 		OBJECT-TYPE
	SYNTAX	L4Flag
	MAX-ACCESS  read-only
	STATUS  current
	DESCRIPTION
		""
	::= { snL4Gen 16 }

snL4Redundancy 		OBJECT-TYPE
	SYNTAX   Integer32
	MAX-ACCESS  read-only
	STATUS  current
	DESCRIPTION
		""
	::= { snL4Gen 17 }

snL4Backup 		OBJECT-TYPE
	SYNTAX	L4Flag
	MAX-ACCESS  read-only
	STATUS  current
	DESCRIPTION
		"true->StandBy,false->active"
	::= { snL4Gen 18 }

snL4BecomeActive 		OBJECT-TYPE
	SYNTAX   Integer32
	MAX-ACCESS  read-only
	STATUS  current
	DESCRIPTION
		"How many times this device become active"
	::= { snL4Gen 19 }

snL4BecomeStandBy 		OBJECT-TYPE
	SYNTAX   Integer32
	MAX-ACCESS  read-only
	STATUS  current
	DESCRIPTION
		"How many times this device become standby"
	::= { snL4Gen 20 }

snL4BackupState 		OBJECT-TYPE
	SYNTAX	 INTEGER {
		slbSyncComplete(0),
		slbSyncReqMap(1),
		slbSyncreqMac(2),
		slbSyncreqServers(3),
		slbSyncReqL4(4)
	}
	MAX-ACCESS  read-only
	STATUS  current
	DESCRIPTION
		"Backup state"
	::= { snL4Gen 21 }

snL4NoPDUSent 		OBJECT-TYPE
	SYNTAX   Integer32
	MAX-ACCESS  read-only
	STATUS  current
	DESCRIPTION
		""
	::= { snL4Gen 22 }


snL4NoPDUCount 		OBJECT-TYPE
	SYNTAX   Integer32
	MAX-ACCESS  read-only
	STATUS  current
	DESCRIPTION
		""
	::= { snL4Gen 23 }


snL4NoPortMap 		OBJECT-TYPE
	SYNTAX   Integer32
	MAX-ACCESS  read-only
	STATUS  current
	DESCRIPTION
		""
	::= { snL4Gen 24 }

snL4unsuccessfulConn 	OBJECT-TYPE
	SYNTAX   Integer32
	MAX-ACCESS  read-only
	STATUS  current
	DESCRIPTION
		"Unsuccessfull connection"
	::= { snL4Gen 25 }

snL4PingInterval 	OBJECT-TYPE
	SYNTAX	INTEGER	 (1..10)
	MAX-ACCESS  read-write
	STATUS  current
	DESCRIPTION
		"Ping retries interval"
	DEFVAL { 2 }
	::= { snL4Gen 26 }

snL4PingRetry 	OBJECT-TYPE
	SYNTAX	INTEGER	(2..10)
	MAX-ACCESS  read-write
	STATUS  current
	DESCRIPTION
		"Ping retries attempts"
	DEFVAL { 4 }
	::= { snL4Gen 27 }

snL4TcpAge 	OBJECT-TYPE
	SYNTAX	INTEGER	(2..60)
	MAX-ACCESS  read-write
	STATUS  current
	DESCRIPTION
		"TCP reset age"
	DEFVAL { 30 }
	::= { snL4Gen 28 }


snL4UdpAge 	OBJECT-TYPE
	SYNTAX	INTEGER	(2..60)
	MAX-ACCESS  read-write
	STATUS  current
	DESCRIPTION
		"UDP reset age"
	DEFVAL { 5 }
	::= { snL4Gen 29 }


-- Enable/disable L4 traps

snL4EnableMaxSessionLimitReachedTrap        OBJECT-TYPE
	SYNTAX INTEGER { disabled(0), enabled(1) }
	MAX-ACCESS read-write
	STATUS current
	DESCRIPTION
		"Enable/disable maximum number of connections reached trap."
	::= { snL4Gen 30 }

snL4EnableTcpSynLimitReachedTrap            OBJECT-TYPE
	SYNTAX INTEGER { disabled(0), enabled(1) }
	MAX-ACCESS read-write
	STATUS current
	DESCRIPTION
		"Enable/disable the number of TCP SYN limits reached trap."
	::= { snL4Gen 31 }

snL4EnableRealServerUpTrap                  OBJECT-TYPE
	SYNTAX INTEGER { disabled(0), enabled(1) }
	MAX-ACCESS read-write
	STATUS current
	DESCRIPTION
		"Enable/disable the real server up trap."
	::= { snL4Gen 32 }

snL4EnableRealServerDownTrap                OBJECT-TYPE
	SYNTAX INTEGER { disabled(0), enabled(1) }
	MAX-ACCESS read-write
	STATUS current
	DESCRIPTION
		"Enable/disable the real server down trap."
	::= { snL4Gen 33 }

snL4EnableRealServerPortUpTrap              OBJECT-TYPE
	SYNTAX INTEGER { disabled(0), enabled(1) }
	MAX-ACCESS read-write
	STATUS current
	DESCRIPTION
		"Enable/disable the real server TCP port up trap."
	::= { snL4Gen 34 }

snL4EnableRealServerPortDownTrap            OBJECT-TYPE
	SYNTAX INTEGER { disabled(0), enabled(1) }
	MAX-ACCESS read-write
	STATUS current
	DESCRIPTION
		"Enable/disable the real server TCP port down trap."
	::= { snL4Gen 35 }

snL4EnableRealServerMaxConnLimitReachedTrap OBJECT-TYPE
	SYNTAX INTEGER { disabled(0), enabled(1) }
	MAX-ACCESS read-write
	STATUS current
	DESCRIPTION
		"Enable/disable the real server maximum number of
		connections reached trap."
	::= { snL4Gen 36 }

snL4EnableBecomeStandbyTrap                 OBJECT-TYPE
	SYNTAX INTEGER { disabled(0), enabled(1) }
	MAX-ACCESS read-write
	STATUS current
	DESCRIPTION
		"Enable/disable trap of the server load balancing
		switch changes state from active to standby."
	::= { snL4Gen 37 }

snL4EnableBecomeActiveTrap                  OBJECT-TYPE
	SYNTAX INTEGER { disabled(0), enabled(1) }
	MAX-ACCESS read-write
	STATUS current
	DESCRIPTION
		"Enable/disable trap of the server load balancing
		switch changes state from standby to active."
	::= { snL4Gen 38 }

snL4slbRouterInterfacePortMask 	OBJECT-TYPE
	SYNTAX   Integer32	
	MAX-ACCESS  read-write
	STATUS  deprecated
	DESCRIPTION
		"Router interface port mask.
		(It was obsoleted after release 07100, replaced by snL4slbRouterInterfacePortList)"
	::= { snL4Gen 39 }

------- Server Cache Group Global MIBs ----------
snL4MaxNumWebCacheGroup 		OBJECT-TYPE
	SYNTAX   Integer32
	MAX-ACCESS  read-only
	STATUS  current
	DESCRIPTION
		"The maximum number of server cache groups"
	::= { snL4Gen 40 }

snL4MaxNumWebCachePerGroup 		OBJECT-TYPE
	SYNTAX   Integer32
	MAX-ACCESS  read-only
	STATUS  current
	DESCRIPTION
		"The maximum number of WEB Cache servers in each of web cache group"
	::= { snL4Gen 41 }

snL4WebCacheStateful 		OBJECT-TYPE
	SYNTAX	L4Status
	MAX-ACCESS  read-write
	STATUS  current
	DESCRIPTION
		"The WEB Cache servers cache-stateful"
	::= { snL4Gen 42 }

------- GSLB Group Global MIBs ----------
snL4EnableGslbHealthCheckIpUpTrap        OBJECT-TYPE
	SYNTAX INTEGER { disabled(0), enabled(1) }
	MAX-ACCESS read-write
	STATUS current
	DESCRIPTION
		"Health check IP up."
	::= { snL4Gen 43 }

snL4EnableGslbHealthCheckIpDownTrap        OBJECT-TYPE
	SYNTAX INTEGER { disabled(0), enabled(1) }
	MAX-ACCESS read-write
	STATUS current
	DESCRIPTION
		"Health check IP down."
	::= { snL4Gen 44 }


snL4EnableGslbHealthCheckIpPortUpTrap        OBJECT-TYPE
	SYNTAX INTEGER { disabled(0), enabled(1) }
	MAX-ACCESS read-write
	STATUS current
	DESCRIPTION
		"Health check IP port up."
	::= { snL4Gen 45 }


snL4EnableGslbHealthCheckIpPortDownTrap        OBJECT-TYPE
	SYNTAX INTEGER { disabled(0), enabled(1) }
	MAX-ACCESS read-write
	STATUS current
	DESCRIPTION
		"Health check IP port down."
	::= { snL4Gen 46 }


snL4EnableGslbRemoteGslbSiDownTrap        OBJECT-TYPE
	SYNTAX INTEGER { disabled(0), enabled(1) }
	MAX-ACCESS read-write
	STATUS current
	DESCRIPTION
		"Connection to GSLB ServerIron is down."
	::= { snL4Gen 47 }


snL4EnableGslbRemoteGslbSiUpTrap        OBJECT-TYPE
	SYNTAX INTEGER { disabled(0), enabled(1) }
	MAX-ACCESS read-write
	STATUS current
	DESCRIPTION
		"Connection to GSLB ServerIron is up."
	::= { snL4Gen 48 }


snL4EnableGslbRemoteSiDownTrap        OBJECT-TYPE
	SYNTAX INTEGER { disabled(0), enabled(1) }
	MAX-ACCESS read-write
	STATUS current
	DESCRIPTION
		"GSLB connection to remote ServerIron is down."
	::= { snL4Gen 49 }


snL4EnableGslbRemoteSiUpTrap        OBJECT-TYPE
	SYNTAX INTEGER { disabled(0), enabled(1) }
	MAX-ACCESS read-write
	STATUS current
	DESCRIPTION
		"GSLB connection to remote ServerIron is up."
	::= { snL4Gen 50 }

snL4slbRouterInterfacePortList 	OBJECT-TYPE
	SYNTAX	OCTET STRING
	MAX-ACCESS  read-write
	STATUS  current
	DESCRIPTION
		"Router interface port list. Each port index is a 16-bit integer
		in big endian order. 8-bit is the slot number, the other 8-bit
		is the port number."
	::= { snL4Gen 51 }


-- Virtual Server table

snL4VirtualServerTable  OBJECT-TYPE
	SYNTAX	SEQUENCE OF SnL4VirtualServerEntry
	MAX-ACCESS  not-accessible
	STATUS  current
	DESCRIPTION
		"Virtual Server table."
	::= { snL4VirtualServer 1 }

snL4VirtualServerEntry  OBJECT-TYPE
	SYNTAX	SnL4VirtualServerEntry
	MAX-ACCESS  not-accessible
	STATUS  current
	DESCRIPTION
		"An entry in L4 Virtual Server table."
	INDEX	{ snL4VirtualServerIndex }
	::= { snL4VirtualServerTable 1 }

SnL4VirtualServerEntry ::= SEQUENCE {
	snL4VirtualServerIndex
		INTEGER,
	snL4VirtualServerName
		L4ServerName,
	snL4VirtualServerVirtualIP
		IpAddress,
	snL4VirtualServerAdminStatus
		L4Status,
	snL4VirtualServerSDAType
		INTEGER,
	snL4VirtualServerRowStatus
		L4RowSts,
	snL4VirtualServerDeleteState
		L4DeleteState
	}

snL4VirtualServerIndex  OBJECT-TYPE
	SYNTAX	INTEGER (1..64)
	MAX-ACCESS  read-only
	STATUS  current
	DESCRIPTION
		"The table index for a Virtual Server  entry."
	::= { snL4VirtualServerEntry 1 }


snL4VirtualServerName  OBJECT-TYPE
	SYNTAX	L4ServerName
	MAX-ACCESS  read-write
	STATUS  current
	DESCRIPTION
		"Virtual server name."
	::= { snL4VirtualServerEntry 2 }

snL4VirtualServerVirtualIP
	OBJECT-TYPE
	SYNTAX IpAddress
	MAX-ACCESS  read-write
	STATUS  current
	DESCRIPTION
		"Virtual Server IP Address."
	::= { snL4VirtualServerEntry 3 }

snL4VirtualServerAdminStatus	OBJECT-TYPE
	SYNTAX	L4Status
	MAX-ACCESS  read-write
	STATUS  current
	DESCRIPTION
		"Virtual Server status is ether disabled(0) or enabled(1)."
	::= { snL4VirtualServerEntry 4 }

snL4VirtualServerSDAType  OBJECT-TYPE
	SYNTAX	 INTEGER {
		default(0),
		leastconnection(1),
		roundrobin(2),
		weighted(3)
	}
	MAX-ACCESS  read-write
	STATUS  current
	DESCRIPTION
		"TCP/UDP Sessions Distribution Algorithms Type."
	::= { snL4VirtualServerEntry 5 }

 snL4VirtualServerRowStatus OBJECT-TYPE
	SYNTAX  L4RowSts
	MAX-ACCESS  read-write
	STATUS  current
	DESCRIPTION
		"To create or delete a virtual server
		entry."
	::= {snL4VirtualServerEntry  6 }

snL4VirtualServerDeleteState	OBJECT-TYPE
	SYNTAX	L4DeleteState
	MAX-ACCESS  read-only
	STATUS  current
	DESCRIPTION
		"Delete operation state." 
	::= { snL4VirtualServerEntry 7 }


-- Real Server table

snL4RealServerTable  OBJECT-TYPE
	SYNTAX	SEQUENCE OF SnL4RealServerEntry
	MAX-ACCESS  not-accessible
	STATUS  current
	DESCRIPTION
		"Real Server table."
	::= { snL4RealServer 1 }

snL4RealServerEntry  OBJECT-TYPE
	SYNTAX	SnL4RealServerEntry
	MAX-ACCESS  not-accessible
	STATUS  current
	DESCRIPTION
		"An entry in the Real Server table."
	INDEX	{ snL4RealServerIndex }
	::= { snL4RealServerTable 1 }

SnL4RealServerEntry ::= SEQUENCE {
	snL4RealServerIndex
		INTEGER,
	snL4RealServerName
		L4ServerName,
	snL4RealServerIP
		IpAddress,
	snL4RealServerAdminStatus
		L4Status,
	snL4RealServerMaxConnections
		INTEGER,
	snL4RealServerWeight
		INTEGER,
	snL4RealServerRowStatus
		L4RowSts,
	snL4RealServerDeleteState
		L4DeleteState
	}

snL4RealServerIndex  OBJECT-TYPE
	SYNTAX	INTEGER (1..256)
	MAX-ACCESS  read-only
	STATUS  current
	DESCRIPTION
		"The table index for a Real Server entry."
	::= { snL4RealServerEntry 1 }
snL4RealServerName  OBJECT-TYPE
	SYNTAX	L4ServerName
	MAX-ACCESS  read-write
	STATUS  current
	DESCRIPTION
		"Real server name."
	::= { snL4RealServerEntry 2 }

snL4RealServerIP
	OBJECT-TYPE
	SYNTAX IpAddress
	MAX-ACCESS  read-write
	STATUS  current
	DESCRIPTION
		"Real Server IP Address."
	::= { snL4RealServerEntry 3 }

snL4RealServerAdminStatus	OBJECT-TYPE
	SYNTAX	L4Status
	MAX-ACCESS  read-write
	STATUS  current
	DESCRIPTION
		"Real Server status is ether disabled(0) or enabled(1)."
	::= { snL4RealServerEntry 4 }

snL4RealServerMaxConnections 	OBJECT-TYPE
	SYNTAX	INTEGER	 (0..1000000)
	MAX-ACCESS  read-write
	STATUS  current
	DESCRIPTION
		"Real Server Maximum Connection allowed."
	::= { snL4RealServerEntry 5 }

 snL4RealServerWeight	OBJECT-TYPE
	SYNTAX	INTEGER	  (0..65000)
	MAX-ACCESS  read-write
	STATUS  current
	DESCRIPTION
		"Real Server weight"
	::= { snL4RealServerEntry 6 }

 snL4RealServerRowStatus OBJECT-TYPE
	SYNTAX  L4RowSts
	MAX-ACCESS  read-write
	STATUS  current
	DESCRIPTION
		"To create or delete a real server entry."
	::= {snL4RealServerEntry  7 }

snL4RealServerDeleteState	OBJECT-TYPE
	SYNTAX	L4DeleteState
	MAX-ACCESS  read-only
	STATUS  current
	DESCRIPTION
		"Delete operation state." 
	::= { snL4RealServerEntry 8 }



-- Virtual Server Port table

snL4VirtualServerPortTable	       OBJECT-TYPE
	SYNTAX	SEQUENCE OF SnL4VirtualServerPortEntry
	MAX-ACCESS  not-accessible
	STATUS  current
	DESCRIPTION
		"Virtual Server Port table."
	::= { snL4VirtualServerPort 1 }

snL4VirtualServerPortEntry	       OBJECT-TYPE
	SYNTAX	SnL4VirtualServerPortEntry
	MAX-ACCESS  not-accessible
	STATUS  current
	DESCRIPTION
		"An entry in the Virtual Server Port table."
	INDEX	{ snL4VirtualServerPortIndex }
	::= { snL4VirtualServerPortTable 1 }

SnL4VirtualServerPortEntry ::= SEQUENCE {
	snL4VirtualServerPortIndex
		INTEGER,
	snL4VirtualServerPortServerName
		L4ServerName,
	snL4VirtualServerPortPort
		INTEGER,
	snL4VirtualServerPortAdminStatus
		L4Status,
	snL4VirtualServerPortSticky
		INTEGER,
	snL4VirtualServerPortConcurrent
		INTEGER,
	snL4VirtualServerPortRowStatus
		L4RowSts,
	snL4VirtualServerPortDeleteState
		L4DeleteState
	}


snL4VirtualServerPortIndex	       OBJECT-TYPE
	SYNTAX	INTEGER (1..2048)
	MAX-ACCESS  read-only
	STATUS  current
	DESCRIPTION
		"The index for Virtual Server Port entry."
	::= { snL4VirtualServerPortEntry 1 }


snL4VirtualServerPortServerName	       OBJECT-TYPE
	SYNTAX	L4ServerName
	MAX-ACCESS  read-write
	STATUS  current
	DESCRIPTION
		""
	::= { snL4VirtualServerPortEntry 2 }

snL4VirtualServerPortPort       OBJECT-TYPE
	SYNTAX	INTEGER	  (0..65535)
	MAX-ACCESS  read-write
	STATUS  current
	DESCRIPTION
		""
	::= { snL4VirtualServerPortEntry 3 }


snL4VirtualServerPortAdminStatus		       OBJECT-TYPE
	SYNTAX	L4Status
	MAX-ACCESS  read-write
	STATUS  current
	DESCRIPTION
		""
	::= { snL4VirtualServerPortEntry 4 }


 snL4VirtualServerPortSticky       OBJECT-TYPE
	 SYNTAX  INTEGER {
			disabled(0),
			enabled(1)       
			}
	MAX-ACCESS  read-write
	STATUS  current
	DESCRIPTION
		""
	::= { snL4VirtualServerPortEntry 5 }


 snL4VirtualServerPortConcurrent       OBJECT-TYPE
	 SYNTAX  INTEGER {
			disabled(0),
			enabled(1)       
			}
	MAX-ACCESS  read-write
	STATUS  current
	DESCRIPTION
		""
	::= { snL4VirtualServerPortEntry 6 }


 snL4VirtualServerPortRowStatus	 	       OBJECT-TYPE
	SYNTAX L4RowSts	
	MAX-ACCESS  read-write
	STATUS  current
	DESCRIPTION
		"To create or delete a virtual server  port entry."
	::= { snL4VirtualServerPortEntry 7 }

snL4VirtualServerPortDeleteState	OBJECT-TYPE
	SYNTAX	L4DeleteState
	MAX-ACCESS  read-only
	STATUS  current
	DESCRIPTION
		"Delete operation state." 
	::= { snL4VirtualServerPortEntry 8 }




-- Real Server Port table

snL4RealServerPortTable	       OBJECT-TYPE
	SYNTAX	SEQUENCE OF SnL4RealServerPortEntry
	MAX-ACCESS  not-accessible
	STATUS  current
	DESCRIPTION
		"Real Server Port table."
	::= { snL4RealServerPort 1 }

snL4RealServerPortEntry	       OBJECT-TYPE
	SYNTAX	SnL4RealServerPortEntry
	MAX-ACCESS  not-accessible
	STATUS  current
	DESCRIPTION
		"An entry in the Real Server Port table."
	INDEX	{ snL4RealServerPortIndex }
	::= { snL4RealServerPortTable 1 }

SnL4RealServerPortEntry ::= SEQUENCE {
	snL4RealServerPortIndex
		INTEGER,
	snL4RealServerPortServerName
		L4ServerName,
	snL4RealServerPortPort
		INTEGER,
	snL4RealServerPortAdminStatus
		L4Status,
	snL4RealServerPortRowStatus
		L4RowSts,
	snL4RealServerPortDeleteState
		L4DeleteState
	}


snL4RealServerPortIndex	       OBJECT-TYPE
	SYNTAX	INTEGER (1..2048)
	MAX-ACCESS  read-only
	STATUS  current
	DESCRIPTION
		"The index for Real Server Port entry."
	::= { snL4RealServerPortEntry 1 }
snL4RealServerPortServerName	       OBJECT-TYPE
	SYNTAX	L4ServerName
	MAX-ACCESS  read-write
	STATUS  current
	DESCRIPTION
		""
	::= { snL4RealServerPortEntry 2 }

snL4RealServerPortPort       OBJECT-TYPE
	SYNTAX	INTEGER	 (0..65535)
	MAX-ACCESS  read-write
	STATUS  current
	DESCRIPTION
		""
	::= { snL4RealServerPortEntry 3 }


snL4RealServerPortAdminStatus		       OBJECT-TYPE
	SYNTAX	L4Status
	MAX-ACCESS  read-write
	STATUS  current
	DESCRIPTION
		""
	::= { snL4RealServerPortEntry 4 }

 snL4RealServerPortRowStatus	 	       OBJECT-TYPE
	SYNTAX L4RowSts	
	MAX-ACCESS  read-write
	STATUS  current
	DESCRIPTION
		"To create or delete a Real server  port entry."
	::= { snL4RealServerPortEntry 5 }

snL4RealServerPortDeleteState	OBJECT-TYPE
	SYNTAX	L4DeleteState
	MAX-ACCESS  read-only
	STATUS  current
	DESCRIPTION
		"Delete operation state." 
	::= { snL4RealServerPortEntry 6 }



-- Bind table

snL4BindTable	       OBJECT-TYPE
	SYNTAX	SEQUENCE OF SnL4BindEntry
	MAX-ACCESS  not-accessible
	STATUS  current
	DESCRIPTION
		"Bind table."
	::= { snL4Bind 1 }

snL4BindEntry	       OBJECT-TYPE
	SYNTAX	SnL4BindEntry
	MAX-ACCESS  not-accessible
	STATUS  current
	DESCRIPTION
		"An entry in the Bind table."
	INDEX	{ snL4BindIndex }
	::= { snL4BindTable 1 }

SnL4BindEntry ::= SEQUENCE {
	snL4BindIndex
		INTEGER,
	snL4BindVirtualServerName
		L4ServerName,
	snL4BindVirtualPortNumber
		INTEGER,
	snL4BindRealServerName
		L4ServerName,
	snL4BindRealPortNumber
		INTEGER,
	snL4BindRowStatus
		INTEGER
	}


snL4BindIndex	       OBJECT-TYPE
	SYNTAX	INTEGER (1..2048)
	MAX-ACCESS  read-only
	STATUS  current
	DESCRIPTION
		"The index for Bind entry."
	::= { snL4BindEntry 1 }

snL4BindVirtualServerName 	       OBJECT-TYPE
	SYNTAX	L4ServerName
	MAX-ACCESS  read-write
	STATUS  current
	DESCRIPTION
		""
	::= { snL4BindEntry 2 }

snL4BindVirtualPortNumber        OBJECT-TYPE
	SYNTAX	INTEGER	 (0..65535)
	MAX-ACCESS  read-write
	STATUS  current
	DESCRIPTION
		""
	::= { snL4BindEntry 3 }


 snL4BindRealServerName	       OBJECT-TYPE
	SYNTAX	L4ServerName
	MAX-ACCESS  read-write
	STATUS  current
	DESCRIPTION
		""
	::= { snL4BindEntry 4 }

snL4BindRealPortNumber       OBJECT-TYPE
	SYNTAX	INTEGER	 (0..65535)
	MAX-ACCESS  read-write
	STATUS  current
	DESCRIPTION
		""
	::= { snL4BindEntry 5 }
snL4BindRowStatus  	 	       OBJECT-TYPE
	SYNTAX	 INTEGER {
			  other(1),
			  valid(2),
			 delete(3),
			 create(4)
	}
	MAX-ACCESS  read-write
	STATUS  current
	DESCRIPTION
		"To create or delete bind entry."
	::= { snL4BindEntry 6 }





-- Virtual Server Status table

snL4VirtualServerStatusTable  OBJECT-TYPE
	SYNTAX	SEQUENCE OF SnL4VirtualServerStatusEntry
	MAX-ACCESS  not-accessible
	STATUS  current
	DESCRIPTION
		"Virtual Server Status table."
	::= { snL4VirtualServerStatus 1 }

snL4VirtualServerStatusEntry  OBJECT-TYPE
	SYNTAX	SnL4VirtualServerStatusEntry
	MAX-ACCESS  not-accessible
	STATUS  current
	DESCRIPTION
		"An entry in L4 Virtual Server Status table."
	INDEX	{ snL4VirtualServerStatusIndex }
	::= { snL4VirtualServerStatusTable 1 }

SnL4VirtualServerStatusEntry ::= SEQUENCE {
	snL4VirtualServerStatusIndex
		INTEGER,
	snL4VirtualServerStatusName
		L4ServerName,
	snL4VirtualServerStatusReceivePkts
		Counter32,
	snL4VirtualServerStatusTransmitPkts
		Counter32,
	snL4VirtualServerStatusTotalConnections
		Counter32
	}

snL4VirtualServerStatusIndex  OBJECT-TYPE
	SYNTAX	INTEGER (1..64)
	MAX-ACCESS  read-only
	STATUS  current
	DESCRIPTION
		"The table index for a Virtual Server  Status entry."
	::= { snL4VirtualServerStatusEntry 1 }


snL4VirtualServerStatusName  OBJECT-TYPE
	SYNTAX	L4ServerName
	MAX-ACCESS  read-only
	STATUS  current
	DESCRIPTION
		"Virtual server name."
	::= { snL4VirtualServerStatusEntry 2 }


snL4VirtualServerStatusReceivePkts  OBJECT-TYPE
	SYNTAX	Counter32
	MAX-ACCESS	read-only
	STATUS  current
	DESCRIPTION
		"" 
	::= { snL4VirtualServerStatusEntry 3 }

snL4VirtualServerStatusTransmitPkts  OBJECT-TYPE
	SYNTAX	Counter32
	MAX-ACCESS	read-only
	STATUS  current
	DESCRIPTION
		"" 
	::= { snL4VirtualServerStatusEntry 4 }

snL4VirtualServerStatusTotalConnections  OBJECT-TYPE
	SYNTAX	Counter32
	MAX-ACCESS	read-only
	STATUS  current
	DESCRIPTION
		"" 
	::= { snL4VirtualServerStatusEntry 5 }


-- Real Server Status Table

snL4RealServerStatusTable  OBJECT-TYPE
	SYNTAX	SEQUENCE OF SnL4RealServerStatusEntry
	MAX-ACCESS  not-accessible
	STATUS  current
	DESCRIPTION
		"Real Server Status table."
	::= { snL4RealServerStatus 1 }

snL4RealServerStatusEntry  OBJECT-TYPE
	SYNTAX	SnL4RealServerStatusEntry
	MAX-ACCESS  not-accessible
	STATUS  current
	DESCRIPTION
		"An entry in the Real Server Status table."
	INDEX	{ snL4RealServerStatusIndex }
	::= { snL4RealServerStatusTable 1 }

SnL4RealServerStatusEntry ::= SEQUENCE {
	snL4RealServerStatusIndex
		INTEGER,
	snL4RealServerStatusName
		L4ServerName,
	snL4RealServerStatusRealIP
		IpAddress,
	snL4RealServerStatusReceivePkts
		Counter32,
	snL4RealServerStatusTransmitPkts
		Counter32,
	snL4RealServerStatusCurConnections
		Integer32,
	snL4RealServerStatusTotalConnections
		Counter32,
	snL4RealServerStatusAge
		Integer32,
	snL4RealServerStatusState
		INTEGER,
	snL4RealServerStatusReassignments
		Integer32,
	snL4RealServerStatusReassignmentLimit
		Integer32,
	snL4RealServerStatusFailedPortExists
		Integer32,
	snL4RealServerStatusFailTime
		Integer32,
	snL4RealServerStatusPeakConnections
		Integer32
	}

snL4RealServerStatusIndex  OBJECT-TYPE
	SYNTAX	INTEGER	 (1..256)
	MAX-ACCESS  read-only
	STATUS  current
	DESCRIPTION
		"The table index for a Real Server Status entry."
	::= { snL4RealServerStatusEntry 1 }

snL4RealServerStatusName OBJECT-TYPE
	SYNTAX	L4ServerName
	MAX-ACCESS  read-only
	STATUS  current
	DESCRIPTION
		""
	::= { snL4RealServerStatusEntry 2 }

snL4RealServerStatusRealIP OBJECT-TYPE
	SYNTAX	IpAddress
	MAX-ACCESS  read-only
	STATUS  current
	DESCRIPTION
		""
	::= { snL4RealServerStatusEntry 3 }

snL4RealServerStatusReceivePkts	  OBJECT-TYPE
	SYNTAX	Counter32
	MAX-ACCESS  read-only
	STATUS  current
	DESCRIPTION
		""
	::= { snL4RealServerStatusEntry 4 }

snL4RealServerStatusTransmitPkts  OBJECT-TYPE
	SYNTAX	Counter32
	MAX-ACCESS  read-only
	STATUS  current
	DESCRIPTION
		""
	::= { snL4RealServerStatusEntry 5 }

snL4RealServerStatusCurConnections   OBJECT-TYPE
	SYNTAX   Integer32
	MAX-ACCESS  read-only
	STATUS  current
	DESCRIPTION
		""
	::= { snL4RealServerStatusEntry 6 }

snL4RealServerStatusTotalConnections   OBJECT-TYPE
	SYNTAX	Counter32
	MAX-ACCESS  read-only
	STATUS  current
	DESCRIPTION
		""
	::= { snL4RealServerStatusEntry 7 }

snL4RealServerStatusAge  OBJECT-TYPE
	SYNTAX   Integer32
	MAX-ACCESS  read-only
	STATUS  current
	DESCRIPTION
		""
	::= { snL4RealServerStatusEntry 8 }

snL4RealServerStatusState  OBJECT-TYPE
	SYNTAX	INTEGER	{
	serverdisabled(0),
	serverenabled(1),
	serverfailed(2),
	servertesting(3),
	serversuspect(4),
	servershutdown(5),
	serveractive(6)
	}
	MAX-ACCESS  read-only
	STATUS  current
	DESCRIPTION
		""
	::= { snL4RealServerStatusEntry 9 }

snL4RealServerStatusReassignments  OBJECT-TYPE
	SYNTAX   Integer32
	MAX-ACCESS  read-only
	STATUS  current
	DESCRIPTION
		""
	::= { snL4RealServerStatusEntry 10 }

snL4RealServerStatusReassignmentLimit  OBJECT-TYPE
	SYNTAX   Integer32
	MAX-ACCESS  read-only
	STATUS  current
	DESCRIPTION
		""
	::= { snL4RealServerStatusEntry 11 }

snL4RealServerStatusFailedPortExists  OBJECT-TYPE
	SYNTAX   Integer32
	MAX-ACCESS  read-only
	STATUS  current
	DESCRIPTION
		""
	::= { snL4RealServerStatusEntry 12 }

snL4RealServerStatusFailTime  OBJECT-TYPE
	SYNTAX   Integer32
	MAX-ACCESS  read-only
	STATUS  current
	DESCRIPTION
		""
	::= { snL4RealServerStatusEntry 13 }


snL4RealServerStatusPeakConnections   OBJECT-TYPE
	SYNTAX   Integer32
	MAX-ACCESS  read-only
	STATUS  current
	DESCRIPTION
		""
	::= { snL4RealServerStatusEntry 14 }




-- Virtual Server Port Status table

snL4VirtualServerPortStatusTable	       OBJECT-TYPE
	SYNTAX	SEQUENCE OF SnL4VirtualServerPortStatusEntry
	MAX-ACCESS  not-accessible
	STATUS  current
	DESCRIPTION
		"Virtual Server Port Status table."
	::= { snL4VirtualServerPortStatus 1 }

snL4VirtualServerPortStatusEntry	       OBJECT-TYPE
	SYNTAX	SnL4VirtualServerPortStatusEntry
	MAX-ACCESS  not-accessible
	STATUS  current
	DESCRIPTION
		"An entry in the Virtual Server Port Status table."
	INDEX	{ snL4VirtualServerPortStatusIndex }
	::= { snL4VirtualServerPortStatusTable 1 }

SnL4VirtualServerPortStatusEntry ::= SEQUENCE {
	snL4VirtualServerPortStatusIndex
		Integer32,
	snL4VirtualServerPortStatusPort
		INTEGER,
	snL4VirtualServerPortStatusServerName
		L4ServerName,
	snL4VirtualServerPortStatusCurrentConnection
		Integer32,
	snL4VirtualServerPortStatusTotalConnection
		Counter32,
	snL4VirtualServerPortStatusPeakConnection
		Integer32
	}

snL4VirtualServerPortStatusIndex	       OBJECT-TYPE
	SYNTAX   Integer32
	MAX-ACCESS  read-only
	STATUS  current
	DESCRIPTION
		"The index for Virtual Server Port Status entry."
	::= { snL4VirtualServerPortStatusEntry 1 }

snL4VirtualServerPortStatusPort   OBJECT-TYPE
	SYNTAX	INTEGER	 (1..2048)
	MAX-ACCESS  read-only
	STATUS  current
	DESCRIPTION
		""
	::= { snL4VirtualServerPortStatusEntry 2 }

 snL4VirtualServerPortStatusServerName 	       OBJECT-TYPE
	SYNTAX	L4ServerName
	MAX-ACCESS  read-only
	STATUS  current
	DESCRIPTION
		""
	::= { snL4VirtualServerPortStatusEntry 3 }

 snL4VirtualServerPortStatusCurrentConnection 	       OBJECT-TYPE
	SYNTAX   Integer32
	MAX-ACCESS  read-only
	STATUS  current
	DESCRIPTION
		""
	::= { snL4VirtualServerPortStatusEntry 4 }

 snL4VirtualServerPortStatusTotalConnection		       OBJECT-TYPE
	SYNTAX	Counter32
	MAX-ACCESS  read-only
	STATUS  current
	DESCRIPTION
		""
	::= { snL4VirtualServerPortStatusEntry 5 }

 snL4VirtualServerPortStatusPeakConnection 	       OBJECT-TYPE
	SYNTAX   Integer32
	MAX-ACCESS  read-only
	STATUS  current
	DESCRIPTION
		""
	::= { snL4VirtualServerPortStatusEntry 6 }

-- Real Server Port Status table

snL4RealServerPortStatusTable	       OBJECT-TYPE
	SYNTAX	SEQUENCE OF SnL4RealServerPortStatusEntry
	MAX-ACCESS  not-accessible
	STATUS  current
	DESCRIPTION
		"Real Server Port Status table."
	::= { snL4RealServerPortStatus 1 }

snL4RealServerPortStatusEntry	       OBJECT-TYPE
	SYNTAX	SnL4RealServerPortStatusEntry
	MAX-ACCESS  not-accessible
	STATUS  current
	DESCRIPTION
		"An entry in the Real Server Port Status table."
	INDEX	{ snL4RealServerPortStatusIndex }
	::= { snL4RealServerPortStatusTable 1 }

SnL4RealServerPortStatusEntry ::= SEQUENCE {
	snL4RealServerPortStatusIndex
		INTEGER,
	snL4RealServerPortStatusPort
		Integer32,
	snL4RealServerPortStatusServerName
		L4ServerName,
	snL4RealServerPortStatusReassignCount
		Integer32,
	snL4RealServerPortStatusState
		INTEGER,
	snL4RealServerPortStatusFailTime
		Integer32,
	snL4RealServerPortStatusCurrentConnection
		Integer32,
	snL4RealServerPortStatusTotalConnection
		Counter32,
	snL4RealServerPortStatusRxPkts
		Counter32,
	snL4RealServerPortStatusTxPkts
		Counter32,
	snL4RealServerPortStatusRxBytes
		Counter32,
	snL4RealServerPortStatusTxBytes
		Counter32,
	snL4RealServerPortStatusPeakConnection
		Integer32
	}


snL4RealServerPortStatusIndex	       OBJECT-TYPE
	SYNTAX	INTEGER	  (1..2048)
	MAX-ACCESS  read-only
	STATUS  current
	DESCRIPTION
		"The index for Real Server Port Status entry."
	::= { snL4RealServerPortStatusEntry 1 }

snL4RealServerPortStatusPort	       OBJECT-TYPE
	SYNTAX   Integer32
	MAX-ACCESS  read-only
	STATUS  current
	DESCRIPTION
		""
	::= { snL4RealServerPortStatusEntry 2 }

snL4RealServerPortStatusServerName	       OBJECT-TYPE
	SYNTAX	L4ServerName
	MAX-ACCESS  read-only
	STATUS  current
	DESCRIPTION
		""
	::= { snL4RealServerPortStatusEntry 3 }

snL4RealServerPortStatusReassignCount	       OBJECT-TYPE
	SYNTAX   Integer32
	MAX-ACCESS  read-only
	STATUS  current
	DESCRIPTION
		""
	::= { snL4RealServerPortStatusEntry 4 }

 snL4RealServerPortStatusState	       OBJECT-TYPE
	SYNTAX	INTEGER	{
		disabled(0),
		enabled(1),
		failed(2),
		testing(3),
		suspect(4),
		shutdown(5),
		active(6),
		unbound(7),
		awaitUnbind(8),
		awaitDelete(9)
	}
	MAX-ACCESS  read-only
	STATUS  current
	DESCRIPTION
		"Real server port state"
	::= { snL4RealServerPortStatusEntry 5 }

snL4RealServerPortStatusFailTime 	       OBJECT-TYPE
	SYNTAX   Integer32
	MAX-ACCESS  read-only
	STATUS  current
	DESCRIPTION
		"Only useful, if real server port state is failed.
		 Indicating how seconds has been elapsed from the last retry."
	::= { snL4RealServerPortStatusEntry 6 }

snL4RealServerPortStatusCurrentConnection	       OBJECT-TYPE
	SYNTAX   Integer32
	MAX-ACCESS  read-only
	STATUS  current
	DESCRIPTION
		"Real server port current connection"
	::= { snL4RealServerPortStatusEntry 7 }

snL4RealServerPortStatusTotalConnection	       OBJECT-TYPE
	SYNTAX	Counter32
	MAX-ACCESS  read-only
	STATUS  current
	DESCRIPTION
		"Real server port total connection"
	::= { snL4RealServerPortStatusEntry 8 }

snL4RealServerPortStatusRxPkts	       OBJECT-TYPE
	SYNTAX	Counter32
	MAX-ACCESS  read-only
	STATUS  current
	DESCRIPTION
		"Real server port receive packets."
	::= { snL4RealServerPortStatusEntry 9 }


snL4RealServerPortStatusTxPkts	       OBJECT-TYPE
	SYNTAX	Counter32
	MAX-ACCESS  read-only
	STATUS  current
	DESCRIPTION
		"Real server port transmit packets."
	::= { snL4RealServerPortStatusEntry 10 }


snL4RealServerPortStatusRxBytes	       OBJECT-TYPE
	SYNTAX	Counter32
	MAX-ACCESS  read-only
	STATUS  current
	DESCRIPTION
		"Real server port receive bytes."
	::= { snL4RealServerPortStatusEntry 11 }

snL4RealServerPortStatusTxBytes	       OBJECT-TYPE
	SYNTAX	Counter32
	MAX-ACCESS  read-only
	STATUS  current
	DESCRIPTION
		"Real server port transmit bytes."
	::= { snL4RealServerPortStatusEntry 12 }


snL4RealServerPortStatusPeakConnection	       OBJECT-TYPE
	SYNTAX   Integer32
	MAX-ACCESS  read-only
	STATUS  current
	DESCRIPTION
		"peak connection for real server port."
	::= { snL4RealServerPortStatusEntry 13 }




-- L4 policy table

snL4PolicyTable	  OBJECT-TYPE
	SYNTAX	SEQUENCE OF SnL4PolicyEntry
	MAX-ACCESS  not-accessible
	STATUS  current
	DESCRIPTION
		"L4 policy table."
	::= {snL4Policy  1 }

snL4PolicyEntry	  OBJECT-TYPE
	SYNTAX	SnL4PolicyEntry
	MAX-ACCESS  not-accessible
	STATUS  current
	DESCRIPTION
		"An entry of the L4 policy table."
	INDEX	{ snL4PolicyId }
	::= { snL4PolicyTable 1 }

SnL4PolicyEntry ::= SEQUENCE {
	snL4PolicyId
		INTEGER,
	snL4PolicyPriority
		INTEGER,
	snL4PolicyScope
		INTEGER,
	snL4PolicyProtocol
		INTEGER,
	snL4PolicyPort
		INTEGER,
	snL4PolicyRowStatus
		INTEGER
	}

snL4PolicyId         OBJECT-TYPE
	SYNTAX	INTEGER (1..64)
	MAX-ACCESS  read-only
	STATUS  current
	DESCRIPTION
		"The  ID to identify a  entry."
	::= { snL4PolicyEntry 1 }

snL4PolicyPriority	   OBJECT-TYPE
	SYNTAX  INTEGER {
		level0(0),
		level1(1),
		level2(2),
		level3(3),
		level4(4),
		level5(5),
		level6(6),
		level7(7)
		}
	MAX-ACCESS  read-write
	STATUS  current
	DESCRIPTION
		"The Stand alone stackable switch L4 Policy Priority values are:
		 normal(0)   		 -- normal prority
		 high(1) 	 		 -- high prority
		 cache(2) 	 		 -- prority for cache
		 transparent(3) 	 -- prority for transparent
		 The BigIron switch L4 Priority values are:
		level0(0), level1(1), level2(2), level3(3),
		level4(4), level5(5), level6(6), level7(7) "
	::= { snL4PolicyEntry 2 }

snL4PolicyScope	   OBJECT-TYPE
	SYNTAX	INTEGER { global(0), local(1) }
	MAX-ACCESS  read-write
	STATUS  current
	DESCRIPTION
		" Scope of the  local or global.
		  Global  automatic apply to all port.
		  Local  apply to a port."
	::= { snL4PolicyEntry 3 }

snL4PolicyProtocol     OBJECT-TYPE
	SYNTAX	INTEGER { udp(0), tcp(1) }

	MAX-ACCESS  read-write
	STATUS  current
	DESCRIPTION
		""
	::= { snL4PolicyEntry 4 }

snL4PolicyPort OBJECT-TYPE
	SYNTAX	INTEGER	 (0..65535)
	MAX-ACCESS  read-write
	STATUS  current
	DESCRIPTION ""
	::= { snL4PolicyEntry 5 }

snL4PolicyRowStatus  OBJECT-TYPE
	SYNTAX	INTEGER {
		invalid(1),
		valid(2),
		delete(3),
		create(4),
		modify(5)
	}
	MAX-ACCESS	 read-write
	STATUS	 current
	DESCRIPTION
		"This object is used to create and
		delete row in the table and control
		if they are used. The values
		that can be written are:
		delete(3)...deletes the row
		create(4)...creates a new row
		modify(5)...modifies an exsisting row

		If the row exists, then a SET with
		value of create(4) returns error
		'badValue'. Deleted rows go away
		immediately. The following values
		can be returned on reads:
		invalid(1)...Setting it to 'invalid' has the effect of
					 rendering it inoperative.
		valid(2).....the row exists and is valid"
	::= { snL4PolicyEntry 6 }

-- L4 policy port access table

snL4PolicyPortAccessTable	     OBJECT-TYPE
	SYNTAX	SEQUENCE OF SnL4PolicyPortAccessEntry
	MAX-ACCESS  not-accessible
	STATUS  current
	DESCRIPTION
		"ip interface L4 policy access table."
	::= {snL4PolicyPortAccess  1}

snL4PolicyPortAccessEntry	     OBJECT-TYPE
	SYNTAX	SnL4PolicyPortAccessEntry
	MAX-ACCESS  not-accessible
	STATUS  current
	DESCRIPTION
		"An entry of the ip interface L4 policy access  table."
	INDEX	{ snL4PolicyPortAccessPort }
	::= { snL4PolicyPortAccessTable 1 }

SnL4PolicyPortAccessEntry ::= SEQUENCE {
	snL4PolicyPortAccessPort
		Integer32,
	snL4PolicyPortAccessList
		OCTET STRING,
	snL4PolicyPortAccessRowStatus
		INTEGER
	}

snL4PolicyPortAccessPort	     OBJECT-TYPE
	SYNTAX   Integer32	
	MAX-ACCESS  read-only
	STATUS  current
	DESCRIPTION
		"The ip interface to which the L4 policy  applies."
	::= { snL4PolicyPortAccessEntry 1 }

snL4PolicyPortAccessList  OBJECT-TYPE
	SYNTAX	OCTET STRING (SIZE(1..64))
	MAX-ACCESS  read-write
	STATUS  current
	DESCRIPTION
		"An ip L4 policy  list, of which each octet contains
		a  ID number that forms a group of s. A
		valid entry in the snL4PolicyTable with the
		corresponding  ID number (i.e. snL4PolicyId)
		must have been created before a  list is initialized."
	::= { snL4PolicyPortAccessEntry 2 }

snL4PolicyPortAccessRowStatus   OBJECT-TYPE
	SYNTAX	 INTEGER {
		invalid(1),
		valid(2),
		delete(3),
		create(4),
		modify(5)
	}
	MAX-ACCESS	 read-write
	STATUS	 current
	DESCRIPTION
		"This object is used to create and
		delete row in the table and control
		if they are used. The values
		that can be written are:
		delete(3)...deletes the row
		create(4)...creates a new row
		modify(5)...modifies an exsisting row

		If the row exists, then a SET with
		value of create(4) returns error
		'badValue'. Deleted rows go away
		immediately. The following values
		can be returned on reads:
		invalid(1)...Setting it to 'invalid' has the effect of
					 rendering it inoperative.
		valid(2).....the row exists and is valid"
	::= { snL4PolicyPortAccessEntry 3 }

-- L4 trap variable binding objects

snL4TrapRealServerIP             OBJECT-TYPE
	SYNTAX IpAddress
	MAX-ACCESS read-only
	STATUS current
	DESCRIPTION
		"Real server IP address."
	::= { snL4Trap 1 }

snL4TrapRealServerName           OBJECT-TYPE
	SYNTAX L4ServerName
	MAX-ACCESS read-only
	STATUS current
	DESCRIPTION
		"Real server name."
	::= { snL4Trap 2 }

snL4TrapRealServerPort           OBJECT-TYPE
	SYNTAX Integer32
	MAX-ACCESS read-only
	STATUS current
	DESCRIPTION
		"Transport protocol port number of the real server."
	::= { snL4Trap 3 }

snL4TrapRealServerCurConnections OBJECT-TYPE
	SYNTAX Integer32
	MAX-ACCESS read-only
	STATUS current
	DESCRIPTION
		"Real Server current connections."
	::= { snL4Trap 4 }

snL4TrapLinkName OBJECT-TYPE
	SYNTAX L4ServerName
	MAX-ACCESS read-only
	STATUS current
	DESCRIPTION
		"Link name."
	::= { snL4Trap 5 }

snL4LinkVirtualInterface OBJECT-TYPE
	SYNTAX Integer32
	MAX-ACCESS read-only
	STATUS current
	DESCRIPTION
		"Link virtual interface."
	::= { snL4Trap 6 }

-- Web Cache table

snL4WebCacheTable  OBJECT-TYPE
	SYNTAX	SEQUENCE OF SnL4WebCacheEntry
	MAX-ACCESS  not-accessible
	STATUS  current
	DESCRIPTION
		"Real Server table."
	::= { snL4WebCache 1 }

snL4WebCacheEntry  OBJECT-TYPE
	SYNTAX	SnL4WebCacheEntry
	MAX-ACCESS  not-accessible
	STATUS  current
	DESCRIPTION
		"An entry in the Real Server table."
	INDEX	{ snL4WebCacheIP }
	::= { snL4WebCacheTable 1 }

SnL4WebCacheEntry ::= SEQUENCE {
	snL4WebCacheIP
		IpAddress,
	snL4WebCacheName
		L4ServerName,
	snL4WebCacheAdminStatus
		L4Status,
	snL4WebCacheMaxConnections
		INTEGER,
	snL4WebCacheWeight
		INTEGER,
	snL4WebCacheRowStatus
		L4RowSts,
	snL4WebCacheDeleteState
		L4DeleteState
	}

snL4WebCacheIP
	OBJECT-TYPE
	SYNTAX IpAddress
	MAX-ACCESS  read-only
	STATUS  current
	DESCRIPTION
		"Real Server IP Address."
	::= { snL4WebCacheEntry 1 }

snL4WebCacheName  OBJECT-TYPE
	SYNTAX	L4ServerName
	MAX-ACCESS  read-write
	STATUS  current
	DESCRIPTION
		"Real server name."
	::= { snL4WebCacheEntry 2 }

snL4WebCacheAdminStatus	OBJECT-TYPE
	SYNTAX	L4Status
	MAX-ACCESS  read-write
	STATUS  current
	DESCRIPTION
		"Real Server status is ether disabled(0) or enabled(1)."
	::= { snL4WebCacheEntry 3 }

snL4WebCacheMaxConnections 	OBJECT-TYPE
	SYNTAX	INTEGER	 (0..1000000)
	MAX-ACCESS  read-write
	STATUS  current
	DESCRIPTION
		"Real Server Maximum Connection allowed."
	::= { snL4WebCacheEntry 4 }

 snL4WebCacheWeight	OBJECT-TYPE
	SYNTAX	INTEGER	  (1..65000)
	MAX-ACCESS  read-write
	STATUS  current
	DESCRIPTION
		"Real Server weight"
	::= { snL4WebCacheEntry 5 }

 snL4WebCacheRowStatus OBJECT-TYPE
	SYNTAX  L4RowSts
	MAX-ACCESS  read-write
	STATUS  current
	DESCRIPTION
		"To create or delete a real server entry."
	::= {snL4WebCacheEntry  6 }

snL4WebCacheDeleteState	OBJECT-TYPE
	SYNTAX	L4DeleteState
	MAX-ACCESS  read-only
	STATUS  current
	DESCRIPTION
		"Delete operation state." 
	::= { snL4WebCacheEntry 7 }


-- Web Cache Group table


snL4WebCacheGroupTable  OBJECT-TYPE
	SYNTAX	SEQUENCE OF SnL4WebCacheGroupEntry
	MAX-ACCESS  not-accessible
	STATUS  current
	DESCRIPTION
		"Web Cache Group table."
	::= { snL4WebCacheGroup 1 }

snL4WebCacheGroupEntry  OBJECT-TYPE
	SYNTAX	SnL4WebCacheGroupEntry
	MAX-ACCESS  not-accessible
	STATUS  current
	DESCRIPTION
		"An entry in the  Web Cache Group table."
	INDEX	{ snL4WebCacheGroupId }
	::= { snL4WebCacheGroupTable 1 }

SnL4WebCacheGroupEntry ::= SEQUENCE {
	snL4WebCacheGroupId
		Integer32,
	snL4WebCacheGroupName
		L4ServerName,
	snL4WebCacheGroupWebCacheIpList
		OCTET STRING,
	snL4WebCacheGroupDestMask
		IpAddress,
	snL4WebCacheGroupSrcMask
		IpAddress,
	snL4WebCacheGroupAdminStatus
		INTEGER,
	snL4WebCacheGroupRowStatus
		L4RowSts
	}

snL4WebCacheGroupId  OBJECT-TYPE
	SYNTAX   Integer32
	MAX-ACCESS  read-only
	STATUS  current
	DESCRIPTION
		"The identification for a Web Cache Group entry.
		 The limit is from 1 to snL4MaxNumWebCacheGroup."
	::= { snL4WebCacheGroupEntry 1 }

snL4WebCacheGroupName  OBJECT-TYPE
	SYNTAX	L4ServerName
	MAX-ACCESS  read-write
	STATUS  current
	DESCRIPTION
		"Web Cache Group name."
	::= { snL4WebCacheGroupEntry 2 }

snL4WebCacheGroupWebCacheIpList
	OBJECT-TYPE
	SYNTAX	OCTET STRING
	MAX-ACCESS  read-write
	STATUS  current
	DESCRIPTION
		"A list of the Server Cache Group Real Server IP Address.
		 The number of IP Address is from 1 (4 OCTETs) to the 
		 snL4MaxNumServersPerWebCacheGroup, maximum number of 
		 server IP Address allowed in the list."
	::= { snL4WebCacheGroupEntry 3 }

snL4WebCacheGroupDestMask 	OBJECT-TYPE
	SYNTAX  IpAddress
	MAX-ACCESS  read-write
	STATUS  current
	DESCRIPTION
		"Cache Server Group Destination Mask."
	::= { snL4WebCacheGroupEntry 4 }

snL4WebCacheGroupSrcMask 	OBJECT-TYPE
	SYNTAX  IpAddress
	MAX-ACCESS  read-write
	STATUS  current
	DESCRIPTION
		"Cache Server Group Source Mask."
	::= { snL4WebCacheGroupEntry 5 }

snL4WebCacheGroupAdminStatus OBJECT-TYPE
	SYNTAX  INTEGER {
		disabled(0),             
		enabled(1)
		}
	MAX-ACCESS  read-write
	STATUS  current
	DESCRIPTION
		"The WEB Cache Group is set either
		 enabled(1)...........activated.
		 disabled(0)..........disabled."  
	::= { snL4WebCacheGroupEntry 6 }

 snL4WebCacheGroupRowStatus OBJECT-TYPE
	SYNTAX  L4RowSts
	MAX-ACCESS  read-write
	STATUS  current
	DESCRIPTION
		"To create or delete a Web Cache Group entry."
	::= { snL4WebCacheGroupEntry 7 }


-- Web Cache Traffic Statistics Table 

snL4WebCacheTrafficStatsTable  OBJECT-TYPE
	SYNTAX	SEQUENCE OF SnL4WebCacheTrafficStatsEntry
	MAX-ACCESS  not-accessible
	STATUS  current
	DESCRIPTION
		"Web Cache Traffic Statistics table."
	::= { snL4WebCacheTrafficStats 1 }

snL4WebCacheTrafficStatsEntry  OBJECT-TYPE
	SYNTAX	SnL4WebCacheTrafficStatsEntry
	MAX-ACCESS  not-accessible
	STATUS  current
	DESCRIPTION
		"An entry in the Web Cache Traffic Statistics table."
	INDEX	{ snL4WebCacheTrafficIp , snL4WebCacheTrafficPort}
	::= { snL4WebCacheTrafficStatsTable 1 }

SnL4WebCacheTrafficStatsEntry ::= SEQUENCE {
	snL4WebCacheTrafficIp
		IpAddress,
	snL4WebCacheTrafficPort
		INTEGER,
	snL4WebCacheCurrConnections
		Integer32,
	snL4WebCacheTotalConnections
		Integer32,
	snL4WebCacheTxPkts
		Counter32,
	snL4WebCacheRxPkts
		Counter32,
	snL4WebCacheTxOctets
		Counter32,
	snL4WebCacheRxOctets
		Counter32,
	snL4WebCachePortState
		WebCacheState
	}

snL4WebCacheTrafficIp 	OBJECT-TYPE
	SYNTAX  IpAddress
	MAX-ACCESS  read-only
	STATUS  current
	DESCRIPTION
		"Cache Server IP Address."
	::= { snL4WebCacheTrafficStatsEntry 1 }

snL4WebCacheTrafficPort 		OBJECT-TYPE
	SYNTAX  INTEGER (0..65535)
	MAX-ACCESS  read-only
	STATUS  current
	DESCRIPTION
		"The WEB Cache port is one of the protocol port such as UDP, TCP etc."
	::= { snL4WebCacheTrafficStatsEntry 2 }

snL4WebCacheCurrConnections 		OBJECT-TYPE
	SYNTAX   Integer32
	MAX-ACCESS  read-only
	STATUS  current
	DESCRIPTION
		"Number of the current connections in WEB Cache group."
	::= { snL4WebCacheTrafficStatsEntry 3 }

snL4WebCacheTotalConnections 		OBJECT-TYPE
	SYNTAX   Integer32
	MAX-ACCESS  read-only
	STATUS  current
	DESCRIPTION
		"The total connections in WEB Cache group."
	::= { snL4WebCacheTrafficStatsEntry 4 }

snL4WebCacheTxPkts 		OBJECT-TYPE
	SYNTAX	Counter32
	MAX-ACCESS  read-only
	STATUS  current
	DESCRIPTION
		"Number of the Packets sending from Client/Web-Server to Cache Server"
	::= { snL4WebCacheTrafficStatsEntry 5 }

snL4WebCacheRxPkts 		OBJECT-TYPE
	SYNTAX	Counter32
	MAX-ACCESS  read-only
	STATUS  current
	DESCRIPTION
		"Number of the Packets sending from Cache Server to Client/Web-Server"
	::= { snL4WebCacheTrafficStatsEntry 6 }

snL4WebCacheTxOctets 		OBJECT-TYPE
	SYNTAX	Counter32
	MAX-ACCESS  read-only
	STATUS  current
	DESCRIPTION
		"Number of the Octets sending from Client/Web-Server to Cache Server"
	::= { snL4WebCacheTrafficStatsEntry 7 }

snL4WebCacheRxOctets 		OBJECT-TYPE
	SYNTAX	Counter32
	MAX-ACCESS  read-only
	STATUS  current
	DESCRIPTION
		"Number of the Octets sending from Cache Server to Client/Web-Server"
	::= { snL4WebCacheTrafficStatsEntry 8 }

snL4WebCachePortState	OBJECT-TYPE
	SYNTAX	WebCacheState
	MAX-ACCESS  read-only
	STATUS  current
	DESCRIPTION
		"Web Cache Port state." 
	::= { snL4WebCacheTrafficStatsEntry 9 }

-- Web Uncached Traffic Statistics Table 

snL4WebUncachedTrafficStatsTable  OBJECT-TYPE
	SYNTAX	SEQUENCE OF SnL4WebUncachedTrafficStatsEntry
	MAX-ACCESS  not-accessible
	STATUS  current
	DESCRIPTION
		"Web Uncached Traffic Statistics table."
	::= { snL4WebUncachedTrafficStats 1 }

snL4WebUncachedTrafficStatsEntry  OBJECT-TYPE
	SYNTAX	SnL4WebUncachedTrafficStatsEntry
	MAX-ACCESS  not-accessible
	STATUS  current
	DESCRIPTION
		"An entry in the Web Uncached Traffic Statistics table."
	INDEX	{ snL4WebServerPort, snL4WebClientPort }
	::= { snL4WebUncachedTrafficStatsTable 1 }

SnL4WebUncachedTrafficStatsEntry ::= SEQUENCE {
	snL4WebServerPort
		Integer32,
	snL4WebClientPort
		Integer32,
	snL4WebUncachedTxPkts
		Counter32,
	snL4WebUncachedRxPkts
		Counter32,
	snL4WebUncachedTxOctets
		Counter32,
	snL4WebUncachedRxOctets
		Counter32,
	snL4WebServerPortName
		DisplayString,
	snL4WebClientPortName
		DisplayString
	}

snL4WebServerPort 			OBJECT-TYPE
	SYNTAX  Integer32 
	MAX-ACCESS  read-only
	STATUS  current
	DESCRIPTION
		"Web Server Port."
	::= { snL4WebUncachedTrafficStatsEntry 1 }

snL4WebClientPort 			OBJECT-TYPE
	SYNTAX  Integer32 
	MAX-ACCESS  read-only
	STATUS  current
	DESCRIPTION
		"Web Client Port."
	::= { snL4WebUncachedTrafficStatsEntry 2 }

snL4WebUncachedTxPkts 		OBJECT-TYPE
	SYNTAX	Counter32
	MAX-ACCESS  read-only
	STATUS  current
	DESCRIPTION
		"Number of the Packets sending from Client port to Web Server port"
	::= { snL4WebUncachedTrafficStatsEntry 3 }

snL4WebUncachedRxPkts 		OBJECT-TYPE
	SYNTAX	Counter32
	MAX-ACCESS  read-only
	STATUS  current
	DESCRIPTION
		"Number of the Packets sending from Web Server port to Client port"
	::= { snL4WebUncachedTrafficStatsEntry 4 }

snL4WebUncachedTxOctets 	OBJECT-TYPE
	SYNTAX	Counter32
	MAX-ACCESS  read-only
	STATUS  current
	DESCRIPTION
		"Number of the Octets sending from Client port to Web Server port"
	::= { snL4WebUncachedTrafficStatsEntry 5 }

snL4WebUncachedRxOctets 	OBJECT-TYPE
	SYNTAX	Counter32
	MAX-ACCESS  read-only
	STATUS  current
	DESCRIPTION
		"Number of the Octets sending from Web Server port to Client port"
	::= { snL4WebUncachedTrafficStatsEntry 6 }

snL4WebServerPortName OBJECT-TYPE
	SYNTAX	DisplayString (SIZE(0..16))
	MAX-ACCESS	read-only
	STATUS	current
	DESCRIPTION
		"Web Server Port Name string."
	::= { snL4WebUncachedTrafficStatsEntry 7 }

snL4WebClientPortName OBJECT-TYPE
	SYNTAX	DisplayString (SIZE(0..16))
	MAX-ACCESS	read-only
	STATUS	current
	DESCRIPTION
		"Web Client Port Name string."
	::= { snL4WebUncachedTrafficStatsEntry 8 }


-- Web Cache Server Port table

snL4WebCachePortTable	       OBJECT-TYPE
	SYNTAX	SEQUENCE OF SnL4WebCachePortEntry
	MAX-ACCESS  not-accessible
	STATUS  current
	DESCRIPTION
		"Real Server Port table."
	::= { snL4WebCachePort 1 }

snL4WebCachePortEntry	       OBJECT-TYPE
	SYNTAX	SnL4WebCachePortEntry
	MAX-ACCESS  not-accessible
	STATUS  current
	DESCRIPTION
		"An entry in the Real Server Port table."
	INDEX	{ snL4WebCachePortServerIp, snL4WebCachePortPort }
	::= { snL4WebCachePortTable 1 }

SnL4WebCachePortEntry ::= SEQUENCE {
	snL4WebCachePortServerIp
		IpAddress,
	snL4WebCachePortPort
		INTEGER,
	snL4WebCachePortAdminStatus
		L4Status,
	snL4WebCachePortRowStatus
		L4RowSts,
	snL4WebCachePortDeleteState
		L4DeleteState
	}


snL4WebCachePortServerIp 	OBJECT-TYPE
	SYNTAX  IpAddress
	MAX-ACCESS  read-only
	STATUS  current
	DESCRIPTION
		"Cache Server IP Address."
	::= { snL4WebCachePortEntry 1 }

snL4WebCachePortPort 		OBJECT-TYPE
	SYNTAX  INTEGER (0..65535)
	MAX-ACCESS  read-only
	STATUS  current
	DESCRIPTION
		"The WEB Cache port is one of the protocol port such as UDP, TCP etc."
	::= { snL4WebCachePortEntry 2 }

snL4WebCachePortAdminStatus		       OBJECT-TYPE
	SYNTAX	L4Status
	MAX-ACCESS  read-write
	STATUS  current
	DESCRIPTION
		""
	::= { snL4WebCachePortEntry 3 }

 snL4WebCachePortRowStatus	 	       OBJECT-TYPE
	SYNTAX 	L4RowSts	
	MAX-ACCESS  read-write
	STATUS  current
	DESCRIPTION
		"To create or delete a Real server  port entry."
	::= { snL4WebCachePortEntry 4 }

snL4WebCachePortDeleteState	OBJECT-TYPE
	SYNTAX	L4DeleteState
	MAX-ACCESS  read-only
	STATUS  current
	DESCRIPTION
		"Delete operation state." 
	::= { snL4WebCachePortEntry 5 }

-- Real Server Configuration table 

snL4RealServerCfgTable  OBJECT-TYPE
	SYNTAX	SEQUENCE OF SnL4RealServerCfgEntry
	MAX-ACCESS  not-accessible
	STATUS  current
	DESCRIPTION
		"Real Server table."
	::= { snL4RealServerCfg 1 }

snL4RealServerCfgEntry  OBJECT-TYPE
	SYNTAX	SnL4RealServerCfgEntry
	MAX-ACCESS  not-accessible
	STATUS  current
	DESCRIPTION
		"An entry in the Real Server table."
	INDEX	{ snL4RealServerCfgIP }
	::= { snL4RealServerCfgTable 1 }

SnL4RealServerCfgEntry ::= SEQUENCE {
	snL4RealServerCfgIP
		IpAddress,
	snL4RealServerCfgName
		L4ServerName,
	snL4RealServerCfgAdminStatus
		L4Status,
	snL4RealServerCfgMaxConnections
		Integer32,
	snL4RealServerCfgWeight
		Integer32,
	snL4RealServerCfgRowStatus
		L4RowSts,
	snL4RealServerCfgDeleteState
		L4DeleteState
	}

snL4RealServerCfgIP		OBJECT-TYPE
	SYNTAX IpAddress
	MAX-ACCESS  read-only
	STATUS  current
	DESCRIPTION
		"Real Server IP Address."
	::= { snL4RealServerCfgEntry 1 }
snL4RealServerCfgName  OBJECT-TYPE
	SYNTAX	L4ServerName
	MAX-ACCESS  read-write
	STATUS  current
	DESCRIPTION
		"Real server name."
	::= { snL4RealServerCfgEntry 2 }

snL4RealServerCfgAdminStatus	OBJECT-TYPE
	SYNTAX	L4Status
	MAX-ACCESS  read-write
	STATUS  current
	DESCRIPTION
		"Real Server status is ether disabled(0) or enabled(1)."
	::= { snL4RealServerCfgEntry 3 }

snL4RealServerCfgMaxConnections 	OBJECT-TYPE
	SYNTAX   Integer32	 (0..1000000)
	MAX-ACCESS  read-write
	STATUS  current
	DESCRIPTION
		"Real Server Maximum Connection allowed."
	::= { snL4RealServerCfgEntry 4 }

 snL4RealServerCfgWeight	OBJECT-TYPE
	SYNTAX   Integer32	  (0..65000)
	MAX-ACCESS  read-write
	STATUS  current
	DESCRIPTION
		"Real Server weight"
	::= { snL4RealServerCfgEntry 5 }

 snL4RealServerCfgRowStatus OBJECT-TYPE
	SYNTAX  L4RowSts
	MAX-ACCESS  read-write
	STATUS  current
	DESCRIPTION
		"To create or delete a real server entry."
	::= {snL4RealServerCfgEntry  6 }

snL4RealServerCfgDeleteState	OBJECT-TYPE
	SYNTAX	L4DeleteState
	MAX-ACCESS  read-only
	STATUS  current
	DESCRIPTION
		"Delete operation state." 
	::= { snL4RealServerCfgEntry 7 }


-- Real Server Port Statistic table

snL4RealServerPortCfgTable	       OBJECT-TYPE
	SYNTAX	SEQUENCE OF SnL4RealServerPortCfgEntry
	MAX-ACCESS  not-accessible
	STATUS  current
	DESCRIPTION
		"Real Server Port table."
	::= { snL4RealServerPortCfg 1 }

snL4RealServerPortCfgEntry	       OBJECT-TYPE
	SYNTAX	SnL4RealServerPortCfgEntry
	MAX-ACCESS  not-accessible
	STATUS  current
	DESCRIPTION
		"An entry in the Real Server Port table."
	INDEX	{snL4RealServerPortCfgIP,snL4RealServerPortCfgPort  }
	::= { snL4RealServerPortCfgTable 1 }

SnL4RealServerPortCfgEntry ::= SEQUENCE {
	snL4RealServerPortCfgIP
		IpAddress,
	snL4RealServerPortCfgPort
		Integer32,
	snL4RealServerPortCfgServerName
		L4ServerName,
	snL4RealServerPortCfgAdminStatus
		L4Status,
	snL4RealServerPortCfgRowStatus
		L4RowSts,
	snL4RealServerPortCfgDeleteState
		L4DeleteState
	}


snL4RealServerPortCfgIP	       OBJECT-TYPE
	SYNTAX IpAddress
	MAX-ACCESS  read-only
	STATUS  current
	DESCRIPTION
		"The IP address for the Real Server ."
	::= { snL4RealServerPortCfgEntry 1 }

snL4RealServerPortCfgPort       OBJECT-TYPE
	SYNTAX   Integer32	 (0..65535)
	MAX-ACCESS  read-only
	STATUS  current
	DESCRIPTION
		""
	::= { snL4RealServerPortCfgEntry 3 }


snL4RealServerPortCfgServerName	       OBJECT-TYPE
	SYNTAX	L4ServerName
	MAX-ACCESS  read-only
	STATUS  current
	DESCRIPTION
		""
	::= { snL4RealServerPortCfgEntry 2 }

snL4RealServerPortCfgAdminStatus		       OBJECT-TYPE
	SYNTAX	L4Status
	MAX-ACCESS  read-write
	STATUS  current
	DESCRIPTION
		""
	::= { snL4RealServerPortCfgEntry 4 }

 snL4RealServerPortCfgRowStatus	 	       OBJECT-TYPE
	SYNTAX L4RowSts	
	MAX-ACCESS  read-write
	STATUS  current
	DESCRIPTION
		"To create or delete a Real server  port entry."
	::= { snL4RealServerPortCfgEntry 5 }

snL4RealServerPortCfgDeleteState	OBJECT-TYPE
	SYNTAX	L4DeleteState
	MAX-ACCESS  read-only
	STATUS  current
	DESCRIPTION
		"Delete operation state." 
	::= { snL4RealServerPortCfgEntry 6 }


-- Virtual Server Configuration table

snL4VirtualServerCfgTable  OBJECT-TYPE
	SYNTAX	SEQUENCE OF SnL4VirtualServerCfgEntry
	MAX-ACCESS  not-accessible
	STATUS  current
	DESCRIPTION
		"Virtual Server table."
	::= { snL4VirtualServerCfg 1 }

snL4VirtualServerCfgEntry  OBJECT-TYPE
	SYNTAX	SnL4VirtualServerCfgEntry
	MAX-ACCESS  not-accessible
	STATUS  current
	DESCRIPTION
		"An entry in L4 Virtual Server table."
	INDEX	{snL4VirtualServerCfgVirtualIP  }
	::= { snL4VirtualServerCfgTable 1 }

SnL4VirtualServerCfgEntry ::= SEQUENCE {
	snL4VirtualServerCfgVirtualIP
		IpAddress,
	snL4VirtualServerCfgName
		L4ServerName,
	snL4VirtualServerCfgAdminStatus
		L4Status,
	snL4VirtualServerCfgSDAType
		INTEGER,
	snL4VirtualServerCfgRowStatus
		L4RowSts,
	snL4VirtualServerCfgDeleteState
		L4DeleteState
	}

snL4VirtualServerCfgVirtualIP  	OBJECT-TYPE
	SYNTAX IpAddress
	MAX-ACCESS  read-only
	STATUS  current
	DESCRIPTION
		"Virtual Server IP Address."
	::= { snL4VirtualServerCfgEntry 1 }

snL4VirtualServerCfgName  OBJECT-TYPE
	SYNTAX	L4ServerName
	MAX-ACCESS  read-write
	STATUS  current
	DESCRIPTION
		"Virtual server name."
	::= { snL4VirtualServerCfgEntry 2 }

snL4VirtualServerCfgAdminStatus	OBJECT-TYPE
	SYNTAX	L4Status
	MAX-ACCESS  read-write
	STATUS  current
	DESCRIPTION
		"Virtual Server status is ether disabled(0) or enabled(1)."
	::= { snL4VirtualServerCfgEntry 3 }

snL4VirtualServerCfgSDAType  OBJECT-TYPE
	SYNTAX	 INTEGER {
		default(0),
		leastconnection(1),
		roundrobin(2),
		weighted(3)
	}
	MAX-ACCESS  read-write
	STATUS  current
	DESCRIPTION
		"TCP/UDP Sessions Distribution Algorithms Type."
	::= { snL4VirtualServerCfgEntry 4 }

 snL4VirtualServerCfgRowStatus OBJECT-TYPE
	SYNTAX  L4RowSts
	MAX-ACCESS  read-write
	STATUS  current
	DESCRIPTION
		"To create or delete a virtual server
		entry."
	::= {snL4VirtualServerCfgEntry  5 }

snL4VirtualServerCfgDeleteState	OBJECT-TYPE
	SYNTAX	L4DeleteState
	MAX-ACCESS  read-only
	STATUS  current
	DESCRIPTION
		"Delete operation state." 
	::= { snL4VirtualServerCfgEntry 6 }


-- Virtual Server Port Configuration table

snL4VirtualServerPortCfgTable	       OBJECT-TYPE
	SYNTAX	SEQUENCE OF SnL4VirtualServerPortCfgEntry
	MAX-ACCESS  not-accessible
	STATUS  current
	DESCRIPTION
		"Virtual Server Port table."
	::= { snL4VirtualServerPortCfg 1 }

snL4VirtualServerPortCfgEntry	       OBJECT-TYPE
	SYNTAX	SnL4VirtualServerPortCfgEntry
	MAX-ACCESS  not-accessible
	STATUS  current
	DESCRIPTION
		"An entry in the Virtual Server Port table."
	INDEX	{snL4VirtualServerPortCfgIP, snL4VirtualServerPortCfgPort  }
	::= { snL4VirtualServerPortCfgTable 1 }

SnL4VirtualServerPortCfgEntry ::= SEQUENCE {
	snL4VirtualServerPortCfgIP
		IpAddress,
	snL4VirtualServerPortCfgPort
		Integer32,
	snL4VirtualServerPortCfgServerName
		L4ServerName,
	snL4VirtualServerPortCfgAdminStatus
		L4Status,
	snL4VirtualServerPortCfgSticky
		INTEGER,
	snL4VirtualServerPortCfgConcurrent
		INTEGER,
	snL4VirtualServerPortCfgRowStatus
		L4RowSts,
	snL4VirtualServerPortCfgDeleteState
		L4DeleteState
	}


snL4VirtualServerPortCfgIP       OBJECT-TYPE
	SYNTAX IpAddress
	MAX-ACCESS  read-only
	STATUS  current
	DESCRIPTION
		"Virtual Server IP Address."
	::= { snL4VirtualServerPortCfgEntry 1 }

snL4VirtualServerPortCfgPort       OBJECT-TYPE
	SYNTAX   Integer32	  (0..65535)
	MAX-ACCESS  read-only
	STATUS  current
	DESCRIPTION
		""
	::= { snL4VirtualServerPortCfgEntry 2 }


snL4VirtualServerPortCfgServerName	       OBJECT-TYPE
	SYNTAX	L4ServerName
	MAX-ACCESS  read-only
	STATUS  current
	DESCRIPTION
		""
	::= { snL4VirtualServerPortCfgEntry 3 }

snL4VirtualServerPortCfgAdminStatus		       OBJECT-TYPE
	SYNTAX	L4Status
	MAX-ACCESS  read-write
	STATUS  current
	DESCRIPTION
		""
	::= { snL4VirtualServerPortCfgEntry 4 }


 snL4VirtualServerPortCfgSticky       OBJECT-TYPE
	 SYNTAX  INTEGER {
			disabled(0),
			enabled(1)       
			}
	MAX-ACCESS  read-write
	STATUS  current
	DESCRIPTION
		""
	::= { snL4VirtualServerPortCfgEntry 5 }


 snL4VirtualServerPortCfgConcurrent       OBJECT-TYPE
	 SYNTAX  INTEGER {
			disabled(0),
			enabled(1)       
			}
	MAX-ACCESS  read-write
	STATUS  current
	DESCRIPTION
		""
	::= { snL4VirtualServerPortCfgEntry 6 }


 snL4VirtualServerPortCfgRowStatus	 	       OBJECT-TYPE
	SYNTAX L4RowSts	
	MAX-ACCESS  read-write
	STATUS  current
	DESCRIPTION
		"To create or delete a virtual server  port entry."
	::= { snL4VirtualServerPortCfgEntry 7 }

snL4VirtualServerPortCfgDeleteState	OBJECT-TYPE
	SYNTAX	L4DeleteState
	MAX-ACCESS  read-only
	STATUS  current
	DESCRIPTION
		"Delete operation state." 
	::= { snL4VirtualServerPortCfgEntry 8 }



-- Virtual Server Statistic table

snL4VirtualServerStatisticTable  OBJECT-TYPE
	SYNTAX	SEQUENCE OF SnL4VirtualServerStatisticEntry
	MAX-ACCESS  not-accessible
	STATUS  current
	DESCRIPTION
		"Virtual Server Statistic table."
	::= { snL4VirtualServerStatistic 1 }

snL4VirtualServerStatisticEntry  OBJECT-TYPE
	SYNTAX	SnL4VirtualServerStatisticEntry
	MAX-ACCESS  not-accessible
	STATUS  current
	DESCRIPTION
		"An entry in L4 Virtual Server Statistic table."
	INDEX	{snL4VirtualServerStatisticIP  }
	::= { snL4VirtualServerStatisticTable 1 }

SnL4VirtualServerStatisticEntry ::= SEQUENCE {
	snL4VirtualServerStatisticIP 
		IpAddress,
	snL4VirtualServerStatisticName
		L4ServerName,
	snL4VirtualServerStatisticReceivePkts
		Counter32,
	snL4VirtualServerStatisticTransmitPkts
		Counter32,
	snL4VirtualServerStatisticTotalConnections
		Counter32,
	snL4VirtualServerStatisticReceiveBytes
	   Counter64,
	snL4VirtualServerStatisticTransmitBytes
	   Counter64,
	snL4VirtualServerStatisticSymmetricState
	   Integer32,
	snL4VirtualServerStatisticSymmetricPriority
	   Integer32,
	snL4VirtualServerStatisticSymmetricKeep
	   Integer32,
	snL4VirtualServerStatisticSymmetricActivates
	   Counter32,
	snL4VirtualServerStatisticSymmetricInactives
	   Counter32,
	snL4VirtualServerStatisticSymmetricBestStandbyMacAddr
	   PhysAddress,
	snL4VirtualServerStatisticSymmetricActiveMacAddr
	   PhysAddress
	}

snL4VirtualServerStatisticIP  OBJECT-TYPE
	SYNTAX IpAddress
	MAX-ACCESS  read-only
	STATUS  current
	DESCRIPTION
		"The table index for a Virtual Server  Statistic entry."
	::= { snL4VirtualServerStatisticEntry 1 }


snL4VirtualServerStatisticName  OBJECT-TYPE
	SYNTAX	L4ServerName
	MAX-ACCESS  read-only
	STATUS  current
	DESCRIPTION
		"Virtual server name."
	::= { snL4VirtualServerStatisticEntry 2 }


snL4VirtualServerStatisticReceivePkts  OBJECT-TYPE
	SYNTAX	Counter32
	MAX-ACCESS	read-only
	STATUS  current
	DESCRIPTION
		"" 
	::= { snL4VirtualServerStatisticEntry 3 }

snL4VirtualServerStatisticTransmitPkts  OBJECT-TYPE
	SYNTAX	Counter32
	MAX-ACCESS	read-only
	STATUS  current
	DESCRIPTION
		"" 
	::= { snL4VirtualServerStatisticEntry 4 }

snL4VirtualServerStatisticTotalConnections  OBJECT-TYPE
	SYNTAX	Counter32
	MAX-ACCESS	read-only
	STATUS  current
	DESCRIPTION
		"" 
	::= { snL4VirtualServerStatisticEntry 5 }

snL4VirtualServerStatisticReceiveBytes  OBJECT-TYPE
	SYNTAX	Counter64
	MAX-ACCESS	read-only
	STATUS  current
	DESCRIPTION
		"" 
	::= { snL4VirtualServerStatisticEntry 6 }

snL4VirtualServerStatisticTransmitBytes  OBJECT-TYPE
	SYNTAX	Counter64
	MAX-ACCESS	read-only
	STATUS  current
	DESCRIPTION
		"" 
	::= { snL4VirtualServerStatisticEntry 7 }

snL4VirtualServerStatisticSymmetricState  OBJECT-TYPE
	SYNTAX   Integer32
	MAX-ACCESS	read-only
	STATUS  current
	DESCRIPTION
		"" 
	::= { snL4VirtualServerStatisticEntry 8 }

snL4VirtualServerStatisticSymmetricPriority  OBJECT-TYPE
	SYNTAX   Integer32
	MAX-ACCESS	read-only
	STATUS  current
	DESCRIPTION
		"" 
	::= { snL4VirtualServerStatisticEntry 9 }

snL4VirtualServerStatisticSymmetricKeep  OBJECT-TYPE
	SYNTAX   Integer32
	MAX-ACCESS	read-only
	STATUS  current
	DESCRIPTION
		"" 
	::= { snL4VirtualServerStatisticEntry 10 }

snL4VirtualServerStatisticSymmetricActivates  OBJECT-TYPE
	SYNTAX	Counter32
	MAX-ACCESS	read-only
	STATUS  current
	DESCRIPTION
		"" 
	::= { snL4VirtualServerStatisticEntry 11 }

snL4VirtualServerStatisticSymmetricInactives  OBJECT-TYPE
	SYNTAX	Counter32
	MAX-ACCESS	read-only
	STATUS  current
	DESCRIPTION
		"" 
	::= { snL4VirtualServerStatisticEntry 12 }

snL4VirtualServerStatisticSymmetricBestStandbyMacAddr  OBJECT-TYPE
	SYNTAX	PhysAddress
	MAX-ACCESS	read-only
	STATUS  current
	DESCRIPTION
		"" 
	::= { snL4VirtualServerStatisticEntry 13 }

snL4VirtualServerStatisticSymmetricActiveMacAddr  OBJECT-TYPE
	SYNTAX	PhysAddress
	MAX-ACCESS	read-only
	STATUS  current
	DESCRIPTION
		"" 
	::= { snL4VirtualServerStatisticEntry 14 }


-- Real Server Statistic Table

snL4RealServerStatisticTable  OBJECT-TYPE
	SYNTAX	SEQUENCE OF SnL4RealServerStatisticEntry
	MAX-ACCESS  not-accessible
	STATUS  current
	DESCRIPTION
		"Real Server Statistic table."
	::= { snL4RealServerStatistic 1 }

snL4RealServerStatisticEntry  OBJECT-TYPE
	SYNTAX	SnL4RealServerStatisticEntry
	MAX-ACCESS  not-accessible
	STATUS  current
	DESCRIPTION
		"An entry in the Real Server Statistic table."
	INDEX	{snL4RealServerStatisticRealIP  }
	::= { snL4RealServerStatisticTable 1 }

SnL4RealServerStatisticEntry ::= SEQUENCE {
	snL4RealServerStatisticRealIP 
		IpAddress,
	snL4RealServerStatisticName
		L4ServerName,
	snL4RealServerStatisticReceivePkts
		Counter32,
	snL4RealServerStatisticTransmitPkts
		Counter32,
	snL4RealServerStatisticCurConnections
		Integer32,
	snL4RealServerStatisticTotalConnections
		Counter32,
	snL4RealServerStatisticAge
		Integer32,
	snL4RealServerStatisticState
		INTEGER,
	snL4RealServerStatisticReassignments
		Integer32,
	snL4RealServerStatisticReassignmentLimit
		Integer32,
	snL4RealServerStatisticFailedPortExists
		Integer32,
	snL4RealServerStatisticFailTime
		Integer32,
	snL4RealServerStatisticPeakConnections
		Integer32
	}

snL4RealServerStatisticRealIP OBJECT-TYPE
	SYNTAX	IpAddress
	MAX-ACCESS  read-only
	STATUS  current
	DESCRIPTION
		""
	::= { snL4RealServerStatisticEntry 1 }


snL4RealServerStatisticName OBJECT-TYPE
	SYNTAX	L4ServerName
	MAX-ACCESS  read-only
	STATUS  current
	DESCRIPTION
		""
	::= { snL4RealServerStatisticEntry 2 }

snL4RealServerStatisticReceivePkts	  OBJECT-TYPE
	SYNTAX	Counter32
	MAX-ACCESS  read-only
	STATUS  current
	DESCRIPTION
		""
	::= { snL4RealServerStatisticEntry 3 }

snL4RealServerStatisticTransmitPkts  OBJECT-TYPE
	SYNTAX	Counter32
	MAX-ACCESS  read-only
	STATUS  current
	DESCRIPTION
		""
	::= { snL4RealServerStatisticEntry 4 }

snL4RealServerStatisticCurConnections   OBJECT-TYPE
	SYNTAX   Integer32
	MAX-ACCESS  read-only
	STATUS  current
	DESCRIPTION
		""
	::= { snL4RealServerStatisticEntry 5 }

snL4RealServerStatisticTotalConnections   OBJECT-TYPE
	SYNTAX	Counter32
	MAX-ACCESS  read-only
	STATUS  current
	DESCRIPTION
		""
	::= { snL4RealServerStatisticEntry 6 }

snL4RealServerStatisticAge  OBJECT-TYPE
	SYNTAX   Integer32
	MAX-ACCESS  read-only
	STATUS  current
	DESCRIPTION
		""
	::= { snL4RealServerStatisticEntry 7 }

snL4RealServerStatisticState  OBJECT-TYPE
	SYNTAX   INTEGER{
	serverdisabled(0),
	serverenabled(1),
	serverfailed(2),
	servertesting(3),
	serversuspect(4),
	servershutdown(5),
	serveractive(6)
	}
	MAX-ACCESS  read-only
	STATUS  current
	DESCRIPTION
		""
	::= { snL4RealServerStatisticEntry 8 }

snL4RealServerStatisticReassignments  OBJECT-TYPE
	SYNTAX   Integer32
	MAX-ACCESS  read-only
	STATUS  current
	DESCRIPTION
		""
	::= { snL4RealServerStatisticEntry 9 }

snL4RealServerStatisticReassignmentLimit  OBJECT-TYPE
	SYNTAX   Integer32
	MAX-ACCESS  read-only
	STATUS  current
	DESCRIPTION
		""
	::= { snL4RealServerStatisticEntry 10 }

snL4RealServerStatisticFailedPortExists  OBJECT-TYPE
	SYNTAX   Integer32
	MAX-ACCESS  read-only
	STATUS  current
	DESCRIPTION
		""
	::= { snL4RealServerStatisticEntry 11 }

snL4RealServerStatisticFailTime  OBJECT-TYPE
	SYNTAX   Integer32
	MAX-ACCESS  read-only
	STATUS  current
	DESCRIPTION
		""
	::= { snL4RealServerStatisticEntry 12 }


snL4RealServerStatisticPeakConnections   OBJECT-TYPE
	SYNTAX   Integer32
	MAX-ACCESS  read-only
	STATUS  current
	DESCRIPTION
		""
	::= { snL4RealServerStatisticEntry 13 }




-- Virtual Server Port Statistic table

snL4VirtualServerPortStatisticTable	       OBJECT-TYPE
	SYNTAX	SEQUENCE OF SnL4VirtualServerPortStatisticEntry
	MAX-ACCESS  not-accessible
	STATUS  current
	DESCRIPTION
		"Virtual Server Port Statistic table."
	::= { snL4VirtualServerPortStatistic 1 }

snL4VirtualServerPortStatisticEntry	       OBJECT-TYPE
	SYNTAX	SnL4VirtualServerPortStatisticEntry
	MAX-ACCESS  not-accessible
	STATUS  current
	DESCRIPTION
		"An entry in the Virtual Server Port Statistic table."
	INDEX	{ snL4VirtualServerPortStatisticIP,snL4VirtualServerPortStatisticPort }
	::= { snL4VirtualServerPortStatisticTable 1 }

SnL4VirtualServerPortStatisticEntry ::= SEQUENCE {
	snL4VirtualServerPortStatisticIP
		IpAddress,
	snL4VirtualServerPortStatisticPort
		INTEGER,
	snL4VirtualServerPortStatisticServerName
		L4ServerName,
	snL4VirtualServerPortStatisticCurrentConnection
		Integer32,
	snL4VirtualServerPortStatisticTotalConnection
		Counter32,
	snL4VirtualServerPortStatisticPeakConnection
		Integer32
	}

snL4VirtualServerPortStatisticIP	       OBJECT-TYPE
	SYNTAX	IpAddress
	MAX-ACCESS  read-only
	STATUS  current
	DESCRIPTION
		"The index for Virtual Server Port Statistic entry."
	::= { snL4VirtualServerPortStatisticEntry 1 }

snL4VirtualServerPortStatisticPort   OBJECT-TYPE
	SYNTAX	INTEGER	 (1..2048)
	MAX-ACCESS  read-only
	STATUS  current
	DESCRIPTION
		""
	::= { snL4VirtualServerPortStatisticEntry 2 }

 snL4VirtualServerPortStatisticServerName 	       OBJECT-TYPE
	SYNTAX	L4ServerName
	MAX-ACCESS  read-only
	STATUS  current
	DESCRIPTION
		""
	::= { snL4VirtualServerPortStatisticEntry 3 }

 snL4VirtualServerPortStatisticCurrentConnection 	       OBJECT-TYPE
	SYNTAX   Integer32
	MAX-ACCESS  read-only
	STATUS  current
	DESCRIPTION
		""
	::= { snL4VirtualServerPortStatisticEntry 4 }

 snL4VirtualServerPortStatisticTotalConnection		       OBJECT-TYPE
	SYNTAX	Counter32
	MAX-ACCESS  read-only
	STATUS  current
	DESCRIPTION
		""
	::= { snL4VirtualServerPortStatisticEntry 5 }

 snL4VirtualServerPortStatisticPeakConnection 	       OBJECT-TYPE
	SYNTAX   Integer32
	MAX-ACCESS  read-only
	STATUS  current
	DESCRIPTION
		""
	::= { snL4VirtualServerPortStatisticEntry 6 }

-- Real Server Port Statistic table

snL4RealServerPortStatisticTable	       OBJECT-TYPE
	SYNTAX	SEQUENCE OF SnL4RealServerPortStatisticEntry
	MAX-ACCESS  not-accessible
	STATUS  current
	DESCRIPTION
		"Real Server Port Statistic table."
	::= { snL4RealServerPortStatistic 1 }

snL4RealServerPortStatisticEntry	       OBJECT-TYPE
	SYNTAX	SnL4RealServerPortStatisticEntry
	MAX-ACCESS  not-accessible
	STATUS  current
	DESCRIPTION
		"An entry in the Real Server Port Statistic table."
	INDEX	{ snL4RealServerPortStatisticIP,snL4RealServerPortStatisticPort }
	::= { snL4RealServerPortStatisticTable 1 }

SnL4RealServerPortStatisticEntry ::= SEQUENCE {
	snL4RealServerPortStatisticIP
		IpAddress,
	snL4RealServerPortStatisticPort
		Integer32,
	snL4RealServerPortStatisticServerName
		L4ServerName,
	snL4RealServerPortStatisticReassignCount
		Integer32,
	snL4RealServerPortStatisticState
		INTEGER,
	snL4RealServerPortStatisticFailTime
		Integer32,
	snL4RealServerPortStatisticCurrentConnection
		Integer32,
	snL4RealServerPortStatisticTotalConnection
		Counter32,
	snL4RealServerPortStatisticRxPkts
		Counter32,
	snL4RealServerPortStatisticTxPkts
		Counter32,
	snL4RealServerPortStatisticRxBytes
		Counter32,
	snL4RealServerPortStatisticTxBytes
		Counter32,
	snL4RealServerPortStatisticPeakConnection
		Integer32
	}


snL4RealServerPortStatisticIP	       OBJECT-TYPE
	SYNTAX IpAddress
	MAX-ACCESS  read-only
	STATUS  current
	DESCRIPTION
		"The index for Real Server Port Statistic entry."
	::= { snL4RealServerPortStatisticEntry 1 }

snL4RealServerPortStatisticPort	       OBJECT-TYPE
	SYNTAX   Integer32
	MAX-ACCESS  read-only
	STATUS  current
	DESCRIPTION
		""
	::= { snL4RealServerPortStatisticEntry 2 }

snL4RealServerPortStatisticServerName	       OBJECT-TYPE
	SYNTAX	L4ServerName
	MAX-ACCESS  read-only
	STATUS  current
	DESCRIPTION
		""
	::= { snL4RealServerPortStatisticEntry 3 }

snL4RealServerPortStatisticReassignCount	       OBJECT-TYPE
	SYNTAX   Integer32
	MAX-ACCESS  read-only
	STATUS  current
	DESCRIPTION
		""
	::= { snL4RealServerPortStatisticEntry 4 }

 snL4RealServerPortStatisticState	       OBJECT-TYPE
	SYNTAX	INTEGER	{
		disabled(0),
		enabled(1),
		failed(2),
		testing(3),
		suspect(4),
		shutdown(5),
		active(6),
		unbound(7),
		awaitUnbind(8),
		awaitDelete(9)
	}
	MAX-ACCESS  read-only
	STATUS  current
	DESCRIPTION
		"Real server port state"
	::= { snL4RealServerPortStatisticEntry 5 }

snL4RealServerPortStatisticFailTime 	       OBJECT-TYPE
	SYNTAX   Integer32
	MAX-ACCESS  read-only
	STATUS  current
	DESCRIPTION
		"Only useful, if real server port state is failed.
		 Indicating how seconds has been elapsed from the last retry."
	::= { snL4RealServerPortStatisticEntry 6 }

snL4RealServerPortStatisticCurrentConnection	       OBJECT-TYPE
	SYNTAX   Integer32
	MAX-ACCESS  read-only
	STATUS  current
	DESCRIPTION
		"Real server port current connection"
	::= { snL4RealServerPortStatisticEntry 7 }

snL4RealServerPortStatisticTotalConnection	       OBJECT-TYPE
	SYNTAX	Counter32
	MAX-ACCESS  read-only
	STATUS  current
	DESCRIPTION
		"Real server port total connection"
	::= { snL4RealServerPortStatisticEntry 8 }

snL4RealServerPortStatisticRxPkts	       OBJECT-TYPE
	SYNTAX	Counter32
	MAX-ACCESS  read-only
	STATUS  current
	DESCRIPTION
		"Real server port receive packets."
	::= { snL4RealServerPortStatisticEntry 9 }


snL4RealServerPortStatisticTxPkts	       OBJECT-TYPE
	SYNTAX	Counter32
	MAX-ACCESS  read-only
	STATUS  current
	DESCRIPTION
		"Real server port transmit packets."
	::= { snL4RealServerPortStatisticEntry 10 }


snL4RealServerPortStatisticRxBytes	       OBJECT-TYPE
	SYNTAX	Counter32
	MAX-ACCESS  read-only
	STATUS  current
	DESCRIPTION
		"Real server port receive bytes."
	::= { snL4RealServerPortStatisticEntry 11 }

snL4RealServerPortStatisticTxBytes	       OBJECT-TYPE
	SYNTAX	Counter32
	MAX-ACCESS  read-only
	STATUS  current
	DESCRIPTION
		"Real server port transmit bytes."
	::= { snL4RealServerPortStatisticEntry 12 }


snL4RealServerPortStatisticPeakConnection	       OBJECT-TYPE
	SYNTAX   Integer32
	MAX-ACCESS  read-only
	STATUS  current
	DESCRIPTION
		"peak connection for real server port."
	::= { snL4RealServerPortStatisticEntry 13 }


-- GSLB Site Remote ServerIron Configuration table

snL4GslbSiteRemoteServerIronTable	       OBJECT-TYPE
	SYNTAX	SEQUENCE OF SnL4GslbSiteRemoteServerIronEntry
	MAX-ACCESS  not-accessible
	STATUS  current
	DESCRIPTION
		"GSLB remote ServerIron configuration table."
	::= { snL4GslbSiteRemoteServerIrons 1 }

snL4GslbSiteRemoteServerIronEntry	       OBJECT-TYPE
	SYNTAX	SnL4GslbSiteRemoteServerIronEntry	
	MAX-ACCESS  not-accessible
	STATUS  current
	DESCRIPTION
		"An entry of a GSLB remote ServerIron configuration."
	INDEX	{ snL4GslbSiteRemoteServerIronIP }
	::= { snL4GslbSiteRemoteServerIronTable 1 }

SnL4GslbSiteRemoteServerIronEntry ::= SEQUENCE {
	snL4GslbSiteRemoteServerIronIP
		IpAddress,
	snL4GslbSiteRemoteServerIronPreference
		INTEGER
	}


snL4GslbSiteRemoteServerIronIP	       OBJECT-TYPE
	SYNTAX IpAddress
	MAX-ACCESS  read-only
	STATUS  current
	DESCRIPTION
		"The index for each remote ServerIron in a site."
	::= { snL4GslbSiteRemoteServerIronEntry 1 }

snL4GslbSiteRemoteServerIronPreference 	OBJECT-TYPE
	SYNTAX	INTEGER	(0..255)
	MAX-ACCESS  read-write
	STATUS  current
	DESCRIPTION
		"The preference of a remote ServerIron. The default value is 128."
	DEFVAL { 128 }
	::= { snL4GslbSiteRemoteServerIronEntry 2 }


-- Real Server Monitor Group

-- The Real Server History Control Group

-- The snL4History control group controls the periodic statistical
-- sampling of data from various types of data sources.  The
-- snL4RealServerHistoryControlTable stores configuration entries that each
-- define an interface, polling period, and other parameters.
-- Once samples are taken, their data is stored in an entry
-- in a media-specific table.  Each such entry defines one
-- sample, and is associated with the snL4RealServerHistoryControlEntry that
-- caused the sample to be taken.  Each counter in the
-- snL4HistoryEntry counts the same event as its
-- similarly-named counterpart in the Statistics Entry,
-- except that each value here is a cumulative sum during a
-- sampling period.
--
-- If the probe keeps track of the time of day, it should
-- start the first sample of the snL4History at a time such that
-- when the next hour of the day begins, a sample is
-- started at that instant.  This tends to make more
-- user-friendly reports, and enables comparison of reports
-- from different probes that have relatively accurate time
-- of day.
--
-- The probe is encouraged to add two snL4History control entries
-- per monitored interface upon initialization that describe
-- a short term and a long term polling period.  Suggested
-- parameters are 30 seconds for the short term polling period
-- and 30 minutes for the long term period.

snL4RealServerHistoryControlTable OBJECT-TYPE
	SYNTAX SEQUENCE OF SnL4RealServerHistoryControlEntry
	MAX-ACCESS not-accessible
	STATUS current
	DESCRIPTION
		"A list of history control entries."
	::= { snL4History 1 }

snL4RealServerHistoryControlEntry OBJECT-TYPE
	SYNTAX SnL4RealServerHistoryControlEntry
	MAX-ACCESS not-accessible
	STATUS current
	DESCRIPTION
		"A list of parameters that set up a periodic sampling
		of statistics.As an example, an instance of the
		snL4RealServerHistoryControlInterval object might be named
		snL4RealServerHistoryControlInterval.2"
	INDEX { snL4RealServerHistoryControlIndex }
	::= { snL4RealServerHistoryControlTable 1 }

	SnL4RealServerHistoryControlEntry ::= SEQUENCE {
		snL4RealServerHistoryControlIndex			 
			INTEGER ,
		snL4RealServerHistoryControlDataSource		
			OBJECT IDENTIFIER,
		snL4RealServerHistoryControlBucketsRequested
			INTEGER ,
		snL4RealServerHistoryControlBucketsGranted	
			INTEGER ,
		snL4RealServerHistoryControlInterval		
			INTEGER ,
		snL4RealServerHistoryControlOwner			 
			DisplayString,
		snL4RealServerHistoryControlStatus			
			INTEGER
	}

snL4RealServerHistoryControlIndex OBJECT-TYPE
	SYNTAX INTEGER (1..65535)
	MAX-ACCESS read-only
	STATUS current
	DESCRIPTION
		"An index that uniquely identifies an entry in the
		snL4RealServerHistoryControl table.Each such entry defines a
		set of samples at a particular interval for an
		interface on the device."
	::= { snL4RealServerHistoryControlEntry 1 }

snL4RealServerHistoryControlDataSource OBJECT-TYPE
	SYNTAX OBJECT IDENTIFIER
	MAX-ACCESS read-write
	STATUS current
	DESCRIPTION
		"This object identifies the source of the data for
		which historical data was collected and
		placed in a media-specific table on behalf of this
		snL4RealServerHistoryControlEntry.This source can be any
		real/virtual server and real/virtual server port on 
		this ServerIron.  In order to identify
		a particular instance, this object shall identify
		the instance of the object, defined in the above 
		statistics tables.
	
		This object may not be modified if the associated
		snL4RealServerHistoryControlStatus object is equal to valid(1)."
	::= { snL4RealServerHistoryControlEntry 2 }

snL4RealServerHistoryControlBucketsRequested OBJECT-TYPE
	SYNTAX INTEGER (1..65535)
	MAX-ACCESS read-write
	STATUS current
	DESCRIPTION
		"The requested number of discrete time intervals
		over which data is to be saved in the part of the
		media-specific table associated with this
		snL4RealServerHistoryControlEntry.
	
		When this object is created or modified, the probe
		should set snL4RealServerHistoryControlBucketsGranted as closely to
		this object as is possible for the particular probe
		implementation and available resources."
	DEFVAL { 50 }
	::= { snL4RealServerHistoryControlEntry 3 }

snL4RealServerHistoryControlBucketsGranted OBJECT-TYPE
	SYNTAX INTEGER (1..65535)
	MAX-ACCESS read-only
	STATUS current
	DESCRIPTION
		"The number of discrete sampling intervals
		over which data shall be saved in the part of
		the media-specific table associated with this
		snL4RealServerHistoryControlEntry.
	
		When the associated snL4RealServerHistoryControlBucketsRequested
		object is created or modified, the probe
		should set this object as closely to the requested
		value as is possible for the particular
		probe implementation and available resources.The
		probe must not lower this value except as a result
		of a modification to the associated
		snL4RealServerHistoryControlBucketsRequested object.
	
		There will be times when the actual number of
		buckets associated with this entry is less than
		the value of this object.In this case, at the
		end of each sampling interval, a new bucket will
		be added to the media-specific table.
	
		When the number of buckets reaches the value of
		this object and a new bucket is to be added to the
		media-specific table, the oldest bucket associated
		with this snL4RealServerHistoryControlEntry shall be deleted by
		the agent so that the new bucket can be added.
	
		When the value of this object changes to a value less
		than the current value, entries are deleted
		from the media-specific table associated with this
		snL4RealServerHistoryControlEntry.Enough of the oldest of these
		entries shall be deleted by the agent so that their
		number remains less than or equal to the new value of
		this object.
	
		When the value of this object changes to a value
		greater than the current value, the number of
		associated media- specific entries may be allowed to
		grow."
	::= { snL4RealServerHistoryControlEntry 4 }

snL4RealServerHistoryControlInterval OBJECT-TYPE
	SYNTAX INTEGER (1..3600)
	MAX-ACCESS read-write
	STATUS current
	DESCRIPTION
		"The interval in seconds over which the data is
		sampled for each bucket in the part of the
		media-specific table associated with this
		snL4RealServerHistoryControlEntry.This interval can
		be set to any number of seconds between 1 and
		3600 (1 hour).
	
		Because the counters in a bucket may overflow at their
		maximum value with no indication, a prudent manager
		will take into account the possibility of overflow
		in any of the associated counters.It is important
		to consider the minimum time in which any counter
		could overflow on a particular media type and set
		the snL4RealServerHistoryControlInterval object to a value less
		than this interval.This is typically most
		important for the 'octets' counter in any
		media-specific table.	
		This object may not be modified if the associated
		snL4RealServerHistoryControlStatus object is equal to valid(1)."
	DEFVAL { 1800 }
	::= { snL4RealServerHistoryControlEntry 5 }

snL4RealServerHistoryControlOwner OBJECT-TYPE
	SYNTAX DisplayString
	MAX-ACCESS read-write
	STATUS current
	DESCRIPTION
		"The entity that configured this entry and is
		therefore using the resources assigned to it."
	::= { snL4RealServerHistoryControlEntry 6 }

snL4RealServerHistoryControlStatus OBJECT-TYPE
	SYNTAX INTEGER { 
				valid(1),
				createRequest(2),
				underCreation(3),
				invalid(4)
		   }
	MAX-ACCESS read-write
	STATUS current
	DESCRIPTION
		"The status of this snL4RealServerHistoryControl entry.
		Each instance of the media-specific table associated
		with this snL4RealServerHistoryControlEntry will be deleted by the
		agent if this snL4RealServerHistoryControlEntry is not equal to
		valid(1)."
	::= { snL4RealServerHistoryControlEntry 7 }


-- The Real Server History Group


snL4RealServerHistoryTable OBJECT-TYPE
	SYNTAX SEQUENCE OF SnL4RealServerHistoryEntry
	MAX-ACCESS not-accessible
	STATUS current
	DESCRIPTION
		"A list of Ethernet snL4History entries."
	::= { snL4History 2 }

snL4RealServerHistoryEntry OBJECT-TYPE
	SYNTAX SnL4RealServerHistoryEntry
	MAX-ACCESS not-accessible
	STATUS current
	DESCRIPTION
		"An historical sample of Ethernet statistics on a
		particular Ethernet interface.  This sample is
		associated with the snL4RealServerHistoryControlEntry which set up
		the parameters for a regular collection of these
		samples.  As an example, an instance of the
		snL4RealServerHistoryReceivePkts object might be named
		snL4RealServerHistoryReceivePkts.2.89"
	INDEX { snL4RealServerHistoryIndex , snL4RealServerHistorySampleIndex }
	::= { snL4RealServerHistoryTable 1 }

SnL4RealServerHistoryEntry ::= SEQUENCE {
	snL4RealServerHistoryIndex                 
		INTEGER ,
	snL4RealServerHistorySampleIndex           
		INTEGER ,
	snL4RealServerHistoryIntervalStart         
		TimeTicks,
	snL4RealServerHistoryReceivePkts
		Counter32,
	snL4RealServerHistoryTransmitPkts
		Counter32,
	snL4RealServerHistoryTotalConnections
		Counter32,
	snL4RealServerHistoryCurConnections
		Integer32,
	snL4RealServerHistoryPeakConnections
		Integer32,
	snL4RealServerHistoryReassignments
		Integer32
	}

snL4RealServerHistoryIndex OBJECT-TYPE
	SYNTAX INTEGER (1..65535)
	MAX-ACCESS read-only
	STATUS current
	DESCRIPTION
		"The snL4RealServerHistory of which this entry is a part.The
		snL4RealServerHistory identified by a particular value of this
		index is the same snL4RealServerHistory as identified
		by the same value of snL4RealServerHistoryControlIndex."
	::= { snL4RealServerHistoryEntry 1 }

snL4RealServerHistorySampleIndex OBJECT-TYPE
	SYNTAX INTEGER (1..2147483647)
	MAX-ACCESS read-only
	STATUS current
	DESCRIPTION
		"An index that uniquely identifies the particular
		sample this entry represents among all samples
		associated with the same snL4RealServerHistoryControlEntry.
		This index starts at 1 and increases by one
		as each new sample is taken."
	::= { snL4RealServerHistoryEntry 2 }

snL4RealServerHistoryIntervalStart OBJECT-TYPE
	SYNTAX TimeTicks
	MAX-ACCESS read-only
	STATUS current
	DESCRIPTION
		"The value of sysUpTime at the start of the interval
		over which this sample was measured.If the probe
		keeps track of the time of day, it should start
		the first sample of the snL4RealServerHistory at a time such that
		when the next hour of the day begins, a sample is
		started at that instant.Note that following this
		rule may require the probe to delay collecting the
		first sample of the snL4RealServerHistory, as each sample must be
		of the same interval.Also note that the sample which
		is currently being collected is not accessible in this
		table until the end of its interval."
	::= { snL4RealServerHistoryEntry 3 }


snL4RealServerHistoryReceivePkts	  OBJECT-TYPE
	SYNTAX	Counter32
	MAX-ACCESS  read-only
	STATUS  current
	DESCRIPTION
		""
	::= { snL4RealServerHistoryEntry 4 }

snL4RealServerHistoryTransmitPkts  OBJECT-TYPE
	SYNTAX	Counter32
	MAX-ACCESS  read-only
	STATUS  current
	DESCRIPTION
		""
	::= { snL4RealServerHistoryEntry 5 }

snL4RealServerHistoryTotalConnections   OBJECT-TYPE
	SYNTAX	Counter32
	MAX-ACCESS  read-only
	STATUS  current
	DESCRIPTION
		""
	::= { snL4RealServerHistoryEntry 6 }

snL4RealServerHistoryCurConnections   OBJECT-TYPE
	SYNTAX   Integer32
	MAX-ACCESS  read-only
	STATUS  current
	DESCRIPTION
		""
	::= { snL4RealServerHistoryEntry 7 }

snL4RealServerHistoryPeakConnections   OBJECT-TYPE
	SYNTAX   Integer32
	MAX-ACCESS  read-only
	STATUS  current
	DESCRIPTION
		""
	::= { snL4RealServerHistoryEntry 8 }

snL4RealServerHistoryReassignments   OBJECT-TYPE
	SYNTAX   Integer32
	MAX-ACCESS  read-only
	STATUS  current
	DESCRIPTION
		""
	::= { snL4RealServerHistoryEntry 9 }


-- Real Server Port Monitor Group

-- The Real Server Port History Control Group

snL4RealServerPortHistoryControlTable OBJECT-TYPE
	SYNTAX SEQUENCE OF SnL4RealServerPortHistoryControlEntry
	MAX-ACCESS not-accessible
	STATUS current
	DESCRIPTION
		"A list of history control entries."
	::= { snL4History 3 }

snL4RealServerPortHistoryControlEntry OBJECT-TYPE
	SYNTAX SnL4RealServerPortHistoryControlEntry
	MAX-ACCESS not-accessible
	STATUS current
	DESCRIPTION
		"A list of parameters that set up a periodic sampling
		of statistics.As an example, an instance of the
		snL4RealServerPortHistoryControlInterval object might be named
		snL4RealServerPortHistoryControlInterval.2"
	INDEX { snL4RealServerPortHistoryControlIndex }
	::= { snL4RealServerPortHistoryControlTable 1 }

	SnL4RealServerPortHistoryControlEntry ::= SEQUENCE {
		snL4RealServerPortHistoryControlIndex			 
			INTEGER ,
		snL4RealServerPortHistoryControlDataSource		
			OBJECT IDENTIFIER,
		snL4RealServerPortHistoryControlBucketsRequested
			INTEGER ,
		snL4RealServerPortHistoryControlBucketsGranted	
			INTEGER,
		snL4RealServerPortHistoryControlInterval		
			INTEGER ,
		snL4RealServerPortHistoryControlOwner			 
			DisplayString,
		snL4RealServerPortHistoryControlStatus			
			INTEGER
	}

snL4RealServerPortHistoryControlIndex OBJECT-TYPE
	SYNTAX INTEGER (1..65535)
	MAX-ACCESS read-only
	STATUS current
	DESCRIPTION
		"An index that uniquely identifies an entry in the
		snL4RealServerPortHistoryControl table.Each such entry defines a
		set of samples at a particular interval for an
		interface on the device."
	::= { snL4RealServerPortHistoryControlEntry 1 }

snL4RealServerPortHistoryControlDataSource OBJECT-TYPE
	SYNTAX OBJECT IDENTIFIER
	MAX-ACCESS read-write
	STATUS current
	DESCRIPTION
		"This object identifies the source of the data for
		which historical data was collected and
		placed in a media-specific table on behalf of this
		snL4RealServerPortHistoryControlEntry.This source can be any
		real/virtual server and real/virtual server port on 
		this ServerIron.  In order to identify
		a particular instance, this object shall identify
		the instance of the object, defined in the above 
		statistics tables.
	
		This object may not be modified if the associated
		snL4RealServerPortHistoryControlStatus object is equal to valid(1)."
	::= { snL4RealServerPortHistoryControlEntry 2 }

snL4RealServerPortHistoryControlBucketsRequested OBJECT-TYPE
	SYNTAX INTEGER (1..65535)
	MAX-ACCESS read-write
	STATUS current
	DESCRIPTION
		"The requested number of discrete time intervals
		over which data is to be saved in the part of the
		media-specific table associated with this
		snL4RealServerPortHistoryControlEntry.
	
		When this object is created or modified, the probe
		should set snL4RealServerPortHistoryControlBucketsGranted as closely to
		this object as is possible for the particular probe
		implementation and available resources."
	DEFVAL { 50 }
	::= { snL4RealServerPortHistoryControlEntry 3 }

snL4RealServerPortHistoryControlBucketsGranted OBJECT-TYPE
	SYNTAX INTEGER (1..65535)
	MAX-ACCESS read-only
	STATUS current
	DESCRIPTION
		"The number of discrete sampling intervals
		over which data shall be saved in the part of
		the media-specific table associated with this
		snL4RealServerPortHistoryControlEntry.
	
		When the associated snL4RealServerPortHistoryControlBucketsRequested
		object is created or modified, the probe
		should set this object as closely to the requested
		value as is possible for the particular
		probe implementation and available resources.The
		probe must not lower this value except as a result
		of a modification to the associated
		snL4RealServerPortHistoryControlBucketsRequested object.
	
		There will be times when the actual number of
		buckets associated with this entry is less than
		the value of this object.In this case, at the
		end of each sampling interval, a new bucket will
		be added to the media-specific table.
	
		When the number of buckets reaches the value of
		this object and a new bucket is to be added to the
		media-specific table, the oldest bucket associated
		with this snL4RealServerPortHistoryControlEntry shall be deleted by
		the agent so that the new bucket can be added.
	
		When the value of this object changes to a value less
		than the current value, entries are deleted
		from the media-specific table associated with this
		snL4RealServerPortHistoryControlEntry.Enough of the oldest of these
		entries shall be deleted by the agent so that their
		number remains less than or equal to the new value of
		this object.
	
		When the value of this object changes to a value
		greater than the current value, the number of
		associated media- specific entries may be allowed to
		grow."
	::= { snL4RealServerPortHistoryControlEntry 4 }

snL4RealServerPortHistoryControlInterval OBJECT-TYPE
	SYNTAX INTEGER (1..3600)
	MAX-ACCESS read-write
	STATUS current
	DESCRIPTION
		"The interval in seconds over which the data is
		sampled for each bucket in the part of the
		media-specific table associated with this
		snL4RealServerPortHistoryControlEntry.This interval can
		be set to any number of seconds between 1 and
		3600 (1 hour).
	
		Because the counters in a bucket may overflow at their
		maximum value with no indication, a prudent manager
		will take into account the possibility of overflow
		in any of the associated counters.It is important
		to consider the minimum time in which any counter
		could overflow on a particular media type and set
		the snL4RealServerPortHistoryControlInterval object to a value less
		than this interval.This is typically most
		important for the 'octets' counter in any
		media-specific table.	
		This object may not be modified if the associated
		snL4RealServerPortHistoryControlStatus object is equal to valid(1)."
	DEFVAL { 1800 }
	::= { snL4RealServerPortHistoryControlEntry 5 }

snL4RealServerPortHistoryControlOwner OBJECT-TYPE
	SYNTAX DisplayString
	MAX-ACCESS read-write
	STATUS current
	DESCRIPTION
		"The entity that configured this entry and is
		therefore using the resources assigned to it."
	::= { snL4RealServerPortHistoryControlEntry 6 }

snL4RealServerPortHistoryControlStatus OBJECT-TYPE
	SYNTAX INTEGER { 
				valid(1),
				createRequest(2),
				underCreation(3),
				invalid(4)
		   }
	MAX-ACCESS read-write
	STATUS current
	DESCRIPTION
		"The status of this snL4RealServerPortHistoryControl entry.
		Each instance of the media-specific table associated
		with this snL4RealServerPortHistoryControlEntry will be deleted by the
		agent if this snL4RealServerPortHistoryControlEntry is not equal to
		valid(1)."
	::= { snL4RealServerPortHistoryControlEntry 7 }


-- The Real Server Port History Group


snL4RealServerPortHistoryTable OBJECT-TYPE
	SYNTAX SEQUENCE OF SnL4RealServerPortHistoryEntry
	MAX-ACCESS not-accessible
	STATUS current
	DESCRIPTION
		"A list of Ethernet snL4History entries."
	::= { snL4History 4 }

snL4RealServerPortHistoryEntry OBJECT-TYPE
	SYNTAX SnL4RealServerPortHistoryEntry
	MAX-ACCESS not-accessible
	STATUS current
	DESCRIPTION
		"An historical sample of Ethernet statistics on a
		particular Ethernet interface.  This sample is
		associated with the snL4RealServerPortHistoryControlEntry which set up
		the parameters for a regular collection of these
		samples.  As an example, an instance of the
		snL4RealServerPortHistoryReceivePkts object might be named
		snL4RealServerPortHistoryReceivePkts.2.89"
	INDEX { snL4RealServerPortHistoryIndex , snL4RealServerPortHistorySampleIndex }
	::= { snL4RealServerPortHistoryTable 1 }

SnL4RealServerPortHistoryEntry ::= SEQUENCE {
	snL4RealServerPortHistoryIndex                 
		INTEGER ,
	snL4RealServerPortHistorySampleIndex           
		INTEGER ,
	snL4RealServerPortHistoryIntervalStart         
		TimeTicks,
	snL4RealServerPortHistoryReceivePkts
		Counter32,
	snL4RealServerPortHistoryTransmitPkts
		Counter32,
	snL4RealServerPortHistoryTotalConnections
		Counter32,
	snL4RealServerPortHistoryCurConnections
		Integer32,
	snL4RealServerPortHistoryPeakConnections
		Integer32,
	snL4RealServerPortHistoryResponseTime
		Integer32
	}

snL4RealServerPortHistoryIndex OBJECT-TYPE
	SYNTAX INTEGER (1..65535)
	MAX-ACCESS read-only
	STATUS current
	DESCRIPTION
		"The snL4RealServerPortHistory of which this entry is a part.The
		snL4RealServerPortHistory identified by a particular value of this
		index is the same snL4RealServerPortHistory as identified
		by the same value of snL4RealServerPortHistoryControlIndex."
	::= { snL4RealServerPortHistoryEntry 1 }

snL4RealServerPortHistorySampleIndex OBJECT-TYPE
	SYNTAX INTEGER (1..2147483647)
	MAX-ACCESS read-only
	STATUS current
	DESCRIPTION
		"An index that uniquely identifies the particular
		sample this entry represents among all samples
		associated with the same snL4RealServerPortHistoryControlEntry.
		This index starts at 1 and increases by one
		as each new sample is taken."
	::= { snL4RealServerPortHistoryEntry 2 }

snL4RealServerPortHistoryIntervalStart OBJECT-TYPE
	SYNTAX TimeTicks
	MAX-ACCESS read-only
	STATUS current
	DESCRIPTION
		"The value of sysUpTime at the start of the interval
		over which this sample was measured.If the probe
		keeps track of the time of day, it should start
		the first sample of the snL4RealServerPortHistory at a time such that
		when the next hour of the day begins, a sample is
		started at that instant.Note that following this
		rule may require the probe to delay collecting the
		first sample of the snL4RealServerPortHistory, as each sample must be
		of the same interval.Also note that the sample which
		is currently being collected is not accessible in this
		table until the end of its interval."
	::= { snL4RealServerPortHistoryEntry 3 }


snL4RealServerPortHistoryReceivePkts	  OBJECT-TYPE
	SYNTAX	Counter32
	MAX-ACCESS  read-only
	STATUS  current
	DESCRIPTION
		""
	::= { snL4RealServerPortHistoryEntry 4 }

snL4RealServerPortHistoryTransmitPkts  OBJECT-TYPE
	SYNTAX	Counter32
	MAX-ACCESS  read-only
	STATUS  current
	DESCRIPTION
		""
	::= { snL4RealServerPortHistoryEntry 5 }

snL4RealServerPortHistoryTotalConnections   OBJECT-TYPE
	SYNTAX	Counter32
	MAX-ACCESS  read-only
	STATUS  current
	DESCRIPTION
		""
	::= { snL4RealServerPortHistoryEntry 6 }

snL4RealServerPortHistoryCurConnections   OBJECT-TYPE
	SYNTAX   Integer32
	MAX-ACCESS  read-only
	STATUS  current
	DESCRIPTION
		""
	::= { snL4RealServerPortHistoryEntry 7 }

snL4RealServerPortHistoryPeakConnections   OBJECT-TYPE
	SYNTAX   Integer32
	MAX-ACCESS  read-only
	STATUS  current
	DESCRIPTION
		""
	::= { snL4RealServerPortHistoryEntry 8 }

snL4RealServerPortHistoryResponseTime   OBJECT-TYPE
	SYNTAX   Integer32
	MAX-ACCESS  read-only
	STATUS  current
	DESCRIPTION
		""
	::= { snL4RealServerPortHistoryEntry 9 }


-- Virtual Server Monitor Group
-- The Virtual Server History Control Group


snL4VirtualServerHistoryControlTable OBJECT-TYPE
	SYNTAX SEQUENCE OF SnL4VirtualServerHistoryControlEntry
	MAX-ACCESS not-accessible
	STATUS current
	DESCRIPTION
		"A list of history control entries."
	::= { snL4History 5 }

snL4VirtualServerHistoryControlEntry OBJECT-TYPE
	SYNTAX SnL4VirtualServerHistoryControlEntry
	MAX-ACCESS not-accessible
	STATUS current
	DESCRIPTION
		"A list of parameters that set up a periodic sampling
		of statistics.As an example, an instance of the
		snL4VirtualServerHistoryControlInterval object might be named
		snL4VirtualServerHistoryControlInterval.2"
	INDEX { snL4VirtualServerHistoryControlIndex }
	::= { snL4VirtualServerHistoryControlTable 1 }

	SnL4VirtualServerHistoryControlEntry ::= SEQUENCE {
		snL4VirtualServerHistoryControlIndex			 
			INTEGER ,
		snL4VirtualServerHistoryControlDataSource		
			OBJECT IDENTIFIER,
		snL4VirtualServerHistoryControlBucketsRequested
			INTEGER ,
		snL4VirtualServerHistoryControlBucketsGranted	
			INTEGER ,
		snL4VirtualServerHistoryControlInterval		
			INTEGER ,
		snL4VirtualServerHistoryControlOwner			 
			DisplayString,
		snL4VirtualServerHistoryControlStatus			
			INTEGER
	}

snL4VirtualServerHistoryControlIndex OBJECT-TYPE
	SYNTAX INTEGER (1..65535)
	MAX-ACCESS read-only
	STATUS current
	DESCRIPTION
		"An index that uniquely identifies an entry in the
		snL4VirtualServerHistoryControl table.Each such entry defines a
		set of samples at a particular interval for an
		interface on the device."
	::= { snL4VirtualServerHistoryControlEntry 1 }

snL4VirtualServerHistoryControlDataSource OBJECT-TYPE
	SYNTAX OBJECT IDENTIFIER
	MAX-ACCESS read-write
	STATUS current
	DESCRIPTION
		"This object identifies the source of the data for
		which historical data was collected and
		placed in a media-specific table on behalf of this
		snL4VirtualServerHistoryControlEntry.This source can be any
		real/virtual server and real/virtual server port on 
		this ServerIron.  In order to identify
		a particular instance, this object shall identify
		the instance of the object, defined in the above 
		statistics tables.
	
		This object may not be modified if the associated
		snL4VirtualServerHistoryControlStatus object is equal to valid(1)."
	::= { snL4VirtualServerHistoryControlEntry 2 }

snL4VirtualServerHistoryControlBucketsRequested OBJECT-TYPE
	SYNTAX INTEGER (1..65535)
	MAX-ACCESS read-write
	STATUS current
	DESCRIPTION
		"The requested number of discrete time intervals
		over which data is to be saved in the part of the
		media-specific table associated with this
		snL4VirtualServerHistoryControlEntry.
	
		When this object is created or modified, the probe
		should set snL4VirtualServerHistoryControlBucketsGranted as closely to
		this object as is possible for the particular probe
		implementation and available resources."
	DEFVAL { 50 }
	::= { snL4VirtualServerHistoryControlEntry 3 }

snL4VirtualServerHistoryControlBucketsGranted OBJECT-TYPE
	SYNTAX INTEGER (1..65535)
	MAX-ACCESS read-only
	STATUS current
	DESCRIPTION
		"The number of discrete sampling intervals
		over which data shall be saved in the part of
		the media-specific table associated with this
		snL4VirtualServerHistoryControlEntry.
	
		When the associated snL4VirtualServerHistoryControlBucketsRequested
		object is created or modified, the probe
		should set this object as closely to the requested
		value as is possible for the particular
		probe implementation and available resources.The
		probe must not lower this value except as a result
		of a modification to the associated
		snL4VirtualServerHistoryControlBucketsRequested object.
	
		There will be times when the actual number of
		buckets associated with this entry is less than
		the value of this object.In this case, at the
		end of each sampling interval, a new bucket will
		be added to the media-specific table.
	
		When the number of buckets reaches the value of
		this object and a new bucket is to be added to the
		media-specific table, the oldest bucket associated
		with this snL4VirtualServerHistoryControlEntry shall be deleted by
		the agent so that the new bucket can be added.
	
		When the value of this object changes to a value less
		than the current value, entries are deleted
		from the media-specific table associated with this
		snL4VirtualServerHistoryControlEntry.Enough of the oldest of these
		entries shall be deleted by the agent so that their
		number remains less than or equal to the new value of
		this object.
	
		When the value of this object changes to a value
		greater than the current value, the number of
		associated media- specific entries may be allowed to
		grow."
	::= { snL4VirtualServerHistoryControlEntry 4 }

snL4VirtualServerHistoryControlInterval OBJECT-TYPE
	SYNTAX INTEGER (1..3600)
	MAX-ACCESS read-write
	STATUS current
	DESCRIPTION
		"The interval in seconds over which the data is
		sampled for each bucket in the part of the
		media-specific table associated with this
		snL4VirtualServerHistoryControlEntry.This interval can
		be set to any number of seconds between 1 and
		3600 (1 hour).
	
		Because the counters in a bucket may overflow at their
		maximum value with no indication, a prudent manager
		will take into account the possibility of overflow
		in any of the associated counters.It is important
		to consider the minimum time in which any counter
		could overflow on a particular media type and set
		the snL4VirtualServerHistoryControlInterval object to a value less
		than this interval.This is typically most
		important for the 'octets' counter in any
		media-specific table.	
		This object may not be modified if the associated
		snL4VirtualServerHistoryControlStatus object is equal to valid(1)."
	DEFVAL { 1800 }
	::= { snL4VirtualServerHistoryControlEntry 5 }

snL4VirtualServerHistoryControlOwner OBJECT-TYPE
	SYNTAX DisplayString
	MAX-ACCESS read-write
	STATUS current
	DESCRIPTION
		"The entity that configured this entry and is
		therefore using the resources assigned to it."
	::= { snL4VirtualServerHistoryControlEntry 6 }

snL4VirtualServerHistoryControlStatus OBJECT-TYPE
	SYNTAX INTEGER { 
				valid(1),
				createRequest(2),
				underCreation(3),
				invalid(4)
		   }
	MAX-ACCESS read-write
	STATUS current
	DESCRIPTION
		"The status of this snL4VirtualServerHistoryControl entry.
		Each instance of the media-specific table associated
		with this snL4VirtualServerHistoryControlEntry will be deleted by the
		agent if this snL4VirtualServerHistoryControlEntry is not equal to
		valid(1)."
	::= { snL4VirtualServerHistoryControlEntry 7 }


-- The Virtual Server History Group


snL4VirtualServerHistoryTable OBJECT-TYPE
	SYNTAX SEQUENCE OF SnL4VirtualServerHistoryEntry
	MAX-ACCESS not-accessible
	STATUS current
	DESCRIPTION
		"A list of Ethernet snL4History entries."
	::= { snL4History 6 }

snL4VirtualServerHistoryEntry OBJECT-TYPE
	SYNTAX SnL4VirtualServerHistoryEntry
	MAX-ACCESS not-accessible
	STATUS current
	DESCRIPTION
		"An historical sample of Ethernet statistics on a
		particular Ethernet interface.  This sample is
		associated with the snL4VirtualServerHistoryControlEntry which set up
		the parameters for a regular collection of these
		samples.  As an example, an instance of the
		snL4VirtualServerHistoryReceivePkts object might be named
		snL4VirtualServerHistoryReceivePkts.2.89"
	INDEX { snL4VirtualServerHistoryIndex , snL4VirtualServerHistorySampleIndex }
	::= { snL4VirtualServerHistoryTable 1 }

SnL4VirtualServerHistoryEntry ::= SEQUENCE {
	snL4VirtualServerHistoryIndex                 
		INTEGER,
	snL4VirtualServerHistorySampleIndex           
		INTEGER,
	snL4VirtualServerHistoryIntervalStart         
		TimeTicks,
	snL4VirtualServerHistoryReceivePkts
		Counter32,
	snL4VirtualServerHistoryTransmitPkts
		Counter32,
	snL4VirtualServerHistoryTotalConnections
		Counter32,
	snL4VirtualServerHistoryCurConnections
		Integer32,
	snL4VirtualServerHistoryPeakConnections
		Integer32
	}

snL4VirtualServerHistoryIndex OBJECT-TYPE
	SYNTAX INTEGER (1..65535)
	MAX-ACCESS read-only
	STATUS current
	DESCRIPTION
		"The snL4VirtualServerHistory of which this entry is a part.The
		snL4VirtualServerHistory identified by a particular value of this
		index is the same snL4VirtualServerHistory as identified
		by the same value of snL4VirtualServerHistoryControlIndex."
	::= { snL4VirtualServerHistoryEntry 1 }

snL4VirtualServerHistorySampleIndex OBJECT-TYPE
	SYNTAX INTEGER (1..2147483647)
	MAX-ACCESS read-only
	STATUS current
	DESCRIPTION
		"An index that uniquely identifies the particular
		sample this entry represents among all samples
		associated with the same snL4VirtualServerHistoryControlEntry.
		This index starts at 1 and increases by one
		as each new sample is taken."
	::= { snL4VirtualServerHistoryEntry 2 }

snL4VirtualServerHistoryIntervalStart OBJECT-TYPE
	SYNTAX TimeTicks
	MAX-ACCESS read-only
	STATUS current
	DESCRIPTION
		"The value of sysUpTime at the start of the interval
		over which this sample was measured.If the probe
		keeps track of the time of day, it should start
		the first sample of the snL4VirtualServerHistory at a time such that
		when the next hour of the day begins, a sample is
		started at that instant.Note that following this
		rule may require the probe to delay collecting the
		first sample of the snL4VirtualServerHistory, as each sample must be
		of the same interval.Also note that the sample which
		is currently being collected is not accessible in this
		table until the end of its interval."
	::= { snL4VirtualServerHistoryEntry 3 }


snL4VirtualServerHistoryReceivePkts	  OBJECT-TYPE
	SYNTAX	Counter32
	MAX-ACCESS  read-only
	STATUS  current
	DESCRIPTION
		""
	::= { snL4VirtualServerHistoryEntry 4 }

snL4VirtualServerHistoryTransmitPkts  OBJECT-TYPE
	SYNTAX	Counter32
	MAX-ACCESS  read-only
	STATUS  current
	DESCRIPTION
		""
	::= { snL4VirtualServerHistoryEntry 5 }

snL4VirtualServerHistoryTotalConnections   OBJECT-TYPE
	SYNTAX	Counter32
	MAX-ACCESS  read-only
	STATUS  current
	DESCRIPTION
		""
	::= { snL4VirtualServerHistoryEntry 6 }

snL4VirtualServerHistoryCurConnections   OBJECT-TYPE
	SYNTAX   Integer32
	MAX-ACCESS  read-only
	STATUS  current
	DESCRIPTION
		""
	::= { snL4VirtualServerHistoryEntry 7 }

snL4VirtualServerHistoryPeakConnections   OBJECT-TYPE
	SYNTAX   Integer32
	MAX-ACCESS  read-only
	STATUS  current
	DESCRIPTION
		""
	::= { snL4VirtualServerHistoryEntry 8 }


-- Virtual Server Port Monitor Group

-- The Virtual Server Port History Control Group


snL4VirtualServerPortHistoryControlTable OBJECT-TYPE
	SYNTAX SEQUENCE OF SnL4VirtualServerPortHistoryControlEntry
	MAX-ACCESS not-accessible
	STATUS current
	DESCRIPTION
		"A list of history control entries."
	::= { snL4History 7 }

snL4VirtualServerPortHistoryControlEntry OBJECT-TYPE
	SYNTAX SnL4VirtualServerPortHistoryControlEntry
	MAX-ACCESS not-accessible
	STATUS current
	DESCRIPTION
		"A list of parameters that set up a periodic sampling
		of statistics.As an example, an instance of the
		snL4VirtualServerPortHistoryControlInterval object might be named
		snL4VirtualServerPortHistoryControlInterval.2"
	INDEX { snL4VirtualServerPortHistoryControlIndex }
	::= { snL4VirtualServerPortHistoryControlTable 1 }

	SnL4VirtualServerPortHistoryControlEntry ::= SEQUENCE {
		snL4VirtualServerPortHistoryControlIndex			 
			INTEGER,
		snL4VirtualServerPortHistoryControlDataSource		
			OBJECT IDENTIFIER,
		snL4VirtualServerPortHistoryControlBucketsRequested
			INTEGER,
		snL4VirtualServerPortHistoryControlBucketsGranted	
			INTEGER,
		snL4VirtualServerPortHistoryControlInterval		
			INTEGER,
		snL4VirtualServerPortHistoryControlOwner			 
			DisplayString,
		snL4VirtualServerPortHistoryControlStatus			
			INTEGER
	}

snL4VirtualServerPortHistoryControlIndex OBJECT-TYPE
	SYNTAX INTEGER (1..65535)
	MAX-ACCESS read-only
	STATUS current
	DESCRIPTION
		"An index that uniquely identifies an entry in the
		snL4VirtualServerPortHistoryControl table.Each such entry defines a
		set of samples at a particular interval for an
		interface on the device."
	::= { snL4VirtualServerPortHistoryControlEntry 1 }

snL4VirtualServerPortHistoryControlDataSource OBJECT-TYPE
	SYNTAX OBJECT IDENTIFIER
	MAX-ACCESS read-write
	STATUS current
	DESCRIPTION
		"This object identifies the source of the data for
		which historical data was collected and
		placed in a media-specific table on behalf of this
		snL4VirtualServerPortHistoryControlEntry.This source can be any
		real/virtual server and real/virtual server port on 
		this ServerIron.  In order to identify
		a particular instance, this object shall identify
		the instance of the object, defined in the above 
		statistics tables.
	
		This object may not be modified if the associated
		snL4VirtualServerPortHistoryControlStatus object is equal to valid(1)."
	::= { snL4VirtualServerPortHistoryControlEntry 2 }

snL4VirtualServerPortHistoryControlBucketsRequested OBJECT-TYPE
	SYNTAX INTEGER (1..65535)
	MAX-ACCESS read-write
	STATUS current
	DESCRIPTION
		"The requested number of discrete time intervals
		over which data is to be saved in the part of the
		media-specific table associated with this
		snL4VirtualServerPortHistoryControlEntry.
	
		When this object is created or modified, the probe
		should set snL4VirtualServerPortHistoryControlBucketsGranted as closely to
		this object as is possible for the particular probe
		implementation and available resources."
	DEFVAL { 50 }
	::= { snL4VirtualServerPortHistoryControlEntry 3 }

snL4VirtualServerPortHistoryControlBucketsGranted OBJECT-TYPE
	SYNTAX INTEGER (1..65535)
	MAX-ACCESS read-only
	STATUS current
	DESCRIPTION
		"The number of discrete sampling intervals
		over which data shall be saved in the part of
		the media-specific table associated with this
		snL4VirtualServerPortHistoryControlEntry.
	
		When the associated snL4VirtualServerPortHistoryControlBucketsRequested
		object is created or modified, the probe
		should set this object as closely to the requested
		value as is possible for the particular
		probe implementation and available resources.The
		probe must not lower this value except as a result
		of a modification to the associated
		snL4VirtualServerPortHistoryControlBucketsRequested object.
	
		There will be times when the actual number of
		buckets associated with this entry is less than
		the value of this object.In this case, at the
		end of each sampling interval, a new bucket will
		be added to the media-specific table.
	
		When the number of buckets reaches the value of
		this object and a new bucket is to be added to the
		media-specific table, the oldest bucket associated
		with this snL4VirtualServerPortHistoryControlEntry shall be deleted by
		the agent so that the new bucket can be added.
	
		When the value of this object changes to a value less
		than the current value, entries are deleted
		from the media-specific table associated with this
		snL4VirtualServerPortHistoryControlEntry.Enough of the oldest of these
		entries shall be deleted by the agent so that their
		number remains less than or equal to the new value of
		this object.
	
		When the value of this object changes to a value
		greater than the current value, the number of
		associated media- specific entries may be allowed to
		grow."
	::= { snL4VirtualServerPortHistoryControlEntry 4 }

snL4VirtualServerPortHistoryControlInterval OBJECT-TYPE
	SYNTAX INTEGER (1..3600)
	MAX-ACCESS read-write
	STATUS current
	DESCRIPTION
		"The interval in seconds over which the data is
		sampled for each bucket in the part of the
		media-specific table associated with this
		snL4VirtualServerPortHistoryControlEntry.This interval can
		be set to any number of seconds between 1 and
		3600 (1 hour).
	
		Because the counters in a bucket may overflow at their
		maximum value with no indication, a prudent manager
		will take into account the possibility of overflow
		in any of the associated counters.It is important
		to consider the minimum time in which any counter
		could overflow on a particular media type and set
		the snL4VirtualServerPortHistoryControlInterval object to a value less
		than this interval.This is typically most
		important for the 'octets' counter in any
		media-specific table.	
		This object may not be modified if the associated
		snL4VirtualServerPortHistoryControlStatus object is equal to valid(1)."
	DEFVAL { 1800 }
	::= { snL4VirtualServerPortHistoryControlEntry 5 }

snL4VirtualServerPortHistoryControlOwner OBJECT-TYPE
	SYNTAX DisplayString
	MAX-ACCESS read-write
	STATUS current
	DESCRIPTION
		"The entity that configured this entry and is
		therefore using the resources assigned to it."
	::= { snL4VirtualServerPortHistoryControlEntry 6 }

snL4VirtualServerPortHistoryControlStatus OBJECT-TYPE
	SYNTAX INTEGER { 
				valid(1),
				createRequest(2),
				underCreation(3),
				invalid(4)
		   }
	MAX-ACCESS read-write
	STATUS current
	DESCRIPTION
		"The status of this snL4VirtualServerPortHistoryControl entry.
		Each instance of the media-specific table associated
		with this snL4VirtualServerPortHistoryControlEntry will be deleted by the
		agent if this snL4VirtualServerPortHistoryControlEntry is not equal to
		valid(1)."
	::= { snL4VirtualServerPortHistoryControlEntry 7 }


-- The Virtual Server Port History Group


snL4VirtualServerPortHistoryTable OBJECT-TYPE
	SYNTAX SEQUENCE OF SnL4VirtualServerPortHistoryEntry
	MAX-ACCESS not-accessible
	STATUS current
	DESCRIPTION
		"A list of Ethernet snL4History entries."
	::= { snL4History 8 }

snL4VirtualServerPortHistoryEntry OBJECT-TYPE
	SYNTAX SnL4VirtualServerPortHistoryEntry
	MAX-ACCESS not-accessible
	STATUS current
	DESCRIPTION
		"An historical sample of Ethernet statistics on a
		particular Ethernet interface.  This sample is
		associated with the snL4VirtualServerPortHistoryControlEntry which set up
		the parameters for a regular collection of these
		samples.  As an example, an instance of the
		snL4VirtualServerPortHistoryReceivePkts object might be named
		snL4VirtualServerPortHistoryReceivePkts.2.89"
	INDEX { snL4VirtualServerPortHistoryIndex , snL4VirtualServerPortHistorySampleIndex }
	::= { snL4VirtualServerPortHistoryTable 1 }

SnL4VirtualServerPortHistoryEntry ::= SEQUENCE {
	snL4VirtualServerPortHistoryIndex                 
		INTEGER ,
	snL4VirtualServerPortHistorySampleIndex           
		INTEGER,
	snL4VirtualServerPortHistoryIntervalStart         
		TimeTicks,
	snL4VirtualServerPortHistoryReceivePkts
		Counter32,
	snL4VirtualServerPortHistoryTransmitPkts
		Counter32,
	snL4VirtualServerPortHistoryTotalConnections
		Counter32,
	snL4VirtualServerPortHistoryCurConnections
		Integer32,
	snL4VirtualServerPortHistoryPeakConnections
		Integer32
	}

snL4VirtualServerPortHistoryIndex OBJECT-TYPE
	SYNTAX INTEGER (1..65535)
	MAX-ACCESS read-only
	STATUS current
	DESCRIPTION
		"The snL4VirtualServerPortHistory of which this entry is a part.The
		snL4VirtualServerPortHistory identified by a particular value of this
		index is the same snL4VirtualServerPortHistory as identified
		by the same value of snL4VirtualServerPortHistoryControlIndex."
	::= { snL4VirtualServerPortHistoryEntry 1 }

snL4VirtualServerPortHistorySampleIndex OBJECT-TYPE
	SYNTAX INTEGER (1..2147483647)
	MAX-ACCESS read-only
	STATUS current
	DESCRIPTION
		"An index that uniquely identifies the particular
		sample this entry represents among all samples
		associated with the same snL4VirtualServerPortHistoryControlEntry.
		This index starts at 1 and increases by one
		as each new sample is taken."
	::= { snL4VirtualServerPortHistoryEntry 2 }

snL4VirtualServerPortHistoryIntervalStart OBJECT-TYPE
	SYNTAX TimeTicks
	MAX-ACCESS read-only
	STATUS current
	DESCRIPTION
		"The value of sysUpTime at the start of the interval
		over which this sample was measured.If the probe
		keeps track of the time of day, it should start
		the first sample of the snL4VirtualServerPortHistory at a time such that
		when the next hour of the day begins, a sample is
		started at that instant.Note that following this
		rule may require the probe to delay collecting the
		first sample of the snL4VirtualServerPortHistory, as each sample must be
		of the same interval.Also note that the sample which
		is currently being collected is not accessible in this
		table until the end of its interval."
	::= { snL4VirtualServerPortHistoryEntry 3 }


snL4VirtualServerPortHistoryReceivePkts	  OBJECT-TYPE
	SYNTAX	Counter32
	MAX-ACCESS  read-only
	STATUS  current
	DESCRIPTION
		""
	::= { snL4VirtualServerPortHistoryEntry 4 }

snL4VirtualServerPortHistoryTransmitPkts  OBJECT-TYPE
	SYNTAX	Counter32
	MAX-ACCESS  read-only
	STATUS  current
	DESCRIPTION
		""
	::= { snL4VirtualServerPortHistoryEntry 5 }

snL4VirtualServerPortHistoryTotalConnections   OBJECT-TYPE
	SYNTAX	Counter32
	MAX-ACCESS  read-only
	STATUS  current
	DESCRIPTION
		""
	::= { snL4VirtualServerPortHistoryEntry 6 }

snL4VirtualServerPortHistoryCurConnections   OBJECT-TYPE
	SYNTAX   Integer32
	MAX-ACCESS  read-only
	STATUS  current
	DESCRIPTION
		""
	::= { snL4VirtualServerPortHistoryEntry 7 }

snL4VirtualServerPortHistoryPeakConnections   OBJECT-TYPE
	SYNTAX   Integer32
	MAX-ACCESS  read-only
	STATUS  current
	DESCRIPTION
		""
	::= { snL4VirtualServerPortHistoryEntry 8 }

END
FOUNDRY-SN-BGP4-GROUP-MIB DEFINITIONS ::= BEGIN

	 IMPORTS
			MODULE-IDENTITY, OBJECT-TYPE, Counter32, IpAddress,Integer32, Unsigned32 
					 FROM SNMPv2-SMI
	router
		FROM FOUNDRY-SN-ROOT-MIB
			 InetAutonomousSystemNumber
					 FROM INET-ADDRESS-MIB;
					 
snBgp4 MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"            
	REVISION     "200909300000Z" -- September 30, 2009
	DESCRIPTION
			"convert from SMIv1 to SMIv2"
   ::= { router 11}

-- Groups

snBgp4Gen 	        	OBJECT IDENTIFIER ::= { snBgp4 1 }
snBgp4AddrFilter 		OBJECT IDENTIFIER ::= { snBgp4 2 }
snBgp4AggregateAddr 	OBJECT IDENTIFIER ::= { snBgp4 3 }
snBgp4AsPathFilter 		OBJECT IDENTIFIER ::= { snBgp4 4 }
snBgp4CommunityFilter 	OBJECT IDENTIFIER ::= { snBgp4 5 }
snBgp4NeighGenCfg 		OBJECT IDENTIFIER ::= { snBgp4 6 }
snBgp4NeighDistGroup 	OBJECT IDENTIFIER ::= { snBgp4 7 }
snBgp4NeighFilterGroup 	OBJECT IDENTIFIER ::= { snBgp4 8 }
snBgp4NeighRouteMap 	OBJECT IDENTIFIER ::= { snBgp4 9 }
snBgp4Network 			OBJECT IDENTIFIER ::= { snBgp4 10 }
snBgp4Redis 			OBJECT IDENTIFIER ::= { snBgp4 11 }
snBgp4RouteMapFilter 	OBJECT IDENTIFIER ::= { snBgp4 12 }
snBgp4RouteMapMatch 	OBJECT IDENTIFIER ::= { snBgp4 13 }
snBgp4RouteMapSet 	    OBJECT IDENTIFIER ::= { snBgp4 14 }
snBgp4NeighOperStatus 	OBJECT IDENTIFIER ::= { snBgp4 15 }
snBgp4RouteOperStatus	OBJECT IDENTIFIER ::= { snBgp4 16 }
snBgp4NeighborSummary	OBJECT IDENTIFIER ::= { snBgp4 17 }
snBgp4Attribute			OBJECT IDENTIFIER ::= { snBgp4 18 }
snBgp4ClearNeighborCmd	OBJECT IDENTIFIER ::= { snBgp4 19 }
snBgp4NeighPrefixGroup 	OBJECT IDENTIFIER ::= { snBgp4 20 }

--  BGP4 General Variables

--  These parameters apply globally to the Router's
--  BGP4 Process.


	 snBgp4GenAlwaysCompareMed OBJECT-TYPE
		 SYNTAX   INTEGER { disabled(0), enabled(1) }
		 MAX-ACCESS   read-write
		 STATUS   current
		 DESCRIPTION
			"To enable/disable the comparison of the Multi-Exit Discriminator for paths from 
			neighbors in different AS."
		 ::= { snBgp4Gen 1 }

	 snBgp4GenAutoSummary OBJECT-TYPE
		 SYNTAX   INTEGER { disabled(0), enabled(1) }
		 MAX-ACCESS   read-write
		 STATUS   current
		 DESCRIPTION
			"To enable/disable the default behavior of automatic summarization of subnet routes
			into network-level routes."  
		 ::= { snBgp4Gen 2 }

	 snBgp4GenDefaultLocalPreference OBJECT-TYPE
		 SYNTAX   Integer32
		 MAX-ACCESS   read-write
		 STATUS  deprecated
		 DESCRIPTION
			"To set the default local preference attribute.This is deprecated and snBgp4GenDefaultLocalPreference1 is introduced."
		 ::= { snBgp4Gen 3 }

	 snBgp4GenDefaultInfoOriginate OBJECT-TYPE
		 SYNTAX   INTEGER { disabled(0), enabled(1) }
		 MAX-ACCESS   read-write
		 STATUS   current
		 DESCRIPTION
			"To enable/disable the default Information Originate."
		 ::= { snBgp4Gen 4 }

	 snBgp4GenFastExternalFallover OBJECT-TYPE
		 SYNTAX   INTEGER { disabled(0), enabled(1) }
		 MAX-ACCESS   read-write
		 STATUS   current
		 DESCRIPTION
			"To enable/disable an action of immediately reset the BGP sessions of any
			directly adjacent external neighbors if the link used to reach them goes
			down."
		 ::= { snBgp4Gen 5 }

	 snBgp4GenNextBootNeighbors OBJECT-TYPE
		 SYNTAX   Integer32
		 MAX-ACCESS   read-write
		 STATUS   current
		 DESCRIPTION
			"The next-boot configured number of neighbors in a BGP Peer Group.
			The minimum value of this MIB is snBgp4GenMinNeighbors.
			The maximum value of this MIB is snBgp4GenMaxNeighbors."
		 ::= { snBgp4Gen 6 }

	 snBgp4GenNextBootRoutes OBJECT-TYPE
		 SYNTAX   Integer32
		 MAX-ACCESS   read-write
		 STATUS   current
		 DESCRIPTION
			"The next-boot configured number of Routes.
			The minimum value of this MIB is snBgp4GenMinRoutes.
			The maximum value of this MIB is snBgp4GenMaxRoutes."
		 ::= { snBgp4Gen 7 }

	 snBgp4GenSynchronization OBJECT-TYPE
		 SYNTAX   INTEGER { disabled(0), enabled(1) }
		 MAX-ACCESS   read-write
		 STATUS   current
		 DESCRIPTION
			"To enable/disable the synchronization between BGP and your IGP."
		 ::= { snBgp4Gen 8 }

	 snBgp4GenKeepAliveTime OBJECT-TYPE
		 SYNTAX   INTEGER (0..65535)
		 MAX-ACCESS   read-write
		 STATUS   current
		 DESCRIPTION
			"The Keep alive timer."
		 ::= { snBgp4Gen 9 }

	 snBgp4GenHoldTime OBJECT-TYPE
		 SYNTAX   INTEGER (0..65535)
		 MAX-ACCESS   read-write
		 STATUS   current
		 DESCRIPTION
			"The Hold time timer."
		 ::= { snBgp4Gen 10 }

	 snBgp4GenRouterId OBJECT-TYPE
		 SYNTAX   IpAddress
		 MAX-ACCESS   read-write
		 STATUS   current
		 DESCRIPTION
			"BGP Router Id."
		 ::= { snBgp4Gen 11 }

	 snBgp4GenTableMap OBJECT-TYPE
		 SYNTAX  OCTET STRING (SIZE(0..32)) 
		 MAX-ACCESS   read-write
		 STATUS   current
		 DESCRIPTION
			"An octet string of the route-map name, each character of the name
			is represented by one octet."
		 ::= { snBgp4Gen 12 }

	 snBgp4GenAdminStat OBJECT-TYPE
		 SYNTAX   INTEGER { disabled (0), enabled (1) }
		 MAX-ACCESS   read-write
		 STATUS   current
		 DESCRIPTION
			"The administrative status of BGP4 in the router.  The
			value 'enabled' denotes that the BGP4 routing is active
			in this router; 'disabled' disables BGP4 routing on this router."
		 ::= { snBgp4Gen 13 }

	 snBgp4GenDefaultMetric OBJECT-TYPE
		 SYNTAX   Integer32
		 MAX-ACCESS   read-write
		 STATUS   deprecated
		 DESCRIPTION
			"To set default metric values for the BGP4 protocol.This is deprecated and snBgp4GenDefaultMetric1 is introduced."
		 ::= { snBgp4Gen 14 }

	 snBgp4GenMaxNeighbors OBJECT-TYPE
		 SYNTAX   Integer32
		 MAX-ACCESS   read-only
		 STATUS   current
		 DESCRIPTION
			"The maximum number of neighbors can be configured in a BGP Peer Group."
		 ::= { snBgp4Gen 15 }

	 snBgp4GenMinNeighbors OBJECT-TYPE
		 SYNTAX   Integer32
		 MAX-ACCESS   read-only
		 STATUS   current
		 DESCRIPTION
			"The minimum number of neighbors can be configured in a BGP Peer Group."
		 ::= { snBgp4Gen 16 }

	 snBgp4GenMaxRoutes OBJECT-TYPE
		 SYNTAX   Integer32
		 MAX-ACCESS   read-only
		 STATUS   current
		 DESCRIPTION
			"The maximum configured number of Routes."
		 ::= { snBgp4Gen 17 }

	 snBgp4GenMinRoutes OBJECT-TYPE
		 SYNTAX   Integer32
		 MAX-ACCESS   read-only
		 STATUS   current
		 DESCRIPTION
			"The minimum configured number of Routes."
		 ::= { snBgp4Gen 18 }

	 snBgp4GenMaxAddrFilters OBJECT-TYPE
		 SYNTAX   Integer32
		 MAX-ACCESS   read-only
		 STATUS   current
		 DESCRIPTION
			"The maximum configured number of BGP4 address filters."
		 ::= { snBgp4Gen 19 }

	 snBgp4GenMaxAggregateAddresses OBJECT-TYPE
		 SYNTAX   Integer32
		 MAX-ACCESS   read-only
		 STATUS   current
		 DESCRIPTION
			"The maximum configured number of BGP4 aggregate addresses."
		 ::= { snBgp4Gen 20 }

	 snBgp4GenMaxAsPathFilters OBJECT-TYPE
		 SYNTAX   Integer32
		 MAX-ACCESS   read-only
		 STATUS   current
		 DESCRIPTION
			"The maximum configured number of BGP4 AS-PATH filters."
		 ::= { snBgp4Gen 21 }

	 snBgp4GenMaxCommunityFilters OBJECT-TYPE
		 SYNTAX   Integer32
		 MAX-ACCESS   read-only
		 STATUS   current
		 DESCRIPTION
			"The maximum configured number of BGP4 Community filters."
		 ::= { snBgp4Gen 22 }

	 snBgp4GenMaxNetworks OBJECT-TYPE
		 SYNTAX   Integer32
		 MAX-ACCESS   read-only
		 STATUS   current
		 DESCRIPTION
			"The maximum configured number of BGP4 Networks."
		 ::= { snBgp4Gen 23 }

	 snBgp4GenMaxRouteMapFilters OBJECT-TYPE
		 SYNTAX   Integer32
		 MAX-ACCESS   read-only
		 STATUS   current
		 DESCRIPTION
			"The maximum configured number of BGP4 Route-map Filters."
		 ::= { snBgp4Gen 24 }

	 snBgp4GenNeighPrefixMinValue OBJECT-TYPE
		 SYNTAX   Integer32
		 MAX-ACCESS   read-only
		 STATUS   current
		 DESCRIPTION
			"The minimum configured value of BGP4 Neighbor Prefix."
		 ::= { snBgp4Gen 25 }

	 snBgp4GenOperNeighbors OBJECT-TYPE
		 SYNTAX   Integer32
		 MAX-ACCESS   read-only
		 STATUS   current
		 DESCRIPTION
			"The current operational max number of neighbors configured for a BGP Group."
		 ::= { snBgp4Gen 26 }

	 snBgp4GenOperRoutes OBJECT-TYPE
		 SYNTAX   Integer32
		 MAX-ACCESS   read-only
		 STATUS   current
		 DESCRIPTION
			"The current operational number of Routes."
		 ::= { snBgp4Gen 27 }

	 snBgp4GenLocalAs OBJECT-TYPE
		 SYNTAX   INTEGER (1..65535)
		 MAX-ACCESS   read-write
		 STATUS   current
		 DESCRIPTION
		"Bgp4 local autonomous system number."
		 ::= { snBgp4Gen 28 }

	 snBgp4GenRoutesInstalled OBJECT-TYPE
		 SYNTAX   Integer32
		 MAX-ACCESS   read-only
		 STATUS   current
		 DESCRIPTION
		"Bgp4 installed routes."
		 ::= { snBgp4Gen 29 }

	 snBgp4GenAsPathInstalled OBJECT-TYPE
		 SYNTAX   Integer32
		 MAX-ACCESS   read-only
		 STATUS   current
		 DESCRIPTION
		"Bgp4 installed autonomous system path."
		 ::= { snBgp4Gen 30 }

	 snBgp4ExternalDistance OBJECT-TYPE
		 SYNTAX  INTEGER (1..255)
		 MAX-ACCESS   read-write
		 STATUS   current
		 DESCRIPTION
		"Administrative distance for BGP external routes."
		 DEFVAL { 20 }
		 ::= { snBgp4Gen 31 }

	 snBgp4InternalDistance OBJECT-TYPE
		 SYNTAX  INTEGER (1..255)
		 MAX-ACCESS   read-write
		 STATUS   current
		 DESCRIPTION
		"Administrative distance for BGP internal routes."
		 DEFVAL { 200 }
		 ::= { snBgp4Gen 32 }

	 snBgp4LocalDistance OBJECT-TYPE
		 SYNTAX  INTEGER (1..255)
		 MAX-ACCESS   read-write
		 STATUS   current
		 DESCRIPTION
		"Administrative distance for BGP local routes."
		 DEFVAL { 200 }
		 ::= { snBgp4Gen 33 }

	 snBgp4OperNumOfAttributes OBJECT-TYPE
		 SYNTAX Integer32
		 MAX-ACCESS   read-only
		 STATUS   current
		 DESCRIPTION
		"The operational number of attribute entries."
		 ::= { snBgp4Gen 34 }

	 snBgp4NextBootMaxAttributes OBJECT-TYPE
		 SYNTAX  INTEGER (200..30000)
		 MAX-ACCESS   read-write
		 STATUS   current
		 DESCRIPTION
		"The next boot maximum attribute entries. 10000 means reset to default."
		 DEFVAL { 10000 }
		 ::= { snBgp4Gen 35 }

	 snBgp4ClusterId OBJECT-TYPE
		 SYNTAX  Integer32 
		 MAX-ACCESS   read-write
		 STATUS   current
		 DESCRIPTION
		"A cluster ID which is represented by 4 bytes unsigned 
		 integer (0..0xFFFFFFFF). 0 means reset to default."
		 ::= { snBgp4Gen 36 }

	 snBgp4ClientToClientReflection OBJECT-TYPE
		 SYNTAX   INTEGER { disabled(0), enabled(1) }
		 MAX-ACCESS   read-write
		 STATUS   current
		 DESCRIPTION
		"To enable/disable the client to client reflection in BGP4."
		 ::= { snBgp4Gen 37 }

	 snBgp4GenTotalNeighbors OBJECT-TYPE
		 SYNTAX   Integer32
		 MAX-ACCESS   read-only
		 STATUS   current
		 DESCRIPTION
			"The current total number of neighbors running in a BGP Group."
		 ::= { snBgp4Gen 38 }

	 snBgp4GenMaxPaths OBJECT-TYPE
		 SYNTAX   INTEGER (1..8)
		 MAX-ACCESS   read-write
		 STATUS   current
		 DESCRIPTION
			"The maximum configured number of Paths."
		 ::= { snBgp4Gen 39 }

	 snBgp4GenConfedId OBJECT-TYPE
		 SYNTAX   INTEGER (1..65535)
		 MAX-ACCESS   read-write
		 STATUS   current
		 DESCRIPTION
		"Bgp4 Confederation Id."
		 ::= { snBgp4Gen 40 }

	 snBgp4GenConfedPeers OBJECT-TYPE
	 SYNTAX  OCTET STRING (SIZE(0..100))
	 MAX-ACCESS  read-write
	 STATUS  current
	 DESCRIPTION
		"An AS number from 1 to 0xFFFF construct confederation peers.
		 There are 50(max peers) of them.  
		 This integer number is represented by 2 OCTETs."
		 ::= { snBgp4Gen 41 }

	 snBgp4GenDampening OBJECT-TYPE
		 SYNTAX   INTEGER { none (0), parameters (1), routeMap (2) }
		 MAX-ACCESS   read-write
		 STATUS   current
		 DESCRIPTION
			"The dampening of BGP4 in the router.  
			value 'none' denotes that the BGP4  dampening is off
			'parameters' denotes parameters are confibrurable.
			'routeMap' denotes routemap is configurable."		
		 ::= { snBgp4Gen 42 }

	 snBgp4GenDampenHalfLife OBJECT-TYPE
		 SYNTAX   INTEGER (1..45)
		 MAX-ACCESS   read-write
		 STATUS   current
		 DESCRIPTION
		"Bgp4 Dampening Half Life."
		 ::= { snBgp4Gen 43 }

	 snBgp4GenDampenReuse OBJECT-TYPE
		 SYNTAX   INTEGER (1..20000)
		 MAX-ACCESS   read-write
		 STATUS   current
		 DESCRIPTION
		"Bgp4 Dampening Reuse."
		 ::= { snBgp4Gen 44 }

	 snBgp4GenDampenSuppress OBJECT-TYPE
		 SYNTAX   INTEGER (1..20000)
		 MAX-ACCESS   read-write
		 STATUS   current
		 DESCRIPTION
		"Bgp4 Dampening Suppress."
		 ::= { snBgp4Gen 45 }

	 snBgp4GenDampenMaxSuppress OBJECT-TYPE
		 SYNTAX   INTEGER (1..20000)
		 MAX-ACCESS   read-write
		 STATUS   current
		 DESCRIPTION
		"Bgp4 Dampening Max Suppress Time."
		 ::= { snBgp4Gen 46 }

	 snBgp4GenDampenMap OBJECT-TYPE
		 SYNTAX  OCTET STRING (SIZE(0..32)) 
		 MAX-ACCESS   read-write
		 STATUS   current
		 DESCRIPTION
			"An octet string of the route-map name for dampening, each character of the name
			is represented by one octet."
		 ::= { snBgp4Gen 47 }

	 snBgp4GenLocalAs4 OBJECT-TYPE
		 SYNTAX   InetAutonomousSystemNumber
		 MAX-ACCESS   read-write
		 STATUS   current
		 DESCRIPTION
		"BGP4 local autonomous system (AS) number to support 4 byte AS format."
		 ::= { snBgp4Gen 48 }
        
	 snBgp4GenDefaultMetric1 OBJECT-TYPE
		 SYNTAX   Unsigned32
		 MAX-ACCESS   read-write
		 STATUS   current
		 DESCRIPTION
			"To set default metric values for the BGP4 protocol."
		 ::= { snBgp4Gen 49 }
        
	 snBgp4GenDefaultLocalPreference1 OBJECT-TYPE
		 SYNTAX   Unsigned32
		 MAX-ACCESS   read-write
		 STATUS   current
		 DESCRIPTION
			"To set the default local preference attribute."
		 ::= { snBgp4Gen 50 }
        
--- Bgp4 Address Filter table

snBgp4AddrFilterTable       OBJECT-TYPE
	SYNTAX  SEQUENCE OF SnBgp4AddrFilterEntry
	MAX-ACCESS  not-accessible
	STATUS  current
	DESCRIPTION
		"Bgp4 Address Filter table."
	::= { snBgp4AddrFilter 1 }

snBgp4AddrFilterEntry       OBJECT-TYPE
	SYNTAX  SnBgp4AddrFilterEntry
	MAX-ACCESS  not-accessible
	STATUS  current
	DESCRIPTION
		"An entry in the Bgp4 Address Filter table."
	INDEX   { snBgp4AddrFilterIndex }
	::= { snBgp4AddrFilterTable 1 }

SnBgp4AddrFilterEntry ::= SEQUENCE {
	snBgp4AddrFilterIndex
		Integer32,
	snBgp4AddrFilterAction              
		INTEGER,
	snBgp4AddrFilterSourceIp
		IpAddress,
	snBgp4AddrFilterSourceMask
		IpAddress,
	snBgp4AddrFilterDestIp
		IpAddress,
	snBgp4AddrFilterDestMask
		IpAddress,
	snBgp4AddrFilterRowStatus
		INTEGER
	}

snBgp4AddrFilterIndex       OBJECT-TYPE
	SYNTAX  Integer32
	MAX-ACCESS  read-only
	STATUS  current
	DESCRIPTION
		"The table index for a filter entry."
	::= { snBgp4AddrFilterEntry 1 }

snBgp4AddrFilterAction      OBJECT-TYPE
	SYNTAX  INTEGER { deny(0), permit(1) } 
	MAX-ACCESS  read-write
	STATUS  current
	DESCRIPTION
		"Action to take if the bgp address match
		with this filter."
	::= { snBgp4AddrFilterEntry 2 }

snBgp4AddrFilterSourceIp    OBJECT-TYPE
	SYNTAX  IpAddress
	MAX-ACCESS  read-write
	STATUS  current
	DESCRIPTION
		"Source IP address."
	::= { snBgp4AddrFilterEntry 3 }

snBgp4AddrFilterSourceMask  OBJECT-TYPE
	SYNTAX  IpAddress
	MAX-ACCESS  read-write
	STATUS  current
	DESCRIPTION
		"Source IP subnet mask."
	::= { snBgp4AddrFilterEntry 4 }

snBgp4AddrFilterDestIp      OBJECT-TYPE
	SYNTAX  IpAddress
	MAX-ACCESS  read-write
	STATUS  current
	DESCRIPTION
		"Destination IP address."
	::= { snBgp4AddrFilterEntry 5 }

snBgp4AddrFilterDestMask    OBJECT-TYPE
	SYNTAX  IpAddress
	MAX-ACCESS  read-write
	STATUS  current
	DESCRIPTION
		"Destination IP subnet mask."
	::= { snBgp4AddrFilterEntry 6 }

snBgp4AddrFilterRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4AddrFilterEntry 7 }

-- Bgp4 Aggregate Address table

snBgp4AggregateAddrTable       OBJECT-TYPE
	SYNTAX  SEQUENCE OF SnBgp4AggregateAddrEntry
	MAX-ACCESS  not-accessible
	STATUS  current
	DESCRIPTION
		"Bgp4 Aggregate Address table."
	::= { snBgp4AggregateAddr 1 }

snBgp4AggregateAddrEntry       OBJECT-TYPE
	SYNTAX  SnBgp4AggregateAddrEntry
	MAX-ACCESS  not-accessible
	STATUS  current
	DESCRIPTION
		"An entry in the Bgp4 Aggregate Address table."
	INDEX   { snBgp4AggregateAddrIp, snBgp4AggregateAddrMask, snBgp4AggregateAddrOption }
	::= { snBgp4AggregateAddrTable 1 }

SnBgp4AggregateAddrEntry ::= SEQUENCE {
	snBgp4AggregateAddrIp
		IpAddress,
	snBgp4AggregateAddrMask
		IpAddress,
	snBgp4AggregateAddrOption
		INTEGER,
	snBgp4AggregateAddrMap
		OCTET STRING,
	snBgp4AggregateAddrRowStatus
		INTEGER
	}

snBgp4AggregateAddrIp    OBJECT-TYPE
	SYNTAX  IpAddress
	MAX-ACCESS  read-only
	STATUS  current
	DESCRIPTION
		"Aggregate Address IP address."
	::= { snBgp4AggregateAddrEntry 1 }

snBgp4AggregateAddrMask  OBJECT-TYPE
	SYNTAX  IpAddress
	MAX-ACCESS  read-only
	STATUS  current
	DESCRIPTION
		"Aggregate Address IP subnet mask."
	::= { snBgp4AggregateAddrEntry 2 }

snBgp4AggregateAddrOption      OBJECT-TYPE
	SYNTAX  INTEGER { 
				address(1), 
				asSet(2), 
				summaryOnly(3), 
				suppressMap(4), 
				advertiseMap(5), 
				attributeMap(6) 
				} 
	MAX-ACCESS  read-only
	STATUS  current
	DESCRIPTION
		"address(1), asSet(2), summaryOnly(3), 
		the suppressMap(4), advertiseMap(5), 
		attributeMap(6) are Options for creating an aggregate entry 
		in a BGP routing table."
	::= { snBgp4AggregateAddrEntry 3 }

snBgp4AggregateAddrMap      OBJECT-TYPE
	SYNTAX  OCTET STRING (SIZE(0..32)) 
	MAX-ACCESS  read-write
	STATUS  current
	DESCRIPTION
		"This object associates with the snBgp4AggregateAddrOption and 
		the suppressMap(4), advertiseMap(5), attributeMap(6) of the 
		snBgp4AggregateAddrOption are only two Options for creating 
		an aggregate address map. A SNMP-SET error will be returned 
		for other options.  An octet string of the map name, 
		each character of the name is represented by one octet."
	::= { snBgp4AggregateAddrEntry 4 }

snBgp4AggregateAddrRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4AggregateAddrEntry 5 }

-- Bgp4 AS-Path Filter table

snBgp4AsPathFilterTable       OBJECT-TYPE
	SYNTAX  SEQUENCE OF SnBgp4AsPathFilterEntry
	MAX-ACCESS  not-accessible
	STATUS  current
	DESCRIPTION
		"Bgp4 AS-Path Filter table."
	::= { snBgp4AsPathFilter 1 }

snBgp4AsPathFilterEntry       OBJECT-TYPE
	SYNTAX  SnBgp4AsPathFilterEntry
	MAX-ACCESS  not-accessible
	STATUS  current
	DESCRIPTION
		"An entry in the Bgp4 As-path Filter table."
	INDEX   { snBgp4AsPathFilterIndex }
	::= { snBgp4AsPathFilterTable 1 }

SnBgp4AsPathFilterEntry ::= SEQUENCE {
	snBgp4AsPathFilterIndex
		Integer32,
	snBgp4AsPathFilterAction              
		INTEGER,
	snBgp4AsPathFilterRegExpression
		OCTET STRING,
	snBgp4AsPathFilterRowStatus
		INTEGER
	}

snBgp4AsPathFilterIndex       OBJECT-TYPE
	SYNTAX  Integer32
	MAX-ACCESS  read-only
	STATUS  current
	DESCRIPTION
		"The table index for a filter entry."
	::= { snBgp4AsPathFilterEntry 1 }

snBgp4AsPathFilterAction      OBJECT-TYPE
	SYNTAX  INTEGER { deny(0), permit(1) } 
	MAX-ACCESS  read-write
	STATUS  current
	DESCRIPTION
		"Action to take if the bgp address match
		with this filter."
	::= { snBgp4AsPathFilterEntry 2 }

snBgp4AsPathFilterRegExpression    OBJECT-TYPE
	SYNTAX  OCTET STRING (SIZE(0..256))
	MAX-ACCESS  read-write
	STATUS  current
	DESCRIPTION
		"Autonomous system in the filter using a regular expression.
		Each character of the regular expression string is represented
		by one octet."
	::= { snBgp4AsPathFilterEntry 3 }

snBgp4AsPathFilterRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4AsPathFilterEntry 4 }


-- Bgp4 Community Filter table

snBgp4CommunityFilterTable       OBJECT-TYPE
	SYNTAX  SEQUENCE OF SnBgp4CommunityFilterEntry
	MAX-ACCESS  not-accessible
	STATUS  current
	DESCRIPTION
		"Bgp4 Community Filter table."
	::= { snBgp4CommunityFilter 1 }

snBgp4CommunityFilterEntry       OBJECT-TYPE
	SYNTAX  SnBgp4CommunityFilterEntry
	MAX-ACCESS  not-accessible
	STATUS  current
	DESCRIPTION
		"An entry in the Bgp4 Community Filter table."
	INDEX   { snBgp4CommunityFilterIndex }
	::= { snBgp4CommunityFilterTable 1 }

SnBgp4CommunityFilterEntry ::= SEQUENCE {
	snBgp4CommunityFilterIndex
		Integer32,
	snBgp4CommunityFilterAction              
		INTEGER,
	snBgp4CommunityFilterCommNum
		OCTET STRING,
	snBgp4CommunityFilterInternet
		INTEGER,
	snBgp4CommunityFilterNoAdvertise
		INTEGER,
	snBgp4CommunityFilterNoExport
		INTEGER,
	snBgp4CommunityFilterRowStatus
		INTEGER,
	snBgp4CommunityFilterLocalAs
		INTEGER
	}

snBgp4CommunityFilterIndex       OBJECT-TYPE
	SYNTAX  Integer32
	MAX-ACCESS  read-only
	STATUS  current
	DESCRIPTION
		"The table index for a filter entry."
	::= { snBgp4CommunityFilterEntry 1 }

snBgp4CommunityFilterAction      OBJECT-TYPE
	SYNTAX  INTEGER { deny(0), permit(1) } 
	MAX-ACCESS  read-write
	STATUS  current
	DESCRIPTION
		"Action to take if the bgp address match
		with this filter."
	::= { snBgp4CommunityFilterEntry 2 }

snBgp4CommunityFilterCommNum    OBJECT-TYPE
	SYNTAX  OCTET STRING (SIZE(0..80))
	MAX-ACCESS  read-write
	STATUS  current
	DESCRIPTION
		"A number from 1 to 0xFFFFFFFF. There are 20 of them.  
		This integer number is represented by 4 OCTETs."
	::= { snBgp4CommunityFilterEntry 3 }

snBgp4CommunityFilterInternet OBJECT-TYPE
	SYNTAX  INTEGER { disabled(0), enabled(1) } 
	MAX-ACCESS  read-write
	STATUS  current
	DESCRIPTION
		"Disabled/Enabled the Internet Community."
	::= { snBgp4CommunityFilterEntry 4 }

snBgp4CommunityFilterNoAdvertise OBJECT-TYPE
	SYNTAX  INTEGER { false(0), true(1) } 
	MAX-ACCESS  read-write
	STATUS  current
	DESCRIPTION
		"Do not advertise this route to any peer (internal or external)."
	::= { snBgp4CommunityFilterEntry 5 }

snBgp4CommunityFilterNoExport OBJECT-TYPE
	SYNTAX  INTEGER { false(0), true(1) } 
	MAX-ACCESS  read-write
	STATUS  current
	DESCRIPTION
		"Do not advertise this route to an EBGP peer."
	::= { snBgp4CommunityFilterEntry 6 }

snBgp4CommunityFilterRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4CommunityFilterEntry 7 }

snBgp4CommunityFilterLocalAs OBJECT-TYPE
	SYNTAX  INTEGER { false(0), true(1) } 
	MAX-ACCESS  read-write
	STATUS  current
	DESCRIPTION
		"Send this route to peers in other sub-autonomous systems within
		the local confederation. Do not advertise this route to an 
		external system."
	::= { snBgp4CommunityFilterEntry 8 }

-- Bgp4 Neighbor General Configuration Table

snBgp4NeighGenCfgTable       OBJECT-TYPE
	SYNTAX  SEQUENCE OF SnBgp4NeighGenCfgEntry
	MAX-ACCESS  not-accessible
	STATUS  current
	DESCRIPTION
		"Bgp4 Neighbor General Configuration table."
	::= { snBgp4NeighGenCfg 1 }

snBgp4NeighGenCfgEntry       OBJECT-TYPE
	SYNTAX  SnBgp4NeighGenCfgEntry
	MAX-ACCESS  not-accessible
	STATUS  current
	DESCRIPTION
		"An entry in the Bgp4 Community Filter table."
	INDEX   { snBgp4NeighGenCfgNeighIp }
	::= { snBgp4NeighGenCfgTable 1 }

SnBgp4NeighGenCfgEntry ::= SEQUENCE {
	snBgp4NeighGenCfgNeighIp
		IpAddress,
	snBgp4NeighGenCfgAdvertlevel
		INTEGER,
	snBgp4NeighGenCfgDefOriginate             
		INTEGER,
	snBgp4NeighGenCfgEbgpMultihop
		INTEGER,
	snBgp4NeighGenCfgMaxPrefix
		Integer32,
	snBgp4NeighGenCfgNextHopSelf
		INTEGER,
	snBgp4NeighGenCfgRemoteAs
		INTEGER,
	snBgp4NeighGenCfgSendComm
		INTEGER,
	snBgp4NeighGenCfgWeight
		INTEGER,
	snBgp4NeighGenCfgWeightFilterList             
		OCTET STRING,
	snBgp4NeighGenCfgRowStatus
		INTEGER,
	snBgp4NeighGenCfgUpdateSrcLpbIntf
		INTEGER,
	snBgp4NeighGenCfgRouteRefClient
		INTEGER,
	snBgp4NeighGenCfgRemovePrivateAs
		INTEGER,
	snBgp4NeighGenCfgEbgpMultihopTtl
		INTEGER,
	snBgp4NeighGenCfgShutdown
		INTEGER,
	snBgp4NeighGenCfgKeepAliveTime
		INTEGER,
	snBgp4NeighGenCfgHoldTime
		INTEGER,
	snBgp4NeighGenCfgDefOrigMap
		OCTET STRING,
	snBgp4NeighGenCfgDesc
		OCTET STRING,
	snBgp4NeighGenCfgPass
		OCTET STRING
	}

snBgp4NeighGenCfgNeighIp       OBJECT-TYPE
	SYNTAX  IpAddress
	MAX-ACCESS  read-only
	STATUS  current
	DESCRIPTION
		"The IP Address for a neighbor entry."
	::= { snBgp4NeighGenCfgEntry 1 }

snBgp4NeighGenCfgAdvertlevel   OBJECT-TYPE
	SYNTAX  INTEGER (0..600) 
	MAX-ACCESS  read-write
	STATUS  current
	DESCRIPTION
		"To set the minimum interval between the 
		sending of BGP routing updates."
	::= { snBgp4NeighGenCfgEntry 2 }

snBgp4NeighGenCfgDefOriginate OBJECT-TYPE
	SYNTAX   INTEGER { disabled(0), enabled(1) }
	MAX-ACCESS   read-write
	STATUS   current
	DESCRIPTION
	   "To enable/disable the default originate for this neighbor."
	::= { snBgp4NeighGenCfgEntry 3 }

snBgp4NeighGenCfgEbgpMultihop    OBJECT-TYPE
	SYNTAX   INTEGER { disabled(0), enabled(1) }
	MAX-ACCESS   read-write
	STATUS   current
	DESCRIPTION
	   "To enable/disable the EBGP Muitihop for this neighbor."
	::= { snBgp4NeighGenCfgEntry 4 }

snBgp4NeighGenCfgMaxPrefix    OBJECT-TYPE
	SYNTAX   Integer32
	MAX-ACCESS   read-write
	STATUS   current
	DESCRIPTION
	   "To control how many prefixes can be received from a neighbor.
	   The minimum value of the maximum prefix is snBgp4GenNeighPrefixMinValue.
	   The maximum value of the maximum prefix is snBgp4GenOperRoutes."
	::= { snBgp4NeighGenCfgEntry 5 }

snBgp4NeighGenCfgNextHopSelf    OBJECT-TYPE
	SYNTAX   INTEGER { disabled(0), enabled(1) }
	MAX-ACCESS   read-write
	STATUS   current
	DESCRIPTION
	   "To enable/disable the next-hop processing of BGP updates on the router."
	::= { snBgp4NeighGenCfgEntry 6 }

snBgp4NeighGenCfgRemoteAs    OBJECT-TYPE
	SYNTAX   INTEGER (1..65535)
	MAX-ACCESS   read-write
	STATUS   current
	DESCRIPTION
	   "To specify a neighbor with an autonomous system number(AS)."
	::= { snBgp4NeighGenCfgEntry 7 }

snBgp4NeighGenCfgSendComm    OBJECT-TYPE
	SYNTAX   INTEGER { disabled(0), enabled(1) }
	MAX-ACCESS   read-write
	STATUS   current
	DESCRIPTION
	   "To specify that a COMMUNITES attribute should be sent to a BGP neighbor."
	::= { snBgp4NeighGenCfgEntry 8 }

snBgp4NeighGenCfgWeight    OBJECT-TYPE
	SYNTAX   INTEGER (0..65535)
	MAX-ACCESS   read-write
	STATUS   current
	DESCRIPTION
	   "To assign a weight to a neighbor connection."
	::= { snBgp4NeighGenCfgEntry 9 }

snBgp4NeighGenCfgWeightFilterList OBJECT-TYPE
	SYNTAX  OCTET STRING (SIZE(0..32)) 
	MAX-ACCESS   read-write
	STATUS   current
	DESCRIPTION
	   "A number from 1 to 0xFFFF. There are 16 of them. 
		This integer number is represented by 2 OCTETs."
	::= { snBgp4NeighGenCfgEntry 10 }

snBgp4NeighGenCfgRowStatus   OBJECT-TYPE
	SYNTAX	 INTEGER {
		invalid(1),
		valid(2),
		delete(3),
		create(4),
		modify(5),
		applyDefault(6)
	}
	MAX-ACCESS	 read-write
	STATUS	 current
	DESCRIPTION
	"This object is used to create and
	 delete row in the table and control
	 if they are used. The values
	 that can be written are:
	 delete(3)...deletes the row
	 create(4)...creates a new row
	 modify(5)...modifies an exsisting row
	 applyDefault(6)...apply default value to an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4NeighGenCfgEntry 11 }

snBgp4NeighGenCfgUpdateSrcLpbIntf    OBJECT-TYPE
	SYNTAX   INTEGER (0..8)
	MAX-ACCESS   read-write
	STATUS   current
	DESCRIPTION
	   "To allow internal BGP sessions to use any operational 
	   loopback interface (1..8) for TCP connections.  Zero
	   interface means to restore the interface assignment to the 
	   closest interface, which is called the best local address."
	::= { snBgp4NeighGenCfgEntry 12 }


snBgp4NeighGenCfgRouteRefClient    OBJECT-TYPE
	SYNTAX   INTEGER { disabled(0), enabled(1) }
	MAX-ACCESS   read-write
	STATUS   current
	DESCRIPTION
	   "To configure the router as a BGP route reflector,
	   enable the specified neighbor as its client.
	   When all the clients are disabled, the local router
	   is no longer a route reflector."
	::= { snBgp4NeighGenCfgEntry 13 }

snBgp4NeighGenCfgRemovePrivateAs    OBJECT-TYPE
	SYNTAX   INTEGER { disabled(0), enabled(1) }
	MAX-ACCESS   read-write
	STATUS   current
	DESCRIPTION
	   "To enable/disable filtering private AS number."
	::= { snBgp4NeighGenCfgEntry 14 }

snBgp4NeighGenCfgEbgpMultihopTtl    OBJECT-TYPE
	SYNTAX   INTEGER (0..255)
	MAX-ACCESS   read-write
	STATUS   current
	DESCRIPTION
	   "The EBGP Muitihop TTL for this neighbor."
	::= { snBgp4NeighGenCfgEntry 15 }

snBgp4NeighGenCfgShutdown    OBJECT-TYPE
	SYNTAX   INTEGER { disabled(0), enabled(1) }
	MAX-ACCESS   read-write
	STATUS   current
	DESCRIPTION
	   "To enable/disable BGP4 Nbr Shutdown."
	::= { snBgp4NeighGenCfgEntry 16 }

snBgp4NeighGenCfgKeepAliveTime OBJECT-TYPE
		 SYNTAX   INTEGER (0..65535)
		 MAX-ACCESS   read-write
		 STATUS   current
		 DESCRIPTION
			"The Keep alive timer."
	::= { snBgp4NeighGenCfgEntry 17 }

snBgp4NeighGenCfgHoldTime OBJECT-TYPE
		 SYNTAX   INTEGER (0..65535)
		 MAX-ACCESS   read-write
		 STATUS   current
		 DESCRIPTION
			"The Hold time timer."
	::= { snBgp4NeighGenCfgEntry 18 }

snBgp4NeighGenCfgDefOrigMap OBJECT-TYPE
		 SYNTAX  OCTET STRING (SIZE(0..32)) 
		 MAX-ACCESS   read-write
		 STATUS   current
		 DESCRIPTION
			"An octet string of the route-map name, each character of the name
			is represented by one octet."
	::= { snBgp4NeighGenCfgEntry 19 }

snBgp4NeighGenCfgDesc OBJECT-TYPE
		 SYNTAX  OCTET STRING (SIZE(0..80)) 
		 MAX-ACCESS   read-write
		 STATUS   current
		 DESCRIPTION
			"An octet string of the neighbor description."
	::= { snBgp4NeighGenCfgEntry 20 }

snBgp4NeighGenCfgPass OBJECT-TYPE
		 SYNTAX  OCTET STRING (SIZE(0..80)) 
		 MAX-ACCESS   read-write
		 STATUS   current
		 DESCRIPTION
			"An octet string of the neighbor Md5 password."
	::= { snBgp4NeighGenCfgEntry 21 }

-- Bgp4 Neighbor Distribute Group Table

snBgp4NeighDistGroupTable    OBJECT-TYPE
	SYNTAX  SEQUENCE OF SnBgp4NeighDistGroupEntry
	MAX-ACCESS  not-accessible
	STATUS  current
	DESCRIPTION
		"Bgp4 Neighbor Distribute Group table."
	::= { snBgp4NeighDistGroup 1 }

snBgp4NeighDistGroupEntry       OBJECT-TYPE
	SYNTAX  SnBgp4NeighDistGroupEntry
	MAX-ACCESS  not-accessible
	STATUS  current
	DESCRIPTION
		"An entry in the Bgp4 Distribute Group table."
	INDEX   { snBgp4NeighDistGroupNeighIp, snBgp4NeighDistGroupDir }
	::= { snBgp4NeighDistGroupTable 1 }

SnBgp4NeighDistGroupEntry ::= SEQUENCE {
	snBgp4NeighDistGroupNeighIp
		IpAddress,
	snBgp4NeighDistGroupDir
		INTEGER,
	snBgp4NeighDistGroupAccessList             
		OCTET STRING,
	snBgp4NeighDistGroupRowStatus
		INTEGER,
	snBgp4NeighDistGroupInFilterList             
		OCTET STRING,
	snBgp4NeighDistGroupOutFilterList             
		OCTET STRING,
	snBgp4NeighDistGroupInIpAccessList             
		OCTET STRING,
	snBgp4NeighDistGroupOutIpAccessList             
		OCTET STRING,
	snBgp4NeighDistGroupInPrefixList             
		OCTET STRING,
	snBgp4NeighDistGroupOutPrefixList             
		OCTET STRING
	}

snBgp4NeighDistGroupNeighIp       OBJECT-TYPE
	SYNTAX  IpAddress
	MAX-ACCESS  read-only
	STATUS  current
	DESCRIPTION
		"The IP Address for a neighbor entry."
	::= { snBgp4NeighDistGroupEntry 1 }

snBgp4NeighDistGroupDir   OBJECT-TYPE
	SYNTAX  INTEGER { out(0), in(1) } 
	MAX-ACCESS  read-only
	STATUS  current
	DESCRIPTION
		"The incoming/outgoing advertisements to which 
		the access list is applied."
	::= { snBgp4NeighDistGroupEntry 2 }

snBgp4NeighDistGroupAccessList OBJECT-TYPE
	SYNTAX  OCTET STRING (SIZE(0..32)) 
	MAX-ACCESS   read-write
	STATUS   current
	DESCRIPTION
	   "A number from 1 to 0xFFFF. There are 16 of them.  
		This integer number is represented by 2 OCTETs."
	::= { snBgp4NeighDistGroupEntry 3 }

snBgp4NeighDistGroupRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4NeighDistGroupEntry 4 }

snBgp4NeighDistGroupInFilterList OBJECT-TYPE
	SYNTAX  OCTET STRING (SIZE(0..32)) 
	MAX-ACCESS   read-write
	STATUS   current
	DESCRIPTION
	   "A number from 1 to 0xFFFF. There are 16 of them.  
		This integer number is represented by 2 OCTETs."
	::= { snBgp4NeighDistGroupEntry 5 }

snBgp4NeighDistGroupOutFilterList OBJECT-TYPE
	SYNTAX  OCTET STRING (SIZE(0..32)) 
	MAX-ACCESS   read-write
	STATUS   current
	DESCRIPTION
	   "A number from 1 to 0xFFFF. There are 16 of them.  
		This integer number is represented by 2 OCTETs."
	::= { snBgp4NeighDistGroupEntry 6 }

snBgp4NeighDistGroupInIpAccessList OBJECT-TYPE
	SYNTAX  OCTET STRING (SIZE(0..2)) 
	MAX-ACCESS   read-write
	STATUS   current
	DESCRIPTION
	   "A number from 1 to 0xFFFF. There are 1 of them.  
		This integer number is represented by 2 OCTETs."
	::= { snBgp4NeighDistGroupEntry 7 }

snBgp4NeighDistGroupOutIpAccessList OBJECT-TYPE
	SYNTAX  OCTET STRING (SIZE(0..2)) 
	MAX-ACCESS   read-write
	STATUS   current
	DESCRIPTION
	   "A number from 1 to 0xFFFF. There are 1 of them.  
		This integer number is represented by 2 OCTETs."
	::= { snBgp4NeighDistGroupEntry 8 }

snBgp4NeighDistGroupInPrefixList OBJECT-TYPE
	SYNTAX  OCTET STRING (SIZE(0..32)) 
	MAX-ACCESS   read-write
	STATUS   current
	DESCRIPTION
	   "A Prefix name list. " 
	::= { snBgp4NeighDistGroupEntry 9 }

snBgp4NeighDistGroupOutPrefixList OBJECT-TYPE
	SYNTAX  OCTET STRING (SIZE(0..32)) 
	MAX-ACCESS   read-write
	STATUS   current
	DESCRIPTION
	   "A Prefix name list. " 
	::= { snBgp4NeighDistGroupEntry 10 }

-- Bgp4 Neighbor Filter Group Table

snBgp4NeighFilterGroupTable    OBJECT-TYPE
	SYNTAX  SEQUENCE OF SnBgp4NeighFilterGroupEntry
	MAX-ACCESS  not-accessible
	STATUS  current
	DESCRIPTION
		"Bgp4 Neighbor Filter Group table."
	::= { snBgp4NeighFilterGroup 1 }

snBgp4NeighFilterGroupEntry       OBJECT-TYPE
	SYNTAX  SnBgp4NeighFilterGroupEntry
	MAX-ACCESS  not-accessible
	STATUS  current
	DESCRIPTION
		"An entry in the Bgp4 Neighbor Filter Group table."
	INDEX   { snBgp4NeighFilterGroupNeighIp, snBgp4NeighFilterGroupDir }
	::= { snBgp4NeighFilterGroupTable 1 }

SnBgp4NeighFilterGroupEntry ::= SEQUENCE {
	snBgp4NeighFilterGroupNeighIp
		IpAddress,
	snBgp4NeighFilterGroupDir
		INTEGER,
	snBgp4NeighFilterGroupAccessList             
		OCTET STRING,
	snBgp4NeighFilterGroupRowStatus
		INTEGER,
	snBgp4NeighFilterGroupInFilterList             
		OCTET STRING,
	snBgp4NeighFilterGroupOutFilterList             
		OCTET STRING,
	snBgp4NeighFilterGroupInAsPathAccessList             
		OCTET STRING,
	snBgp4NeighFilterGroupOutAsPathAccessList             
		OCTET STRING,
	snBgp4NeighFilterGroupWeight             
		INTEGER,
	snBgp4NeighFilterGroupWeightAccessList             
		OCTET STRING
	}

snBgp4NeighFilterGroupNeighIp       OBJECT-TYPE
	SYNTAX  IpAddress
	MAX-ACCESS  read-only
	STATUS  current
	DESCRIPTION
		"The IP Address for a neighbor entry."
	::= { snBgp4NeighFilterGroupEntry 1 }

snBgp4NeighFilterGroupDir   OBJECT-TYPE
	SYNTAX  INTEGER { out(0), in(1) } 
	MAX-ACCESS  read-only
	STATUS  current
	DESCRIPTION
		"The incoming/outgoing advertisements to which 
		the access list is applied."
	::= { snBgp4NeighFilterGroupEntry 2 }

snBgp4NeighFilterGroupAccessList OBJECT-TYPE
	SYNTAX  OCTET STRING (SIZE(0..32)) 
	MAX-ACCESS   read-write
	STATUS   current
	DESCRIPTION
	   "A number from 1 to 0xFFFF. There are 16 of them.  
		This integer number is represented by 2 OCTETs."
	::= { snBgp4NeighFilterGroupEntry 3 }

snBgp4NeighFilterGroupRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4NeighFilterGroupEntry 4 }

snBgp4NeighFilterGroupInFilterList OBJECT-TYPE
	SYNTAX  OCTET STRING (SIZE(0..32)) 
	MAX-ACCESS   read-write
	STATUS   current
	DESCRIPTION
	   "A number from 1 to 0xFFFF. There are 16 of them.  
		This integer number is represented by 2 OCTETs."
	::= { snBgp4NeighFilterGroupEntry 5 }

snBgp4NeighFilterGroupOutFilterList OBJECT-TYPE
	SYNTAX  OCTET STRING (SIZE(0..32)) 
	MAX-ACCESS   read-write
	STATUS   current
	DESCRIPTION
	   "A number from 1 to 0xFFFF. There are 16 of them.  
		This integer number is represented by 2 OCTETs."
	::= { snBgp4NeighFilterGroupEntry 6 }

snBgp4NeighFilterGroupInAsPathAccessList OBJECT-TYPE
	SYNTAX  OCTET STRING (SIZE(0..2)) 
	MAX-ACCESS   read-write
	STATUS   current
	DESCRIPTION
	   "A number from 1 to 0xFFFF. There are 1 of them.  
		This integer number is represented by 2 OCTETs."
	::= { snBgp4NeighFilterGroupEntry 7 }

snBgp4NeighFilterGroupOutAsPathAccessList OBJECT-TYPE
	SYNTAX  OCTET STRING (SIZE(0..2)) 
	MAX-ACCESS   read-write
	STATUS   current
	DESCRIPTION
	   "A number from 1 to 0xFFFF. There are 1 of them.  
		This integer number is represented by 2 OCTETs."
	::= { snBgp4NeighFilterGroupEntry 8 }

snBgp4NeighFilterGroupWeight OBJECT-TYPE
	SYNTAX   INTEGER  (0..65535)
	MAX-ACCESS   read-write
	STATUS   current
	DESCRIPTION
	   "To assign a weight to a neighbor filter."
	::= { snBgp4NeighFilterGroupEntry 9 }

snBgp4NeighFilterGroupWeightAccessList OBJECT-TYPE
	SYNTAX  OCTET STRING (SIZE(0..2)) 
	MAX-ACCESS   read-write
	STATUS   current
	DESCRIPTION
	   "A number from 1 to 0xFFFF. There are 1 of them.  
		This integer number is represented by 2 OCTETs."
	::= { snBgp4NeighFilterGroupEntry 10 }

-- Bgp4 Neighbor Route Map Table

snBgp4NeighRouteMapTable    OBJECT-TYPE
	SYNTAX  SEQUENCE OF SnBgp4NeighRouteMapEntry
	MAX-ACCESS  not-accessible
	STATUS  current
	DESCRIPTION
		"Bgp4 Neighbor Route Map table."
	::= { snBgp4NeighRouteMap 1 }

snBgp4NeighRouteMapEntry       OBJECT-TYPE
	SYNTAX  SnBgp4NeighRouteMapEntry
	MAX-ACCESS  not-accessible
	STATUS  current
	DESCRIPTION
		"An entry in the Bgp4 Route Map table."
	INDEX   { snBgp4NeighRouteMapNeighIp, snBgp4NeighRouteMapDir }
	::= { snBgp4NeighRouteMapTable 1 }

SnBgp4NeighRouteMapEntry ::= SEQUENCE {
	snBgp4NeighRouteMapNeighIp
		IpAddress,
	snBgp4NeighRouteMapDir
		INTEGER,
	snBgp4NeighRouteMapMapName             
		OCTET STRING,
	snBgp4NeighRouteMapRowStatus
		INTEGER
	}

snBgp4NeighRouteMapNeighIp       OBJECT-TYPE
	SYNTAX  IpAddress
	MAX-ACCESS  read-only
	STATUS  current
	DESCRIPTION
		"The IP Address for a neighbor entry."
	::= { snBgp4NeighRouteMapEntry 1 }

snBgp4NeighRouteMapDir   OBJECT-TYPE
	SYNTAX  INTEGER { out(0), in(1) } 
	MAX-ACCESS  read-only
	STATUS  current
	DESCRIPTION
		"The incoming/outgoing advertisements to which 
		the access list is applied."
	::= { snBgp4NeighRouteMapEntry 2 }

snBgp4NeighRouteMapMapName OBJECT-TYPE
	SYNTAX  OCTET STRING (SIZE(0..32)) 
	MAX-ACCESS   read-write
	STATUS   current
	DESCRIPTION
	   "An octet string of the route-map name, Each character of the name
		is represented by one octet."
	::= { snBgp4NeighRouteMapEntry 3 }

snBgp4NeighRouteMapRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4NeighRouteMapEntry 4 }


-- Bgp4 Network Table

snBgp4NetworkTable       OBJECT-TYPE
	SYNTAX  SEQUENCE OF SnBgp4NetworkEntry
	MAX-ACCESS  not-accessible
	STATUS  current
	DESCRIPTION
		"Bgp4 Network Weight table."
	::= { snBgp4Network 1 }

snBgp4NetworkEntry       OBJECT-TYPE
	SYNTAX  SnBgp4NetworkEntry
	MAX-ACCESS  not-accessible
	STATUS  current
	DESCRIPTION
		"An entry in the Bgp4 Network Weight table."
	INDEX   { snBgp4NetworkIp, snBgp4NetworkSubnetMask }
	::= { snBgp4NetworkTable 1 }

SnBgp4NetworkEntry ::= SEQUENCE {
	snBgp4NetworkIp
		IpAddress,
	snBgp4NetworkSubnetMask             
		IpAddress,
	snBgp4NetworkWeight
		INTEGER,
	snBgp4NetworkBackdoor
		INTEGER,
	snBgp4NetworkRowStatus
		INTEGER
	}

snBgp4NetworkIp       OBJECT-TYPE
	SYNTAX  IpAddress
	MAX-ACCESS  read-only
	STATUS  current
	DESCRIPTION
		"The IP Address for a network entry."
	::= { snBgp4NetworkEntry 1 }

snBgp4NetworkSubnetMask OBJECT-TYPE
	SYNTAX  IpAddress
	MAX-ACCESS  read-only
	STATUS  current
	DESCRIPTION
		"The subnet mask for a network entry."
	::= { snBgp4NetworkEntry 2 }

snBgp4NetworkWeight    OBJECT-TYPE
	SYNTAX   INTEGER  (0..65535)
	MAX-ACCESS   read-write
	STATUS   current
	DESCRIPTION
	   "To assign a weight to a neighbor connection."
	::= { snBgp4NetworkEntry 3 }

snBgp4NetworkBackdoor   OBJECT-TYPE
	SYNTAX  INTEGER { disabled (0), enabled (1) }
	MAX-ACCESS  read-write
	STATUS  current
	DESCRIPTION
	   "To enable/disable the backdoor for this network."
	::= { snBgp4NetworkEntry 4 }

snBgp4NetworkRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4NetworkEntry 5 }

--  BGP4 Redistribution of Routes Table


	 snBgp4RedisTable OBJECT-TYPE
		 SYNTAX   SEQUENCE OF SnBgp4RedisEntry
		 MAX-ACCESS   not-accessible
		 STATUS   current
		 DESCRIPTION
			"The BGP4 Redistribution contains configurations
			that could be imported into the BGP4 domain."
		 ::= { snBgp4Redis 1 }

	 snBgp4RedisEntry OBJECT-TYPE
		 SYNTAX   SnBgp4RedisEntry
		 MAX-ACCESS   not-accessible
		 STATUS   current
		 DESCRIPTION
			"The BGP4 Redistribution Entry specifies a particular RIP 
			or , OSPF, or Static route to be imported into the BGP4 domain."
		 INDEX { snBgp4RedisProtocol }
		 ::= { snBgp4RedisTable 1 }

	 SnBgp4RedisEntry ::=
		 SEQUENCE {
			 snBgp4RedisProtocol
				 INTEGER,
			 snBgp4RedisMetric
				 Integer32,
			 snBgp4RedisRouteMap
				 OCTET STRING,
			 snBgp4RedisWeight
				 INTEGER,
			 snBgp4RedisMatchInternal
				 INTEGER,
			 snBgp4RedisMatchExternal1
				 INTEGER,
			 snBgp4RedisMatchExternal2
				 INTEGER,
			 snBgp4RedisRowStatus
				 INTEGER
		 }


	snBgp4RedisProtocol OBJECT-TYPE
		 SYNTAX   INTEGER {
			rip(1),
			ospf(2),
			static(3),
			connected(4),
			isis(5)
				  }
		 MAX-ACCESS   read-only
		 STATUS   current
		 DESCRIPTION
			"The imported configuration into BGP4 domain is set in the following: 
				rip(1):		- the RIP.
				ospf(2):	- the OSPF.
				static(3):	- the static.
				connected(4):	- the connected.
				isis(5):	- the ISIS."
		 ::= { snBgp4RedisEntry 1 }

	snBgp4RedisMetric OBJECT-TYPE
		 SYNTAX   Integer32
		 MAX-ACCESS   read-write
		 STATUS   current 
		 DESCRIPTION
			"The metric of using the specified protocol Metric value."
		 ::= { snBgp4RedisEntry 2 }


	snBgp4RedisRouteMap OBJECT-TYPE
		 SYNTAX  OCTET STRING (SIZE(0..32)) 
		 MAX-ACCESS   read-write
		 STATUS   current
		 DESCRIPTION
			"An octet string of the route-map name, each character of the name
			is represented by one octet."
		 ::= { snBgp4RedisEntry 3 }

	snBgp4RedisWeight OBJECT-TYPE
		 SYNTAX   INTEGER (0..65535)
		 MAX-ACCESS   read-write
		 STATUS   current 
		 DESCRIPTION
			"To assign a weight for the specified protocol."
		 ::= { snBgp4RedisEntry 4 }

	snBgp4RedisMatchInternal OBJECT-TYPE
		 SYNTAX   INTEGER { disabled(0), enabled(1) }
		 MAX-ACCESS   read-write
		 STATUS   current 
		 DESCRIPTION
			"This object is only applicable to the OSPF protocol."
		 ::= { snBgp4RedisEntry 5 }

	snBgp4RedisMatchExternal1 OBJECT-TYPE
		 SYNTAX   INTEGER { disabled(0), enabled(1) }
		 MAX-ACCESS   read-write
		 STATUS   current 
		 DESCRIPTION
			"This object is only applicable to the OSPF protocol."
		 ::= { snBgp4RedisEntry 6 }

	snBgp4RedisMatchExternal2 OBJECT-TYPE
		 SYNTAX   INTEGER { disabled(0), enabled(1) }
		 MAX-ACCESS   read-write
		 STATUS   current 
		 DESCRIPTION
			"This object is only applicable to the OSPF protocol."
		 ::= { snBgp4RedisEntry 7 }

	snBgp4RedisRowStatus   OBJECT-TYPE
		 SYNTAX	 INTEGER {
			invalid(1),
			valid(2),
			delete(3),
			create(4),
			modify(5)
		 }
		 MAX-ACCESS	 read-write
		 STATUS	 current
		 DESCRIPTION
			"This object is used to create and
			delete row in the table and control
			if they are used. The values
			that can be written are:
			delete(3)...deletes the row
			create(4)...creates a new row
			modify(5)...modifies an exsisting row

			If the row exists, then a SET with
			value of create(4) returns error
			'badValue'. Deleted rows go away
			immediately. The following values
			can be returned on reads:
			noSuch(0)...no such row
			invalid(1)...Setting it to 'invalid' has the effect of
						 rendering it inoperative..
			valid(2)....the row exists and is valid"
		 ::= { snBgp4RedisEntry 8 }

-- Bgp4 Route Map Filter table

snBgp4RouteMapFilterTable       OBJECT-TYPE
	SYNTAX  SEQUENCE OF SnBgp4RouteMapFilterEntry
	MAX-ACCESS  not-accessible
	STATUS  current
	DESCRIPTION
		"Bgp4 RouteMap Filter table."
	::= { snBgp4RouteMapFilter 1 }

snBgp4RouteMapFilterEntry       OBJECT-TYPE
	SYNTAX  SnBgp4RouteMapFilterEntry
	MAX-ACCESS  not-accessible
	STATUS  current
	DESCRIPTION
		"An entry in the Bgp4 RouteMap Filter table."
	INDEX   { snBgp4RouteMapFilterMapName, snBgp4RouteMapFilterSequenceNum}
	::= { snBgp4RouteMapFilterTable 1 }

SnBgp4RouteMapFilterEntry ::= SEQUENCE {
	snBgp4RouteMapFilterMapName
		OCTET STRING,
	snBgp4RouteMapFilterSequenceNum
		Integer32,
	snBgp4RouteMapFilterAction              
		INTEGER,
	snBgp4RouteMapFilterRowStatus
		INTEGER
	}

snBgp4RouteMapFilterMapName    OBJECT-TYPE
	SYNTAX  OCTET STRING (SIZE(0..32))
	MAX-ACCESS  read-only
	STATUS  current
	DESCRIPTION
		"An octet string of the route-map name, each character of the name
		 is represented by one octet."
	::= { snBgp4RouteMapFilterEntry 1 }

snBgp4RouteMapFilterSequenceNum OBJECT-TYPE
	SYNTAX  Integer32
	MAX-ACCESS  read-only
	STATUS  current
	DESCRIPTION
		"A sequence number for this particular route-map."
	::= { snBgp4RouteMapFilterEntry 2 }

snBgp4RouteMapFilterAction      OBJECT-TYPE
	SYNTAX  INTEGER { deny(0), permit(1) } 
	MAX-ACCESS  read-write
	STATUS  current
	DESCRIPTION
		"Action to take if the bgp address match
		with this filter."
	::= { snBgp4RouteMapFilterEntry 3 }

snBgp4RouteMapFilterRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4RouteMapFilterEntry 4 }


--  BGP4 Route Map Match Configuration Table


snBgp4RouteMapMatchTable       OBJECT-TYPE
	SYNTAX  SEQUENCE OF SnBgp4RouteMapMatchEntry
	MAX-ACCESS  not-accessible
	STATUS  current
	DESCRIPTION
		"Bgp4 Route Map Set table."
	::= { snBgp4RouteMapMatch 1 }

snBgp4RouteMapMatchEntry       OBJECT-TYPE
	SYNTAX  SnBgp4RouteMapMatchEntry
	MAX-ACCESS  not-accessible
	STATUS  current
	DESCRIPTION
		"An entry in the Bgp4 Route Map Match table."
	INDEX   { snBgp4RouteMapMatchMapName, snBgp4RouteMapMatchSequenceNum }
	::= { snBgp4RouteMapMatchTable 1 }

SnBgp4RouteMapMatchEntry ::= SEQUENCE {
	snBgp4RouteMapMatchMapName
		OCTET STRING,
	snBgp4RouteMapMatchSequenceNum
		Integer32,
	snBgp4RouteMapMatchAsPathFilter
		OCTET STRING,
	snBgp4RouteMapMatchCommunityFilter
		OCTET STRING,
	snBgp4RouteMapMatchAddressFilter
		OCTET STRING,
	snBgp4RouteMapMatchMetric              
		Integer32,
	snBgp4RouteMapMatchNextHopList
		OCTET STRING,
	snBgp4RouteMapMatchRouteType              
		INTEGER,
	snBgp4RouteMapMatchTagList
		OCTET STRING,
	snBgp4RouteMapMatchRowMask
		Integer32,
	snBgp4RouteMapMatchAsPathAccessList
		OCTET STRING,
	snBgp4RouteMapMatchCommunityList
		OCTET STRING,
	snBgp4RouteMapMatchAddressAccessList
		OCTET STRING,
	snBgp4RouteMapMatchAddressPrefixList
		OCTET STRING,
	snBgp4RouteMapMatchNextHopAccessList
		OCTET STRING,
	snBgp4RouteMapMatchNextHopPrefixList
		OCTET STRING
	}

snBgp4RouteMapMatchMapName    OBJECT-TYPE
	SYNTAX  OCTET STRING (SIZE(0..32))
	MAX-ACCESS  read-only
	STATUS  current
	DESCRIPTION
		"An octet string of the route-map name, each character of the name
		 is represented by one octet."
	::= { snBgp4RouteMapMatchEntry 1 }

snBgp4RouteMapMatchSequenceNum OBJECT-TYPE
	SYNTAX  Integer32
	MAX-ACCESS  read-only
	STATUS  current
	DESCRIPTION
		"A sequence number for this particular route-map."
	::= { snBgp4RouteMapMatchEntry 2 }

snBgp4RouteMapMatchAsPathFilter OBJECT-TYPE
	SYNTAX  OCTET STRING (SIZE(0..20)) 
	MAX-ACCESS   read-write
	STATUS   current
	DESCRIPTION
		"A number from 1 to 0xFFFF and there are 10 of 2 OCTETs. 
		This integer number is represented by 2 OCTETs.
		To match a BGP autonomous system path access list."
	::= { snBgp4RouteMapMatchEntry 3 }

snBgp4RouteMapMatchCommunityFilter OBJECT-TYPE
	SYNTAX  OCTET STRING (SIZE(0..20)) 
	MAX-ACCESS   read-write
	STATUS   current
	DESCRIPTION
		"A number from 1 to 0xFFFF and there are 10 of 2 OCTETs. 
		This integer number is represented by 2 OCTETs.
		To match a BGP community access list."
	::= { snBgp4RouteMapMatchEntry 4 }

snBgp4RouteMapMatchAddressFilter OBJECT-TYPE
	SYNTAX  OCTET STRING (SIZE(0..20)) 
	MAX-ACCESS   read-write
	STATUS   current
	DESCRIPTION
		"A number from 1 to 0xFFFF and there are 10 of 2 OCTETs. 
		This integer number is represented by 2 OCTETs.
		To match a BGP address access list."
	::= { snBgp4RouteMapMatchEntry 5 }

snBgp4RouteMapMatchMetric OBJECT-TYPE
	SYNTAX   Integer32
	MAX-ACCESS   read-write
	STATUS   current
	DESCRIPTION
		"To match a metric for BGP routes."
	::= { snBgp4RouteMapMatchEntry 6 }

snBgp4RouteMapMatchNextHopList OBJECT-TYPE
	SYNTAX  OCTET STRING (SIZE(0..32)) 
	MAX-ACCESS   read-write
	STATUS   current
	DESCRIPTION
		"A number from 1 to 0xFFFF and there are 16 of 2 OCTETs. 
		This integer number is represented by 2 OCTETs.
		To match a BGP next-hop access list."
	::= { snBgp4RouteMapMatchEntry 7 }

snBgp4RouteMapMatchRouteType OBJECT-TYPE
	SYNTAX   INTEGER {
				none(0), 
				external(1), 
				externalType1(2), 
				externalType2(3), 
				internal(4), 
				local(5) 
				}
	MAX-ACCESS   read-write
	STATUS   current
	DESCRIPTION
		"To match a route-type. 
		Currently only externalType1(2), 
		externalType2(3), internal(4) is supported for SNMP-SET."
	::= { snBgp4RouteMapMatchEntry 8 }

snBgp4RouteMapMatchTagList OBJECT-TYPE
	SYNTAX  OCTET STRING (SIZE(0..32)) 
	MAX-ACCESS   read-write
	STATUS   current
	DESCRIPTION
		"To match a BGP tag access list."
	::= { snBgp4RouteMapMatchEntry 9 }

snBgp4RouteMapMatchRowMask   OBJECT-TYPE
	SYNTAX	 Integer32 
	MAX-ACCESS	 read-write
	STATUS	 current
	DESCRIPTION
	"This object is used together with above
	 MIBs in the same VARBIND to set and
	 reset any MIBs in the table.
	 The bit number is referred to the 
	 snBgp4RouteMapMatchEntry number
	 of each row in the table.
	 The bit is ON  - means set,
	 The bit is OFF - means reset"
	::= { snBgp4RouteMapMatchEntry 10 }

snBgp4RouteMapMatchAsPathAccessList OBJECT-TYPE
	SYNTAX  OCTET STRING (SIZE(0..20)) 
	MAX-ACCESS   read-write
	STATUS   current
	DESCRIPTION
		"A number from 1 to 0xFFFFFFFF and there are 5 of 4 OCTETs. 
		This integer number is represented by 4 OCTETs.
		To match a BGP autonomous system path access list."
	::= { snBgp4RouteMapMatchEntry 11 }

snBgp4RouteMapMatchCommunityList OBJECT-TYPE
	SYNTAX  OCTET STRING (SIZE(0..20)) 
	MAX-ACCESS   read-write
	STATUS   current
	DESCRIPTION
		"A number from 1 to 0xFFFFFFFF and there are 5 of 4 OCTETs. 
		This integer number is represented by 4 OCTETs.
		To match a BGP community access list."
	::= { snBgp4RouteMapMatchEntry 12 }

snBgp4RouteMapMatchAddressAccessList OBJECT-TYPE
	SYNTAX  OCTET STRING (SIZE(0..10)) 
	MAX-ACCESS   read-write
	STATUS   current
	DESCRIPTION
		"A number from 1 to 0xFFFF and there are 5 of 2 OCTETs. 
		This integer number is represented by 2 OCTETs.
		To match a BGP address access list."
	::= { snBgp4RouteMapMatchEntry 13 }

snBgp4RouteMapMatchAddressPrefixList OBJECT-TYPE
	SYNTAX  OCTET STRING (SIZE(0..170)) 
	MAX-ACCESS   read-write
	STATUS   current
	DESCRIPTION
		"Prefix list 
		To match a BGP address access list."
	::= { snBgp4RouteMapMatchEntry 14 }

snBgp4RouteMapMatchNextHopAccessList OBJECT-TYPE
	SYNTAX  OCTET STRING (SIZE(0..10)) 
	MAX-ACCESS   read-write
	STATUS   current
	DESCRIPTION
		"A number from 1 to 0xFFFF and there are 5 of 2 OCTETs. 
		This integer number is represented by 2 OCTETs.
		To match a BGP address access list."
	::= { snBgp4RouteMapMatchEntry 15 }

snBgp4RouteMapMatchNextHopPrefixList OBJECT-TYPE
	SYNTAX  OCTET STRING (SIZE(0..170)) 
	MAX-ACCESS   read-write
	STATUS   current
	DESCRIPTION
		"Prefix list 
		To match a BGP address access list."
	::= { snBgp4RouteMapMatchEntry 16 }

--  BGP4 Route Map Set Configuration Table

snBgp4RouteMapSetTable       OBJECT-TYPE
	SYNTAX  SEQUENCE OF SnBgp4RouteMapSetEntry
	MAX-ACCESS  not-accessible
	STATUS  current
	DESCRIPTION
		"Bgp4 Route Map Set table."
	::= { snBgp4RouteMapSet 1 }

snBgp4RouteMapSetEntry       OBJECT-TYPE
	SYNTAX  SnBgp4RouteMapSetEntry
	MAX-ACCESS  not-accessible
	STATUS  current
	DESCRIPTION
		"An entry in the Bgp4 Route Map Set table."
	INDEX   { snBgp4RouteMapSetMapName, snBgp4RouteMapSetSequenceNum }
	::= { snBgp4RouteMapSetTable 1 }

SnBgp4RouteMapSetEntry ::= SEQUENCE {
	snBgp4RouteMapSetMapName
		OCTET STRING,
	snBgp4RouteMapSetSequenceNum              
		Integer32,
	snBgp4RouteMapSetAsPathType              
		INTEGER,
	snBgp4RouteMapSetAsPathString
		OCTET STRING,
	snBgp4RouteMapSetAutoTag              
		INTEGER,
	snBgp4RouteMapSetCommunityType              
		INTEGER,
	snBgp4RouteMapSetCommunityNum              
		Integer32,
	snBgp4RouteMapSetCommunityAdditive              
		INTEGER,
	snBgp4RouteMapSetLocalPreference              
		Integer32,
	snBgp4RouteMapSetMetric              
		Integer32,
	snBgp4RouteMapSetNextHop              
		IpAddress,
	snBgp4RouteMapSetOrigin              
		INTEGER,
	snBgp4RouteMapSetTag              
		Integer32,
	snBgp4RouteMapSetWeight              
		INTEGER,
	snBgp4RouteMapSetRowMask
		Integer32,
	snBgp4RouteMapSetCommunityNums              
		OCTET STRING,
	snBgp4RouteMapSetDampenHalfLife
		INTEGER,
	snBgp4RouteMapSetDampenReuse
		INTEGER,
	snBgp4RouteMapSetDampenSuppress
		INTEGER,
	snBgp4RouteMapSetDampenMaxSuppress
		INTEGER
	}

snBgp4RouteMapSetMapName    OBJECT-TYPE
	SYNTAX  OCTET STRING (SIZE(0..32))
	MAX-ACCESS  read-only
	STATUS  current
	DESCRIPTION
		"An octet string of the route-map name, each character of the name
		 is represented by one octet."
	::= { snBgp4RouteMapSetEntry 1 }

snBgp4RouteMapSetSequenceNum OBJECT-TYPE
	SYNTAX  Integer32
	MAX-ACCESS  read-only
	STATUS  current
	DESCRIPTION
		"A sequence number for this particular route-map."
	::= { snBgp4RouteMapSetEntry 2 }

snBgp4RouteMapSetAsPathType OBJECT-TYPE
	SYNTAX   INTEGER { tag(0), prepend(1) }
	MAX-ACCESS   read-write
	STATUS   current
	DESCRIPTION
		"To modify an autonomous system path for BGP routes. 
		tag(0) - Converts the tag of a route into an autonomous system path.
		prepend(1) - Appends the string from snBgp4RouteMapSetAsPathString to the 
					 as-path of the route that is matched by the route map."
	::= { snBgp4RouteMapSetEntry 3 }

snBgp4RouteMapSetAsPathString OBJECT-TYPE
	SYNTAX  OCTET STRING (SIZE(0..32)) 
	MAX-ACCESS   read-write
	STATUS   current
	DESCRIPTION
		"as-path string. This string is used if only if the snBgp4RouteMapSetAsPathCmd
		was sent together with the value set to prepend(1)."
	::= { snBgp4RouteMapSetEntry 4 }

snBgp4RouteMapSetAutoTag OBJECT-TYPE
	SYNTAX   INTEGER { disabled(0), enabled(1) }
	MAX-ACCESS   read-write
	STATUS   current
	DESCRIPTION
		"To enable/disable the automatic-tag for BGP routes."
	::= { snBgp4RouteMapSetEntry 5 }

snBgp4RouteMapSetCommunityType OBJECT-TYPE
	SYNTAX   INTEGER { nums(0), none(3)}
	MAX-ACCESS   read-write
	STATUS   current
	DESCRIPTION
		"To set the BGP COMMUNITIES attribute. none means no other
	 community attributes are allowed, nums means allowing community
	 attributesi, the old values 1 and 2 are not valid since 5.03.00"
	::= { snBgp4RouteMapSetEntry 6 }

snBgp4RouteMapSetCommunityNum OBJECT-TYPE
	SYNTAX   Integer32
	MAX-ACCESS   read-write
	STATUS   deprecated
	DESCRIPTION
		"community-number. This number is used if only if the snBgp4RouteMapSetCommunityCmd
		was sent together with the value set to number(0)."
	::= { snBgp4RouteMapSetEntry 7 }

snBgp4RouteMapSetCommunityAdditive OBJECT-TYPE
	SYNTAX   INTEGER { disabled(0), enabled(1) }
	MAX-ACCESS   read-write
	STATUS   current
	DESCRIPTION
		"To add the community to the already existing communities." 
	::= { snBgp4RouteMapSetEntry 8 }

snBgp4RouteMapSetLocalPreference OBJECT-TYPE
	SYNTAX   Integer32
	MAX-ACCESS   read-write
	STATUS   current
	DESCRIPTION
		"To modify a local-preference for BGP routes."
	::= { snBgp4RouteMapSetEntry 9 }

snBgp4RouteMapSetMetric OBJECT-TYPE
	SYNTAX   Integer32
	MAX-ACCESS   read-write
	STATUS   current
	DESCRIPTION
		"To modify a metric for BGP routes."
	::= { snBgp4RouteMapSetEntry 10 }

snBgp4RouteMapSetNextHop OBJECT-TYPE
	SYNTAX   IpAddress
	MAX-ACCESS   read-write
	STATUS   current
	DESCRIPTION
		"To modify the IP address of the next hop for BGP routes."
	::= { snBgp4RouteMapSetEntry 11 }

snBgp4RouteMapSetOrigin OBJECT-TYPE
	SYNTAX   INTEGER { igp(0), egp(1), incomplete(2) }
	MAX-ACCESS   read-write
	STATUS   current
	DESCRIPTION
		"To set the BGP origin code."
	::= { snBgp4RouteMapSetEntry 12 }

snBgp4RouteMapSetTag OBJECT-TYPE
	SYNTAX   Integer32
	MAX-ACCESS   read-write
	STATUS   current
	DESCRIPTION
		"To specify the tag for BGP routes."
	::= { snBgp4RouteMapSetEntry 13 }

snBgp4RouteMapSetWeight OBJECT-TYPE
	SYNTAX   INTEGER (0..65535)
	MAX-ACCESS   read-write
	STATUS   current
	DESCRIPTION
		"To specify the BGP weight for the routing table."
	::= { snBgp4RouteMapSetEntry 14 }

snBgp4RouteMapSetRowMask   OBJECT-TYPE
	SYNTAX	 Integer32
	MAX-ACCESS	 read-write
	STATUS	 current
	DESCRIPTION
	"This object is used together with above
	 MIBs in the same VARBIND to set and
	 reset any MIBs in the table.
	 The bit number is referred to the 
	 snBgp4RouteMapSetEntry number
	 of each row in the table. 
	 The bit is ON  - means set,
	 The bit is OFF - means reset"
	::= { snBgp4RouteMapSetEntry 15 }

snBgp4RouteMapSetCommunityNums OBJECT-TYPE
	SYNTAX  OCTET STRING (SIZE(0..24))
	MAX-ACCESS  read-write
	STATUS  current
	DESCRIPTION
		"Community number is from 1 to 0xFFFFFFFF. There are 6 of them.  
		This integer number is represented by 4 OCTETs."
	::= { snBgp4RouteMapSetEntry 16 }

snBgp4RouteMapSetDampenHalfLife OBJECT-TYPE
		 SYNTAX   INTEGER (1..45)
		 MAX-ACCESS   read-write
		 STATUS   current
		 DESCRIPTION
		"Bgp4 Route Map Dampening Half Life."
	::= { snBgp4RouteMapSetEntry 17 }

snBgp4RouteMapSetDampenReuse OBJECT-TYPE
		 SYNTAX   INTEGER (1..20000)
		 MAX-ACCESS   read-write
		 STATUS   current
		 DESCRIPTION
		"Bgp4 Route Map Dampening Reuse."
	::= { snBgp4RouteMapSetEntry 18 }

snBgp4RouteMapSetDampenSuppress OBJECT-TYPE
		 SYNTAX   INTEGER (1..20000)
		 MAX-ACCESS   read-write
		 STATUS   current
		 DESCRIPTION
		"Bgp4 Route Map Dampening Suppress."
	::= { snBgp4RouteMapSetEntry 19 }

snBgp4RouteMapSetDampenMaxSuppress OBJECT-TYPE
		 SYNTAX   INTEGER (1..20000)
		 MAX-ACCESS   read-write
		 STATUS   current
		 DESCRIPTION
		"Bgp4 Route Map Dampening Max Suppress Time."
	::= { snBgp4RouteMapSetEntry 20 }

-- Bgp4 Neighbor Operational Status Table

snBgp4NeighOperStatusTable       OBJECT-TYPE
	SYNTAX  SEQUENCE OF SnBgp4NeighOperStatusEntry
	MAX-ACCESS  not-accessible
	STATUS  current
	DESCRIPTION
		"Bgp4 Neighbor Operational Status table."
	::= { snBgp4NeighOperStatus 1 }

snBgp4NeighOperStatusEntry       OBJECT-TYPE
	SYNTAX  SnBgp4NeighOperStatusEntry
	MAX-ACCESS  not-accessible
	STATUS  current
	DESCRIPTION
		"An entry in the Bgp4 Operational Status table."
	INDEX   { snBgp4NeighOperStatusIndex }
	::= { snBgp4NeighOperStatusTable 1 }

SnBgp4NeighOperStatusEntry ::= SEQUENCE {
	snBgp4NeighOperStatusIndex
		Integer32,
	snBgp4NeighOperStatusIp
		IpAddress,
	snBgp4NeighOperStatusRemoteAs
		Integer32,
	snBgp4NeighOperStatusBgpType
		INTEGER,
	snBgp4NeighOperStatusState
		INTEGER,
	snBgp4NeighOperStatusKeepAliveTime
		Integer32,
	snBgp4NeighOperStatusHoldTime
		Integer32,
	snBgp4NeighOperStatusAdvertlevel
		Integer32,
	snBgp4NeighOperStatusKeepAliveTxCounts             
		Counter32,
	snBgp4NeighOperStatusKeepAliveRxCounts             
		Counter32,
	snBgp4NeighOperStatusUpdateTxCounts             
		Counter32,
	snBgp4NeighOperStatusUpdateRxCounts             
		Counter32,
	snBgp4NeighOperStatusNotifTxCounts
		Counter32,
	snBgp4NeighOperStatusNotifRxCounts
		Counter32,
	snBgp4NeighOperStatusOpenTxCounts
		Counter32,
	snBgp4NeighOperStatusOpenRxCounts
		Counter32
	}

snBgp4NeighOperStatusIndex   OBJECT-TYPE
	SYNTAX  Integer32
	MAX-ACCESS  read-only
	STATUS  current
	DESCRIPTION
		"The index for a neighbor entry." 
	::= { snBgp4NeighOperStatusEntry 1 }

snBgp4NeighOperStatusIp       OBJECT-TYPE
	SYNTAX  IpAddress
	MAX-ACCESS  read-only
	STATUS  current
	DESCRIPTION
		"The IP Address for a neighbor entry."
	::= { snBgp4NeighOperStatusEntry 2 }

snBgp4NeighOperStatusRemoteAs    OBJECT-TYPE
	SYNTAX   Integer32
	MAX-ACCESS   read-only
	STATUS   current
	DESCRIPTION
	   "To show a neighbor with an autonomous system number(AS)."
	::= { snBgp4NeighOperStatusEntry 3 }

snBgp4NeighOperStatusBgpType    OBJECT-TYPE
	SYNTAX   INTEGER  { ebgp(0), ibgp(1) }
	MAX-ACCESS   read-only
	STATUS   current
	DESCRIPTION
	   "To show the type of BGP protocol whether is internal or external."
	::= { snBgp4NeighOperStatusEntry 4 }

snBgp4NeighOperStatusState    OBJECT-TYPE
	SYNTAX   INTEGER  { 
				noState(0), 
				idle(1), 
				connect(2), 
				active(3), 
				openSent(4), 
				openConfirm(5), 
				established(6) 
				}
	MAX-ACCESS   read-only
	STATUS   current
	DESCRIPTION
	   "To show the state of this neighbor."
	::= { snBgp4NeighOperStatusEntry 5 }

snBgp4NeighOperStatusKeepAliveTime OBJECT-TYPE
	SYNTAX   Integer32 
	MAX-ACCESS   read-only
	STATUS   current
	DESCRIPTION
		"The Keep alive timer."
	::= { snBgp4NeighOperStatusEntry 6 }

snBgp4NeighOperStatusHoldTime OBJECT-TYPE
	SYNTAX   Integer32 
	MAX-ACCESS   read-only
	STATUS   current
	DESCRIPTION
		"The Hold time timer."
	::= { snBgp4NeighOperStatusEntry 7 }

snBgp4NeighOperStatusAdvertlevel   OBJECT-TYPE
	SYNTAX  Integer32
	MAX-ACCESS  read-only
	STATUS  current
	DESCRIPTION
		"To show the minimum interval between the 
		sending of BGP routing updates."
	::= { snBgp4NeighOperStatusEntry 8 }

snBgp4NeighOperStatusKeepAliveTxCounts OBJECT-TYPE
	SYNTAX   Counter32
	MAX-ACCESS   read-only
	STATUS   current
	DESCRIPTION
	   "Keep alive message sent counts."
	::= { snBgp4NeighOperStatusEntry 9 }

snBgp4NeighOperStatusKeepAliveRxCounts OBJECT-TYPE
	SYNTAX   Counter32
	MAX-ACCESS   read-only
	STATUS   current
	DESCRIPTION
	   "Keep alive message received counts."
	::= { snBgp4NeighOperStatusEntry 10 }

snBgp4NeighOperStatusUpdateTxCounts OBJECT-TYPE
	SYNTAX   Counter32
	MAX-ACCESS   read-only
	STATUS   current
	DESCRIPTION
	   "Update message sent counts."
	::= { snBgp4NeighOperStatusEntry 11 }

snBgp4NeighOperStatusUpdateRxCounts OBJECT-TYPE
	SYNTAX   Counter32
	MAX-ACCESS   read-only
	STATUS   current
	DESCRIPTION
	   "Update message received counts."
	::= { snBgp4NeighOperStatusEntry 12 }

snBgp4NeighOperStatusNotifTxCounts OBJECT-TYPE
	SYNTAX   Counter32
	MAX-ACCESS   read-only
	STATUS   current
	DESCRIPTION
	   "Notification message sent counts."
	::= { snBgp4NeighOperStatusEntry 13 }

snBgp4NeighOperStatusNotifRxCounts OBJECT-TYPE
	SYNTAX   Counter32
	MAX-ACCESS   read-only
	STATUS   current
	DESCRIPTION
	   "Notification message received counts."
	::= { snBgp4NeighOperStatusEntry 14 }

snBgp4NeighOperStatusOpenTxCounts OBJECT-TYPE
	SYNTAX   Counter32
	MAX-ACCESS   read-only
	STATUS   current
	DESCRIPTION
	   "Open message sent counts."
	::= { snBgp4NeighOperStatusEntry 15 }

snBgp4NeighOperStatusOpenRxCounts OBJECT-TYPE
	SYNTAX   Counter32
	MAX-ACCESS   read-only
	STATUS   current
	DESCRIPTION
	   "Open message received counts."
	::= { snBgp4NeighOperStatusEntry 16 }

-- Bgp4 Routes Operational Status Table

snBgp4RouteOperStatusTable       OBJECT-TYPE
	SYNTAX  SEQUENCE OF SnBgp4RouteOperStatusEntry
	MAX-ACCESS  not-accessible
	STATUS  current
	DESCRIPTION
		"Bgp4 Routebor Operational Status table."
	::= { snBgp4RouteOperStatus 1 }

snBgp4RouteOperStatusEntry       OBJECT-TYPE
	SYNTAX  SnBgp4RouteOperStatusEntry
	MAX-ACCESS  not-accessible
	STATUS  current
	DESCRIPTION
		"An entry in the Bgp4 Operational Status table."
	INDEX   { snBgp4RouteOperStatusIndex }
	::= { snBgp4RouteOperStatusTable 1 }

SnBgp4RouteOperStatusEntry ::= SEQUENCE {
	snBgp4RouteOperStatusIndex
		Integer32,
	snBgp4RouteOperStatusIp
		IpAddress,
	snBgp4RouteOperStatusSubnetMask
		IpAddress,
	snBgp4RouteOperStatusNextHop
		IpAddress,
	snBgp4RouteOperStatusMetric
		Integer32,
	snBgp4RouteOperStatusLocalPreference
		Integer32,
	snBgp4RouteOperStatusWeight
		Integer32,
	snBgp4RouteOperStatusOrigin
		INTEGER,
	snBgp4RouteOperStatusStatus
		Integer32,
	snBgp4RouteOperStatusRouteTag
		Integer32,
	snBgp4RouteOperStatusCommunityList
		OCTET STRING,
	snBgp4RouteOperStatusAsPathList
		OCTET STRING
	}

snBgp4RouteOperStatusIndex   OBJECT-TYPE
	SYNTAX  Integer32 
	MAX-ACCESS  read-only
	STATUS  current
	DESCRIPTION
		"The index for a route entry." 
	::= { snBgp4RouteOperStatusEntry 1 }

snBgp4RouteOperStatusIp       OBJECT-TYPE
	SYNTAX  IpAddress
	MAX-ACCESS  read-only
	STATUS  current
	DESCRIPTION
		"The IP Address for a route entry."
	::= { snBgp4RouteOperStatusEntry 2 }

snBgp4RouteOperStatusSubnetMask       OBJECT-TYPE
	SYNTAX  IpAddress
	MAX-ACCESS  read-only
	STATUS  current
	DESCRIPTION
		"The IP Subnet Mask for a route entry."
	::= { snBgp4RouteOperStatusEntry 3 }

snBgp4RouteOperStatusNextHop       OBJECT-TYPE
	SYNTAX  IpAddress
	MAX-ACCESS  read-only
	STATUS  current
	DESCRIPTION
		"The next-hop IP for a route entry."
	::= { snBgp4RouteOperStatusEntry 4 }

snBgp4RouteOperStatusMetric    OBJECT-TYPE
	SYNTAX   Integer32
	MAX-ACCESS   read-only
	STATUS   current
	DESCRIPTION
	   "To show the metric value of a route entry."
	::= { snBgp4RouteOperStatusEntry 5 }

snBgp4RouteOperStatusLocalPreference    OBJECT-TYPE
	SYNTAX   Integer32
	MAX-ACCESS   read-only
	STATUS   current
	DESCRIPTION
	   "To show the local preference of a route entry."
	::= { snBgp4RouteOperStatusEntry 6 }

snBgp4RouteOperStatusWeight    OBJECT-TYPE
	SYNTAX   Integer32 
	MAX-ACCESS   read-only
	STATUS   current
	DESCRIPTION
	   "To show the weight of this route."
	::= { snBgp4RouteOperStatusEntry 7 }

snBgp4RouteOperStatusOrigin    OBJECT-TYPE
	SYNTAX   INTEGER  { 
				igp(0), 
				egp(1),
				incomplete(2)
			 }
	MAX-ACCESS   read-only
	STATUS   current
	DESCRIPTION
	   "To show the origin of this route."
	::= { snBgp4RouteOperStatusEntry 8 }

snBgp4RouteOperStatusStatus    OBJECT-TYPE
	SYNTAX   Integer32
	MAX-ACCESS   read-only
	STATUS   current
	DESCRIPTION
	   "A bit array that contains the status of this route.
	   This is a packed bit string; The following shows the
	   meaning of each bit:
		(bit 0 is the least significant bit and 0=FALSE, 1=TRUE).

		  bit position   meaning
		  ------------   -------
			  6-31   reserved.
			  5    	 aggregate.
			  4      best.
			  3      internal.
			  2      local.
			  1      suppressed.
			  0      valid."
	::= { snBgp4RouteOperStatusEntry 9 }

snBgp4RouteOperStatusRouteTag    OBJECT-TYPE
	SYNTAX   Integer32 
	MAX-ACCESS   read-only
	STATUS   current
	DESCRIPTION
	   "To show the route tag of this route."
	::= { snBgp4RouteOperStatusEntry 10 }

snBgp4RouteOperStatusCommunityList    OBJECT-TYPE
	SYNTAX   OCTET STRING 
	MAX-ACCESS   read-only
	STATUS   current
	DESCRIPTION
	   "To show the community list of this route.
	   If the community list is an NULL string that means an empty list, then
	   the community is INTERNET. A number from 1 to 0xFFFFFFFF.  
	   This integer number is represented by 4 OCTETs.
	   In the community list, it could have some Well-known numbers such as:  
	   BGP_COMMUNITY_ATTRIBUTE_NO_EXPORT		0xFFFFFF01
	   BGP_COMMUNITY_ATTRIBUTE_NO_ADVERTISE		0xFFFFFF02"
	::= { snBgp4RouteOperStatusEntry 11 }


snBgp4RouteOperStatusAsPathList    OBJECT-TYPE
	SYNTAX   OCTET STRING 
	MAX-ACCESS   read-only
	STATUS   current
	DESCRIPTION
	   "To show the AS Path list of this route.
	   A number from 1 to 0xFFFF.  
	   This integer number is represented by 2 OCTETs."
	::= { snBgp4RouteOperStatusEntry 12 }

-- Bgp4 Neighbor Summary Table

snBgp4NeighborSummaryTable       OBJECT-TYPE
	SYNTAX  SEQUENCE OF SnBgp4NeighborSummaryEntry
	MAX-ACCESS  not-accessible
	STATUS  current
	DESCRIPTION
		"Bgp4 Routebor Operational Status table."
	::= { snBgp4NeighborSummary 1 }

snBgp4NeighborSummaryEntry       OBJECT-TYPE
	SYNTAX  SnBgp4NeighborSummaryEntry
	MAX-ACCESS  not-accessible
	STATUS  current
	DESCRIPTION
		"An entry in the Bgp4 Operational Status table."
	INDEX   { snBgp4NeighborSummaryIndex }
	::= { snBgp4NeighborSummaryTable 1 }

SnBgp4NeighborSummaryEntry ::= SEQUENCE {
	snBgp4NeighborSummaryIndex
		Integer32,
	snBgp4NeighborSummaryIp
		IpAddress,
	snBgp4NeighborSummaryState
		INTEGER,
	snBgp4NeighborSummaryStateChgTime
		Integer32,
	snBgp4NeighborSummaryRouteReceived
		Integer32,
	snBgp4NeighborSummaryRouteInstalled
		Integer32
	}

snBgp4NeighborSummaryIndex   OBJECT-TYPE
	SYNTAX  Integer32
	MAX-ACCESS  read-only
	STATUS  current
	DESCRIPTION
		"The index for a route entry." 
	::= { snBgp4NeighborSummaryEntry 1 }

snBgp4NeighborSummaryIp       OBJECT-TYPE
	SYNTAX  IpAddress
	MAX-ACCESS  read-only
	STATUS  current
	DESCRIPTION
		"The IP Address for a route entry."
	::= { snBgp4NeighborSummaryEntry 2 }

snBgp4NeighborSummaryState    OBJECT-TYPE
	SYNTAX   INTEGER  { 
				noState(0), 
				idle(1), 
				connect(2), 
				active(3), 
				openSent(4), 
				openConfirm(5), 
				established(6) 
				}
	MAX-ACCESS   read-only
	STATUS   current
	DESCRIPTION
	   "To show the state of this neighbor."
	::= { snBgp4NeighborSummaryEntry 3 }

snBgp4NeighborSummaryStateChgTime OBJECT-TYPE
	SYNTAX   Integer32 
	MAX-ACCESS   read-only
	STATUS   current
	DESCRIPTION
		"The time of a change of the state of this neighbor."
	::= { snBgp4NeighborSummaryEntry 4 }

snBgp4NeighborSummaryRouteReceived OBJECT-TYPE
	SYNTAX   Integer32 
	MAX-ACCESS   read-only
	STATUS   current
	DESCRIPTION
		"The number of routes received of this neighbor."
	::= { snBgp4NeighborSummaryEntry 5 }

snBgp4NeighborSummaryRouteInstalled OBJECT-TYPE
	SYNTAX   Integer32 
	MAX-ACCESS   read-only
	STATUS   current
	DESCRIPTION
		"The number of routes installed of this neighbor."
	::= { snBgp4NeighborSummaryEntry 6 }

-- Bgp4 Attribute Entries Table

snBgp4AttributeTable       OBJECT-TYPE
	SYNTAX  SEQUENCE OF SnBgp4AttributeEntry
	MAX-ACCESS  not-accessible
	STATUS  current
	DESCRIPTION
		"Bgp4 Attribute entries table."
	::= { snBgp4Attribute 1 }

snBgp4AttributeEntry       OBJECT-TYPE
	SYNTAX  SnBgp4AttributeEntry
	MAX-ACCESS  not-accessible
	STATUS  current
	DESCRIPTION
		"An entry in the Bgp4 Attribute table."
	INDEX   { snBgp4AttributeIndex }
	::= { snBgp4AttributeTable 1 }

SnBgp4AttributeEntry ::= SEQUENCE {
	snBgp4AttributeIndex
		Integer32,
	snBgp4AttributeNextHop
		IpAddress,
	snBgp4AttributeMetric
		Integer32,
	snBgp4AttributeOrigin
		INTEGER,
	snBgp4AttributeAggregatorAs
		Integer32,
	snBgp4AttributeRouterId
		IpAddress,
	snBgp4AttributeAtomicAggregatePresent
		INTEGER,
	snBgp4AttributeLocalPreference
		Integer32,
	snBgp4AttributeCommunityList
		OCTET STRING,
	snBgp4AttributeAsPathList
		OCTET STRING,
	snBgp4AttributeOriginator
		IpAddress,
	snBgp4AttributeClusterList
		OCTET STRING
	}

snBgp4AttributeIndex   OBJECT-TYPE
	SYNTAX  Integer32 
	MAX-ACCESS  read-only
	STATUS  current
	DESCRIPTION
		"The index for a route entry." 
	::= { snBgp4AttributeEntry 1 }

snBgp4AttributeNextHop       OBJECT-TYPE
	SYNTAX  IpAddress
	MAX-ACCESS  read-only
	STATUS  current
	DESCRIPTION
		"The next-hop IP for a route entry."
	::= { snBgp4AttributeEntry 2 }

snBgp4AttributeMetric    OBJECT-TYPE
	SYNTAX   Integer32
	MAX-ACCESS   read-only
	STATUS   current
	DESCRIPTION
	   "To show the metric value of a route entry."
	::= { snBgp4AttributeEntry 3 }

snBgp4AttributeOrigin    OBJECT-TYPE
	SYNTAX   INTEGER  { 
				igp(0), 
				egp(1),
				incomplete(2)
			 }
	MAX-ACCESS   read-only
	STATUS   current
	DESCRIPTION
	   "To show the origin of this route."
	::= { snBgp4AttributeEntry 4 }

snBgp4AttributeAggregatorAs    OBJECT-TYPE
	SYNTAX   Integer32
	MAX-ACCESS   read-only
	STATUS   current
	DESCRIPTION
	   "The aggregator AS number for an attribute entry."
	::= { snBgp4AttributeEntry 5 }

snBgp4AttributeRouterId       OBJECT-TYPE
	SYNTAX  IpAddress
	MAX-ACCESS  read-only
	STATUS  current
	DESCRIPTION
		"The router ID for an attribute entry."
	::= { snBgp4AttributeEntry 6 }

snBgp4AttributeAtomicAggregatePresent    OBJECT-TYPE
	SYNTAX   INTEGER { false(0), true(1) }
	MAX-ACCESS   read-only
	STATUS   current
	DESCRIPTION
	   "The atomic aggregate present in an attribute entry."
	::= { snBgp4AttributeEntry 7 }

snBgp4AttributeLocalPreference    OBJECT-TYPE
	SYNTAX   Integer32
	MAX-ACCESS   read-only
	STATUS   current
	DESCRIPTION
	   "To show the local preference of a route entry."
	::= { snBgp4AttributeEntry 8 }

snBgp4AttributeCommunityList    OBJECT-TYPE
	SYNTAX   OCTET STRING 
	MAX-ACCESS   read-only
	STATUS   current
	DESCRIPTION
	   "To show the community list of this attribute entry.
	   If the community list is an NULL string that means an empty list, then
	   the community is INTERNET. A number from 1 to 0xFFFFFFFF.  
	   This integer number is represented by 4 OCTETs.
	   In the community list, it could have some Well-known numbers such as:  
	   BGP_COMMUNITY_ATTRIBUTE_NO_EXPORT		0xFFFFFF01
	   BGP_COMMUNITY_ATTRIBUTE_NO_ADVERTISE		0xFFFFFF02"
	::= { snBgp4AttributeEntry 9 }


snBgp4AttributeAsPathList    OBJECT-TYPE
	SYNTAX   OCTET STRING 
	MAX-ACCESS   read-only
	STATUS   current
	DESCRIPTION
	   "To show the AS Path list of this attribute entry.
	   A number from 1 to 0xFFFF.  
	   This integer number is represented by 2 OCTETs."
	::= { snBgp4AttributeEntry 10 }

snBgp4AttributeOriginator       OBJECT-TYPE
	SYNTAX  IpAddress
	MAX-ACCESS  read-only
	STATUS  current
	DESCRIPTION
		"The originator IP address for an attribute entry."
	::= { snBgp4AttributeEntry 11 }

snBgp4AttributeClusterList    OBJECT-TYPE
	SYNTAX   OCTET STRING 
	MAX-ACCESS   read-only
	STATUS   current
	DESCRIPTION
	   "To show the cluster list of this attribute entry.
	   If the cluster list is an NULL string, it means an empty list. 
	   Otherwise, the list is a group of cluster ID which is
	   represented by 4 OCTETs IP address."
	::= { snBgp4AttributeEntry 12 }

-- Bgp4 Clear Neighbor Command Table

snBgp4ClearNeighborCmdTable       OBJECT-TYPE
	SYNTAX  SEQUENCE OF SnBgp4ClearNeighborCmdEntry
	MAX-ACCESS  not-accessible
	STATUS  current
	DESCRIPTION
		"Clear Bgp4 command table."
	::= { snBgp4ClearNeighborCmd 1 }

snBgp4ClearNeighborCmdEntry       OBJECT-TYPE
	SYNTAX  SnBgp4ClearNeighborCmdEntry
	MAX-ACCESS  not-accessible
	STATUS  current
	DESCRIPTION
		"An entry in the clear Bgp4 neighbor command table."
	INDEX   { snBgp4ClearNeighborCmdIp }
	::= { snBgp4ClearNeighborCmdTable 1 }

SnBgp4ClearNeighborCmdEntry ::= SEQUENCE {
	snBgp4ClearNeighborCmdIp
		IpAddress,
	snBgp4ClearNeighborCmdElement
		INTEGER
	}

snBgp4ClearNeighborCmdIp       OBJECT-TYPE
	SYNTAX  IpAddress
	MAX-ACCESS  read-only
	STATUS  current
	DESCRIPTION
		"The IP Address for a neighbor entry. 
		If the IP address is 255.255.255.255, it
		means for all neighbors."
	::= { snBgp4ClearNeighborCmdEntry 1 }

snBgp4ClearNeighborCmdElement    OBJECT-TYPE
	SYNTAX   INTEGER  { 
				valid(0), 
				lastPacketWithError(1), 
				notificationErrors(2), 
				softOutbound(3), 
				traffic(4), 
				neighbor(5) 
				}
	MAX-ACCESS   read-write
	STATUS   current
	DESCRIPTION
	   "To send the command element of this neighbor for value(1) to (5)
	valid(0) is received in SNMP-get."
	::= { snBgp4ClearNeighborCmdEntry 2 }

-- Bgp4 Neighbor Prefix Group Table

snBgp4NeighPrefixGroupTable    OBJECT-TYPE
	SYNTAX  SEQUENCE OF SnBgp4NeighPrefixGroupEntry
	MAX-ACCESS  not-accessible
	STATUS  current
	DESCRIPTION
		"Bgp4 Neighbor Prefix Group table."
	::= { snBgp4NeighPrefixGroup 1 }

snBgp4NeighPrefixGroupEntry       OBJECT-TYPE
	SYNTAX  SnBgp4NeighPrefixGroupEntry
	MAX-ACCESS  not-accessible
	STATUS  current
	DESCRIPTION
		"An entry in the Bgp4 Prefix Group table."
	INDEX   { snBgp4NeighPrefixGroupNeighIp, snBgp4NeighPrefixGroupDir }
	::= { snBgp4NeighPrefixGroupTable 1 }

SnBgp4NeighPrefixGroupEntry ::= SEQUENCE {
	snBgp4NeighPrefixGroupNeighIp
		IpAddress,
	snBgp4NeighPrefixGroupDir
		INTEGER,
	snBgp4NeighPrefixGroupInAccessList             
		OCTET STRING,
	snBgp4NeighPrefixGroupOutAccessList             
		OCTET STRING,
	snBgp4NeighPrefixGroupRowStatus
		INTEGER
	}

snBgp4NeighPrefixGroupNeighIp       OBJECT-TYPE
	SYNTAX  IpAddress
	MAX-ACCESS  read-only
	STATUS  current
	DESCRIPTION
		"The IP Address for a neighbor entry."
	::= { snBgp4NeighPrefixGroupEntry 1 }

snBgp4NeighPrefixGroupDir   OBJECT-TYPE
	SYNTAX  INTEGER { out(0), in(1) } 
	MAX-ACCESS  read-only
	STATUS  current
	DESCRIPTION
		"The incoming/outgoing advertisements to which 
		the access list is applied."
	::= { snBgp4NeighPrefixGroupEntry 2 }

snBgp4NeighPrefixGroupInAccessList OBJECT-TYPE
	SYNTAX  OCTET STRING (SIZE(0..32)) 
	MAX-ACCESS   read-write
	STATUS   current
	DESCRIPTION
	   "An in access prefix list name. " 
	::= { snBgp4NeighPrefixGroupEntry 3 }

snBgp4NeighPrefixGroupOutAccessList OBJECT-TYPE
	SYNTAX  OCTET STRING (SIZE(0..32)) 
	MAX-ACCESS   read-write
	STATUS   current
	DESCRIPTION
	   "An out prefix list name. " 
	::= { snBgp4NeighPrefixGroupEntry 4 }

snBgp4NeighPrefixGroupRowStatus   OBJECT-TYPE
	SYNTAX	 INTEGER {
		invalid(1),
		valid(2),
		delete(3),
		create(4),
		modify(5)
	}
	MAX-ACCESS	 read-write
	STATUS	 current
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
			  rendering it inoperative..
	 valid(2)....the row exists and is valid"
	::= { snBgp4NeighPrefixGroupEntry 5 }
END
FOUNDRY-SN-POS-GROUP-MIB DEFINITIONS ::= BEGIN

IMPORTS
	MODULE-IDENTITY, OBJECT-TYPE,Counter32, Gauge32, Unsigned32,Integer32
		FROM SNMPv2-SMI
	router
		FROM FOUNDRY-SN-ROOT-MIB
	ifIndex
		FROM IF-MIB	
	DisplayString,TEXTUAL-CONVENTION
		FROM SNMPv2-TC;
		
snPOS MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"            
	REVISION     "200909300000Z" -- September 30, 2009
	DESCRIPTION
			""
   ::= { router 14}

	-- textual conventions

	POSStatus ::= TEXTUAL-CONVENTION
		STATUS	  current
		DESCRIPTION
			"
			Status Values
			"
		SYNTAX	INTEGER { disabled(0), enabled(1) }

snPOSInfo						OBJECT IDENTIFIER	  ::= { snPOS 1  }

-- POS Port table information

snPOSInfoTable OBJECT-TYPE
	SYNTAX  SEQUENCE OF SnPOSInfoEntry
	MAX-ACCESS  not-accessible
	STATUS  current
	DESCRIPTION
		"A specific snPOSInfo group consists of a number of 
		 switch ports.  "
	::= { snPOSInfo 1 }

snPOSInfoEntry OBJECT-TYPE
	SYNTAX  SnPOSInfoEntry
	MAX-ACCESS  not-accessible
	STATUS  current
	DESCRIPTION
		"An entry in the snPOSInfo table indicates the 
		 configuration on a specified port. A SNMP SET PDU 
		 for a row of the snPOSInfoTable requires the entired 
		 sequence of the MIB Objects in each 
		 snPOSInfoEntry stored in one PDU.  Otherwise, 
		 GENERR return-value will be returned."
	INDEX   { 
		snPOSInfoPortNum
	}
	::= { snPOSInfoTable 1 }

SnPOSInfoEntry ::= SEQUENCE {
	snPOSInfoPortNum
		Integer32,
	snPOSIfIndex
		Integer32,
	snPOSDescr
		DisplayString,
	snPOSName
		DisplayString,
	snPOSInfoSpeed
		INTEGER,
	snPOSInfoAdminStatus
		INTEGER,
	snPOSInfoLinkStatus
		INTEGER,
	snPOSInfoClock
		INTEGER,
	snPOSInfoLoopBack
		INTEGER,
	snPOSInfoScrambleATM
		POSStatus,
	snPOSInfoFraming
		INTEGER,
	snPOSInfoCRC
		INTEGER,
	snPOSInfoKeepAlive
		INTEGER,
	snPOSInfoFlagC2
		INTEGER,
	snPOSInfoFlagJ0
		INTEGER,
	snPOSInfoFlagH1
		INTEGER,
	snPOSStatsInFrames
		Counter32,
	snPOSStatsOutFrames
		Counter32,
	snPOSStatsAlignErrors
		Counter32,
	snPOSStatsFCSErrors
		Counter32,
	snPOSStatsFrameTooLongs              
		Counter32,
	snPOSStatsFrameTooShorts
		Counter32,
	snPOSStatsInDiscard
		Counter32,
	snPOSStatsOutDiscard
		Counter32,
	snPOSInOctets
		OCTET STRING,
	snPOSOutOctets
		OCTET STRING,
	snPOSStatsInBitsPerSec
		Gauge32,
	snPOSStatsOutBitsPerSec
		Gauge32,
	snPOSStatsInPktsPerSec
		Gauge32,
	snPOSStatsOutPktsPerSec
		Gauge32,
	snPOSStatsInUtilization
		INTEGER ,
	snPOSStatsOutUtilization
		INTEGER ,
	snPOSTagType
		INTEGER,
	snPOSStatsB1
		Counter32,
	snPOSStatsB2
		Counter32,
	snPOSStatsB3
		Counter32,
	snPOSStatsAIS
		Counter32,
	snPOSStatsRDI
		Counter32,
	snPOSStatsLOP
		Counter32,
	snPOSStatsLOF
		Counter32,
	snPOSStatsLOS
		Counter32
	}


snPOSInfoPortNum OBJECT-TYPE
	SYNTAX  Integer32
	MAX-ACCESS  read-only
	STATUS  current
	DESCRIPTION
		"The port index.
		 The bit 0 to bit 7: port number. 
		 The bit 8 to bit 11: slot number (slot for chassis only)."
	::= { snPOSInfoEntry 1 }


snPOSIfIndex OBJECT-TYPE
	SYNTAX  Integer32
	MAX-ACCESS  read-only
	STATUS  current
	DESCRIPTION
		"In order to identify a particular interface, this
		object shall identify the instance of the ifIndex
		object, defined in RFC 1213 and RFC 1573."
	::= { snPOSInfoEntry 2 }


snPOSDescr OBJECT-TYPE
	SYNTAX  DisplayString
	MAX-ACCESS  read-only
	STATUS  current
	DESCRIPTION
		"A textual string containing the slot/port information
		about the interface."
	::= { snPOSInfoEntry 3 }


snPOSName OBJECT-TYPE
	SYNTAX	DisplayString (SIZE(0..255))
	MAX-ACCESS	read-write
	STATUS	current
	DESCRIPTION
		"Port Name string."
	::= { snPOSInfoEntry 4 }

snPOSInfoSpeed OBJECT-TYPE
	SYNTAX  INTEGER {
		s155000(1),
		s622000(2),
		other(3),
		s2488000(4)
		}
	MAX-ACCESS  read-write
	STATUS  current
	DESCRIPTION     
		"The speed configuration for a port. The values are:
		155000
		622000
		2488000
		"
	::= { snPOSInfoEntry 5 }


snPOSInfoAdminStatus OBJECT-TYPE
	SYNTAX  INTEGER {
		up(1),       -- ready to pass packets
		down(2),
		testing(3)   -- in some test mode
		}
	MAX-ACCESS  read-write
	STATUS  current
	DESCRIPTION
		"The desired state of all ports.  The
		testing(3) state indicates that no operational
		packets can be passed. 
		(same as ifAdminStatus in MIB-II)"
	::= { snPOSInfoEntry 6 }


snPOSInfoLinkStatus OBJECT-TYPE
	SYNTAX  INTEGER {
		up(1),       -- ready to pass packets
		down(2),
		testing(3)   -- in some test mode
		}
	MAX-ACCESS  read-only
	STATUS  current
	DESCRIPTION
		"The current operational state of the interface.
		 The testing(3) state indicates that no operational
		 packets can be passed. 
		 (same as ifOperStatus in MIB-II)"
	::= { snPOSInfoEntry 7 }


snPOSInfoClock  OBJECT-TYPE
	SYNTAX  INTEGER {
		internal(1),     
		line(2)
		}
	MAX-ACCESS  read-write
	STATUS  current
	DESCRIPTION
		"Clock default internal"
	::= { snPOSInfoEntry 8 }

snPOSInfoLoopBack   OBJECT-TYPE
	SYNTAX  INTEGER {
		line(1),     
		internal(2),
		none(3)
		}
	MAX-ACCESS  read-write
	STATUS  current
	DESCRIPTION
		"Loop back default none"
	::= { snPOSInfoEntry 9 }

snPOSInfoScrambleATM  OBJECT-TYPE
	SYNTAX	POSStatus
	MAX-ACCESS  read-write
	STATUS  current
	DESCRIPTION
		"ATM style scrambling default off"
	::= { snPOSInfoEntry 10 }

snPOSInfoFraming  OBJECT-TYPE
	SYNTAX  INTEGER {
		sonet(1),     
		sdh(2)
		}
	MAX-ACCESS  read-write
	STATUS  current
	DESCRIPTION
		"Framing default SONET"
	::= { snPOSInfoEntry 11 }

snPOSInfoCRC  OBJECT-TYPE
	SYNTAX  INTEGER {
		crc32bits(1),     
		crc16bits(2)
		}
	MAX-ACCESS  read-write
	STATUS  current
	DESCRIPTION
		"CRC default 32 bit"
	::= { snPOSInfoEntry 12 }

snPOSInfoKeepAlive  OBJECT-TYPE
	SYNTAX  INTEGER (0..32767)
	MAX-ACCESS  read-write
	STATUS  current
	DESCRIPTION
		"Keep-alive default 10"
	::= { snPOSInfoEntry 13 }

snPOSInfoFlagC2  OBJECT-TYPE
	SYNTAX  INTEGER (0..255)
	MAX-ACCESS  read-write
	STATUS  current
	DESCRIPTION
		"C2 flag"
	::= { snPOSInfoEntry 14 }


snPOSInfoFlagJ0  OBJECT-TYPE
	SYNTAX  INTEGER (0..255)
	MAX-ACCESS  read-write
	STATUS  current
	DESCRIPTION
		"J0 flag"
	::= { snPOSInfoEntry 15 }

snPOSInfoFlagH1  OBJECT-TYPE
	SYNTAX  INTEGER (0..255)
	MAX-ACCESS  read-write
	STATUS  current
	DESCRIPTION
		"H1 flag"
	::= { snPOSInfoEntry 16 }

snPOSStatsInFrames OBJECT-TYPE
	SYNTAX  Counter32
	MAX-ACCESS  read-only
	STATUS  current
	DESCRIPTION
		"The total number of packets received on the interface."
	::= { snPOSInfoEntry 17 }


snPOSStatsOutFrames OBJECT-TYPE
	SYNTAX  Counter32
	MAX-ACCESS  read-only
	STATUS  current
	DESCRIPTION
		"The total number of packets transmitted out of the interface."
	::= { snPOSInfoEntry 18 }


snPOSStatsAlignErrors   OBJECT-TYPE
	 SYNTAX     Counter32
	 MAX-ACCESS     read-only
	 STATUS     current
	 DESCRIPTION
		"dot3StatsAlignmentErrors : A count of frames 
		received on a particular interface that are 
		not an integral number of octets in length 
		and do not pass the FCS check.

		The count represented by an instance of this
		object is incremented when the alignmentError
		status is returned by the MAC service to the
		LLC (or other MAC user). Received frames for
		which multiple error conditions obtain are,
		according to the conventions of IEEE 802.3
		Layer Management, counted exclusively according
		to the error status presented to the LLC."
	::= { snPOSInfoEntry 19 }

snPOSStatsFCSErrors   OBJECT-TYPE
	 SYNTAX      Counter32
	 MAX-ACCESS      read-only
	 STATUS      current
	 DESCRIPTION
		"dot3StatsFCSErrors : A count of frames received 
		on a particular interface that are an integral 
		number of octets in length but do not pass the 
		FCS check.

		The count represented by an instance of this
		object is incremented when the frameCheckError
		status is returned by the MAC service to the
		LLC (or other MAC user). Received frames for
		which multiple error conditions obtain are,
		according to the conventions of IEEE 802.3
		Layer Management, counted exclusively according
		to the error status presented to the LLC."
	::= { snPOSInfoEntry 20 }


snPOSStatsFrameTooLongs   OBJECT-TYPE
	 SYNTAX    Counter32
	 MAX-ACCESS    read-only
	 STATUS    current
	 DESCRIPTION
		"dot3StatsFrameTooLongs : A count of frames 
		received on a particular interface that 
		exceed the maximum permitted frame size.

		The count represented by an instance of this
		object is incremented when the frameTooLong
		status is returned by the MAC service to the
		LLC (or other MAC user). Received frames for
		which multiple error conditions obtain are,
		according to the conventions of IEEE 802.3
		Layer Management, counted exclusively according
		to the error status presented to the LLC."
	::= { snPOSInfoEntry 21 }


snPOSStatsFrameTooShorts   OBJECT-TYPE
	 SYNTAX    Counter32
	 MAX-ACCESS    read-only
	 STATUS    current
	 DESCRIPTION
		" A count of frames received on a particular 
		interface that below the minimum permitted 
		frame size."
	::= { snPOSInfoEntry 22 }

snPOSStatsInDiscard OBJECT-TYPE
	SYNTAX  Counter32
	MAX-ACCESS  read-only
	STATUS  current
	DESCRIPTION
		"The number of inbound packets which were chosen
		 to be discarded even though no errors had been
		 detected to prevent their being deliverable to a
		 higher-layer protocol.  One possible reason for
		 discarding such a packet could be to free up
		 buffer space."
	::= { snPOSInfoEntry 23 }


snPOSStatsOutDiscard OBJECT-TYPE
	SYNTAX  Counter32
	MAX-ACCESS  read-only
	STATUS  current
	DESCRIPTION
		"The number of outbound packets which were chosen
		 to be discarded even though no errors had been
		 detected to prevent their being transmitted.  One
		 possible reason for discarding such a packet could
		 be to free up buffer space."
	::= { snPOSInfoEntry 24 }

snPOSInOctets OBJECT-TYPE
	SYNTAX  OCTET STRING (SIZE(8))
	MAX-ACCESS  read-only
	STATUS  current
	DESCRIPTION
		"The total number of octets received on the interface,
		including framing characters. This object is a 64-bit
		counter of the ifInOctets object, defined in RFC 1213.
		The octet string is in big-endian byte order."
	::= { snPOSInfoEntry 25 }


snPOSOutOctets OBJECT-TYPE
	SYNTAX  OCTET STRING (SIZE(8))
	MAX-ACCESS  read-only
	STATUS  current
	DESCRIPTION
		"The total number of octets transmitted out of the interface,
		including framing characters. This object is a 64-bit
		counter of the ifOutOctets object, defined in RFC 1213.
		The octet string is in big-endian byte order."
	::= { snPOSInfoEntry 26 }


snPOSStatsInBitsPerSec OBJECT-TYPE
	SYNTAX  Gauge32
	MAX-ACCESS  read-only
	STATUS  current
	DESCRIPTION
		"The number of bits per second received on the interface
		over a 5 minutes interval."
	::= { snPOSInfoEntry 27 }


snPOSStatsOutBitsPerSec OBJECT-TYPE
	SYNTAX  Gauge32
	MAX-ACCESS  read-only
	STATUS  current
	DESCRIPTION
		"The number of bits per second transmitted out of the interface
		over a 5 minutes interval."
	::= { snPOSInfoEntry 28 }


snPOSStatsInPktsPerSec OBJECT-TYPE
	SYNTAX  Gauge32
	MAX-ACCESS  read-only
	STATUS  current
	DESCRIPTION
		"The number of packets per second received on the interface
		over a 5 minutes interval."
	::= { snPOSInfoEntry 29 }


snPOSStatsOutPktsPerSec OBJECT-TYPE
	SYNTAX  Gauge32
	MAX-ACCESS  read-only
	STATUS  current
	DESCRIPTION
		"The number of packets per second transmitted out of the interface
		over a 5 minutes interval."
	::= { snPOSInfoEntry 30 }


snPOSStatsInUtilization OBJECT-TYPE
	SYNTAX  INTEGER (0..10000)
	MAX-ACCESS  read-only
	STATUS  current
	DESCRIPTION
		"The input network utilization in hundredths of a percent
		over a 5 minutes interval."
	::= { snPOSInfoEntry 31 }


snPOSStatsOutUtilization OBJECT-TYPE
	SYNTAX  INTEGER (0..10000)
	MAX-ACCESS  read-only
	STATUS  current
	DESCRIPTION
		"The output network utilization in hundredths of a percent
		over a 5 minutes interval."
	::= { snPOSInfoEntry 32 }

snPOSTagType OBJECT-TYPE
	SYNTAX  INTEGER {
		tagged(1),      
		untagged(2)    
		}
	MAX-ACCESS  read-only
	STATUS  current
	DESCRIPTION
		"For tagged port, we could have multiple VLANs 
		 per port."  
	::= {snPOSInfoEntry  33}

snPOSStatsB1 OBJECT-TYPE
	SYNTAX  Counter32
	MAX-ACCESS  read-only
	STATUS  current
	DESCRIPTION
		"Section error monitoring."
	::= { snPOSInfoEntry 34 }

snPOSStatsB2 OBJECT-TYPE
	SYNTAX  Counter32
	MAX-ACCESS  read-only
	STATUS  current
	DESCRIPTION
		"Line error monitoring."
	::= { snPOSInfoEntry 35 }

snPOSStatsB3 OBJECT-TYPE
	SYNTAX  Counter32
	MAX-ACCESS  read-only
	STATUS  current
	DESCRIPTION
		"Path error monitoring."
	::= { snPOSInfoEntry 36 }

snPOSStatsAIS OBJECT-TYPE
	SYNTAX  Counter32
	MAX-ACCESS  read-only
	STATUS  current
	DESCRIPTION
		"Alarm indication signal."
	::= { snPOSInfoEntry 37 }

snPOSStatsRDI OBJECT-TYPE
	SYNTAX  Counter32
	MAX-ACCESS  read-only
	STATUS  current
	DESCRIPTION
		"Remote defect indication."
	::= { snPOSInfoEntry 38 }

snPOSStatsLOP OBJECT-TYPE
	SYNTAX  Counter32
	MAX-ACCESS  read-only
	STATUS  current
	DESCRIPTION
		"Loss of pointer."
	::= { snPOSInfoEntry 39 }

snPOSStatsLOF OBJECT-TYPE
	SYNTAX  Counter32
	MAX-ACCESS  read-only
	STATUS  current
	DESCRIPTION
		"Loss of frame."
	::= { snPOSInfoEntry 40 }

snPOSStatsLOS OBJECT-TYPE
	SYNTAX  Counter32
	MAX-ACCESS  read-only
	STATUS  current
	DESCRIPTION
		"Loss of signal."
	::= { snPOSInfoEntry 41 }

-- POS Port table information

snPOSInfo2Table OBJECT-TYPE
	SYNTAX		SEQUENCE OF SnPOSInfo2Entry
	MAX-ACCESS		not-accessible
	STATUS		current
	DESCRIPTION
		"An snPOSInfo2Table consists of a number of 
		 SnPOSInfo2Entry entries"
	::= { snPOSInfo 2 }

snPOSInfo2Entry OBJECT-TYPE
	SYNTAX		SnPOSInfo2Entry
	MAX-ACCESS		not-accessible
	STATUS		current
	DESCRIPTION
		"An entry in the snPOSInfo2Table indicates the 
		 POS configuration on a specified port"
	INDEX {
		ifIndex 
	}
	::= { snPOSInfo2Table 1 }

SnPOSInfo2Entry ::= SEQUENCE {
	snPOSInfo2Clock
		INTEGER,
	snPOSInfo2ScrambleATM
		POSStatus,
	snPOSInfo2CRC
		INTEGER,
	snPOSInfo2KeepAlive
		Unsigned32,	
	snPOSInfo2FlagC2
		Unsigned32,		
	snPOSInfo2SSM
		INTEGER,
	snPOSInfo2Encapsulation
		INTEGER,
	snPOSInfo2AlarmMonitoring
		INTEGER,
	snPOSInfo2OverheadJ0ExpectedMessage
		OCTET STRING,
	snPOSInfo2OverheadJ0TransmitMessage
		OCTET STRING,
	snPOSInfo2OverheadJ1ExpectedMessage
		OCTET STRING,
	snPOSInfo2OverheadJ1MessageLength
		INTEGER,
	snPOSInfo2OverheadJ1TransmitMessage
		OCTET STRING
	}

snPOSInfo2Clock  OBJECT-TYPE
	SYNTAX		INTEGER {
		internal(1),
		line(2)
	}
	MAX-ACCESS		read-write
	STATUS		current
	DESCRIPTION
		"Clock source for the POS Interface
		 internal(1) - internal source
		 line    (2) - clocking is derived from line"
	DEFVAL		{ internal }
	::= { snPOSInfo2Entry 1 }

snPOSInfo2ScrambleATM  OBJECT-TYPE
	SYNTAX		POSStatus
	MAX-ACCESS		read-write
	STATUS		current
	DESCRIPTION
		"ATM style scrambling for the POS interface
		 disabled(0)  - scrambling is disabled
		 enabled(1)   - scrambling is enabled"
	DEFVAL		{ disabled }
	::= { snPOSInfo2Entry 2 }

snPOSInfo2CRC  OBJECT-TYPE
	SYNTAX		INTEGER {
		crc32bits(1),
		crc16bits(2)
	}
	MAX-ACCESS		read-write
	STATUS		current
	DESCRIPTION
		"Length of Cyclic Redundnacy Check (CRC) on the
		 POS interface
		 crc32bits(1)  - 32 bits
		 crc16bits(2)  - 16 buts"
	DEFVAL		{ crc32bits }
	::= { snPOSInfo2Entry 3 }

snPOSInfo2KeepAlive  OBJECT-TYPE
	SYNTAX		Unsigned32 (0..65535)
	MAX-ACCESS		read-write
	STATUS		current
	DESCRIPTION
		"Keep-alive timer for the POS interface in seconds"
	DEFVAL		{ 10 }
	::= { snPOSInfo2Entry 4 }

snPOSInfo2FlagC2  OBJECT-TYPE
	SYNTAX		Unsigned32 (0..255)
	MAX-ACCESS		read-write
	STATUS		current
	DESCRIPTION
		"C2 flag"
	::= { snPOSInfo2Entry 5 }

snPOSInfo2SSM OBJECT-TYPE
	SYNTAX		INTEGER {
		t1SonetPrimaryReferenceSource(1)		,
		t1SonetTraceabilityUnknown(2)			,
		t1SonetStratum2Traceable(3)				,
		t1SonetTransitNodeClock(4)				,
		t1SonetStratum3eTraceable(5)			,
		t1SonetStratum3Traceable(6)				,
		t1SonetMinClockTraceable(7)				,
		t1SonetDus(8)							,
		e1SdhTraceabilityUnknown(9)				,
		e1SdhSsmTransitNodeClockG812(10)		,
		e1SdhDus(11)							,
		e1SdhSsmPrimaryReferenceClockG811(12)	,
		e1SdhSsmLocalG812(13)					,
		e1SdhSsmSyncEquipmentTimingSource(14)
	}
	MAX-ACCESS		read-write
	STATUS		current
	DESCRIPTION
		"The S(ynchronization) S(tatus) M(essage) is sent over 
		 the SONET/SDH line to tell the other end about the 
		 quality of clock being sent over the line.
		 
		t1SonetPrimaryReferenceSource(1)		- SONET Primary Reference Source
		t1SonetTraceabilityUnknown(2}			- SONET Traceability Unknown
		t1SonetStratum2Traceable(3)				- SONET Stratum 2 Traceable
		t1SonetTransitNodeClock(4)				- SONET Transit Node Clock
		t1SonetStratum3eTraceable(5)			- SONET Stratum 3e Traceable
		t1SonetStratum3Traceable(6)				- SONET Stratum 3 Traceable
		t1SonetMinClockTraceable(7)				- SONET Minimum Clock Traceable
		t1SonetDus(8)							- SONET Do not Use for Synchronization
		e1SdhTraceabilityUnknown(9)				- SDH Traceability Unknown
		e1SdhSsmTransitNodeClockG812(10)		- SDH Transit Node Clock G812
		e1SdhDus(11)							- SDH Do not Use for Synchronization
		e1SdhSsmPrimaryReferenceClockG811(12)	- SDH Primary Reference Clock G811
		e1SdhSsmLocalG812(13)					- SDH Local G812
		e1SdhSsmSyncEquipmentTimingSource(14)	- SDH Synchronization Equipment Timing Source"
	DEFVAL		{ t1SonetTraceabilityUnknown }
	::= { snPOSInfo2Entry 6 }

snPOSInfo2Encapsulation OBJECT-TYPE
	SYNTAX		INTEGER {
		ppp(1),
		hdlc(2)
	}
	MAX-ACCESS		read-write
	STATUS		current
	DESCRIPTION
		"Layer 2 encapsulation on the POS interface
		 ppp(1)   - Point to Point Protocol (PPP)
		 hdlc(2)  - Cisco High-level Data Link Control (cHDLC)"
	DEFVAL		{ ppp }
	::= { snPOSInfo2Entry 7 }

snPOSInfo2AlarmMonitoring OBJECT-TYPE
	SYNTAX		INTEGER {
		off(0),
		on(1)
	}
	MAX-ACCESS		read-write
	STATUS		current
	DESCRIPTION
		"Alarm Monitoring on POS interface
		 off(0)    - Alarm Monitoring is off
		 on(1)     - Alarm Montioring is on"
	DEFVAL		{ on }
	::= { snPOSInfo2Entry 8 }

snPOSInfo2OverheadJ0ExpectedMessage OBJECT-TYPE
	SYNTAX		OCTET STRING (SIZE (1))
	MAX-ACCESS		read-write
	STATUS		current
	DESCRIPTION
		"Overhead J0 Expected Message"
	::= { snPOSInfo2Entry 9 }

snPOSInfo2OverheadJ0TransmitMessage OBJECT-TYPE
	SYNTAX		OCTET STRING (SIZE (1))
	MAX-ACCESS		read-write
	STATUS		current
	DESCRIPTION
		"Overhead J0 Transmit Message"
	::= { snPOSInfo2Entry 10 }

snPOSInfo2OverheadJ1ExpectedMessage OBJECT-TYPE
	SYNTAX		OCTET STRING (SIZE (16..64))
	MAX-ACCESS		read-write
	STATUS		current
	DESCRIPTION
		"Overhead J1 Expected Message"
	::= { snPOSInfo2Entry 11 }

snPOSInfo2OverheadJ1MessageLength OBJECT-TYPE
	SYNTAX		INTEGER {
		s16 (16),
		s64 (64)
	}
	MAX-ACCESS		read-write
	STATUS		current
	DESCRIPTION
		"Overhead J1 Length of Message
		 s16(16)...........16 bytes
		 s64(64)............64 bytes"  
	DEFVAL		{ s64 }
	::= { snPOSInfo2Entry 12 }

snPOSInfo2OverheadJ1TransmitMessage OBJECT-TYPE
	SYNTAX		OCTET STRING (SIZE (16..64))
	MAX-ACCESS		read-write
	STATUS		current
	DESCRIPTION
		"Overhead J1 Transmit Message"
	::= { snPOSInfo2Entry 13 }

-- POS PPP Group
-- If the L2 encapsulation is PPP, the following will provide 
-- information on the states of various control protocols

snPOSPPPTable OBJECT-TYPE
	SYNTAX		SEQUENCE OF SnPOSPPPEntry
	MAX-ACCESS		not-accessible
	STATUS		current
	DESCRIPTION
		"An snPOSPPPTable consists of a number of 
		 SnPOSPPPEntry entries"
	::= { snPOSInfo 3 }

snPOSPPPEntry OBJECT-TYPE
	SYNTAX		SnPOSPPPEntry
	MAX-ACCESS		not-accessible
	STATUS		current
	DESCRIPTION
		"An entry in the snPOSPPPTable indicates the 
		 PPP control protocol status on a specified port"
	INDEX  {
		ifIndex
	}
	::= { snPOSPPPTable 1 }
	
SnPOSPPPEntry ::= SEQUENCE {
	snPosPppLcp
		DisplayString,
	snPosPppIpCp
		DisplayString,
	snPosPppIpv6Cp
		DisplayString,
	snPosPppOsInLcp
		DisplayString,
	snPosPppMpLscp
		DisplayString
	}

snPosPppLcp  OBJECT-TYPE
	SYNTAX		DisplayString (SIZE(0..32))
	MAX-ACCESS		read-only
	STATUS		current
	DESCRIPTION
		"The PPP Link Control Protocol state"
	::= { snPOSPPPEntry 1 }

snPosPppIpCp  OBJECT-TYPE
	SYNTAX		DisplayString (SIZE(0..32))
	MAX-ACCESS		read-only
	STATUS		current
	DESCRIPTION
		"The PPP IP Control Protocol state"
	::= { snPOSPPPEntry 2 }

snPosPppIpv6Cp  OBJECT-TYPE
	SYNTAX		DisplayString (SIZE(0..32))
	MAX-ACCESS		read-only
	STATUS		current
	DESCRIPTION
		"The PPP IPv6 Control Protocol state"
	::= { snPOSPPPEntry 3 }

snPosPppOsInLcp  OBJECT-TYPE
	SYNTAX		DisplayString (SIZE(0..32))
	MAX-ACCESS		read-only
	STATUS		current
	DESCRIPTION
		"The PPP OSI Network Layer Control Protocol state"
	::= { snPOSPPPEntry 4 }

snPosPppMpLscp  OBJECT-TYPE
	SYNTAX		DisplayString (SIZE(0..32))
	MAX-ACCESS		read-only
	STATUS		current
	DESCRIPTION
		"The PPP MPLS Control Protocol state"
	::= { snPOSPPPEntry 5 }

-- POS cHDLC Group
-- If the L2 encapsulation is cHDLC, the following will provide 
-- information various cHDLC paraemters

snPOScHDLCTable OBJECT-TYPE
	SYNTAX		SEQUENCE OF SnPOScHDLCEntry
	MAX-ACCESS		not-accessible
	STATUS		current
	DESCRIPTION
		"An snPOScHDLCTable consists of a number of 
		 SnPOScHDLCEntry entries"
	::= { snPOSInfo 4 }

snPOScHDLCEntry OBJECT-TYPE
	SYNTAX		SnPOScHDLCEntry
	MAX-ACCESS		not-accessible
	STATUS		current
	DESCRIPTION
		"An entry in snPOScHDLCEntry shows the 
		 cHDLC information on a specified port"
	INDEX {
		ifIndex
	}
	::= { snPOScHDLCTable 1 }
	
SnPOScHDLCEntry ::= SEQUENCE {
	snPOScHDLCLineState
		INTEGER,
	snPOScHDLCInLoopback
		INTEGER,
	snPOScHDLCMySeq
		Unsigned32,
	snPOScHDLCMySeqSeen
		Unsigned32,
	snPOScHDLCPeerSeqSeen
		Unsigned32,
	snPOScHDLCUniqueSent
		Unsigned32,
	snPOScHDLCUniqueReceived
		Unsigned32
	}

snPOScHDLCLineState  OBJECT-TYPE
	SYNTAX		INTEGER {
		down (0),
		up (1),
		unknown (2)
		}
	MAX-ACCESS		read-only
	STATUS		current
	DESCRIPTION
		"cHDLC Line State"
	::= { snPOScHDLCEntry 1 }

snPOScHDLCInLoopback  OBJECT-TYPE
	SYNTAX		INTEGER {
		no (0),
		yes (1),
		unknown (2)
		}
	MAX-ACCESS		read-only
	STATUS		current
	DESCRIPTION
		"cHDLC in loopback"
	::= { snPOScHDLCEntry 2 }

snPOScHDLCMySeq  OBJECT-TYPE
	SYNTAX		Unsigned32
	MAX-ACCESS		read-only
	STATUS		current
	DESCRIPTION
		"cHDLC my sequence number"
	::= { snPOScHDLCEntry 3 }

snPOScHDLCMySeqSeen  OBJECT-TYPE
	SYNTAX		Unsigned32
	MAX-ACCESS		read-only
	STATUS		current
	DESCRIPTION
		"cHDLC my sequence number seen"
	::= { snPOScHDLCEntry 4 }

snPOScHDLCPeerSeqSeen  OBJECT-TYPE
	SYNTAX		Unsigned32
	MAX-ACCESS		read-only
	STATUS		current
	DESCRIPTION
		"cHDLC peer sequence number seen"
	::= { snPOScHDLCEntry 5 }

snPOScHDLCUniqueSent  OBJECT-TYPE
	SYNTAX		Unsigned32
	MAX-ACCESS		read-only
	STATUS		current
	DESCRIPTION
		"cHDLC unique sent"
	::= { snPOScHDLCEntry 6 }

snPOScHDLCUniqueReceived  OBJECT-TYPE
	SYNTAX		Unsigned32
	MAX-ACCESS		read-only
	STATUS		current
	DESCRIPTION
		"cHDLC unique received"
	::= { snPOScHDLCEntry 7 }

END
-- *****************************************************************
-- Commited Access Rate MIB file.
-- *****************************************************************
FOUNDRY-CAR-MIB DEFINITIONS ::= BEGIN

IMPORTS

	MODULE-IDENTITY, OBJECT-TYPE,Gauge32, Counter64,Integer32
		FROM SNMPv2-SMI
	TEXTUAL-CONVENTION
		FROM SNMPv2-TC
	snSwitch
		FROM FOUNDRY-SN-SWITCH-GROUP-MIB
	InterfaceIndex, ifIndex
		FROM IF-MIB;

snCAR MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"        
	REVISION     "200909300000Z" -- September 30, 2009
	DESCRIPTION
			"convert from SMIv1 to SMIv2"
   ::= { snSwitch 16}	
snPortCARs	OBJECT IDENTIFIER ::= { snCAR 1 }

	--  Textual Conventions

	PacketSource::= TEXTUAL-CONVENTION 
	STATUS      current 
	DESCRIPTION 
		"
		"
	SYNTAX  INTEGER { 
		input(0), --for inbound traffic
		output(1) --for outbound traffic
	}
	

	RateLimitType::= TEXTUAL-CONVENTION 
	STATUS      current 
	DESCRIPTION 
		"
		"
	SYNTAX   INTEGER{ 
		all(3), 		--	all traffic.                             
		quickAcc(2), 	--	traffic matches rate-limit's access list.
		standardAcc(1) 	--	traffic matches standard access list.    
	}

	RateLimitAction::= TEXTUAL-CONVENTION 
	STATUS      current 
	DESCRIPTION 
		"
		"
	SYNTAX  INTEGER {
		continue(1), 
		drop(2), 
		precedCont(3),
		precedXmit(4), 
		xmit(5) 
	}


snPortCARTable OBJECT-TYPE
	SYNTAX  SEQUENCE OF SnPortCAREntry
	MAX-ACCESS  not-accessible
		STATUS  current
		DESCRIPTION
		"A table of rate limit configuration entries.
	Rate Limit is a method of traffic control.  It allows a set
	of rate limits to be configured and applied to packets flowing
	into/out of an interface to regulate network traffic."

		::= { snPortCARs 1 }

snPortCAREntry OBJECT-TYPE
		SYNTAX SnPortCAREntry
		MAX-ACCESS  not-accessible
		STATUS  current
		DESCRIPTION
			"A collection of rate-limit configuration objects on this 
		interface."
		INDEX { snPortCARifIndex, snPortCARDirection, snPortCARRowIndex }
		::= { snPortCARTable 1 }

SnPortCAREntry ::=
	SEQUENCE {
		snPortCARifIndex
						InterfaceIndex,
		snPortCARDirection
					PacketSource,
		snPortCARRowIndex
						INTEGER,
		snPortCARType
						RateLimitType,
		snPortCARAccIdx
						Integer32,
		snPortCARRate
						Integer32,
		snPortCARLimit
						Integer32,
		snPortCARExtLimit
						Integer32,
		snPortCARConformAction
						RateLimitAction,
		snPortCARExceedAction
						RateLimitAction,
		snPortCARStatSwitchedPkts
						Counter64,
		snPortCARStatSwitchedBytes
						Counter64,
		snPortCARStatFilteredPkts
						Counter64,
		snPortCARStatFilteredBytes
						Counter64,
		snPortCARStatCurBurst
						Gauge32
	}
snPortCARifIndex OBJECT-TYPE
	SYNTAX     InterfaceIndex 
	MAX-ACCESS     read-only
	STATUS     current
	DESCRIPTION
			"The ifIndex value for this rate limit entry."
	::= { snPortCAREntry 1 }

snPortCARDirection OBJECT-TYPE
	SYNTAX  PacketSource
		MAX-ACCESS  read-only
		STATUS  current
		DESCRIPTION
			"The input or output transmission direction for the 
				Rate Limit object.
				input (0), --for inbound traffic
				output(1) --for outbound traffic "
		::= { snPortCAREntry 2 }

snPortCARRowIndex OBJECT-TYPE
	SYNTAX  INTEGER (1..2147483647)
		MAX-ACCESS  read-only
		STATUS  current
		DESCRIPTION
				"The table index for rate limit objects.
		It increases as the rate limit entries are added.
		Skips the number when a row is deleted."

		::= { snPortCAREntry 3 }

snPortCARType OBJECT-TYPE
	SYNTAX  RateLimitType
		MAX-ACCESS  read-only
		STATUS  current
		DESCRIPTION
		"The type of traffic rate-limited against."

	::= { snPortCAREntry 4 }

snPortCARAccIdx OBJECT-TYPE
	SYNTAX  Integer32
		MAX-ACCESS  read-only
		STATUS  current
		DESCRIPTION
		"The index to the access list if RateLimitType is either
		quickAcc or standardAcc."

	::= { snPortCAREntry 5 }

snPortCARRate OBJECT-TYPE
	SYNTAX  Integer32
		MAX-ACCESS  read-only
		STATUS  current
		DESCRIPTION
		"The comitted access rate. This determines the long term
		average transmission rate. Traffic that falls under this
		rate always conforms. This is average rate in bits per 
		second."

	::= { snPortCAREntry 6 }

snPortCARLimit OBJECT-TYPE
	SYNTAX  Integer32
		MAX-ACCESS  read-only
		STATUS  current
		DESCRIPTION
		"This is the normal burst size that determines how large traffic
		bursts can be before some traffic exceeds the rate limit. This
		specifies the number of bytes that are guaranteed to be transported
		by the network at the average rate under normal conditions during
		committed time interval. This normal burst size is in bytes."

	::= { snPortCAREntry 7 }

snPortCARExtLimit OBJECT-TYPE
	SYNTAX  Integer32
	MAX-ACCESS  read-only
	STATUS  current
	DESCRIPTION
		"This is the extended burst limit that determines how large traffic
		bursts can be before all the traffic exceeds the rate limit. This
		burst size is in bytes."

	::= { snPortCAREntry 8 }

snPortCARConformAction OBJECT-TYPE
	SYNTAX	RateLimitAction
	MAX-ACCESS  read-only
	STATUS	current
	DESCRIPTION
		"Action to be taken when the traffic is within
		the Rate Limit.
		drop		drop the packet.
		xmit		transmit the packet.
		continue	continue to evaluate to the subsequent
					rate limits.
		precedXmit	rewrite the IP precedence and transmit
					the packet.
		precedCont	rewrite the IP precedence and allow it
					evaluated by subsequent rate limits."

	::= { snPortCAREntry 9 }

snPortCARExceedAction OBJECT-TYPE
	SYNTAX	RateLimitAction
	MAX-ACCESS  read-only
	STATUS	current
	DESCRIPTION
		"Action to be taken when the traffic exceeds
		the Rate Limit.drop		
		drop the packet.
		xmit		transmit the packet.
		continue	continue to evaluate to the subsequent
					rate limits.
		precedXmit	rewrite the IP precedence and transmit
					the packet.
		precedCont	rewrite the IP precedence and allow it
					evaluated by subsequent rate limits."

	::= { snPortCAREntry 10 }

snPortCARStatSwitchedPkts OBJECT-TYPE
	SYNTAX  Counter64
	MAX-ACCESS  read-only
	STATUS  current
	DESCRIPTION
		"The counter of packets permitted by this rate limit."

	::= { snPortCAREntry 11 }

snPortCARStatSwitchedBytes OBJECT-TYPE
	SYNTAX  Counter64
	MAX-ACCESS  read-only
	STATUS  current
	DESCRIPTION
		"The counter of bytes permitted by this interface."

	::= { snPortCAREntry 12 }

snPortCARStatFilteredPkts OBJECT-TYPE
	SYNTAX  Counter64
	--UNITS	"packets"
	MAX-ACCESS  read-only
	STATUS  current
	DESCRIPTION
		"The counter of packets which exceeded this rate limit."

	::= { snPortCAREntry 13 }

snPortCARStatFilteredBytes OBJECT-TYPE
	SYNTAX  Counter64
	MAX-ACCESS  read-only
	STATUS  current
	DESCRIPTION
		"The counter of bytes which exceeded this rate limit."

	::= { snPortCAREntry 14 }

snPortCARStatCurBurst OBJECT-TYPE
	SYNTAX  Gauge32
	MAX-ACCESS  read-only
	STATUS  current
	DESCRIPTION
		"The current received burst size."
	::= { snPortCAREntry 15 }

-- end of snPortCARTable

-- RL Counter Table

agRateLimitCounterTable OBJECT-TYPE
	SYNTAX		SEQUENCE OF AgRateLimitCounterEntry
	MAX-ACCESS		not-accessible
	STATUS		current
	DESCRIPTION
	"A table of rate limit counter entries."
	::= { snPortCARs 2 }

agRateLimitCounterEntry OBJECT-TYPE
	SYNTAX		AgRateLimitCounterEntry
	MAX-ACCESS		not-accessible
	STATUS		current
	DESCRIPTION
	"A collection of rate-limit counter objects on a
	interface, direction and configuration row index within that interface."
	INDEX { ifIndex, snPortCARRowIndex }
	::= { agRateLimitCounterTable 1 }

AgRateLimitCounterEntry ::=
	SEQUENCE {
		agRateLimitCounterFwdedOctets
			Counter64,
		agRateLimitCounterDroppedOctets
			Counter64,
		agRateLimitCounterReMarkedOctets
			Counter64,
		agRateLimitCounterTotalOctets
			Counter64
	}

agRateLimitCounterFwdedOctets OBJECT-TYPE
	SYNTAX	Counter64
	MAX-ACCESS	read-only
	STATUS	current
	DESCRIPTION
	"The forwarded octet count for this rate limit entry."
	::= { agRateLimitCounterEntry 1 }

agRateLimitCounterDroppedOctets OBJECT-TYPE
	SYNTAX	Counter64
	MAX-ACCESS	read-only
	STATUS	current
	DESCRIPTION
	"The dropped octet count for this rate limit entry."
	::= { agRateLimitCounterEntry 2 }

agRateLimitCounterReMarkedOctets OBJECT-TYPE
	SYNTAX	Counter64
	MAX-ACCESS	read-only
	STATUS	current
	DESCRIPTION
	"The remarked octet count for this rate limit entry."
	::= { agRateLimitCounterEntry 3 }

agRateLimitCounterTotalOctets OBJECT-TYPE
	SYNTAX	Counter64
	MAX-ACCESS	read-only
	STATUS	current
	DESCRIPTION
	"The total octet count for this rate limit entry."
	::= { agRateLimitCounterEntry 4 }

END
-- *****************************************************************
-- Foundry Commited Access Rate MIB file.
-- *****************************************************************
FOUNDRY-VLAN-CAR-MIB DEFINITIONS ::= BEGIN

IMPORTS

	MODULE-IDENTITY, OBJECT-TYPE,Gauge32, Counter64,Integer32 
		FROM SNMPv2-SMI
	snSwitch
		FROM FOUNDRY-SN-SWITCH-GROUP-MIB
	PacketSource, RateLimitType, RateLimitAction
		FROM FOUNDRY-CAR-MIB; 



snVLanCAR MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"            
	REVISION     "200909300000Z" -- September 30, 2009
	DESCRIPTION
			"convert from SMIv1 to SMIv2"
   ::= {snSwitch  17}	
snVLanCARs	OBJECT IDENTIFIER ::= { snVLanCAR 1 }



snVLanCARTable OBJECT-TYPE
	SYNTAX  SEQUENCE OF SnVLanCAREntry
	MAX-ACCESS  not-accessible
		STATUS  current
		DESCRIPTION
		"A table of rate limit configuration entries for a vlan.
	Rate Limit is a method of traffic control.  It allows a set
	of rate limits to be configured and applied to packets flowing
	into/out of an interface to regulate network traffic."

		::= { snVLanCARs 1 }


snVLanCAREntry OBJECT-TYPE
		SYNTAX SnVLanCAREntry
		MAX-ACCESS  not-accessible
		STATUS  current
		DESCRIPTION
			"A collection of rate-limit configuration objects on this 
		vlan."
		INDEX { snVLanCARVLanId, snVLanCARDirection, snVLanCARRowIndex }
		::= { snVLanCARTable 1 }

SnVLanCAREntry ::=
	SEQUENCE {
		snVLanCARDirection
					PacketSource,
		snVLanCARVLanId
						INTEGER,
		snVLanCARRowIndex
						INTEGER,
		snVLanCARType
						RateLimitType,
		snVLanCARAccIdx
						Integer32,
		snVLanCARRate
						Integer32,
		snVLanCARLimit
						Integer32,
		snVLanCARExtLimit
						Integer32,
		snVLanCARConformAction
			RateLimitAction,
		snVLanCARExceedAction
				RateLimitAction,
		snVLanCARStatSwitchedPkts
						Counter64,
		snVLanCARStatSwitchedBytes
						Counter64,
		snVLanCARStatFilteredPkts
						Counter64,
		snVLanCARStatFilteredBytes
						Counter64,
		snVLanCARStatCurBurst
				Gauge32
	}

--need to refer to the vlan table
--index once it is changed to single
--vlan id as the row index

snVLanCARVLanId OBJECT-TYPE
	SYNTAX  INTEGER (1..4095)
	MAX-ACCESS  read-only
	STATUS  current
	DESCRIPTION
		"The VLAN ID as one of the indices of this table .
		 Each VLAN ID can have a membership of multiple 
		 ports."
	::= { snVLanCAREntry 1 }

snVLanCARDirection OBJECT-TYPE
	SYNTAX  PacketSource
		MAX-ACCESS  read-only
		STATUS  current
		DESCRIPTION
			"The input or output transmission direction for the 
				Rate Limit object."
		::= { snVLanCAREntry 2 }

snVLanCARRowIndex OBJECT-TYPE
	SYNTAX  INTEGER (1..2147483647)
		MAX-ACCESS  read-only
		STATUS  current
		DESCRIPTION
				"The table index for rate limit objects.
		It increases as the rate limit entries are added.
		Skips the number when a row is deleted."

		::= { snVLanCAREntry 3 }

snVLanCARType OBJECT-TYPE
	SYNTAX  RateLimitType
		MAX-ACCESS  read-only
		STATUS  current
		DESCRIPTION
		"The type of traffic rate-limited against."

	::= { snVLanCAREntry 4 }

snVLanCARAccIdx OBJECT-TYPE
	SYNTAX  Integer32
		MAX-ACCESS  read-only
		STATUS  current
		DESCRIPTION
		"The index to the access list if RateLimitType is either
		quickAcc or standardAcc."

	::= { snVLanCAREntry 5 }

snVLanCARRate OBJECT-TYPE
	SYNTAX  Integer32
		MAX-ACCESS  read-only
		STATUS  current
		DESCRIPTION
		"The comitted access rate. This determines the long term
		average transmission rate. Traffic that falls under this
		rate always conforms. This is average rate in bits per 
		second."

	::= { snVLanCAREntry 6 }

snVLanCARLimit OBJECT-TYPE
	SYNTAX  Integer32
		MAX-ACCESS  read-only
		STATUS  current
		DESCRIPTION
		"This is the normal burst size that determines how large traffic
		bursts can be before some traffic exceeds the rate limit. This
		specifies the number of bytes that are guaranteed to be transported
		by the network at the average rate under normal conditions during
		committed time interval. This normal burst size is in bytes."

	::= { snVLanCAREntry 7 }

snVLanCARExtLimit OBJECT-TYPE
	SYNTAX  Integer32
	MAX-ACCESS  read-only
	STATUS  current
	DESCRIPTION
		"This is the extended burst limit that determines how large traffic
		bursts can be before all the traffic exceeds the rate limit. This
		burst size is in bytes. "

	::= { snVLanCAREntry 8 }

snVLanCARConformAction OBJECT-TYPE
	SYNTAX	RateLimitAction
	MAX-ACCESS  read-only
	STATUS	current
	DESCRIPTION
		"Action to be taken when the traffic is within
		the Rate Limit.
		drop		drop the packet.
		xmit		transmit the packet.
		continue	continue to evaluate to the subsequent
					rate limits.
		precedXmit	rewrite the IP precedence and transmit
					the packet.
		precedCont	rewrite the IP precedence and allow it
					evaluated by subsequent rate limits."

	::= { snVLanCAREntry 9 }

snVLanCARExceedAction OBJECT-TYPE
	SYNTAX	RateLimitAction
	MAX-ACCESS  read-only
	STATUS	current
	DESCRIPTION
		"Action to be taken when the traffic exceeds
		the Rate Limit.
		drop		drop the packet.
		xmit		transmit the packet.
		continue	continue to evaluate to the subsequent
					rate limits.
		precedXmit	rewrite the IP precedence and transmit
					the packet.
		precedCont	rewrite the IP precedence and allow it
					evaluated by subsequent rate limits."

	::= { snVLanCAREntry 10 }

snVLanCARStatSwitchedPkts OBJECT-TYPE
	SYNTAX  Counter64
	MAX-ACCESS  read-only
	STATUS  current
	DESCRIPTION
		"The counter of packets permitted by this rate limit."

	::= { snVLanCAREntry 11 }

snVLanCARStatSwitchedBytes OBJECT-TYPE
	SYNTAX  Counter64
	MAX-ACCESS  read-only
	STATUS  current
	DESCRIPTION
		"The counter of bytes permitted by this interface."

	::= { snVLanCAREntry 12 }

snVLanCARStatFilteredPkts OBJECT-TYPE
	SYNTAX  Counter64
	--UNITS	"packets"
	MAX-ACCESS  read-only
	STATUS  current
	DESCRIPTION
		"The counter of packets which exceeded this rate limit."

	::= { snVLanCAREntry 13 }

snVLanCARStatFilteredBytes OBJECT-TYPE
	SYNTAX  Counter64
	MAX-ACCESS  read-only
	STATUS  current
	DESCRIPTION
		"The counter of bytes which exceeded this rate limit."

	::= { snVLanCAREntry 14 }

snVLanCARStatCurBurst OBJECT-TYPE
	SYNTAX  Gauge32
	MAX-ACCESS  read-only
	STATUS  current
	DESCRIPTION
		"The current received burst size."
	::= { snVLanCAREntry 15 }

-- end of snVLanCARTable


END
FOUNDRY-SN-IP-ACL-MIB DEFINITIONS ::= BEGIN

IMPORTS
	MODULE-IDENTITY, OBJECT-TYPE,IpAddress,Counter64, Unsigned32,Integer32
		FROM SNMPv2-SMI
	DisplayString, MacAddress, TruthValue, RowStatus, TEXTUAL-CONVENTION
		FROM SNMPv2-TC
	router
		FROM FOUNDRY-SN-ROOT-MIB
	InterfaceIndex, ifIndex
		FROM IF-MIB
	RtrStatus
		FROM FOUNDRY-SN-IP-MIB
	PortQosTC, FdryVlanIdOrNoneTC
		FROM FOUNDRY-SN-SWITCH-GROUP-MIB;
		
snAgAcl MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"            
	REVISION     "200909300000Z" -- September 30, 2009
	DESCRIPTION
			""
   ::= {router 2 15}

	--  Textual Conventions
	
	SnRowStatus ::= TEXTUAL-CONVENTION 
	STATUS      current 
	DESCRIPTION 
		"The status of a given row in the table."
	SYNTAX  INTEGER {other(1), valid(2), delete(3), create(4)}

	Action ::= TEXTUAL-CONVENTION 
	STATUS      current 
	DESCRIPTION 
		"The action to be taken on the packet after filtering is done."
	SYNTAX  INTEGER { deny(0), permit(1) }

	TruthVal ::= TEXTUAL-CONVENTION 
	STATUS      current 
	DESCRIPTION 
		"Boolean value."
	SYNTAX  INTEGER { false (0), true (1)  }

	FdryClauseIndexTC ::= TEXTUAL-CONVENTION 
	STATUS      current 
	DESCRIPTION 
		"One-based clause index value within a given ACL number."
	SYNTAX  Unsigned32

	AclNumber ::= TEXTUAL-CONVENTION 
	STATUS      current 
	DESCRIPTION 
		"The Access control list number for an entry.
		The standard Access list is in the range <1..99>.
		The extended Access list is in the range <100-199>.
		The named standard Access list is in the range <200..299>.
		The named extended Access list is in the range <300-399>.
		The L2 Access list is in the range <400-499>."
	SYNTAX  INTEGER (1..499)

	AclNameString ::= TEXTUAL-CONVENTION 
	STATUS      current 
	DESCRIPTION 
		"The optional name for a given access-list. In general, the ACL number
		for a named ACL is in the range of 200 and 399."
	SYNTAX  OCTET STRING (SIZE (0..255))

	Operator ::= TEXTUAL-CONVENTION 
	STATUS      current 
	DESCRIPTION 
		"The operation used within a given ACL filter to determine permit or deny."
	SYNTAX  INTEGER { eq(0), neq(1), lt(2), gt(3), range(4), undefined(7) }

	IpProtocol ::= TEXTUAL-CONVENTION 
	STATUS      current 
	DESCRIPTION 
		"The IP protocol number on which ACL can be applied.
		0=IP, 1=ICMP, 2=IGMP, 6=TCP, 17=UDP, 88=IGRP, 89=OSPF"
	SYNTAX  INTEGER {ip(0), icmp(1), igmp(2), tcp(6), udp(17), igrp(88), ospf(89)}

	PrecedenceValue ::= TEXTUAL-CONVENTION 
	STATUS      current 
	DESCRIPTION 
		"The IP precedence value on which ACL can be applied."
	SYNTAX  INTEGER {
				routine(0),
				priority(1),
				immediate(2), 
				flash(3),
				flashoverride(4),
				critical(5),
				internet(6),
				network(7),
				undefined(8)
				}

	TosValue ::= TEXTUAL-CONVENTION 
	STATUS      current 
	DESCRIPTION 
		"The IP TOS value on which ACL can be applied."
	SYNTAX  INTEGER {
				normal(0),
				minMonetaryCost(1),
				maxReliability(2),
				tosValue3(3),
				maxThroughput(4),
				tosValue5(5),
				tosValue6(6),
				tosValue7(7),
				minDelay(8),
				tosValue9(9),
				tosValue10(10),
				tosValue11(11),
				tosValue12(12),
				tosValue13(13),
				tosValue14(14),
				tosValue15(15),
				undefined(16)
			}

	Direction ::= TEXTUAL-CONVENTION 
	STATUS      current 
	DESCRIPTION 
		"The packet flow direction within an interface for which ACL needs to be applied."
	SYNTAX  INTEGER { inbound(0), outbound(1) }

	FdryEnetTypeOrZeroTC ::= TEXTUAL-CONVENTION
	STATUS		current
	DESCRIPTION
		"Ethernet Type field within the Ethernet-II frame"
	SYNTAX	INTEGER {
				invalid(0),
				ipv4(1),
				arp(2),
				ipv6(3)
			}



snAgAclGlobal	OBJECT IDENTIFIER ::= { snAgAcl 1 }

snAgAclGblCurRowIndex	OBJECT-TYPE
	SYNTAX				Integer32
	MAX-ACCESS			read-only
	STATUS				current
	DESCRIPTION
		"The current row index of the ACL table entry."
	::= { snAgAclGlobal 1 }

--
-- ACL Table
--
snAgAclTable	OBJECT-TYPE
	SYNTAX		SEQUENCE OF SnAgAclEntry
	MAX-ACCESS	not-accessible
	STATUS		current
	DESCRIPTION
		"Table of Access Control List"
	::= { snAgAcl 2 }

snAgAclEntry	OBJECT-TYPE
	SYNTAX		SnAgAclEntry
	MAX-ACCESS	not-accessible
	STATUS		current
	DESCRIPTION
		"An entry in the IP access control list table."
	INDEX   { snAgAclIndex }
	::= { snAgAclTable 1 }

SnAgAclEntry ::= SEQUENCE {
	snAgAclIndex
		Integer32,
	snAgAclNumber
		AclNumber,
	snAgAclName
		DisplayString,
	snAgAclAction              
		Action,
	snAgAclProtocol            
		IpProtocol,
	snAgAclSourceIp
		IpAddress,
	snAgAclSourceMask
		IpAddress,
	snAgAclSourceOperator
		Operator,
	snAgAclSourceOperand1
		INTEGER,
	snAgAclSourceOperand2
		INTEGER,
	snAgAclDestinationIp
		IpAddress,
	snAgAclDestinationMask
		IpAddress,
	snAgAclDestinationOperator
		Operator,
	snAgAclDestinationOperand1
		INTEGER,
	snAgAclDestinationOperand2
		INTEGER,
	snAgAclPrecedence
		PrecedenceValue,
	snAgAclTos
		TosValue,
	snAgAclEstablished
		RtrStatus,
	snAgAclLogOption
		TruthVal,
	snAgAclStandardFlag
		TruthVal,
	snAgAclRowStatus
		SnRowStatus,
	snAgAclFlowCounter
		Counter64,
	snAgAclPacketCounter
		Counter64,
	snAgAclComments
		DisplayString,
	snAgAclIpPriority
		INTEGER,
	snAgAclPriorityForce
		INTEGER,
	snAgAclPriorityMapping
		INTEGER,
	snAgAclDscpMarking
		INTEGER,
	snAgAclDscpMapping
		INTEGER,
	snAgAclIcmpCode
		INTEGER,
	snAgAclParameters
		BITS
	}

snAgAclIndex	OBJECT-TYPE
	SYNTAX		Integer32
	MAX-ACCESS	read-only
	STATUS		current
	DESCRIPTION
		"The Access control list item number for an entry. This is a unique
		 number that identifies different Access list entries combined with
		 the Access list name and Access list number. This one has to be
		 unique even though the name and number are not unique for a given
		 Access list with same or different source address, subnet mask,
		 destination address and destination mask, protocol type, action
		 (permit/deny) type and the operator (neq, eq, gt and, lt) which
		 makes the index a unique tuple (name, number, itemnumber)."
	::= { snAgAclEntry 1 }

snAgAclNumber	OBJECT-TYPE
	SYNTAX		AclNumber
	MAX-ACCESS	read-write
	STATUS		current
	DESCRIPTION
		"The access-list number for this entry."
	::= { snAgAclEntry 2 }

snAgAclName		OBJECT-TYPE
	SYNTAX		DisplayString
	MAX-ACCESS  read-write
	STATUS		current
	DESCRIPTION
		"ACL name for an entry."
	::= { snAgAclEntry 3 }

snAgAclAction	OBJECT-TYPE
	SYNTAX		Action 
	MAX-ACCESS  read-write
	STATUS		current
	DESCRIPTION
		"Action to take if the ip packet matches with this access control list."
	::= { snAgAclEntry 4 }

snAgAclProtocol	OBJECT-TYPE
	SYNTAX		IpProtocol
	MAX-ACCESS  read-write
	STATUS		current
	DESCRIPTION
		"Transport protocol. 0 means any IP protocol."
	::= { snAgAclEntry 5 }

snAgAclSourceIp OBJECT-TYPE
	SYNTAX		IpAddress
	MAX-ACCESS  read-write
	STATUS		current
	DESCRIPTION
		"Source IP address."
	::= { snAgAclEntry 6 }

snAgAclSourceMask	OBJECT-TYPE
	SYNTAX		IpAddress
	MAX-ACCESS	read-write
	STATUS		current
	DESCRIPTION
		"Source IP subnet mask."
	::= { snAgAclEntry 7 }

snAgAclSourceOperator	OBJECT-TYPE
	SYNTAX		Operator
	MAX-ACCESS	read-write
	STATUS		current
	DESCRIPTION
		"Type of comparison to perform.	For now, this only applys to tcp or udp
		to compare the port number"
	::= { snAgAclEntry 8 }

snAgAclSourceOperand1	OBJECT-TYPE
	SYNTAX		INTEGER(0..65535)
	MAX-ACCESS  read-write
	STATUS		current
	DESCRIPTION
		"For now this only refers to transport protocol port number. 0 means NA"
	::= { snAgAclEntry 9 }

snAgAclSourceOperand2	OBJECT-TYPE
	SYNTAX		INTEGER(0..65535)
	MAX-ACCESS  read-write
	STATUS		current
	DESCRIPTION
		"For now this only refers to transport protocol port number.
		 Used in ICMP Protocol to convey the ICMP Type
		 value. 0 means NA.
		 Valid values for ICMP Type:
		 1 = Echo reply
		 4 = Destination unreachable
		 5 = Source quench
		 6 = Redirect
		 9 = Echo request
		 10=Router advertisement
		 11=Router solicitation
		 12=Time exceeded
		 13=Parameter problem
		 14=Timestamp request
		 15=Timestamp reply
		 16=Information request
		 17=Information reply
		 18=Address mask request
		 19=Address mask reply.
		 "
	::= { snAgAclEntry 10 }

snAgAclDestinationIp	OBJECT-TYPE
	SYNTAX		IpAddress
	MAX-ACCESS  read-write
	STATUS		current
	DESCRIPTION
		"Destination IP address."
	::= { snAgAclEntry 11 }

snAgAclDestinationMask	OBJECT-TYPE
	SYNTAX		IpAddress
	MAX-ACCESS  read-write
	STATUS		current
	DESCRIPTION
		"Destination IP subnet mask."
	::= { snAgAclEntry 12 }

snAgAclDestinationOperator	OBJECT-TYPE
	SYNTAX		Operator
	MAX-ACCESS  read-write
	STATUS		current
	DESCRIPTION
		"Type of comparison to perform. For now, this only applys to tcp or udp
		to compare the port number"
	::= { snAgAclEntry 13 }

snAgAclDestinationOperand1	OBJECT-TYPE
	SYNTAX		INTEGER(0..65535)
	MAX-ACCESS  read-write
	STATUS		current
	DESCRIPTION
		"For now this only refers to transport protocol port number. 0 means NA"
	::= { snAgAclEntry 14 }

snAgAclDestinationOperand2	OBJECT-TYPE
	SYNTAX		INTEGER(0..65535)
	MAX-ACCESS  read-write
	STATUS		current
	DESCRIPTION
		"For now this only refers to transport protocol port number. 0 means NA"
	::= { snAgAclEntry 15 }

snAgAclPrecedence	OBJECT-TYPE
	SYNTAX		PrecedenceValue
	MAX-ACCESS	read-write
	STATUS		current
	DESCRIPTION
		"This refers to IP precedence value in the range <0-7>
		critical(5), 
		flash(3), 
		flash-override(4), 
		immediate(2), 
		internet(6), 
		network(7), 
		priority(1), 
		routine(0)"
		::= { snAgAclEntry 16 }

snAgAclTos		OBJECT-TYPE
	SYNTAX		TosValue
	MAX-ACCESS  read-write
	STATUS		current
	DESCRIPTION
		"This refers to the IP type of service value in range <0-15>, which is
		 the sum of numeric vlaues of the following options -
		match packets with maximum reliability TOS (2)
		match packets with maximum throughput TOS (4)
		match packets with minimum delay (8)
		match packets with minimum monetary cost TOS (1)
		match packets with normal TOS  (0)"
		::= { snAgAclEntry 17 }

snAgAclEstablished OBJECT-TYPE
	SYNTAX		RtrStatus
	MAX-ACCESS  read-write
	STATUS		current
	DESCRIPTION
		"Enable/Disable the filtering of established TCP packets of which the
		 ACK or RESET flag is on. This additional filter only applies to TCP
		 transport protocol."
	::= { snAgAclEntry 18 }

snAgAclLogOption OBJECT-TYPE
	SYNTAX		TruthVal
	MAX-ACCESS  read-write
	STATUS		current
	DESCRIPTION
		"Log flag"
	::= { snAgAclEntry 19 }

snAgAclStandardFlag OBJECT-TYPE
	SYNTAX		TruthVal
	MAX-ACCESS  read-write
	STATUS		current
	DESCRIPTION
		"Return whether the ACL is standard or extended, 1 for standard ACL"
	::= { snAgAclEntry 20 }

snAgAclRowStatus   OBJECT-TYPE
	SYNTAX		SnRowStatus
	MAX-ACCESS  read-write
	STATUS		current
	DESCRIPTION
		"To create or delete a access list entry."
	::= { snAgAclEntry 21 }

snAgAclFlowCounter   OBJECT-TYPE
	SYNTAX		Counter64
	MAX-ACCESS  read-only
	STATUS		current
	DESCRIPTION
		"Approximate count of flows matching individual ACL entry."
	::= { snAgAclEntry 22 }

snAgAclPacketCounter   OBJECT-TYPE
	SYNTAX		Counter64
	MAX-ACCESS  read-only
	STATUS		current
	DESCRIPTION
		"Accurate count of packets matching individual ACL entry."
	::= { snAgAclEntry 23 }

snAgAclComments   OBJECT-TYPE
	SYNTAX		DisplayString
	MAX-ACCESS  read-write
	STATUS		current
	DESCRIPTION
		"Remark description of individual ACL entry."
	::= { snAgAclEntry 24 }

snAgAclIpPriority   OBJECT-TYPE
	SYNTAX		INTEGER(0..3)
	MAX-ACCESS  read-write
	STATUS		current
	DESCRIPTION
		"QoS priority option for IP ACL entry."
	::= { snAgAclEntry 25 }

snAgAclPriorityForce   OBJECT-TYPE
	SYNTAX		INTEGER(0..4)
	MAX-ACCESS  read-write
	STATUS		current
	DESCRIPTION
		"Force packet outgoing priority.  Not defined(4)"
	::= { snAgAclEntry 26 }

snAgAclPriorityMapping   OBJECT-TYPE
	SYNTAX		INTEGER(0..8)
	MAX-ACCESS  read-write
	STATUS		current
	DESCRIPTION
		"Map incoming packet priority. Not defined(8)"
	::= { snAgAclEntry 27 }

snAgAclDscpMarking   OBJECT-TYPE
	SYNTAX		INTEGER(0..64)
	MAX-ACCESS  read-write
	STATUS		current
	DESCRIPTION
		"Mark packets with given DSCP value.  Not defined(64)"
	::= { snAgAclEntry 28 }

snAgAclDscpMapping   OBJECT-TYPE
	SYNTAX		INTEGER(0..64)
	MAX-ACCESS  read-write
	STATUS		current
	DESCRIPTION
		"Map incoming DSCP value.  Not defined(64)"
	::= { snAgAclEntry 29 }

snAgAclIcmpCode   OBJECT-TYPE
	SYNTAX		INTEGER(0..255)
	MAX-ACCESS  read-write
	STATUS		current
	DESCRIPTION
		"ICMP Message Code value. Used in combination with
		ICMP Message Type (use snAgAclSourceOperand2) to
		setup an ICMP filter. This object is not used with any
		other protocol. 0 means NA.
		Supported values
		Type: Echo reply
		--------------
		1 = Echo reply
		Type: Destination unreachable
		-------------------------
		1 = Network unreachable
		2 = Host unreachable
		3 = Protocol unreachable
		4 = Port unreachable
		5 = Fragmentation needed by don't fragment bit set
		6 = Source route failed
		7 = Destination network unknown
		8 = Destination host unknown
		9 = Source host isolated
		10 = Destination network administratively prohibited
		11=Destination host administratively prohibited
		12=Network unreachable for TOS
		13=Host unreachable for TOS
		14=Communication administratively prohibited by filter
		15=Host precedence violation
		16=Precedence cutoff in effect
		Type: Source quench
		------------------
		1 = Source quench
		Type: Redirect
		------------
		1 = Redirect for network
		2 = Redirect for host
		3 = Redirect for TOS and network
		4 = Redirect for TOS and host
		Type: Echo request
		-----------------
		1 = Echo request
		Type: Router advertisement
		------------------------
		1 = Router advertisement
		Type: Router solicitation
		---------------------
		1 = Router solicitation
		Type: Time exceeded
		------------------
		1 = Time to live equals 0 during transmit
		2 = Time to live equals 0 during reassembly
		Type: Parameter problem
		---------------------
		1 = IP header bad (catchall error)
		2 = Required option missing
		Type: Timestamp request
		----------------------
		1 = Timestamp request
		Type: Timestamp reply
		-------------------
		1 = Timestamp reply
		Type: Information request
		----------------------
		1 = Information request
		Type: Information reply
		--------------------
		1 = Information reply
		Type: Address mask request
		------------------------
		1 = Address mask request
		Type: Address mask reply
		----------------------
		1 = Address mask reply"
	::= { snAgAclEntry 30 }
	
snAgAclParameters   OBJECT-TYPE
	SYNTAX		BITS { 
		matchFragmentedPackets (0),
		matchNonFragmentedPackets (1),
		matchTcpSynSetPackets (2),
		permitFailedRPFCheckPackets (3),
		mirrorPermitPackets (4), 
		sendPermitPacketsToSflowCollector (5),
		dscpMappingFlagSet (6),
		dscpMarkingFlagSet (7)
		}
	MAX-ACCESS  read-write
	STATUS		current
	DESCRIPTION
		"This mask represents multiple parameters configured for this ACL.
		Bit 0 specified in the BITS construct is the MS bit of the first octet.
		Bit 0: Match fragmented IP packets
		Bit 1: Match non-fragmented IP packets
		Bit 2: Match only TCP packets with SYN Bit set. Valid only if snAgAclSourceOperator
				or snAgAclDestinationOperator is set to TCP.
		Bit 3: Permit packets that fail RPF check
		Bit 4: Mirror packets matching ACL permit clause
		Bit 5: Send packets matching ACL permit clause to sFlow collector
		Bit 6: Set dscp-mapping. The value is given by snAgAclDscpMarking
		Bit 7: Set dscp-marking. The value is given by snAgAclDscpMapping
		"
	::= { snAgAclEntry 31 }

--
-- Acl Port Table
--
-- snAgAclIfBindTable replaces snAgAclBindToPortTable

snAgAclBindToPortTable   OBJECT-TYPE
	SYNTAX  SEQUENCE OF SnAgAclBindToPortEntry
	MAX-ACCESS  not-accessible
	STATUS	current
	DESCRIPTION
		"Table of ACL binding to port for router"
	::= { snAgAcl 3 }

snAgAclBindToPortEntry       OBJECT-TYPE
	SYNTAX  SnAgAclBindToPortEntry
	MAX-ACCESS  not-accessible
	STATUS	current
	DESCRIPTION
		"An entry in the ACL-binding-to-port table."
	INDEX   { 
			   snAgAclPortNum, 
			   snAgAclPortBindDirection
			}
	::= { snAgAclBindToPortTable 1 }

SnAgAclBindToPortEntry ::= SEQUENCE {
	snAgAclPortNum
		Integer32,
	snAgAclPortBindDirection
		Direction,
	snAgAclNum
		Integer32,
	snAgAclNameString
		DisplayString,
	snAgBindPortListInVirtualInterface
		OCTET STRING,
	snAgAclPortRowStatus
		SnRowStatus
	}

snAgAclPortNum      OBJECT-TYPE
	SYNTAX  Integer32
	MAX-ACCESS  read-only
	STATUS	current
	DESCRIPTION
		"Binding-to port num, either physical port or virtual interface."
	::= { snAgAclBindToPortEntry 1 }

snAgAclPortBindDirection   OBJECT-TYPE
	SYNTAX  Direction
	MAX-ACCESS  read-only
	STATUS	current
	DESCRIPTION
		"ACL port direction, inbound or outbound"
	::= { snAgAclBindToPortEntry 2 }

snAgAclNum      OBJECT-TYPE
	SYNTAX  Integer32
	MAX-ACCESS  read-write
	STATUS	current
	DESCRIPTION
		"Defined ACL number"
	::= { snAgAclBindToPortEntry 3 }

snAgAclNameString      OBJECT-TYPE
	SYNTAX  DisplayString
	MAX-ACCESS  read-write
	STATUS	current
	DESCRIPTION
		"Defined ACL name"
	::= { snAgAclBindToPortEntry 4 }

snAgBindPortListInVirtualInterface   OBJECT-TYPE
	SYNTAX  OCTET STRING
	MAX-ACCESS  read-write
	STATUS	current
	DESCRIPTION
		"Port list for binding virtual interface"
	::= { snAgAclBindToPortEntry 5 }

snAgAclPortRowStatus   OBJECT-TYPE
	SYNTAX  SnRowStatus
	MAX-ACCESS  read-write
	STATUS	current
	DESCRIPTION
		"To create or delete a ACL port entry."
	::= { snAgAclBindToPortEntry 6 }

--
-- Acl Port Table
--

snAgAclIfBindTable   OBJECT-TYPE
	SYNTAX		SEQUENCE OF SnAgAclIfBindEntry
	MAX-ACCESS  not-accessible
	STATUS		current
	DESCRIPTION
		"Table of ACL binding to port for router"
	::= { snAgAcl 4 }

snAgAclIfBindEntry       OBJECT-TYPE
	SYNTAX		SnAgAclIfBindEntry
	MAX-ACCESS  not-accessible
	STATUS		current
	DESCRIPTION
		"An entry in the ACL-binding-to-port table."
	INDEX   {snAgAclIfBindIndex, snAgAclIfBindDirection}
	::= { snAgAclIfBindTable 1 }

SnAgAclIfBindEntry ::= SEQUENCE {
	snAgAclIfBindIndex
		InterfaceIndex,
	snAgAclIfBindDirection
		Direction,
	snAgAclIfBindNum
		INTEGER,
	snAgAclIfBindName
		DisplayString,
	snAgAclIfBindVifPortList
		OCTET STRING,
	snAgAclIfBindRowStatus
		SnRowStatus,
	snAgAclIfBindDenyLogging
		INTEGER
	}

snAgAclIfBindIndex      OBJECT-TYPE
	SYNTAX		InterfaceIndex
	MAX-ACCESS  read-only
	STATUS		current
	DESCRIPTION
		"Binding-to port num, either physical port or virtual interface."
	::= { snAgAclIfBindEntry 1 }
 
snAgAclIfBindDirection   OBJECT-TYPE
	SYNTAX		Direction
	MAX-ACCESS  read-only
	STATUS		current
	DESCRIPTION
		"ACL port direction, inbound or outbound"
	::= { snAgAclIfBindEntry 2 }

snAgAclIfBindNum      OBJECT-TYPE
	SYNTAX		INTEGER (0..199)
	MAX-ACCESS  read-write
	STATUS		current
	DESCRIPTION
		"Defined ACL number (0 represents named ACL)"

	::= { snAgAclIfBindEntry 3 }

snAgAclIfBindName      OBJECT-TYPE
	SYNTAX		DisplayString (SIZE (0..255))
	MAX-ACCESS  read-write
	STATUS		current
	DESCRIPTION
		"Defined ACL name"
	::= { snAgAclIfBindEntry 4 }

snAgAclIfBindVifPortList   OBJECT-TYPE
	SYNTAX		OCTET STRING
	MAX-ACCESS  read-write
	STATUS		current
	DESCRIPTION
		"This object specifies the port list for binding virtual interface.
		 Each port index is an ifIndex, if there are consecutive 4 or more
		 ifIndex then, they will be encoded like below. 
		 
		 Encoding and decoding scheme is range based: Each range prefix with
		 0000 (2 octets) where 0000 is not valid ifIndex. Next 2 octets
		 indicates lower range ifIndex, followed by 2 octets of higher range
		 ifIndex. Individual(non range) ones will be displayed as it is.
		 
		 Ex: port list: 0001..0005 0015 0032..0047
		 Port list in PDU:  0000 0001 0005 000f 0000 0020 002f."
	::= { snAgAclIfBindEntry 5 }

snAgAclIfBindRowStatus   OBJECT-TYPE
	SYNTAX		SnRowStatus
	MAX-ACCESS  read-write
	STATUS		current
	DESCRIPTION
		"To create or delete a ACL port entry."
	::= { snAgAclIfBindEntry 6 }

snAgAclIfBindDenyLogging    OBJECT-TYPE
	SYNTAX		INTEGER {
					disable(0),
					enable(1)
				}
	MAX-ACCESS  read-write
	STATUS		current
	DESCRIPTION
		"Enable or disable deny logging."
	::= { snAgAclIfBindEntry 7 }

--
-- Acl Accounting Table
--

agAclAccntTable   OBJECT-TYPE
	SYNTAX		SEQUENCE OF AgAclAccntEntry
	MAX-ACCESS  not-accessible
	STATUS		current
	DESCRIPTION
		"Table of ACL Accounting Statistics for router"
	::= { snAgAcl 5 }

agAclAccntEntry       OBJECT-TYPE
	SYNTAX		AgAclAccntEntry
	MAX-ACCESS  not-accessible
	STATUS		current
	DESCRIPTION
		"An entry in the ACL-binding-to-port table."
	INDEX   { agAclAccntKind, agAclAccntIfIndex, agAclAccntDirection, agAclAccntAclNumber, agAclAccntFilterId}
	::= { agAclAccntTable 1 }

AgAclAccntEntry ::= SEQUENCE {
	agAclAccntKind
		INTEGER,
	agAclAccntIfIndex
		InterfaceIndex,
	agAclAccntDirection
		Direction,
	agAclAccntAclNumber
		AclNumber,
	agAclAccntFilterId
		Unsigned32,
	agAclAccntAclName
		AclNameString,
	agAclAccntOneSecond
		Counter64,
	agAclAccntOneMinute
		Counter64,
	agAclAccntFiveMinute
		Counter64,
	agAclAccntCumulative
		Counter64,
	agAclAccntRaclDropCnt
		Counter64,
	agAclAccntRaclFwdCnt
		Counter64,
	agAclAccntRaclRemarkCnt
		Counter64,
	agAclAccntRaclTotalCnt
		Counter64,
	agAclAccntRaclTotalSWHitCountCnt
		Counter64
	}

agAclAccntKind	OBJECT-TYPE
	SYNTAX		INTEGER {
					ipv4(0),
					l2(1),
					policyBasedRouting(2),
					rateLimit(3),
					receiveAcl(4)
				}
	MAX-ACCESS	not-accessible
	STATUS		current
	DESCRIPTION
		"Kind of ACL Accounting statistics needed."
	::= { agAclAccntEntry 1 }

agAclAccntIfIndex	OBJECT-TYPE
	SYNTAX			InterfaceIndex
	MAX-ACCESS		not-accessible
	STATUS			current
	DESCRIPTION
		"Physical or virtual interface on which ACL accounting is desired.
		For Receive ACL, we use the lowest port of the management module
		as value for this object."
	::= { agAclAccntEntry 2 }

agAclAccntDirection	OBJECT-TYPE
	SYNTAX			Direction
	MAX-ACCESS		not-accessible
	STATUS			current
	DESCRIPTION
		"ACL port direction, inbound or outbound. For receive-acl kind, direction cannot be outbound."
	::= { agAclAccntEntry 3 }

agAclAccntAclNumber	OBJECT-TYPE
	SYNTAX			AclNumber
	MAX-ACCESS		not-accessible
	STATUS			current
	DESCRIPTION
		"The access-list number for this entry."
	::= { agAclAccntEntry 4 }

agAclAccntFilterId	OBJECT-TYPE
	SYNTAX			Unsigned32
	MAX-ACCESS		not-accessible
	STATUS			current
	DESCRIPTION
		"FilterId within a given ACL. This is a zero based value."
	::= { agAclAccntEntry 5 }

agAclAccntAclName	OBJECT-TYPE
	SYNTAX			AclNameString
	MAX-ACCESS		read-only
	STATUS			current
	DESCRIPTION
		"ACL name for an entry, if applicable. Otherwise, null string is returned."
	::= { agAclAccntEntry 6 }

agAclAccntOneSecond    OBJECT-TYPE
	SYNTAX		Counter64
	MAX-ACCESS	read-only
	STATUS		current
	DESCRIPTION
		"Last one second accounting data."
	::= { agAclAccntEntry 7 }

agAclAccntOneMinute    OBJECT-TYPE
	SYNTAX		Counter64
	MAX-ACCESS	read-only
	STATUS		current
	DESCRIPTION
		"Last one minute accounting data."
	::= { agAclAccntEntry 8 }

agAclAccntFiveMinute    OBJECT-TYPE
	SYNTAX		Counter64
	MAX-ACCESS	read-only
	STATUS		current
	DESCRIPTION
		"Last five minute accounting data."
	::= { agAclAccntEntry 9 }

agAclAccntCumulative    OBJECT-TYPE
	SYNTAX		Counter64
	MAX-ACCESS	read-only
	STATUS		current
	DESCRIPTION
		"Cummulative accounting data since the ACL was installed."
	::= { agAclAccntEntry 10 }

agAclAccntRaclDropCnt    OBJECT-TYPE
	SYNTAX		Counter64
	MAX-ACCESS	read-only
	STATUS		current
	DESCRIPTION
		"Receive-ACL drop counter used for rate limiting. Not used for other ACL kind.
		The value returned is per ACL, instead of per filter within the ACL."
	::= { agAclAccntEntry 11 }

agAclAccntRaclFwdCnt    OBJECT-TYPE
	SYNTAX		Counter64
	MAX-ACCESS	read-only
	STATUS		current
	DESCRIPTION
		"Receive-ACL forward counter used for rate limiting. Not used for other ACL kind.
		The value returned is per ACL, instead of per filter within the ACL."
	::= { agAclAccntEntry 12 }

agAclAccntRaclRemarkCnt    OBJECT-TYPE
	SYNTAX		Counter64
	MAX-ACCESS	read-only
	STATUS		current
	DESCRIPTION
		"Receive-ACL remark counter used for rate limiting. Not used for other ACL kind.
		The value returned is per ACL, instead of per filter within the ACL."
	::= { agAclAccntEntry 13 }

agAclAccntRaclTotalCnt    OBJECT-TYPE
	SYNTAX		Counter64
	MAX-ACCESS	read-only
	STATUS		current
	DESCRIPTION
		"Receive-ACL total counter used for rate limiting. Not used for other ACL kind.
		The value returned is per ACL, instead of per filter within the ACL."
	::= { agAclAccntEntry 14 }

agAclAccntRaclTotalSWHitCountCnt    OBJECT-TYPE
	SYNTAX		Counter64
	MAX-ACCESS	read-only
	STATUS		current
	DESCRIPTION
		"Receive-ACL cumulative software hit counter. Not used for other ACL kind.
		The value returned is per ACL, instead of per filter within the ACL."
	::= { agAclAccntEntry 15 }
	
--
-- L2 ACL Next Clause Table
--

fdryL2AclNextClauseTable	OBJECT-TYPE
	SYNTAX		SEQUENCE OF FdryL2AclNextClauseEntry
	MAX-ACCESS	not-accessible
	STATUS		current
	DESCRIPTION
		"This read-only table contains the list of next lowest available clause index that 
		can be used for creating a new instance in the fdryL2AclTable.
		The clause index values will not change as a result of switchovers or hitless upgrades,
		but may change as a result of a device reload (though the relative order of persistent 
		entries would remain the same).
		"
	::= { snAgAcl 6 }

fdryL2AclNextClauseEntry	OBJECT-TYPE
	SYNTAX		FdryL2AclNextClauseEntry
	MAX-ACCESS	not-accessible
	STATUS		current
	DESCRIPTION
		"An entry specifying the next lowest available clause index for this ACL number."
	INDEX   { fdryL2AclNumber }
	::= { fdryL2AclNextClauseTable 1 }

FdryL2AclNextClauseEntry ::= SEQUENCE {
	fdryL2AclNextClauseIndex
		FdryClauseIndexTC
	}

fdryL2AclNextClauseIndex	OBJECT-TYPE
	SYNTAX		FdryClauseIndexTC
	MAX-ACCESS	read-only
	STATUS		current
	DESCRIPTION
		"The next lowest available clause index for a given ACL number. The maximum value
		of this object is the configured maximum number of clauses for a L2 ACL."
	::= { fdryL2AclNextClauseEntry 1 }
	
--
-- L2 ACL Configuration Table
--

fdryL2AclTable	OBJECT-TYPE
	SYNTAX		SEQUENCE OF FdryL2AclEntry
	MAX-ACCESS	not-accessible
	STATUS		current
	DESCRIPTION
		"Table of Layer 2 Access Control Lists. Layer 2 ACLs filter traffic 
		based on any of the following fields:
		- Source MAC address and source MAC mask
		- Destination MAC address and destination MAC mask
		- VLAN ID
		- Ethernet type.
		For a given ACL number, one can have 64 (default) to 256 clauses.
		The clause index values will not change as a result of switchovers or hitless upgrades,
		but may change as a result of a device reload (though the relative order of persistent 
		entries would remain the same).
		"
	::= { snAgAcl 7 }
	

fdryL2AclEntry	OBJECT-TYPE
	SYNTAX		FdryL2AclEntry
	MAX-ACCESS	not-accessible
	STATUS		current
	DESCRIPTION
		"An entry in the L2 Access Control List table."
	INDEX   { fdryL2AclNumber, fdryL2AclClauseIndex }
	::= { fdryL2AclTable 1 }

FdryL2AclEntry ::= SEQUENCE {
	fdryL2AclNumber
		AclNumber,
	fdryL2AclClauseIndex
		FdryClauseIndexTC,
	fdryL2AclAction
		Action,
	fdryL2AclSourceMac
		MacAddress,
	fdryL2AclSourceMacMask
		MacAddress,
	fdryL2AclDestinationMac
		MacAddress,
	fdryL2AclDestinationMacMask
		MacAddress,
	fdryL2AclVlanId
		FdryVlanIdOrNoneTC,
	fdryL2AclEthernetType
		FdryEnetTypeOrZeroTC,
	fdryL2AclDot1pPriority
		PortQosTC,
	fdryL2AclDot1pPriorityForce
		PortQosTC,
	fdryL2AclDot1pPriorityMapping
		PortQosTC,
	fdryL2AclMirrorPackets
		TruthValue,
	fdryL2AclLogEnable
		TruthValue,
	fdryL2AclRowStatus
		RowStatus
}

fdryL2AclNumber	OBJECT-TYPE
	SYNTAX		AclNumber
	MAX-ACCESS	not-accessible
	STATUS		current
	DESCRIPTION
		"The access-list number for this entry.
		For L2ACL, the valid values are between 400 and 499."
	::= { fdryL2AclEntry 1 }

fdryL2AclClauseIndex	OBJECT-TYPE
	SYNTAX		FdryClauseIndexTC
	MAX-ACCESS	not-accessible
	STATUS		current
	DESCRIPTION
		"The index of the clause within a given ACL number.
		During row creation, the clause index value should match
		with the next available clause index for a given ACL number.
		It is advisable to first do a Get operation on the 
		fdryL2AclNextClauseTable for a given ACL number, and use
		the value of fdryL2AclNextClauseIndex returned by the agent."
	::= { fdryL2AclEntry 2 }

fdryL2AclAction	OBJECT-TYPE
	SYNTAX		Action 
	MAX-ACCESS	read-create
	STATUS		current
	DESCRIPTION
		"Action to take if the ingress L2 packet matches this ACL."
	::= { fdryL2AclEntry 3 }

fdryL2AclSourceMac	OBJECT-TYPE
	SYNTAX		MacAddress
	MAX-ACCESS	read-create
	STATUS		current
	DESCRIPTION
		"Optional Source MAC address. By default, it matches with
		any source MAC within a packet."
	DEFVAL  { '000000000000'H }
	::= { fdryL2AclEntry 4 }

fdryL2AclSourceMacMask	OBJECT-TYPE
	SYNTAX		MacAddress
	MAX-ACCESS	read-create
	STATUS		current
	DESCRIPTION
		"Optional Source MAC address mask.
		For Set operation, this object can only be used in 
		conjunction with fdryL2AclSourceMac.
		By default,  it matches with any source MAC within a packet.
		it matches with any source MAC within a packet.
		To match on the first two bytes of the address 
		aabb.ccdd.eeff, use the mask ffff.0000.0000. In this case,
		the clause matches all source MAC addresses that contain 
		'aabb' as the first two bytes and any values in the
		remaining bytes of the MAC address."
	DEFVAL  { '000000000000'H }
	::= { fdryL2AclEntry 5 }

fdryL2AclDestinationMac	OBJECT-TYPE
	SYNTAX		MacAddress
	MAX-ACCESS	read-create
	STATUS		current
	DESCRIPTION
		"Optional destination MAC address. 
		By default, it matches with any destination MAC within a packet."
	DEFVAL  { '000000000000'H }
	::= { fdryL2AclEntry 6 }

fdryL2AclDestinationMacMask	OBJECT-TYPE
	SYNTAX		MacAddress
	MAX-ACCESS	read-create
	STATUS		current
	DESCRIPTION
		"Optional destination MAC address mask.
		For Set operation, this object can only be used in 
		conjunction with fdryL2AclDestinationMac.
		By default, it matches with any destination MAC within a packet.
		To match on the first two bytes of the address 
		aabb.ccdd.eeff, use the mask ffff.0000.0000. In this case,
		the clause matches all destination MAC addresses that contain 
		'aabb' as the first two bytes and any values in the
		remaining bytes of the MAC address."
	DEFVAL  { '000000000000'H }
	::= { fdryL2AclEntry 7 }

fdryL2AclVlanId 	OBJECT-TYPE
	SYNTAX		FdryVlanIdOrNoneTC
	MAX-ACCESS	read-create
	STATUS		current
	DESCRIPTION
		"Optional VLAN ID to match against that of the incoming packet.
		By default, the VLAN ID field is ignored during the match. In this case,
		value 0 is returned."
	DEFVAL  { 0 }
	::= { fdryL2AclEntry 8 }

fdryL2AclEthernetType 	OBJECT-TYPE
	SYNTAX		FdryEnetTypeOrZeroTC
	MAX-ACCESS	read-create
	STATUS		current
	DESCRIPTION
		"Optional Ethernet Type to match against the etype field
		of the incoming packet.
		By default, etype field is ignored during the match."
	DEFVAL  { invalid }
	::= { fdryL2AclEntry 9 }

fdryL2AclDot1pPriority 	OBJECT-TYPE
	SYNTAX		PortQosTC
	MAX-ACCESS	read-create
	STATUS		current
	DESCRIPTION
		"The priority option assigns traffic that matches the ACL to a 
		hardware forwarding queue. In addition to changing the internal 
		forwarding priority, if the outgoing interface is an 802.1q interface, 
		this option maps the specified priority to its equivalent 802.1p (QoS)
		priority and marks the packet with the new 802.1p priority. 
		This option is applicable for inbound ACLs only. 
		   This object is not supported in RX, where it always returns 
		enum value invalid.
		NOTE: fdryL2AclDot1pPriority following fdryL2AclDot1pPriorityForce
		cannot be used together in an ACL entry."
	DEFVAL  { level0 }
	::= { fdryL2AclEntry 10 }

fdryL2AclDot1pPriorityForce 	OBJECT-TYPE
	SYNTAX		PortQosTC
	MAX-ACCESS	read-create
	STATUS		current
	DESCRIPTION
		"The priority-force option assigns packets of outgoing traffic 
		that match the ACL to a specific hardware forwarding queue, 
		even though the incoming packet may be assigned to another queue. 
		This option is applicable for inbound ACLs only.
		   This object is not supported in RX, where it always returns 
		enum value invalid.
		NOTE: fdryL2AclDot1pPriority following fdryL2AclDot1pPriorityForce
		cannot be used together in an ACL entry."
	DEFVAL  { level0 }
	::= { fdryL2AclEntry 11 }

fdryL2AclDot1pPriorityMapping 	OBJECT-TYPE
	SYNTAX		PortQosTC
	MAX-ACCESS	read-create
	STATUS		current
	DESCRIPTION
		"The priority-mapping option matches on the packets 802.1p value.
		This option does not change the packets forwarding priority through
		the device or mark the packet. This keyword is applicable for both
		inbound and outbound ACLs.
		   This object is not supported in RX, where it always returns 		
		enum value invalid."		
	DEFVAL  { level0 }
	::= { fdryL2AclEntry 12 }	

fdryL2AclMirrorPackets OBJECT-TYPE
	SYNTAX		TruthValue
	MAX-ACCESS  read-create
	STATUS		current
	DESCRIPTION
		"Mirror packets matching ACL permit clause."
	DEFVAL  { false }
	::= { fdryL2AclEntry 13 }

fdryL2AclLogEnable	OBJECT-TYPE
	SYNTAX		TruthValue
	MAX-ACCESS	read-create
	STATUS		current
	DESCRIPTION
		"Optional parameter to enable logging only when deny clause
		is specified. Note that traffic denied by implicit deny mechanism is not 
		subject to logging. The implicit deny kicks in when the traffic
		does not match any of the clauses and there is no 'permit any any'
		clause specified at the end."
	DEFVAL  { false }
	::= { fdryL2AclEntry 14 }

fdryL2AclRowStatus	OBJECT-TYPE
	SYNTAX		RowStatus
	MAX-ACCESS	read-create
	STATUS		current
	DESCRIPTION
		"The row status variable, used according to installation
		and removal conventions for conceptual rows. Setting this
		object to active(1) or createAndGo(4) results in the
		addition of a L2 ACL filter in the router. Duplicate entry will
		be rejected during row creation. As part of row creation, we
		support only appending to this table. Row insertion may not
		be supported.
		  Setting this object to destroy(6) removes the associated filter 
		from the router. Other values in the enumeration are not used.
		"
	::= { fdryL2AclEntry 15 }

--
-- L2 ACL Binding Configuration Table
--

fdryL2AclIfBindTable   OBJECT-TYPE
	SYNTAX		SEQUENCE OF FdryL2AclIfBindEntry
	MAX-ACCESS  not-accessible
	STATUS		current
	DESCRIPTION
		"Table of L2 ACL binding to port. 
		- One cannot bind Layer 2 ACLs and Layer 3 ACLs to the same port.
		However, one can configure a port to use Layer 2 ACLs, and
		another port on the same device to use Layer 3 ACLs.
		- In general, Layer 2 ACLs cannot be bound to virtual interfaces, unlike L3 ACLs.
		- One cannot modify an existing Layer 2 ACL clause. For that, one must
		unbind the ACL, delete it and make a new clause.
		"
	::= { snAgAcl 8 }

fdryL2AclIfBindEntry       OBJECT-TYPE
	SYNTAX		FdryL2AclIfBindEntry
	MAX-ACCESS  not-accessible
	STATUS		current
	DESCRIPTION
		"An entry in the L2ACL binding table which lists the ACL bindings to a port.
		"
	INDEX   {ifIndex, fdryL2AclIfBindDirection}
	::= { fdryL2AclIfBindTable 1 }


FdryL2AclIfBindEntry ::= SEQUENCE {
	fdryL2AclIfBindDirection
		Direction,
	fdryL2AclIfBindAclNumber
		Unsigned32,
	fdryL2AclIfBindRowStatus
		RowStatus
	}

fdryL2AclIfBindDirection   OBJECT-TYPE
	SYNTAX		Direction
	MAX-ACCESS  not-accessible
	STATUS		current
	DESCRIPTION
		"Direction in which this ACL should be applied on this port."
	::= { fdryL2AclIfBindEntry 1 }

fdryL2AclIfBindAclNumber      OBJECT-TYPE
	SYNTAX		Unsigned32
	MAX-ACCESS  read-create
	STATUS		current
	DESCRIPTION
		"The ACL number that is to be bound to given physical interface.
		The valid values are between 400 and 499."
	::= { fdryL2AclIfBindEntry 2 }

fdryL2AclIfBindRowStatus      OBJECT-TYPE
	SYNTAX		RowStatus
	MAX-ACCESS  read-create
	STATUS		current
	DESCRIPTION
		"The row status variable, used according to installation
		and removal conventions for conceptual rows. Setting this
		object to active(1) or createAndGo(4) results in the
		binding of a L2 ACL with a given physical port.
		Setting this object to destroy(6) unbinds this L2 ACL from the port.
		Other values in the enumeration are not used."
	::= { fdryL2AclIfBindEntry 3 }
	
	
END
FOUNDRY-SN-WIRELESS-GROUP-MIB DEFINITIONS ::= BEGIN
-- Foundry SN WIRELESS GROUP MIB Release 1.0.0
-- Revision 0 04/15/04

-- Copyright 1996-2004 Foundry Networks, Inc.
-- All rights reserved.
-- This Foundry Networks SNMP Management Information Base Specification
-- (Specification) embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.

-- SECTION 1: Top Level Definitions

IMPORTS
	MODULE-IDENTITY, OBJECT-TYPE, IpAddress,Integer32
		FROM SNMPv2-SMI
	MacAddress
		FROM FOUNDRY-SN-AGENT-MIB
	snSwitch
		FROM FOUNDRY-SN-SWITCH-GROUP-MIB
	TEXTUAL-CONVENTION
		FROM SNMPv2-TC;

snWireless MODULE-IDENTITY
	LAST-UPDATED "200909300000Z" -- September 30, 2009
	ORGANIZATION "Foundry Networks, Inc"
	CONTACT-INFO
			"Technical Support Center, Foundry Networks,
			4980 Great America Parkway,
			Santa Clara, CA 95054
			Email: support@foundrynet.com
			Phone: 1-877-TURBO-CALL"    
	DESCRIPTION
			""
	REVISION     "200909300000Z" -- September 30, 2009
	DESCRIPTION
			"convert from SMIv1 to SMIv2"
   ::= {snSwitch  23}	

-- textual conventions

	IfIndexList ::= TEXTUAL-CONVENTION
		STATUS      current
		DESCRIPTION
			"Each octet within this value specifies a set of eight
			interfaces by their ifIndex values, with the first octet
			specifying interfaces 1 through 8, the second octet
			specifying interfaces 9 through 16, etc.  Within each
			octet, the most significant bit represents the lowest
			numbered interface, and the least significant bit
			represents the highest numbered interface.  Thus, each
			interface of the device is represented by a single bit
			within the value of this object.  If that bit has a value
			of '1' then that interface is included in the set of
			interfaces; the interface is not included if its bit has a
			value of '0'."
		SYNTAX      OCTET STRING

-- iso(1).org(3).dod(6).internet(1).private(4).enterprises(1).foundry(1991)

wgGroup     OBJECT IDENTIFIER ::= { snWireless 1 }

wgMobilityId OBJECT-TYPE
	SYNTAX  Integer32
	MAX-ACCESS  read-write
	STATUS  current
	DESCRIPTION
		"Unique Identifier used to specify the mobility doamin.
		 Valid range is <1 - 65535>. Use <0> to remove the domain."
	::= { wgGroup 1 }

wgVpnPTDeletePolicy OBJECT-TYPE
	SYNTAX  Integer32
	MAX-ACCESS  read-write
	STATUS  current
	DESCRIPTION
		"Write a valid VPN pass through policy ID to remove the policy.
		Return zero when reading this object."
	::= { wgGroup 2 }


--
-- WiFi Interface Table
--

wgIfTable OBJECT-TYPE
	SYNTAX SEQUENCE OF WgIfEntry
	MAX-ACCESS not-accessible
	STATUS current
	DESCRIPTION
		"WiFi Interface Table."
	::= { snWireless 2 }
	
wgIfEntry OBJECT-TYPE
	SYNTAX WgIfEntry
	MAX-ACCESS not-accessible
	STATUS current
	DESCRIPTION
		"An entry of the WiFi Interface Table."
	INDEX { wgIfIndex }
	::= { wgIfTable 1 }

WgIfEntry ::= SEQUENCE {
	wgIfIndex                 Integer32,
	wgIfWirelessEnable        INTEGER,
	wgIfPnPLearnNewAP         INTEGER,
	wgIfAutoPortDisable       INTEGER,
	wgIfVpnPTPolicyId         Integer32,
	wgIfFullCompRoamingEnable INTEGER
}

wgIfIndex OBJECT-TYPE
	SYNTAX  Integer32
	MAX-ACCESS  read-only
	STATUS  current
	DESCRIPTION
		"ifIndex value of the switch interface."
	::= { wgIfEntry 1 }

wgIfWirelessEnable OBJECT-TYPE
	SYNTAX  INTEGER {
		other(1),
		enable(2),
		disable(3)
		}
	MAX-ACCESS  read-write
	STATUS  current
	DESCRIPTION
		"Control wireless function of the switch interface."
	DEFVAL { disable }
	::= { wgIfEntry 2 }

wgIfPnPLearnNewAP OBJECT-TYPE
	SYNTAX  INTEGER {
		other(1),
		enable(2),
		disable(3)
		}
	MAX-ACCESS  read-write
	STATUS  current
	DESCRIPTION
		"Control the interface to learn new AP."
	::= { wgIfEntry 3 }

wgIfAutoPortDisable  OBJECT-TYPE
	SYNTAX  INTEGER {
		other(1),
		enable(2),
		disable(3)
		}
	MAX-ACCESS  read-write
	STATUS  current
	DESCRIPTION
		"Disable the interface if the interface link status change."
	::= { wgIfEntry 4 }

wgIfVpnPTPolicyId OBJECT-TYPE
	SYNTAX Integer32
	MAX-ACCESS  read-write
	STATUS  current
	DESCRIPTION
		"To bind an interface to a VPN pass through policy, write
		a valid policy number which is larger than zero. To unbind
		an interface to a VPN pass through policy, write a zero."
	::= { wgIfEntry 5 }

wgIfFullCompRoamingEnable OBJECT-TYPE
	SYNTAX  INTEGER {
		other(1),
		enable(2),
		disable(3)
		}
	MAX-ACCESS  read-write
	STATUS  current
	DESCRIPTION
		"Control full compatibility roaming of an interface."
	DEFVAL { disable }
	::= { wgIfEntry 6 }


--
-- Roaming Peer table
--

wgRoamingPeerTable OBJECT-TYPE
	SYNTAX  SEQUENCE OF WgRoamingPeerEntry
	MAX-ACCESS  not-accessible
	STATUS  current
	DESCRIPTION
		"Roaming Peer table contains information of peers."
	::= { snWireless 3 }

wgRoamingPeerEntry OBJECT-TYPE
	SYNTAX  WgRoamingPeerEntry
	MAX-ACCESS  not-accessible
	STATUS  current
	DESCRIPTION
		"An entry of the roaming peer table."
	INDEX   { wgRoamingPeerIpAddress }
	::= { wgRoamingPeerTable 1 }

WgRoamingPeerEntry ::= SEQUENCE {
	wgRoamingPeerIpAddress
		IpAddress,
	wgRoamingPeerConnectionStatus
		INTEGER,
	wgRoamingPeerRowStatus
		INTEGER
	}

wgRoamingPeerIpAddress OBJECT-TYPE
	SYNTAX  IpAddress
	MAX-ACCESS  read-only
	STATUS  current
	DESCRIPTION
		"IP Address of the ISRP peer."
	::= { wgRoamingPeerEntry 1 }

wgRoamingPeerConnectionStatus OBJECT-TYPE
	SYNTAX  INTEGER {
		other(1),
		configured(2),
		established(3)
		}
	MAX-ACCESS  read-only
	STATUS  current
	DESCRIPTION
		"Shows the state of the ISRP Connection."
	::= { wgRoamingPeerEntry 2 }

wgRoamingPeerRowStatus OBJECT-TYPE
	SYNTAX  INTEGER {
		other(1),
		valid(2),
		delete(3),
		create(4)
		}
	MAX-ACCESS  read-write
	STATUS  current
	DESCRIPTION
		"Shows the state of the row in the PeerRow Table."
	::= { wgRoamingPeerEntry 3 }


--
-- AP Plug and Play Table
--

wgPnPTable OBJECT-TYPE
	SYNTAX SEQUENCE OF WgPnPEntry
	MAX-ACCESS not-accessible
	STATUS current
	DESCRIPTION
		"AP Plug and Play Table."
	::= { snWireless 4 }

wgPnPEntry OBJECT-TYPE
	SYNTAX WgPnPEntry
	MAX-ACCESS not-accessible
	STATUS current
	DESCRIPTION
		"An entry of the AP Plug and Play Table."
	INDEX { wgPnPIfIndex, wgPnPMacAddress }
	::= { wgPnPTable 1 }

WgPnPEntry ::= SEQUENCE {
	wgPnPIfIndex             Integer32,
	wgPnPMacAddress          MacAddress,
	wgPnPIpAddress           IpAddress,
	wgPnPIpMask              IpAddress,
	wgPnPIpDefaultGw         IpAddress,
	wgPnPStatus              INTEGER,
	wgPnPRowStatus           INTEGER
}

wgPnPIfIndex OBJECT-TYPE
	SYNTAX  Integer32
	MAX-ACCESS  read-only
	STATUS  current
	DESCRIPTION
		"ifIndex value of the switch interface."
	::= { wgPnPEntry 1 }

wgPnPMacAddress OBJECT-TYPE
	SYNTAX  MacAddress
	MAX-ACCESS  read-only
	STATUS  current
	DESCRIPTION
		"MAC address of the attached AP."
	::= { wgPnPEntry 2 }

wgPnPIpAddress OBJECT-TYPE
	SYNTAX  IpAddress
	MAX-ACCESS  read-write
	STATUS  current
	DESCRIPTION
		"IP address of the attached AP."
	::= { wgPnPEntry 3 }

wgPnPIpMask OBJECT-TYPE
	SYNTAX  IpAddress
	MAX-ACCESS  read-write
	STATUS  current
	DESCRIPTION
		"Subnet mask of the attached AP."
	::= { wgPnPEntry 4 }

wgPnPIpDefaultGw OBJECT-TYPE
	SYNTAX  IpAddress
	MAX-ACCESS  read-write
	STATUS  current
	DESCRIPTION
		"Default gateway of the attached AP."
	::= { wgPnPEntry 5 }

wgPnPStatus OBJECT-TYPE
	SYNTAX  INTEGER {
		other(1),
		discovered(2),
		configured(3),
		operational(4)
		}
	MAX-ACCESS  read-only
	STATUS  current
	DESCRIPTION
		"AP device status. If the switch diecovered a new AP which
		had not been configured, the 'discovered' state will return.
		If the AP's IP address, subnet mask and default gateway were
		configured to the switch port but the AP with the matching
		MAC address had not attached to the switch port, 'configured'
		state will return. If the AP's IP address, subnet mask and
		default gateway were configured to the switch port and the
		AP with the matching MAC address had attached to the switch
		port and was operating, 'operational' state will return."
	::= { wgPnPEntry 6 }

wgPnPRowStatus OBJECT-TYPE
	SYNTAX  INTEGER {
		other(1),
		valid(2),
		delete(3),
		create(4),
		modify(5)
		}
	MAX-ACCESS  read-write
	STATUS  current
	DESCRIPTION
		"Create, delete or modify a row of AP Plug and Play Table."
	::= { wgPnPEntry 7 }

--
-- VPN Pass Through Server Table
--

wgVpnPTServerTable OBJECT-TYPE
	SYNTAX SEQUENCE OF WgVpnPTServerEntry
	MAX-ACCESS not-accessible
	STATUS current
	DESCRIPTION
		"VPN pass through server table"
	::= { snWireless 5 }

wgVpnPTServerEntry OBJECT-TYPE
	SYNTAX WgVpnPTServerEntry
	MAX-ACCESS not-accessible
	STATUS current
	DESCRIPTION
		"An entry of the VPN pass through server table."
	INDEX { wgVpnPTServerPolicyId, wgVpnPTServerIpAddress }
	::= { wgVpnPTServerTable 1 }

WgVpnPTServerEntry ::= SEQUENCE {
	wgVpnPTServerPolicyId       Integer32,
	wgVpnPTServerIpAddress      IpAddress,
	wgVpnPTServerRowStatus      INTEGER
}

wgVpnPTServerPolicyId OBJECT-TYPE
	SYNTAX  Integer32
	MAX-ACCESS  read-only
	STATUS  current
	DESCRIPTION
		"VPN pass through policy identifier. It must be greater than zero."
	::= { wgVpnPTServerEntry 1 }

wgVpnPTServerIpAddress OBJECT-TYPE
	SYNTAX  IpAddress
	MAX-ACCESS  read-only
	STATUS  current
	DESCRIPTION
		"VPN server IP address."
	::= { wgVpnPTServerEntry 2 }

wgVpnPTServerRowStatus OBJECT-TYPE
	SYNTAX  INTEGER {
		other(1),
		valid(2),
		delete(3),
		create(4)
		}
	MAX-ACCESS  read-write
	STATUS  current
	DESCRIPTION
		"Create or delete a row of VPN pass through server table."
	::= { wgVpnPTServerEntry 3 }


--
-- VPN Pass Through Filter Table
--

wgVpnPTFilterTable OBJECT-TYPE
	SYNTAX SEQUENCE OF WgVpnPTFilterEntry
	MAX-ACCESS not-accessible
	STATUS current
	DESCRIPTION
		"VPN pass through filter table"
	::= { snWireless 6 }

wgVpnPTFilterEntry OBJECT-TYPE
	SYNTAX WgVpnPTFilterEntry
	MAX-ACCESS not-accessible
	STATUS current
	DESCRIPTION
		"An entry of the VPN pass through filter table."
	INDEX { wgVpnPTFilterPolicyId, wgVpnPTFilterProtocol, wgVpnPTFilterPort }
	::= { wgVpnPTFilterTable 1 }

WgVpnPTFilterEntry ::= SEQUENCE {
	wgVpnPTFilterPolicyId       Integer32,
	wgVpnPTFilterProtocol       INTEGER,
	wgVpnPTFilterPort           Integer32,
	wgVpnPTFilterRowStatus      INTEGER
}

wgVpnPTFilterPolicyId OBJECT-TYPE
	SYNTAX  Integer32
	MAX-ACCESS  read-only
	STATUS  current
	DESCRIPTION
		"VPN pass through policy identifier. It must be greater than zero."
	::= { wgVpnPTFilterEntry 1 }

wgVpnPTFilterProtocol OBJECT-TYPE
	SYNTAX  INTEGER {
		other(1),
		udp(2),
		tcp(3)
		}
	MAX-ACCESS  read-only
	STATUS  current
	DESCRIPTION
		"Allow this type of protocol to pass through."
	::= { wgVpnPTFilterEntry 2 }

wgVpnPTFilterPort OBJECT-TYPE
	SYNTAX  Integer32
	MAX-ACCESS  read-only
	STATUS  current
	DESCRIPTION
		"Allow this protocol port to pass through."
	::= { wgVpnPTFilterEntry 3 }

wgVpnPTFilterRowStatus OBJECT-TYPE
	SYNTAX  INTEGER {
		other(1),
		valid(2),
		delete(3),
		create(4)
		}
	MAX-ACCESS  read-write
	STATUS  current
	DESCRIPTION
		"Create or delete a row of VPN pass through filter table."
	::= { wgVpnPTFilterEntry 4 }

--
-- VPN Pass Through Policy Table
--

wgVpnPTPolicyTable OBJECT-TYPE
	SYNTAX SEQUENCE OF WgVpnPTPolicyEntry
	MAX-ACCESS not-accessible
	STATUS current
	DESCRIPTION
		"VPN pass through policy table"
	::= { snWireless 7 }

wgVpnPTPolicyEntry OBJECT-TYPE
	SYNTAX WgVpnPTPolicyEntry
	MAX-ACCESS not-accessible
	STATUS current
	DESCRIPTION
		"An entry of the VPN pass through policy table."
	INDEX { wgVpnPTPolicyId }
	::= { wgVpnPTPolicyTable 1 }

WgVpnPTPolicyEntry ::= SEQUENCE {
	wgVpnPTPolicyId        Integer32,
	wgVpnPTPolicyPortList  IfIndexList
}

wgVpnPTPolicyId OBJECT-TYPE
	SYNTAX  Integer32
	MAX-ACCESS  read-only
	STATUS  current
	DESCRIPTION
		"VPN pass through policy identifier. It must be greater than zero."
	::= { wgVpnPTPolicyEntry 1 }

wgVpnPTPolicyPortList OBJECT-TYPE
	SYNTAX  IfIndexList
	MAX-ACCESS  read-only
	STATUS  current
	DESCRIPTION
		"A list of ports bound to this VPN pass through policy."
	::= { wgVpnPTPolicyEntry 2 }

END


FOUNDRY-SN-MAC-AUTHENTICATION-MIB DEFINITIONS ::= BEGIN

IMPORTS
    MODULE-IDENTITY, OBJECT-TYPE, Integer32
      FROM SNMPv2-SMI
    MacAddress, TimeStamp
      FROM SNMPv2-TC
    InterfaceIndex
      FROM IF-MIB;


snMacAuth MODULE-IDENTITY
    LAST-UPDATED "200706250000Z" -- June 25, 2007
    ORGANIZATION "Foundry Networks, Inc"
    CONTACT-INFO
            ""
    DESCRIPTION
            "Management Information Base module for MAC authentication
            configuration and statistics."
    REVISION     "200706250000Z" -- June 25, 2007
    DESCRIPTION
            ""
   ::= { iso(1) org(3) dod(6) internet(1) private(4) enterprises(1) foundry(1991) products(1) switch(1) snSwitch(3) 28 }


-- MAC Authentication MIBs

snMacAuthGlobal		OBJECT IDENTIFIER ::= { snMacAuth 1 }

snMacAuthClearGlobalCmd OBJECT-TYPE
	SYNTAX     INTEGER { valid(0), clear(1) }
	MAX-ACCESS read-write
	STATUS     current
	DESCRIPTION
		"valid(0) - a SNMP-GET of this mib shows that it is valid command to use. 
		 clear(1) - represents clear MAC Authentication table for all ports."
	::= { snMacAuthGlobal 1 }

snMacAuthGlobalConfigState OBJECT-TYPE
	SYNTAX     INTEGER { disabled(0), enabled(1) }
	MAX-ACCESS read-write
	STATUS     current
	DESCRIPTION
		"Enable/disable MAC authentication on the global level."
	::= { snMacAuthGlobal 2 }

--
-- MAC Authentication Clear Interface command Table
--

snMacAuthClearIfCmdTable OBJECT-TYPE
	SYNTAX     SEQUENCE OF SnMacAuthClearIfCmdEntry
	MAX-ACCESS not-accessible
	STATUS     current
	DESCRIPTION
		"The status of clearing an MAC Authentication entry for an interface."
	::= { snMacAuth 2 }

snMacAuthClearIfCmdEntry OBJECT-TYPE
	SYNTAX     SnMacAuthClearIfCmdEntry
	MAX-ACCESS not-accessible
	STATUS     current
	DESCRIPTION
		"An entry of clearing an MAC Authentication entry for an interface."
	INDEX { snMacAuthClearIfCmdIfIndex }
	::= { snMacAuthClearIfCmdTable 1 }

SnMacAuthClearIfCmdEntry ::= SEQUENCE {
    snMacAuthClearIfCmdIfIndex     InterfaceIndex,
    snMacAuthClearIfCmdAction      INTEGER
}

snMacAuthClearIfCmdIfIndex OBJECT-TYPE
    SYNTAX     InterfaceIndex
    MAX-ACCESS not-accessible
    STATUS     current
    DESCRIPTION
            "ifIndex value of the local interface on which a clear command is issued and monitored."
	::= { snMacAuthClearIfCmdEntry 1 }

snMacAuthClearIfCmdAction      OBJECT-TYPE
	SYNTAX     INTEGER { valid(0), clear(1) }
	MAX-ACCESS read-write
	STATUS     current
	DESCRIPTION
		"valid(0) - a SNMP-GET of this mib shows that it is valid command to use. 
		 clear(1) - represents clearing an MAC Authentication entry for an interface."
	::= { snMacAuthClearIfCmdEntry 2 }

--
-- MAC Authentication Table
--

snMacAuthTable OBJECT-TYPE
	SYNTAX     SEQUENCE OF SnMacAuthEntry
	MAX-ACCESS not-accessible
	STATUS     current
	DESCRIPTION
		"MAC Authentication table."
	::= { snMacAuth 3 }

snMacAuthEntry OBJECT-TYPE
	SYNTAX     SnMacAuthEntry
	MAX-ACCESS not-accessible
	STATUS     current
	DESCRIPTION
		"An entry in the MAC Authentication table."
	INDEX { snMacAuthIfIndex, snMacAuthVlanId, snMacAuthMac }
	::= { snMacAuthTable 1 }

SnMacAuthEntry ::= SEQUENCE {
    snMacAuthIfIndex               InterfaceIndex,
    snMacAuthVlanId                Integer32,
    snMacAuthMac                   MacAddress,
    snMacAuthState                 INTEGER,
    snMacAuthTimeStamp             TimeStamp,
    snMacAuthAge                   Integer32,
    snMacAuthDot1x                 INTEGER
}

snMacAuthIfIndex OBJECT-TYPE
    SYNTAX     InterfaceIndex
    MAX-ACCESS not-accessible
    STATUS     current
    DESCRIPTION
    	"In order to identify a particular interface, this
		object shall identify the instance of the ifIndex
		object, defined in RFC 2863."
	::= { snMacAuthEntry 1 }

snMacAuthVlanId OBJECT-TYPE
     SYNTAX     Integer32
     MAX-ACCESS not-accessible
     STATUS     current
     DESCRIPTION
        "The ID of a VLAN of which this port is a member. Port must
        be untagged. For tagged port which belongs to multiple
        VLANs, this object return 0 which is an invalid VLAN ID
        value."
     ::= { snMacAuthEntry 2 }

snMacAuthMac OBJECT-TYPE
	SYNTAX     MacAddress
	MAX-ACCESS not-accessible
	STATUS     current
	DESCRIPTION
		"MAC Address to be authenticated."
	::= { snMacAuthEntry 3 }

snMacAuthState OBJECT-TYPE
	SYNTAX     INTEGER { authenticate(1), unauthenticate(2) }
	MAX-ACCESS read-only
	STATUS     current
	DESCRIPTION
		"."
	::= { snMacAuthEntry 4 }

snMacAuthTimeStamp OBJECT-TYPE
	SYNTAX     TimeStamp
	MAX-ACCESS read-only
	STATUS     current
	DESCRIPTION
		"Timestamp at which the MAC was authenticated or failed to be authenticated."
	::= { snMacAuthEntry 5 }

snMacAuthAge OBJECT-TYPE
	SYNTAX     Integer32
	MAX-ACCESS read-only
	STATUS     current
	DESCRIPTION
		"Age of the mac session in which the MAC address is authenticated."
	::= { snMacAuthEntry 6 }

snMacAuthDot1x OBJECT-TYPE
	SYNTAX     INTEGER { disabled(0), enabled(1) }
	MAX-ACCESS read-only
	STATUS     current
	DESCRIPTION
		"Indicates whether the Dot1x is enabled or not."
	::= { snMacAuthEntry 7 }

--
-- MAC Authentication MAC Session Clear Table
--

snMacAuthClearMacSessionTable OBJECT-TYPE
	SYNTAX     SEQUENCE OF SnMacAuthClearMacSessionEntry
	MAX-ACCESS not-accessible
	STATUS     current
	DESCRIPTION
		"The status of clearing an MAC Session entry indexed by a MAC address."
	::= { snMacAuth 4 }

snMacAuthClearMacSessionEntry OBJECT-TYPE
	SYNTAX     SnMacAuthClearMacSessionEntry
	MAX-ACCESS not-accessible
	STATUS     current
	DESCRIPTION
		"An entry of clearing an MAC Session entry indexed by a MAC address."
	INDEX { snMacAuthClearMacSessionIfIndex, snMacAuthClearMacSessionMac }
	::= { snMacAuthClearMacSessionTable 1 }

SnMacAuthClearMacSessionEntry ::= SEQUENCE {
    snMacAuthClearMacSessionIfIndex InterfaceIndex,
    snMacAuthClearMacSessionMac     MacAddress,
    snMacAuthClearMacSessionAction  INTEGER
}

snMacAuthClearMacSessionIfIndex OBJECT-TYPE
    SYNTAX     InterfaceIndex
    MAX-ACCESS not-accessible
    STATUS     current
    DESCRIPTION
            "ifIndex value of the local interface on which a clear command is issued and monitored."
	::= { snMacAuthClearMacSessionEntry 1 }

snMacAuthClearMacSessionMac OBJECT-TYPE
	SYNTAX     MacAddress
	MAX-ACCESS not-accessible
	STATUS     current
	DESCRIPTION
		"An MAC Session entry indexed by a MAC address."
	::= { snMacAuthClearMacSessionEntry 2 }

snMacAuthClearMacSessionAction OBJECT-TYPE
	SYNTAX     INTEGER { valid(0), clear(1) }
	MAX-ACCESS read-write
	STATUS     current
	DESCRIPTION
		"valid(0) - a SNMP-GET of this mib shows that it is valid command to use. 
		 clear(1) - represents clearing an MAC Session entry indexed by a MAC address."
	::= { snMacAuthClearMacSessionEntry 3 }

END
FOUNDRY-SN-MRP-MIB DEFINITIONS ::= BEGIN

IMPORTS
    MODULE-IDENTITY, OBJECT-TYPE, Integer32, Counter32
      FROM SNMPv2-SMI
    InterfaceIndex
      FROM IF-MIB
    DisplayString
      FROM SNMPv2-TC;

snMetroRing MODULE-IDENTITY
    LAST-UPDATED "200705160000Z" -- May 16, 2007
    ORGANIZATION "Foundry Networks, Inc"
    CONTACT-INFO
            ""
    DESCRIPTION
            "Management Information Base module for metro ring
            configuration and statistics."
    REVISION     "200705160000Z" -- May 16, 2007
    DESCRIPTION
            ""
   ::= { iso(1) org(3) dod(6) internet(1) private(4) enterprises(1) foundry(1991) products(1) switch(1) snSwitch(3) 29 }

snMetroRingGlobalObjects OBJECT IDENTIFIER ::= { snMetroRing 1 }
snMetroRingTableObjects  OBJECT IDENTIFIER ::= { snMetroRing 2 }

-- Metro Ring Global Scalar Object Section

-- Metro Ring Table Object Section

--
-- Metro Ring Table
--

snMetroRingTable OBJECT-TYPE
    SYNTAX     SEQUENCE OF SnMetroRingEntry
    MAX-ACCESS not-accessible
    STATUS     current
    DESCRIPTION
            "Metro ring table."
    ::= { snMetroRingTableObjects 1 }

snMetroRingEntry OBJECT-TYPE
    SYNTAX     SnMetroRingEntry
    MAX-ACCESS not-accessible
    STATUS     current
    DESCRIPTION
            "An entry of the metro ring table."
    INDEX { snMetroRingVLanId, snMetroRingId }
    ::= { snMetroRingTable 1 }

SnMetroRingEntry ::= SEQUENCE {
    snMetroRingVLanId              Integer32,
    snMetroRingId                  Integer32,
    snMetroRingConfigState         INTEGER,
    snMetroRingRole                INTEGER,
    snMetroRingHelloTime           Integer32,
    snMetroRingPreforwardingTime   Integer32,
    snMetroRingPort1               InterfaceIndex,
    snMetroRingPort2               InterfaceIndex,
    snMetroRingName                DisplayString,
    snMetroRingRowStatus           INTEGER,
    snMetroRingOperState           INTEGER,
    snMetroRingTopoGroupId         Integer32,
    snMetroRingRHPTransmitted      Counter32,
    snMetroRingRHPReceived         Counter32,
    snMetroRingStateChanged        Counter32,
    snMetroRingTCRBPDUReceived     Counter32,
    snMetroRingPriPort             InterfaceIndex,
    snMetroRingSecPort             InterfaceIndex,
    snMetroRingPriPortState        INTEGER,
    snMetroRingSecPortState        INTEGER,
    snMetroRingPriPortType         INTEGER,
    snMetroRingSecPortType         INTEGER,
    snMetroRingPriPortActivePort   InterfaceIndex,
    snMetroRingSecPortActivePort   InterfaceIndex
}

snMetroRingVLanId OBJECT-TYPE
    SYNTAX     Integer32
    MAX-ACCESS not-accessible
    STATUS     current
    DESCRIPTION
            "Identifier of a VLAN that controls the metro ring."
    ::= { snMetroRingEntry 1 }

snMetroRingId OBJECT-TYPE
    SYNTAX     Integer32
    MAX-ACCESS not-accessible
    STATUS     current
    DESCRIPTION
            "Metro ring identifier."
    ::= { snMetroRingEntry 2 }

snMetroRingConfigState OBJECT-TYPE
    SYNTAX     INTEGER { other(1), enabled(2), disabled(3) }
    MAX-ACCESS read-write
    STATUS     current
    DESCRIPTION
            "Metro ring state."
    ::= { snMetroRingEntry 3 }

snMetroRingRole OBJECT-TYPE
    SYNTAX     INTEGER { other(1), master(2), member(3) }
    MAX-ACCESS read-write
    STATUS     current
    DESCRIPTION
            "Metro ring role.
            other(1).........none of the cases in below.
            master(2)........device which originates RHP packets.
            member(3)........device which forwards RHP packets."
    ::= { snMetroRingEntry 4 }

snMetroRingHelloTime OBJECT-TYPE
    SYNTAX     Integer32
    MAX-ACCESS read-write
    STATUS     current
    DESCRIPTION
            "The time interval to periodically transmit ring health
            protocol (RHP). Each unit is millisecond."
    ::= { snMetroRingEntry 5 }

snMetroRingPreforwardingTime OBJECT-TYPE
    SYNTAX     Integer32
    MAX-ACCESS read-write
    STATUS     current
    DESCRIPTION
            "The time interval of which a metro ring port is staying
            in preforwarding state before changing to forwarding state.
            Each unit is millisecond."
    ::= { snMetroRingEntry 6 }

snMetroRingPort1 OBJECT-TYPE
    SYNTAX     InterfaceIndex
    MAX-ACCESS read-write
    STATUS     current
    DESCRIPTION
            "The ifIndex value of port 1 to configure into the metro ring."
    ::= { snMetroRingEntry 7 }

snMetroRingPort2 OBJECT-TYPE
    SYNTAX     InterfaceIndex
    MAX-ACCESS read-write
    STATUS     current
    DESCRIPTION
            "The ifIndex value of port 2 to configure into the metro ring."
    ::= { snMetroRingEntry 8 }

snMetroRingName OBJECT-TYPE
    SYNTAX     DisplayString
    MAX-ACCESS read-write
    STATUS     current
    DESCRIPTION
            "The metro ring description."
    ::= { snMetroRingEntry 9 }

snMetroRingRowStatus OBJECT-TYPE
    SYNTAX     INTEGER {
                 other(1),
                 valid(2),
                 delete(3),
                 create(4)
               }
    MAX-ACCESS read-write
    STATUS     current
    DESCRIPTION
            "This object is used to create and delete row in the
            table and control if they are used. The values that
            can be written are:
            delete(3)...deletes the row
            create(4)...creates a new row

            If the row exists, then a SET with value of create(4)
            returns error 'badValue'. Deleted rows go away immediately.
            The following values can be returned on reads:
            noSuchName...no such row
            other(1).....some other cases
            valid(2)....the row exists and is valid"
    ::= { snMetroRingEntry 10 }

snMetroRingOperState OBJECT-TYPE
    SYNTAX     INTEGER { other(1), enabled(2), disabled(3) }
    MAX-ACCESS read-only
    STATUS     current
    DESCRIPTION
            "Metro ring operational state."
    ::= { snMetroRingEntry 11 }

snMetroRingTopoGroupId OBJECT-TYPE
    SYNTAX     Integer32
    MAX-ACCESS read-only
    STATUS     current
    DESCRIPTION
            "Topology group ID that controls the metro ring."
    ::= { snMetroRingEntry 12 }

snMetroRingRHPTransmitted OBJECT-TYPE
    SYNTAX     Counter32
    MAX-ACCESS read-only
    STATUS     current
    DESCRIPTION
            "Ring health protocol (RHP) transmitted counter."
    ::= { snMetroRingEntry 13 }

snMetroRingRHPReceived OBJECT-TYPE
    SYNTAX     Counter32
    MAX-ACCESS read-only
    STATUS     current
    DESCRIPTION
            "Ring health protocol (RHP) received counter."
    ::= { snMetroRingEntry 14 }

snMetroRingStateChanged OBJECT-TYPE
    SYNTAX     Counter32
    MAX-ACCESS read-only
    STATUS     current
    DESCRIPTION
            "Ring state changed counter."
    ::= { snMetroRingEntry 15 }

snMetroRingTCRBPDUReceived OBJECT-TYPE
    SYNTAX     Counter32
    MAX-ACCESS read-only
    STATUS     current
    DESCRIPTION
            "Topology change protocol received counter."
    ::= { snMetroRingEntry 16 }

snMetroRingPriPort OBJECT-TYPE
    SYNTAX     InterfaceIndex
    MAX-ACCESS read-only
    STATUS     current
    DESCRIPTION
            "The ifIndex value of primary port."
    ::= { snMetroRingEntry 17 }

snMetroRingSecPort OBJECT-TYPE
    SYNTAX     InterfaceIndex
    MAX-ACCESS read-only
    STATUS     current
    DESCRIPTION
            "The ifIndex value of secondary port."
    ::= { snMetroRingEntry 18 }

snMetroRingPriPortState OBJECT-TYPE
    SYNTAX     INTEGER {
                 other(1),
                 preforwarding(2),
                 forwarding(3),
                 blocking(4),
                 disabled(5)
               }
    MAX-ACCESS read-only
    STATUS     current
    DESCRIPTION
            "Metro ring primary port state.
            other(1)...........none of the cases in below.
            preforwarding(2)...port transmits RHP packets,
                               port does not transmit data packets.
            forwarding(3)......port transmits RHP and data packets.
            blocking(4)........port receives RHP packets,
                               port does not receive data packets.
            disabled(5)........port is disabled from metro ring."
    ::= { snMetroRingEntry 19 }

snMetroRingSecPortState OBJECT-TYPE
    SYNTAX     INTEGER {
                 other(1),
                 preforwarding(2),
                 forwarding(3),
                 blocking(4),
                 disabled(5)
               }
    MAX-ACCESS read-only
    STATUS     current
    DESCRIPTION
            "Metro ring secondary port state.
            other(1)...........none of the cases in below.
            preforwarding(2)...port transmits RHP packets,
                               port does not transmit data packets.
            forwarding(3)......port transmits RHP and data packets.
            blocking(4)........port receives RHP packets,
                               port does not receive data packets.
            disabled(5)........port is disabled from metro ring."
    ::= { snMetroRingEntry 20 }

snMetroRingPriPortType OBJECT-TYPE
    SYNTAX     INTEGER { other(1), regular(2), tunnel(3) }
    MAX-ACCESS read-only
    STATUS     current
    DESCRIPTION
            "Metro ring primary port type.
            other(1).....none of the cases in below.
            regular(2)...port is configured to operate on a single ring.
            tunnel(3)....port is configured to operate on multiple rings."
    ::= { snMetroRingEntry 21 }

snMetroRingSecPortType OBJECT-TYPE
    SYNTAX     INTEGER { other(1), regular(2), tunnel(3) }
    MAX-ACCESS read-only
    STATUS     current
    DESCRIPTION
            "Metro ring secondary port type.
            other(1).....none of the cases in below.
            regular(2)...port is configured to operate on a single ring.
            tunnel(3)....port is configured to operate on multiple rings."
    ::= { snMetroRingEntry 22 }

snMetroRingPriPortActivePort OBJECT-TYPE
    SYNTAX     InterfaceIndex
    MAX-ACCESS read-only
    STATUS     current
    DESCRIPTION
            "The ifIndex value of active primary port."
    ::= { snMetroRingEntry 23 }

snMetroRingSecPortActivePort OBJECT-TYPE
    SYNTAX     InterfaceIndex
    MAX-ACCESS read-only
    STATUS     current
    DESCRIPTION
            "The ifIndex value of active secondary port."
    ::= { snMetroRingEntry 24 }

END		
FOUNDRY-SN-STACKING-MIB DEFINITIONS ::= BEGIN

IMPORTS
	MODULE-IDENTITY, OBJECT-TYPE, Integer32
	  FROM SNMPv2-SMI
	snSwitch
		FROM FOUNDRY-SN-SWITCH-GROUP-MIB
	MacAddress
	  FROM SNMPv2-TC
	DisplayString
	  FROM FOUNDRY-SN-AGENT-MIB
	InterfaceIndexOrZero
	  FROM IF-MIB;
snStacking MODULE-IDENTITY
	LAST-UPDATED "200805050000Z" -- May 5, 2008
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			Management Information for stacking system
			configuration and operational status.
			
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"
	REVISION     "200805050000Z" -- May 5, 2008
	DESCRIPTION
			""
   ::= { snSwitch 31}


--
-- Stacking system
--

snStackingGlobalObjects OBJECT IDENTIFIER ::= { snStacking 1 }
snStackingTableObjects  OBJECT IDENTIFIER ::= { snStacking 2 }

--
-- Stacking system Global Scalar Object Section
--

snStackingGlobalConfigState OBJECT-TYPE
	SYNTAX     INTEGER { 
			  none(0), 
			  enabled(1),
			  disabled(2)
			}
	MAX-ACCESS read-write
	STATUS     current
	DESCRIPTION
		"Configure stack state for stacking feature on the global level.
		 none: neutral, receive packets only
		 enable: stacking is enable, send and receive packets
		 disable: stacking is disable, No send and receive packets"
	::= { snStackingGlobalObjects 1}

snStackingGlobalMacAddress OBJECT-TYPE
	SYNTAX     MacAddress
	MAX-ACCESS read-write
	STATUS     current
	DESCRIPTION
		"Management MAC address of the stacking system.
		This is available to change management MAC address of stack 
		for administrative purpose. It is strongly recommended that this 
		command should be used with upmost caution to prevent duplicate 
		MAC address and must reboot the system to take an effect.
		It is mutually exclusive from enabling the persistent MAC timer. 
		Enter zero MAC address to remove the configured MAC address"
	::= { snStackingGlobalObjects 2 }

snStackingGlobalPersistentMacTimerState OBJECT-TYPE
	SYNTAX     INTEGER { 
			  enabled(0),
			  disabled(1)
			}
	MAX-ACCESS read-write
	STATUS     current
	DESCRIPTION
		"Configure persistent MAC timer state for stacking feature on the global level.
		 enable: the persistent MAC timer is active and configured. The persistent MAC 
					  timer is set as the default timer (60 minutes)
		 disable: deactivate the persistent MAC timer. It will stop the use of persistent MAC
					  address and use new active stack unit's base MAC address "
	::= { snStackingGlobalObjects 3}
	
snStackingGlobalPersistentMacTimer OBJECT-TYPE
	SYNTAX     Integer32
	MAX-ACCESS read-write
	STATUS     current
	DESCRIPTION
		"Persistent MAC timer in minutes for the stacking system
		Number of minutes to retain original active stack unit's base MAC address in event of 
		active unit crash or removal. This timer is triggered when new active unit is elected. 
		When timer expires, new active unit will change stacking MAC to its own base MAC 
		address and advertise its own base MAC address to management VLAN to update the
		ARP table of peers. If you decide to use new active unit's MAC address, one must enter 
		this timer again to reactivate the persistent MAC.
				  0 - keep it forever.
				  5  to 6000 - valid value range. 
				  60 - default value."
	::= { snStackingGlobalObjects 4 }

snStackingGlobalTopology OBJECT-TYPE
	SYNTAX     INTEGER {
			  other(1),
				 chain(2),
				 ring(3),
				 standalone(4)
			   }
	MAX-ACCESS read-only
	STATUS     current
	DESCRIPTION
		"The topology of the stacking system "
	::= { snStackingGlobalObjects 5 }

snStackingGlobalMode OBJECT-TYPE
	SYNTAX     INTEGER {
			stackingMode(1),
			nonStackingMode(2)
			}
	MAX-ACCESS read-only
	STATUS     current
	DESCRIPTION
		"The stacking mode of the system. 
		stackingMode: the system has been installed STK EEPROM, and it is in stacking mode.
		nonStackingMode:the system has not been installed STK EEPROM, and it is not in stacking mode.
		"
	::= { snStackingGlobalObjects 6 }

snStackingGlobalMixedMode OBJECT-TYPE
	SYNTAX     INTEGER {
			mixedStackingMode(1),
			classicStackingMode(2)
			}
	MAX-ACCESS read-only
	STATUS     current
	DESCRIPTION
		"The mixed stacking mode of the system. 
		mixedStackingMode: the system is in a mixed stacking mode (heterogeneous stacking).
		classicStackingMode: the system is not in a mixed stacking mode (homogeneous stacking).
		"
	::= { snStackingGlobalObjects 7 }

snStackingGlobalMaxUnitNumber OBJECT-TYPE
	SYNTAX     Integer32
	MAX-ACCESS read-only
	STATUS     current
	DESCRIPTION
		"The max number of units in the stacking system. 1 as default value for no-stacking device"
	::= { snStackingGlobalObjects 8 }

snStackingGlobalHighestPriority OBJECT-TYPE
	SYNTAX     Integer32
	MAX-ACCESS read-only
	STATUS     current
	DESCRIPTION
		"The highest stack priority that can be configured in the stacking system. 0 as default value 
		for no-stacking device"
	::= { snStackingGlobalObjects 9 }

	
--
-- Stacking system Table Object Section
--

--
-- Stacking configuration unit Table
-- Use this table to display and configure stacking related information for each unit
--

snStackingConfigUnitTable OBJECT-TYPE
	SYNTAX     SEQUENCE OF SnStackingConfigUnitEntry
	MAX-ACCESS not-accessible
	STATUS     current
	DESCRIPTION
		"Stacking configuration unit table."
	::= { snStackingTableObjects 1 }

snStackingConfigUnitEntry OBJECT-TYPE
	SYNTAX     SnStackingConfigUnitEntry
	MAX-ACCESS not-accessible
	STATUS     current
	DESCRIPTION
		"An entry in the stacking configuration table."
	INDEX { snStackingConfigUnitIndex }
	::= { snStackingConfigUnitTable 1 }

SnStackingConfigUnitEntry ::= SEQUENCE {
	snStackingConfigUnitIndex                          Integer32,
	snStackingConfigUnitPriority                       Integer32,
	snStackingConfigUnitConfigStackPort          InterfaceIndexOrZero,
	snStackingConfigUnitRowStatus                  INTEGER,
	snStackingConfigUnitType                          DisplayString,
	snStackingConfigUnitState                          INTEGER,
	snStackingConfigUnitStackPort1                  InterfaceIndexOrZero,
	snStackingConfigUnitStackPort2                  InterfaceIndexOrZero,
	snStackingConfigUnitConnectPort1              InterfaceIndexOrZero,
	snStackingConfigUnitConnectPort2              InterfaceIndexOrZero
}

snStackingConfigUnitIndex OBJECT-TYPE
	SYNTAX Integer32
	MAX-ACCESS not-accessible
	STATUS     current
	DESCRIPTION
		"The stacking unit Id"
	::= { snStackingConfigUnitEntry 1 }

 snStackingConfigUnitPriority OBJECT-TYPE
	SYNTAX     Integer32 (0..255)
	MAX-ACCESS read-write
	STATUS     current
	DESCRIPTION
		"The priority in Active/backup eclection."
	::= { snStackingConfigUnitEntry 2 }

 snStackingConfigUnitConfigStackPort OBJECT-TYPE
	SYNTAX		InterfaceIndexOrZero
	MAX-ACCESS  read-write
	STATUS     current
	DESCRIPTION
		"The IfIndex for the configured stacking port. If no 
		stacking port is configured, it will be displayed zero 
		and the first  two 10G ports as the default stacking ports. 
		Enter zero to remove the configured stacking port. "
	::= { snStackingConfigUnitEntry 3 }
	
snStackingConfigUnitRowStatus OBJECT-TYPE
	SYNTAX     INTEGER {
				 other(1),
				 valid(2),
				 delete(3)
		  --       create(4)
			   }
	MAX-ACCESS read-write
	STATUS     current
	DESCRIPTION
			"This object is used to delete row in the
			table and control if they are used. The values that
			can be written are:
			delete(3)...deletes the row

			If the row exists, then a SET with value of create(4)
			returns error 'wrongValue'. Deleted rows go away immediately.
			The following values can be returned on reads:
			noSuchName...no such row
			other(1).....some other cases
			valid(2)....the row exists and is valid"
	::= { snStackingConfigUnitEntry 4 }


snStackingConfigUnitType OBJECT-TYPE
	SYNTAX	DisplayString
	MAX-ACCESS read-only
	   STATUS     current
	DESCRIPTION
		"A description of the configured/active system type for each unit."
	::= { snStackingConfigUnitEntry 5 }

snStackingConfigUnitState OBJECT-TYPE
	SYNTAX     INTEGER {
				 local(1),
				 remote(2),
				 reserved(3),
				 empty(4)
			   }
	MAX-ACCESS read-only
	STATUS     current
	DESCRIPTION
		"A state for each unit "
	::= { snStackingConfigUnitEntry 6 }

 snStackingConfigUnitStackPort1 OBJECT-TYPE
	SYNTAX		InterfaceIndexOrZero
	MAX-ACCESS read-only
	STATUS     current
	DESCRIPTION
		"First stack port for each unit. It returns 0 if stack port does not exist."
	::= { snStackingConfigUnitEntry 7 }


 snStackingConfigUnitStackPort2 OBJECT-TYPE
	SYNTAX		InterfaceIndexOrZero
	MAX-ACCESS read-only
	STATUS     current
	DESCRIPTION
		"Second stack port for each unit. It returns 0 if stack port does not exist."
	::= { snStackingConfigUnitEntry 8 }

 snStackingConfigUnitConnectPort1 OBJECT-TYPE
	SYNTAX		InterfaceIndexOrZero
	MAX-ACCESS read-write
	STATUS     current
	DESCRIPTION
		"First connect port for a peripheral unit in a mixed stacking system.  A peripheral
		unit can have up to two connect ports that is is conected to. They are suggested
		neighbor linking ports. Thus, they could be code units' periport/trunk or peripheral 
		units' stacking port. It returns 0 if connect port does not exist."
	::= { snStackingConfigUnitEntry 9 }

 snStackingConfigUnitConnectPort2 OBJECT-TYPE
	SYNTAX		InterfaceIndexOrZero
	MAX-ACCESS read-write
	STATUS     current
	DESCRIPTION
		"second connect port for a peripheral unit in a mixed stacking system.  A peripheral
		unit can have up to two connect ports that is is conected to. They are suggested
		neighbor linking ports. Thus, they could be code units' periport/trunk or peripheral 
		units' stacking port. It returns 0 if connect port does not exist."
	::= { snStackingConfigUnitEntry 10 }

	
--
-- Stacking operation unit Table
-- Use this table to display stacking related information for each operational unit
--

snStackingOperUnitTable OBJECT-TYPE
	SYNTAX     SEQUENCE OF SnStackingOperUnitEntry
	MAX-ACCESS not-accessible
	STATUS     current
	DESCRIPTION
		"Stacking operation unit table."
	::= { snStackingTableObjects 2 }

snStackingOperUnitEntry OBJECT-TYPE
	SYNTAX     SnStackingOperUnitEntry
	MAX-ACCESS not-accessible
	STATUS     current
	DESCRIPTION
		"An entry in the stacking operation table."
	INDEX { snStackingOperUnitIndex }
	::= { snStackingOperUnitTable 1 }

SnStackingOperUnitEntry ::= SEQUENCE {
	snStackingOperUnitIndex                    Integer32,
	snStackingOperUnitRole                     INTEGER,
	snStackingOperUnitMac                      MacAddress,
	snStackingOperUnitPriority                 Integer32,
	snStackingOperUnitState                    INTEGER,
	snStackingOperUnitDescription            DisplayString,
	snStackingOperUnitStackPort1            InterfaceIndexOrZero,
	snStackingOperUnitStackPort1State     INTEGER,
	snStackingOperUnitStackPort2            InterfaceIndexOrZero,
	snStackingOperUnitStackPort2State     INTEGER,
	snStackingOperUnitNeighbor1             Integer32,
	snStackingOperUnitNeighbor2             Integer32,
	snStackingOperUnitImgVer                 DisplayString,
	snStackingOperUnitBuildlVer               DisplayString
  
}

snStackingOperUnitIndex OBJECT-TYPE
	SYNTAX     Integer32 
	MAX-ACCESS not-accessible
	STATUS     current
	DESCRIPTION
		"The stacking unit Id"
	::= { snStackingOperUnitEntry 1 }

 snStackingOperUnitRole OBJECT-TYPE
	SYNTAX     INTEGER {
			  other(1),
				 active(2),
				 standby(3),
				 member(4),
				 standalone(5)
			   }
	MAX-ACCESS read-only
	STATUS     current
	DESCRIPTION
		"A role for each unit "
	::= { snStackingOperUnitEntry 2 }

snStackingOperUnitMac OBJECT-TYPE
	SYNTAX     MacAddress
	MAX-ACCESS read-only
	STATUS     current
	DESCRIPTION
		"A MAC address for each unit"
	::= { snStackingOperUnitEntry 3 }

snStackingOperUnitPriority OBJECT-TYPE
	SYNTAX     Integer32 (0..255)
	MAX-ACCESS read-only
	STATUS     current
	DESCRIPTION
		"The priority in Active/backup eclection."
	::= { snStackingOperUnitEntry 4 }

 snStackingOperUnitState OBJECT-TYPE
	SYNTAX     INTEGER {
				 local(1),
				 remote(2),
				 reserved(3),
				 empty(4)
			   }
	MAX-ACCESS read-only
	STATUS     current
	DESCRIPTION
		"A state for each unit "
	::= { snStackingOperUnitEntry 5}

 snStackingOperUnitDescription OBJECT-TYPE
	SYNTAX		DisplayString (SIZE (0..128))
	MAX-ACCESS read-only
	STATUS     current
	DESCRIPTION
		"Describes the stacking state for each unit."
	::= { snStackingOperUnitEntry 6 }

 snStackingOperUnitStackPort1 OBJECT-TYPE
	SYNTAX		InterfaceIndexOrZero
	MAX-ACCESS read-only
	STATUS     current
	DESCRIPTION
		"First stack port for each unit. It returns 0 if stack port does not exist."
	::= { snStackingOperUnitEntry 7 }

 snStackingOperUnitStackPort1State OBJECT-TYPE
	SYNTAX     INTEGER {
		other(1),
		up(2),
		down(3)
	}
	MAX-ACCESS read-only
	STATUS     current
	DESCRIPTION
		"The first stack port state for each unit. "
	::= { snStackingOperUnitEntry 8 }


 snStackingOperUnitStackPort2 OBJECT-TYPE
	SYNTAX		InterfaceIndexOrZero
	MAX-ACCESS read-only
	STATUS     current
	DESCRIPTION
		"Second stack port for each unit. It returns 0 if stack port does not exist."
	::= { snStackingOperUnitEntry 9 }

 snStackingOperUnitStackPort2State OBJECT-TYPE
	SYNTAX     INTEGER {
		other(1),
		up(2),
		down(3)
	}
	MAX-ACCESS read-only
	STATUS     current
	DESCRIPTION
		"The second stack port state for each unit. "
	::= { snStackingOperUnitEntry 10 }

 snStackingOperUnitNeighbor1 OBJECT-TYPE
	SYNTAX		 Integer32
	MAX-ACCESS read-only
	STATUS     current
	DESCRIPTION
	"Stacking neighbor unit (left) number. 
	If there is no neighbor unit, then it returns 0."

	::= { snStackingOperUnitEntry 11 }

 snStackingOperUnitNeighbor2 OBJECT-TYPE
	SYNTAX		Integer32
	MAX-ACCESS read-only
	STATUS     current
	DESCRIPTION
	"Stacking neighbor unit (left) number. 
	If there is no neighbor unit, then it returns 0."
	::= { snStackingOperUnitEntry 12 }
	
snStackingOperUnitImgVer OBJECT-TYPE
	SYNTAX		DisplayString (SIZE (0..32))
	MAX-ACCESS read-only
	STATUS     current
	DESCRIPTION
		"The version of the running software image"
	::= { snStackingOperUnitEntry 13 }

snStackingOperUnitBuildlVer OBJECT-TYPE
	SYNTAX		DisplayString (SIZE (0..32))
	MAX-ACCESS read-only
	STATUS     current
	DESCRIPTION
		"The version of the running software build"
	::= { snStackingOperUnitEntry 14 }

--
-- Stacking configuration stack trunk Table
-- Use this table to display and configure stack trunks for each unit
--

snStackingConfigStackTrunkTable OBJECT-TYPE
	SYNTAX     SEQUENCE OF SnStackingConfigStackTrunkEntry
	MAX-ACCESS not-accessible
	STATUS     current
	DESCRIPTION
		"Stacking configuration stack trunk table."
	::= { snStackingTableObjects 3 }

snStackingConfigStackTrunkEntry OBJECT-TYPE
	SYNTAX     SnStackingConfigStackTrunkEntry
	MAX-ACCESS not-accessible
	STATUS     current
	DESCRIPTION
		"An entry in the stacking configuration Stack trunk table."
	INDEX { snStackingConfigStackTrunkUnit, snStackingConfigStackTrunkPort1,
	             snStackingConfigStackTrunkPort2 }
	::= { snStackingConfigStackTrunkTable 1 }

SnStackingConfigStackTrunkEntry ::= SEQUENCE {
	snStackingConfigStackTrunkUnit                   Integer32,
	snStackingConfigStackTrunkPort1                 InterfaceIndexOrZero,
	snStackingConfigStackTrunkPort2                 InterfaceIndexOrZero,
	snStackingConfigStackTrunkRowStatus        INTEGER,
 	snStackingConfigStackTrunkNumPort1          Integer32,
 	snStackingConfigStackTrunkNumPort2          Integer32
}

snStackingConfigStackTrunkUnit OBJECT-TYPE
	SYNTAX Integer32
	MAX-ACCESS not-accessible
	STATUS     current
	DESCRIPTION
		"The stacking unit Id"
	::= { snStackingConfigStackTrunkEntry 1 }

 snStackingConfigStackTrunkPort1 OBJECT-TYPE
	SYNTAX		InterfaceIndexOrZero
	MAX-ACCESS  not-accessible
	STATUS     current
	DESCRIPTION
		"The IfIndex for the first (primary) port of the configured stack trunk. 
		There are two ports per stack trunk. In some case, a physical port may contain 
		more than one port, e.g. one 40G (1/2/2) for ICX6610 has 4x10G ports. 
		It returns 0 if the port does not exist." 
	::= { snStackingConfigStackTrunkEntry 2 }

 snStackingConfigStackTrunkPort2 OBJECT-TYPE
	SYNTAX		InterfaceIndexOrZero
	MAX-ACCESS  not-accessible
	STATUS     current
	DESCRIPTION
		"The IfIndex for the second port of the configured stack trunk. 
		There are two ports per stack trunk. In some case, a physical port may contain 
		more than one logical port, e.g. one 40G (1/2/2) for ICX6610 has 4x10G ports. 
		It returns 0 if the port does not exist." 
	::= { snStackingConfigStackTrunkEntry 3 }
	
snStackingConfigStackTrunkRowStatus OBJECT-TYPE
	SYNTAX     INTEGER {
				 other(1),
				 valid(2),
				 delete(3),
		                 create(4)
			   }
	MAX-ACCESS read-write
	STATUS     current
	DESCRIPTION
			"This object is used to delete row in the
			table and control if they are used. The values that
			can be written are:
			delete(3)...deletes the row

			If the row exists, then a SET with value of create(4)
			returns error 'wrongValue'. Deleted rows go away immediately.
			The following values can be returned on reads:
			noSuchName...no such row
			other(1).....some other cases
			valid(2)....the row exists and is valid"
	::= { snStackingConfigStackTrunkEntry 4 }

 snStackingConfigStackTrunkNumPort1 OBJECT-TYPE
	SYNTAX		Integer32
	MAX-ACCESS  read-only
	STATUS     current
	DESCRIPTION
		" Number of logical ports for the first (primary) port of the configured stack trunk. 
		In some case, a physical port may contain more than one logical port, 
		e.g. one 40G (1/2/2) for ICX6610 has 4x10G ports.  It returns 0 if the port 
		does not exist." 
	::= { snStackingConfigStackTrunkEntry 5 }

 snStackingConfigStackTrunkNumPort2 OBJECT-TYPE
	SYNTAX		Integer32
	MAX-ACCESS  read-only
	STATUS     current
	DESCRIPTION
		" Number of logical ports for the second port of the configured stack trunk. 
		In some case, a physical port may contain more than one logical port, 
		e.g. one 40G (1/2/2) for ICX6610 has 4x10G ports.  It returns 0 if the port 
		does not exist." 
	::= { snStackingConfigStackTrunkEntry 6 }

--
-- Stacking configuration peripheral port Table
-- Use this table to display and configure mixed stacking peripheral ports  for each unit
--

snStackingConfigPeriPortTable OBJECT-TYPE
	SYNTAX     SEQUENCE OF SnStackingConfigPeriPortEntry
	MAX-ACCESS not-accessible
	STATUS     current
	DESCRIPTION
		"Stacking configuration peripheral port table."
	::= { snStackingTableObjects 4 }

snStackingConfigPeriPortEntry OBJECT-TYPE
	SYNTAX     SnStackingConfigPeriPortEntry
	MAX-ACCESS not-accessible
	STATUS     current
	DESCRIPTION
		"An entry in the stacking configuration peripheral port table."
	INDEX { snStackingConfigPeriPortUnit, snStackingConfigPeriPortPort }
	::= { snStackingConfigPeriPortTable 1 }

SnStackingConfigPeriPortEntry ::= SEQUENCE {
	snStackingConfigPeriPortUnit                   Integer32,
	snStackingConfigPeriPortPort                  InterfaceIndexOrZero,
	snStackingConfigPeriPortRowStatus        INTEGER
}

snStackingConfigPeriPortUnit OBJECT-TYPE
	SYNTAX Integer32
	MAX-ACCESS not-accessible
	STATUS     current
	DESCRIPTION
		"The stacking unit Id"
	::= { snStackingConfigPeriPortEntry 1 }

 snStackingConfigPeriPortPort OBJECT-TYPE
	SYNTAX		InterfaceIndexOrZero
	MAX-ACCESS  not-accessible
	STATUS     current
	DESCRIPTION
		"The IfIndex for the configured mixed stacking peripheral port. 
		It is up to eight peripheral ports per unit. "
	::= { snStackingConfigPeriPortEntry 2 }
	
snStackingConfigPeriPortRowStatus OBJECT-TYPE
	SYNTAX     INTEGER {
				 other(1),
				 valid(2),
				 delete(3),
		                 create(4)
			   }
	MAX-ACCESS read-write
	STATUS     current
	DESCRIPTION
			"This object is used to delete row in the
			table and control if they are used. The values that
			can be written are:
			delete(3)...deletes the row

			If the row exists, then a SET with value of create(4)
			returns error 'wrongValue'. Deleted rows go away immediately.
			The following values can be returned on reads:
			noSuchName...no such row
			other(1).....some other cases
			valid(2)....the row exists and is valid"
	::= { snStackingConfigPeriPortEntry 3 }


--
-- Stacking configuration peripheral trunk Table
-- Use this table to display and configure mixed stacking peripheral trunks  for each unit
--

snStackingConfigPeriTrunkTable OBJECT-TYPE
	SYNTAX     SEQUENCE OF SnStackingConfigPeriTrunkEntry
	MAX-ACCESS not-accessible
	STATUS     current
	DESCRIPTION
		"Stacking configuration peripheral trunk table."
	::= { snStackingTableObjects 5 }

snStackingConfigPeriTrunkEntry OBJECT-TYPE
	SYNTAX     SnStackingConfigPeriTrunkEntry
	MAX-ACCESS not-accessible
	STATUS     current
	DESCRIPTION
		"An entry in the stacking configuration peripheral trunk table."
	INDEX { snStackingConfigPeriTrunkUnit, snStackingConfigPeriTrunkPort1,
	             snStackingConfigPeriTrunkPort2 }
	::= { snStackingConfigPeriTrunkTable 1 }

SnStackingConfigPeriTrunkEntry ::= SEQUENCE {
	snStackingConfigPeriTrunkUnit                   Integer32,
	snStackingConfigPeriTrunkPort1                 InterfaceIndexOrZero,
	snStackingConfigPeriTrunkPort2                 InterfaceIndexOrZero,
	snStackingConfigPeriTrunkRowStatus        INTEGER
}

snStackingConfigPeriTrunkUnit OBJECT-TYPE
	SYNTAX Integer32
	MAX-ACCESS not-accessible
	STATUS     current
	DESCRIPTION
		"The stacking unit Id"
	::= { snStackingConfigPeriTrunkEntry 1 }

 snStackingConfigPeriTrunkPort1 OBJECT-TYPE
	SYNTAX		InterfaceIndexOrZero
	MAX-ACCESS  not-accessible
	STATUS     current
	DESCRIPTION
		"The IfIndex for the first port of the configured mixed stacking peripheral trunk. 
		There are two ports per peripheral trunk. It is up to four peripheral trunks per unit." 
	::= { snStackingConfigPeriTrunkEntry 2 }

 snStackingConfigPeriTrunkPort2 OBJECT-TYPE
	SYNTAX		InterfaceIndexOrZero
	MAX-ACCESS  not-accessible
	STATUS     current
	DESCRIPTION
		"The IfIndex for the second port of the configured mixed stacking peripheral trunk. 
		There are two ports per peripheral trunk. It is up to four peripheral trunks per unit." 
	::= { snStackingConfigPeriTrunkEntry 3 }
	
snStackingConfigPeriTrunkRowStatus OBJECT-TYPE
	SYNTAX     INTEGER {
				 other(1),
				 valid(2),
				 delete(3),
		                 create(4)
			   }
	MAX-ACCESS read-write
	STATUS     current
	DESCRIPTION
			"This object is used to delete row in the
			table and control if they are used. The values that
			can be written are:
			delete(3)...deletes the row

			If the row exists, then a SET with value of create(4)
			returns error 'wrongValue'. Deleted rows go away immediately.
			The following values can be returned on reads:
			noSuchName...no such row
			other(1).....some other cases
			valid(2)....the row exists and is valid"
	::= { snStackingConfigPeriTrunkEntry 4 }

--
-- Stacking neighbor port Table
-- Use this table to display stacking neighbor ports  for each unit
--

snStackingNeighborPortTable OBJECT-TYPE
	SYNTAX     SEQUENCE OF SnStackingNeighborPortEntry
	MAX-ACCESS not-accessible
	STATUS     current
	DESCRIPTION
		"Stacking neighbor port table."
	::= { snStackingTableObjects 6 }

snStackingNeighborPortEntry OBJECT-TYPE
	SYNTAX     SnStackingNeighborPortEntry
	MAX-ACCESS not-accessible
	STATUS     current
	DESCRIPTION
		"An entry in the stacking neighborport table."
	INDEX { snStackingNeighborPortUnit, snStackingNeighborPortStackPort }
	::= { snStackingNeighborPortTable 1 }

SnStackingNeighborPortEntry ::= SEQUENCE {
	snStackingNeighborPortUnit                   Integer32,
	snStackingNeighborPortStackPort                  InterfaceIndexOrZero,
	snStackingNeighborPortNeighborPort                  InterfaceIndexOrZero
}

snStackingNeighborPortUnit OBJECT-TYPE
	SYNTAX Integer32
	MAX-ACCESS not-accessible
	STATUS     current
	DESCRIPTION
		"The stacking unit Id"
	::= { snStackingNeighborPortEntry 1 }

 snStackingNeighborPortStackPort OBJECT-TYPE
	SYNTAX		InterfaceIndexOrZero
	MAX-ACCESS  not-accessible
	STATUS     current
	DESCRIPTION
		"The IfIndex for the stack port on this unit. 
		It is up to ten stack ports and peripheral ports per unit. "
	::= { snStackingNeighborPortEntry 2 }
	
 snStackingNeighborPortNeighborPort OBJECT-TYPE
	SYNTAX		InterfaceIndexOrZero
	MAX-ACCESS  read-only
	STATUS     current
	DESCRIPTION
		"The IfIndex for the neighbor port of  the stack port on this unit. 
		It returns 0 if neighbor port does not exist for this stack port. "
	::= { snStackingNeighborPortEntry 3 }
	
END
FOUNDRY-LAG-MIB DEFINITIONS ::= BEGIN

IMPORTS
    MODULE-IDENTITY, OBJECT-TYPE, Unsigned32
      FROM SNMPv2-SMI			-- [RFC2578]
    InterfaceIndex, ifIndex, InterfaceIndexOrZero
      FROM IF-MIB				-- [RFC2863]
    DisplayString, RowStatus
      FROM SNMPv2-TC			-- [RFC2579]
    snSwitch
      FROM FOUNDRY-SN-ROOT-MIB
    PhysAddress
      FROM FOUNDRY-SN-SWITCH-GROUP-MIB;

fdryLinkAggregationGroupMIB MODULE-IDENTITY
	LAST-UPDATED "200909300000Z" -- September 30, 2009
    ORGANIZATION "Foundry Networks, Inc"
    CONTACT-INFO
            "Technical Support Center, Foundry Networks,
            4980 Great America Parkway,
            Santa Clara, CA 95054
            Email: support@foundrynet.com
            Phone: 1-877-TURBO-CALL"
    DESCRIPTION
			"
			Management Information Base module for link aggregate group
            configuration and statistics. Link aggregation group is a new concept
            of trunk and this MIB is replacing FOUNDRY-SN-LAG-MIB in MLX/XMR products
			starting release 4.1.0.
			
			Copyright 1996-2008 Foundry Networks, Inc.
			All rights reserved.
			This Foundry Networks SNMP Management Information Base Specification
			embodies Foundry Networks confidential and proprietary
			intellectual property. Foundry Networks retains all
			title and ownership in the Specification, including any
			revisions.
			
			This Specification is supplied AS IS, and Foundry Networks makes
			no warranty, either express or implied, as to the use,
			operation, condition, or performance of the Specification.            
			
			"
	REVISION     "200909300000Z" -- September 30, 2009
	DESCRIPTION
			"convert from SMIv1 to SMIv2"            

   ::= { snSwitch 33 }

fdryLinkAggregationGroupTableObjects  OBJECT IDENTIFIER ::= { fdryLinkAggregationGroupMIB 1 }
fdryLinkAggregationGroupPortTableObjects  OBJECT IDENTIFIER ::= { fdryLinkAggregationGroupMIB 2 }
fdryLinkAggregationGroupLacpPortTableObjects  OBJECT IDENTIFIER ::= { fdryLinkAggregationGroupMIB 3 }

-- LinkAggregationGroup Global Scalar Object Section

-- LinkAggregationGroup Table Object Section

--
-- LinkAggregationGroup Table
--

fdryLinkAggregationGroupTable OBJECT-TYPE
    SYNTAX     SEQUENCE OF FdryLinkAggregationGroupEntry
    MAX-ACCESS not-accessible
    STATUS     current
    DESCRIPTION
            "LinkAggregationGroup table."
    ::= { fdryLinkAggregationGroupTableObjects 1 }

fdryLinkAggregationGroupEntry OBJECT-TYPE
    SYNTAX     FdryLinkAggregationGroupEntry
    MAX-ACCESS not-accessible
    STATUS     current
    DESCRIPTION
            "An entry of the Link Aggregate Group table."
    INDEX { fdryLinkAggregationGroupName }
    ::= { fdryLinkAggregationGroupTable 1 }

FdryLinkAggregationGroupEntry ::= SEQUENCE {
	fdryLinkAggregationGroupName                 DisplayString,
    fdryLinkAggregationGroupType                  INTEGER,
    fdryLinkAggregationGroupAdminStatus       INTEGER,
    fdryLinkAggregationGroupIfList                  OCTET STRING,
    fdryLinkAggregationGroupPrimaryPort        InterfaceIndexOrZero,
    fdryLinkAggregationGroupTrunkType          INTEGER,
    fdryLinkAggregationGroupTrunkThreshold   Unsigned32,
    fdryLinkAggregationGroupLacpTimeout       INTEGER,
    fdryLinkAggregationGroupIfIndex              InterfaceIndexOrZero,
    fdryLinkAggregationGroupPortCount           Unsigned32,
    fdryLinkAggregationGroupRowStatus          RowStatus,
    fdryLinkAggregationGroupId                      Unsigned32
}

fdryLinkAggregationGroupName OBJECT-TYPE
    SYNTAX     DisplayString (SIZE(1..64))
    MAX-ACCESS not-accessible
    STATUS     current
    DESCRIPTION
            "Name of a LinkAggregationGroup."
    ::= { fdryLinkAggregationGroupEntry 1 }

fdryLinkAggregationGroupType OBJECT-TYPE
    SYNTAX     INTEGER { static(1), dynamic(2), keepalive(3) }
    MAX-ACCESS read-create
    STATUS     current
    DESCRIPTION
            "LinkAggregationGroup type."
    ::= { fdryLinkAggregationGroupEntry 2 }

fdryLinkAggregationGroupAdminStatus OBJECT-TYPE
    SYNTAX     INTEGER { deploy(1), deployPassive(2), undeploy(3), undeployForced(4) }
    MAX-ACCESS read-create
    STATUS     current
    DESCRIPTION
         "The desired deplyed state of this LinkAggregationGroup entry. 
         This is not the operational status. Refer to ifTable for the 
         operational status.
         deploy(1).............deploy the LAG and set to LACP active if dynamic LAG.
         deployPassive(2)..deploy the LAG and set to LACP passive if dynamic LAG.
         undeploy(3).........undeploy the LAG if no more than 2 ports are enabled.
         undeployForced(4)..undeploy the LAG regardless number of ports enabled.
                                      This is a write-only value.
         In particular, a row cannot be deployed until the corresponding 
         instances of fdryLinkAggregationGroupIfList has been set."
    ::= { fdryLinkAggregationGroupEntry 3 }

fdryLinkAggregationGroupIfList OBJECT-TYPE
    SYNTAX  OCTET STRING
    MAX-ACCESS read-create
    STATUS     current
    DESCRIPTION
            "A list of interface indices which are the port membership
            of a trunk group. Each interface index is a 32-bit integer
            in big endian order."
    ::= { fdryLinkAggregationGroupEntry 4 }

fdryLinkAggregationGroupPrimaryPort OBJECT-TYPE
    SYNTAX     InterfaceIndexOrZero
    MAX-ACCESS read-create
    STATUS     current
    DESCRIPTION
            "The primary port for the Link Aggregation Group. This must
            be set before deploying the LinkAggregateGroup unless this is
            a keepalive LinkAggregateGroup.  Zero will be returned 
            for primary ports not set"
    ::= { fdryLinkAggregationGroupEntry 5 }

fdryLinkAggregationGroupTrunkType OBJECT-TYPE
    SYNTAX     INTEGER { hashBased(1), perPacket(2) }
    MAX-ACCESS read-create
    STATUS     current
    DESCRIPTION
            "The trunk connection type which specifies what the scheme
            of load-sharing among the trunk ports is."
    ::= { fdryLinkAggregationGroupEntry 6 }

fdryLinkAggregationGroupTrunkThreshold OBJECT-TYPE
    SYNTAX     Unsigned32
    MAX-ACCESS read-create
    STATUS     current
    DESCRIPTION
            "The number of UP ports needed to keep the trunk up.
            Not applicable for keepalive LAG."
    ::= { fdryLinkAggregationGroupEntry 7 }

fdryLinkAggregationGroupLacpTimeout OBJECT-TYPE
    SYNTAX     INTEGER { default(1), long(2), short(3) }
    MAX-ACCESS read-create
    STATUS     current
    DESCRIPTION
            "The LACP timeout value this LACP LAG will use. Applicable for
            dynamic and keepalive LAG only."
    ::= { fdryLinkAggregationGroupEntry 8 }

fdryLinkAggregationGroupIfIndex OBJECT-TYPE
    SYNTAX     InterfaceIndexOrZero
    MAX-ACCESS read-only
    STATUS     current
    DESCRIPTION
            "After deployment the operation information of a LAG entry will be
            represented in an entry in ifTable. Use this variable as the ifIndex
            to access the entry in ifTable and ifXTable. Zero will be returned 
            for LAGs not yet deployed."
    ::= { fdryLinkAggregationGroupEntry 9 }

fdryLinkAggregationGroupPortCount OBJECT-TYPE
    SYNTAX     Unsigned32
    MAX-ACCESS read-only
    STATUS     current
    DESCRIPTION
            "The number of member ports belong to this LAG."
    ::= { fdryLinkAggregationGroupEntry 10 }

fdryLinkAggregationGroupRowStatus OBJECT-TYPE
    SYNTAX      RowStatus
    MAX-ACCESS  read-create
    STATUS      current
    DESCRIPTION
        "The status of this conceptual row.

        createAndWait(5) is not supported.

        To create a row in this table, a manager must
        set this object to createAndGo(4) together with the setting of
        fdryLinkAggregationGroupType. After that the row status becomes
        active(1) regardless the LAG entry is deployed or not.

        To deploy the LAG entry, set the corresponding instance of
        fdryLinkAggregationGroupAdminStatus to deployActive or deployPassive."
    ::= { fdryLinkAggregationGroupEntry 11 }

fdryLinkAggregationGroupId OBJECT-TYPE
    SYNTAX     Unsigned32
    MAX-ACCESS read-only
    STATUS     current
    DESCRIPTION
            "The numeric identifier assigned to this LAG."
    ::= { fdryLinkAggregationGroupEntry 12 }

--
-- LinkAggregationGroupPort Table
--

fdryLinkAggregationGroupPortTable OBJECT-TYPE
    SYNTAX     SEQUENCE OF FdryLinkAggregationGroupPortEntry
    MAX-ACCESS not-accessible
    STATUS     current
    DESCRIPTION
            "A table that contains Link Aggregation Control
            configuration information about every
            Aggregation Port associated with this device.
            A row appears in this table for each physical port."
    ::= { fdryLinkAggregationGroupPortTableObjects 1 }

fdryLinkAggregationGroupPortEntry OBJECT-TYPE
    SYNTAX     FdryLinkAggregationGroupPortEntry
    MAX-ACCESS not-accessible
    STATUS     current
    DESCRIPTION
            "An entry of the Link Aggregate Group Port table."
    INDEX { fdryLinkAggregationGroupName, ifIndex }
    ::= { fdryLinkAggregationGroupPortTable 1 }

FdryLinkAggregationGroupPortEntry ::= SEQUENCE {
    fdryLinkAggregationGroupPortLacpPriority   INTEGER
}

fdryLinkAggregationGroupPortLacpPriority OBJECT-TYPE
    SYNTAX     INTEGER (0..65535)
    MAX-ACCESS read-write
    STATUS     current
    DESCRIPTION
            "The LACP priority value assigned to this link aggregation port. Applicable 
            for dynamic and keepalive LAG only."
    DEFVAL { 1 }
    ::= { fdryLinkAggregationGroupPortEntry 1 }

--
-- LinkAggregationGroupLacpPort Table
--

fdryLinkAggregationGroupLacpPortTable OBJECT-TYPE
    SYNTAX     SEQUENCE OF FdryLinkAggregationGroupLacpPortEntry
    MAX-ACCESS not-accessible
    STATUS     current
    DESCRIPTION
            "A table that contains Link Aggregation Control
             information about every LACP port associated with this device.
            A row appears in this table for each physical port."
    ::= { fdryLinkAggregationGroupLacpPortTableObjects 1 }

fdryLinkAggregationGroupLacpPortEntry OBJECT-TYPE
    SYNTAX     FdryLinkAggregationGroupLacpPortEntry
    MAX-ACCESS not-accessible
    STATUS     current
    DESCRIPTION
            "An entry of the Link Aggregate Group LACP Port table.
            Applicable for dynamic and keepalive LAG only."
    INDEX { fdryLinkAggregationGroupName, ifIndex }
    ::= { fdryLinkAggregationGroupLacpPortTable 1 }

FdryLinkAggregationGroupLacpPortEntry ::= SEQUENCE {
    fdryLinkAggregationGroupLacpPortAdminStatus             INTEGER,
    fdryLinkAggregationGroupLacpPortLinkStatus                INTEGER,
    fdryLinkAggregationGroupLacpPortLacpStatus               INTEGER,
    fdryLinkAggregationGroupLacpPortLacpSysID                 PhysAddress,
    fdryLinkAggregationGroupLacpPortLacpKey                    INTEGER,
    fdryLinkAggregationGroupLacpPortLacpRemoteSysID     PhysAddress,
    fdryLinkAggregationGroupLacpPortLacpRemoteKey        INTEGER
}

fdryLinkAggregationGroupLacpPortAdminStatus OBJECT-TYPE
    SYNTAX  INTEGER {
				up(1),       -- ready to pass packets
				down(2),
				testing(3)   -- in some test mode
			}
    MAX-ACCESS read-only
    STATUS     current
    DESCRIPTION
            "The current admin state of the interface.
            The testing(3) state indicates that no operational
	    packets can be passed. 
	    (same as ifAdminStatus in MIB-II)"
    ::= { fdryLinkAggregationGroupLacpPortEntry 1 }

fdryLinkAggregationGroupLacpPortLinkStatus OBJECT-TYPE
    SYNTAX  INTEGER {
				up(1),       -- ready to pass packets
				down(2),
				testing(3)   -- in some test mode
			}
    MAX-ACCESS read-only
    STATUS     current
    DESCRIPTION
            "The current operational state of the interface.
            The testing(3) state indicates that no operational
	    packets can be passed. 
	    (same as ifOperStatus in MIB-II)"
    ::= { fdryLinkAggregationGroupLacpPortEntry 2 }

 fdryLinkAggregationGroupLacpPortLacpStatus OBJECT-TYPE
    SYNTAX  INTEGER {
				operation(1),     
				down(2),
				blocked(3),
				inactive(4),
				pexforceup(5)				
			}
    MAX-ACCESS read-only
    STATUS     current
    DESCRIPTION
            "The current LACP state of the interface."
    ::= { fdryLinkAggregationGroupLacpPortEntry 3 }

 fdryLinkAggregationGroupLacpPortLacpSysID OBJECT-TYPE
    SYNTAX  PhysAddress
    MAX-ACCESS read-only
    STATUS     current
    DESCRIPTION
            "The LACP system ID of the LAG."
    ::= { fdryLinkAggregationGroupLacpPortEntry 4 }

 fdryLinkAggregationGroupLacpPortLacpKey OBJECT-TYPE
    SYNTAX  INTEGER
    MAX-ACCESS read-only
    STATUS     current
    DESCRIPTION
            "The LACP key ID of the interface."
    ::= { fdryLinkAggregationGroupLacpPortEntry 5 }

 fdryLinkAggregationGroupLacpPortLacpRemoteSysID OBJECT-TYPE
    SYNTAX  PhysAddress
    MAX-ACCESS read-only
    STATUS     current
    DESCRIPTION
            "The LACP remote system ID of the LAG."
    ::= { fdryLinkAggregationGroupLacpPortEntry 6 }

 fdryLinkAggregationGroupLacpPortLacpRemoteKey OBJECT-TYPE
    SYNTAX  INTEGER
    MAX-ACCESS read-only
    STATUS     current
    DESCRIPTION
            "The LACP remote key ID of the interface."
    ::= { fdryLinkAggregationGroupLacpPortEntry 7 }

END
FOUNDRY-SN-CAM-MIB DEFINITIONS ::= BEGIN
IMPORTS
    MODULE-IDENTITY, 
    OBJECT-TYPE,
    Gauge32,
    Unsigned32
        FROM SNMPv2-SMI               -- [RFC2578]
    TEXTUAL-CONVENTION
        FROM SNMPv2-TC                 -- [RFC2579]
    platform
        FROM FOUNDRY-SN-ROOT-MIB;

snCamMIB MODULE-IDENTITY
    LAST-UPDATED "200711190000Z"		-- Nov 19, 2007
    ORGANIZATION "Foundry Networks, Inc"
    CONTACT-INFO
            "Technical Support Center, Foundry Networks,
            4980 Great America Parkway,
            Santa Clara, CA 95054
            Email: support@foundrynet.com
            Phone: 1-877-TURBO-CALL"
    DESCRIPTION
            "The MIB module to describe generic objects for the usage of 
            Content Addressable Memory (CAM). "
    REVISION      "200711190000Z"		-- Nov 19, 2007
    DESCRIPTION
            "Initial revision"
    ::= { platform 1  }  
    
       
--
-- Textual Conventions
--

-- Percentage
--
Percent ::= TEXTUAL-CONVENTION
    STATUS current
    DESCRIPTION        
        "An integer that is in the range of a percent value."
    SYNTAX Gauge32 (0..100)

--
-- high level object identifiers
--
snCamObjects  OBJECT IDENTIFIER ::= { snCamMIB 1 }


-- snCamProfile
snCamProfile OBJECT-TYPE
    SYNTAX  INTEGER {
                default(1),
                ipv4(2),
                ipv4Ipv6(3),
                ipv4Ipv62(4),
                ipv4Vpls(5),
                ipv4Vpn(6),
                ipv6(7),
                l2Metro(8),
                l2Metro2(9),
                mplsL3vpn(10),
                mplsL3vpn2(11),
                mplsVpls(12),
                mplsVpls2(13),
                mplsVpnVpls(14),
                multiService(15),
                multiService2(16),
                multiService3(17),
                multiService4(18)
            }
    MAX-ACCESS  read-only
    STATUS      current
    DESCRIPTION
            "This object identifies CAM partition profile. Each profile
            adjusts the partitions to optimize the device for corresponding
            applications."
    ::= { snCamObjects 1 }


-- cam usage objects
snCamUsage  OBJECT IDENTIFIER ::= { snCamObjects 2 }


-- the snCamUsageL3 table

-- The snCamUsageL3 table contains information of the entity's
-- CAM usage for layer 3 traffic.  

snCamUsageL3Table OBJECT-TYPE
    SYNTAX      SEQUENCE OF SnCamUsageL3Entry
    MAX-ACCESS  not-accessible
    STATUS      current
    DESCRIPTION
            "A list of snCamUsageL3 entries. This table contains 
            information of the entity's CAM usage for layer 3 traffic."
    ::= { snCamUsage 1 }

snCamUsageL3Entry OBJECT-TYPE
    SYNTAX      SnCamUsageL3Entry
    MAX-ACCESS  not-accessible
    STATUS      current
    DESCRIPTION
            "An entry containing management information applicable to
            CAM usage for layer 3 traffic"
    INDEX   {   snCamUsageL3Slot,	
                    snCamUsageL3Processor, 
                    snCamUsageL3Type,
                    snCamUsageL3Supernet   }
    ::= { snCamUsageL3Table 1 }

SnCamUsageL3Entry ::=
    SEQUENCE {
        snCamUsageL3Slot			Unsigned32,
        snCamUsageL3Processor		Unsigned32,
        snCamUsageL3Type			INTEGER,
        snCamUsageL3Supernet		Unsigned32,
        snCamUsageL3Size			Unsigned32,
        snCamUsageL3Free			Gauge32,
        snCamUsageL3UsedPercent		Percent
    }

snCamUsageL3Slot OBJECT-TYPE
    SYNTAX  Unsigned32 
    MAX-ACCESS  not-accessible
    STATUS      current
    DESCRIPTION
            "A number which uniquely identifies a linecard  in the device"
    ::= { snCamUsageL3Entry 1 }

snCamUsageL3Processor OBJECT-TYPE
    SYNTAX  Unsigned32 (1..2) 
    MAX-ACCESS  not-accessible
    STATUS      current
    DESCRIPTION
            "A number which uniquely identifies the network processor within a 
            linecard in the device"
    ::= { snCamUsageL3Entry 2 }

snCamUsageL3Type OBJECT-TYPE
    SYNTAX  INTEGER {
                ipv4(1),
                ipv6(2),
                ipv4vpn(3),
                ipv6vpn(4)
            }
    MAX-ACCESS  not-accessible
    STATUS      current
    DESCRIPTION
            "This object identifies the type of layer 3 traffic passing through the
            network processor."
    ::= { snCamUsageL3Entry 3 }

snCamUsageL3Supernet OBJECT-TYPE
    SYNTAX  Unsigned32
    MAX-ACCESS  not-accessible
    STATUS      current
    DESCRIPTION
            "This object identifies the Supernet for the layer 3 type traffic. It
            provides information for longest match lookup. For example,  zero 
            indicates all the bits of IP address will be matched, and one indicates
            all but the lowest bit in IP address will be matched. The range is
            [0..32] for IPv4 and IPv4VPN, where a value of 32 indicates the entry is
            the total of other supernets indexed by [0..31]. The range is [0..10] for 
            IPv6, where a value of 10 indicates the entry is the total of other 
            supernets indexed by [0..9]."
    ::= { snCamUsageL3Entry 4 }

snCamUsageL3Size OBJECT-TYPE
    SYNTAX  Unsigned32 
    UNITS   "Entries"
    MAX-ACCESS  read-only
    STATUS      current
    DESCRIPTION
            "The effective CAM size for this layer 3 traffic entry. For ipv4 traffic, each
            unit is 4 bytes. For ipv4vpn, each unit is 8 bytes. For ipv6, each unit is
            16 bytes."
    ::= { snCamUsageL3Entry 5 }

snCamUsageL3Free OBJECT-TYPE
    SYNTAX  Gauge32       
    UNITS   "Entries"
    MAX-ACCESS  read-only
    STATUS      current
    DESCRIPTION
            "The amount of CAM currently available for this layer 3 traffic entry. For ipv4 
            traffic, each unit is 4 bytes. For ipv4vpn, each unit is 8 bytes. For ipv6, each 
            unit is 16 bytes." 
    ::= { snCamUsageL3Entry 6 }

snCamUsageL3UsedPercent OBJECT-TYPE
    SYNTAX  Percent 
    MAX-ACCESS  read-only
    STATUS      current
    DESCRIPTION
            "The percentage of CAM currently being used for this layer 3 traffic entry. "
    ::= { snCamUsageL3Entry 7 }


-- the snCamUsageL2 table

-- The snCamUsageL2 table contains information of the entity's
-- CAM usage for layer 2 traffic.  

snCamUsageL2Table OBJECT-TYPE
    SYNTAX      SEQUENCE OF SnCamUsageL2Entry
    MAX-ACCESS  not-accessible
    STATUS      current
    DESCRIPTION
            "A list of snCamUsageL2 entries. This table contains information of 
            the entity's CAM usage for layer 2 traffic."
    ::= { snCamUsage 2 }

snCamUsageL2Entry OBJECT-TYPE
    SYNTAX      SnCamUsageL2Entry
    MAX-ACCESS  not-accessible
    STATUS      current
    DESCRIPTION
            "An entry containing management information applicable to
            CAM usage for layer 2 traffic"
    INDEX   {	snCamUsageL2Slot,
			snCamUsageL2Processor,
			snCamUsageL2Type }
    ::= { snCamUsageL2Table 1 }

SnCamUsageL2Entry ::=
    SEQUENCE {
        snCamUsageL2Slot			Unsigned32,
        snCamUsageL2Processor		Unsigned32,
        snCamUsageL2Type			INTEGER,
        snCamUsageL2Size			Unsigned32,
        snCamUsageL2Free			Gauge32,
        snCamUsageL2UsedPercent		Percent
    }

snCamUsageL2Slot OBJECT-TYPE
    SYNTAX  Unsigned32 
    MAX-ACCESS  not-accessible
    STATUS      current
    DESCRIPTION
            "A number which uniquely identifies a linecard in the device"
    ::= { snCamUsageL2Entry 1 }

snCamUsageL2Processor OBJECT-TYPE
    SYNTAX  Unsigned32 (1..2) 
    MAX-ACCESS  not-accessible
    STATUS      current
    DESCRIPTION
            "A number which uniquely identifies the network processor within a 
            linecard in the device"
    ::= { snCamUsageL2Entry 2 }

snCamUsageL2Type OBJECT-TYPE
    SYNTAX  INTEGER {
                forwarding(1),
                protocol(2),
                flooding(3),
                total(4)
            }
    MAX-ACCESS  not-accessible
    STATUS      current
    DESCRIPTION
            "This object identifies the type of layer 2 traffic passing through
            the network processor."
    ::= { snCamUsageL2Entry 3 }

snCamUsageL2Size OBJECT-TYPE
    SYNTAX  Unsigned32 
    UNITS  "Entries"
    MAX-ACCESS  read-only
    STATUS      current
    DESCRIPTION
            "The effective CAM size for this layer 2 traffic entry. Each unit is 8 bytes."
    ::= { snCamUsageL2Entry 4 }

snCamUsageL2Free OBJECT-TYPE
    SYNTAX  Gauge32
    UNITS  "Entries" 
    MAX-ACCESS  read-only
    STATUS      current
    DESCRIPTION
            "The amount of CAM currently available for this layer 2 traffic entry. 
             Each unit is 8 bytes." 
    ::= { snCamUsageL2Entry 5 }

snCamUsageL2UsedPercent OBJECT-TYPE
    SYNTAX  Percent 
    MAX-ACCESS  read-only
    STATUS      current
    DESCRIPTION
            "The percentage of CAM currently being used for this layer 2 traffic entry. "
    ::= { snCamUsageL2Entry 6 }

-- the snCamUsageSession table

-- The snCamUsageSession table contains information of the entity's
-- CAM usage for sessions.  

snCamUsageSessionTable OBJECT-TYPE
    SYNTAX      SEQUENCE OF SnCamUsageSessionEntry
    MAX-ACCESS  not-accessible
    STATUS      current
    DESCRIPTION
            "A list of snCamUsageSession entries. This table contains information
            of the entitiy's CAM usage for sessions. "
    ::= { snCamUsage 3 }

snCamUsageSessionEntry OBJECT-TYPE
    SYNTAX      SnCamUsageSessionEntry
    MAX-ACCESS  not-accessible
    STATUS      current
    DESCRIPTION
            "An entry containing management information applicable to CAM usage
            for sessions. "
    INDEX   { snCamUsageSessionSlot,
                   snCamUsageSessionProcessor,
                   snCamUsageSessionType }
    ::= { snCamUsageSessionTable 1 }

SnCamUsageSessionEntry ::=
    SEQUENCE {
        snCamUsageSessionSlot			Unsigned32,
        snCamUsageSessionProcessor		Unsigned32,
        snCamUsageSessionType			INTEGER,
        snCamUsageSessionSize			Unsigned32,
        snCamUsageSessionFree			Gauge32,
        snCamUsageSessionUsedPercent		Percent
    }

snCamUsageSessionSlot OBJECT-TYPE
    SYNTAX  Unsigned32 
    MAX-ACCESS  not-accessible
    STATUS      current
    DESCRIPTION
            "A number which uniquely identifies a linecard in the device"
    ::= { snCamUsageSessionEntry 1 }

snCamUsageSessionProcessor OBJECT-TYPE
    SYNTAX  Unsigned32 (1..2) 
    MAX-ACCESS  not-accessible
    STATUS      current
    DESCRIPTION
            "A number which uniquely identifies the network processor within a 
            linecard in the device"
    ::= { snCamUsageSessionEntry 2 }

snCamUsageSessionType OBJECT-TYPE
    SYNTAX  INTEGER {
                ipv4Multicast(1),
                ipv4andMacReceiveAcl(2),
                ipv4andMacRuleAcl(3),
                ipv4andMacTotal(4),
                ipv4andMacOut(5),
                ipv6Multicast(6),
                ipv6ReceiveAcl(7),
                ipv6RuleAcl(8),
                ipv6Total(9),
                ipv6Out(10),
                labelOut(11),
                ipv4SrcGuardDenial(12),   
                ipv4SrcGuardPermit(13),   
                internalForwardingLookup(14)
            }
    MAX-ACCESS  not-accessible
    STATUS      current
    DESCRIPTION
            "This object identifies the type of sessions."
    ::= { snCamUsageSessionEntry 3 }


snCamUsageSessionSize OBJECT-TYPE
    SYNTAX  Unsigned32    
    UNITS  "Entries"
    MAX-ACCESS  read-only
    STATUS      current 
    DESCRIPTION
            "The effective CAM size for this session traffic entry. For IPv4 sessions,
            each unit is 16 bytes. For IPv4 sessions, each unit is 64 bytes."
    ::= { snCamUsageSessionEntry 4 }

snCamUsageSessionFree OBJECT-TYPE
    SYNTAX  Gauge32 
    UNITS  "Entries"
    MAX-ACCESS  read-only
    STATUS      current
    DESCRIPTION
        "The amount of CAM currently available this session traffic entry. 
        For IPv4 sessions, each unit is 16 bytes. For IPv4 sessions, each unit is 
        64 bytes."
    ::= { snCamUsageSessionEntry 5 }

snCamUsageSessionUsedPercent OBJECT-TYPE
    SYNTAX  Percent 
    MAX-ACCESS  read-only
    STATUS      current
    DESCRIPTION
            "The percentage of CAM currently being used by this session traffic entry "
    ::= { snCamUsageSessionEntry 6 }


-- the snCamUsageOther table

-- The snCamUsageOthers table contains information of the entity's
-- CAM usage for types other than L3, L2, or Session.  

snCamUsageOtherTable OBJECT-TYPE
    SYNTAX      SEQUENCE OF SnCamUsageOtherEntry
    MAX-ACCESS  not-accessible
    STATUS      current
    DESCRIPTION
            "A list of snCamUsageOther entries. This table contains information
            of the entitiy's CAM usage for types other than L3, L2, or Session."
    ::= { snCamUsage 4 }

snCamUsageOtherEntry OBJECT-TYPE
    SYNTAX      SnCamUsageOtherEntry
    MAX-ACCESS  not-accessible
    STATUS      current
    DESCRIPTION
            "An entry containing management information applicable to CAM usage
            for types other than L3, L2, or Session"
    INDEX   { snCamUsageOtherSlot,
              snCamUsageOtherProcessor,
              snCamUsageOtherType }
    ::= { snCamUsageOtherTable 1 }

SnCamUsageOtherEntry ::=
    SEQUENCE {
        snCamUsageOtherSlot			Unsigned32,
        snCamUsageOtherProcessor		Unsigned32,
        snCamUsageOtherType			INTEGER,
        snCamUsageOtherSize			Unsigned32,
        snCamUsageOtherFree			Gauge32,
        snCamUsageOtherUsedPercent		Percent
    }

snCamUsageOtherSlot OBJECT-TYPE
    SYNTAX  Unsigned32 
    MAX-ACCESS  not-accessible
    STATUS      current
    DESCRIPTION
            "A number which uniquely identifies a linecard in the device"
    ::= { snCamUsageOtherEntry 1 }

snCamUsageOtherProcessor OBJECT-TYPE
    SYNTAX  Unsigned32 (1..2) 
    MAX-ACCESS  not-accessible
    STATUS      current
    DESCRIPTION
            "A number which uniquely identifies the network processor within a 
            linecard in the device"
    ::= { snCamUsageOtherEntry 2 }

snCamUsageOtherType OBJECT-TYPE
    SYNTAX  INTEGER {
                gre(1),
                multicastVpls(2)
            }
    MAX-ACCESS  not-accessible
    STATUS      current
    DESCRIPTION
            "This object identifies the type."
    ::= { snCamUsageOtherEntry 3 }

snCamUsageOtherSize OBJECT-TYPE
    SYNTAX  Unsigned32    
    UNITS  "Entries"
    MAX-ACCESS  read-only
    STATUS      current 
    DESCRIPTION
            "The effective CAM size for this Other traffic entry. For GRE,
            each unit is 8 bytes. For multicast VPLS, each unit is 16 bytes."
    ::= { snCamUsageOtherEntry 4 }

snCamUsageOtherFree OBJECT-TYPE
    SYNTAX  Gauge32 
    UNITS  "Entries"
    MAX-ACCESS  read-only
    STATUS      current
    DESCRIPTION
            "The amount of CAM currently available this Other traffic entry. 
            For GRE, each unit is 8 bytes. For multicast VPLS, each unit is 16 bytes."
    ::= { snCamUsageOtherEntry 5 }

snCamUsageOtherUsedPercent OBJECT-TYPE
    SYNTAX  Percent 
    MAX-ACCESS  read-only
    STATUS      current
    DESCRIPTION
            "The percentage of CAM currently being used by this entry "
    ::= { snCamUsageOtherEntry 6 }    
    
    
END
   PW-TC-STD-MIB DEFINITIONS ::= BEGIN

   IMPORTS
      MODULE-IDENTITY, Unsigned32
         FROM SNMPv2-SMI               -- [RFC2578]

     pwe3
        FROM FOUNDRY-SN-ROOT-MIB

      TEXTUAL-CONVENTION
         FROM SNMPv2-TC;               -- [RFC2579]

   pwTcStdMIB MODULE-IDENTITY
      LAST-UPDATED "200705241200Z"  -- 24 May 2007 12:00:00 GMT
      ORGANIZATION "Pseudo Wire Edge-to-Edge Emulation (PWE3) Working
                    Group"
      CONTACT-INFO
      " Thomas D. Nadeau
        Email:  tnadeau@cisco.com

        David Zelig
        Email: davidz@corrigent.com

        Orly Nicklass
        Email: orly_n@rad.com

        The PWE3 Working Group (email distribution pwe3@ietf.org,
        http://www.ietf.org/html.charters/pwe3-charter.html)
       "

      DESCRIPTION
           "This MIB module defines TEXTUAL CONVENTIONs
            for concepts used in Pseudo Wire Edge-to-Edge
            networks.

            Copyright (C) The IETF Trust (2007). The
            initial version of this MIB module as published
            in RFC YYYY. For full legal notices see the RFC
            itself or see:
            http://www.ietf.org/copyrights/ianamib.html

   -- RFC Editor: Please replace YYYY with the RFC number and remove
   -- this note.
               "
      -- Revision history.

      REVISION "200705241200Z"  -- 24 May 2007 12:00:00 GMT
      DESCRIPTION
           "Original Version"
         ::= { pwe3 1 }
         --::= { transmission XXXX }
   -- RFC Editor: please replace XXXX with IANA assigned value and
   -- delete this note.

   PwGroupID ::= TEXTUAL-CONVENTION
      DISPLAY-HINT "d"
      STATUS      current
      DESCRIPTION
           "An administrative identification for grouping a
            set of service-specific pseudo-wire services."
      SYNTAX  Unsigned32

   PwIDType ::= TEXTUAL-CONVENTION
      DISPLAY-HINT "d"
      STATUS      current
      DESCRIPTION
           "Pseudo-Wire Identifier. Used to identify the PW
            (together with some other fields) in the signaling
            session."
      SYNTAX  Unsigned32

   PwIndexType ::= TEXTUAL-CONVENTION
      DISPLAY-HINT "d"
      STATUS      current
      DESCRIPTION
           "Pseudo Wire Index. A unique value, greater than zero,
           for each locally-defined PW for indexing
           several MIB tables associated with the particular PW.
           It is recommended that values are assigned contiguously
           starting from 1.  The value for each PW MUST remain
           constant at least from one re-initialization
           to the next re-initialization."
      SYNTAX  Unsigned32 (1..4294967295)

   PwIndexOrZeroType ::= TEXTUAL-CONVENTION
      DISPLAY-HINT "d"
      STATUS      current
      DESCRIPTION
           "This textual convention is an extension of the
            PwIndexType convention.  The latter defines a greater-
            than-zero value used to identify a Pseudo Wire
            in the managed system.  This extension permits the
            additional value of zero. The zero value is object-specific
            and MUST therefore be defined as part of the description of
            any object which uses this syntax.  Examples of the usage of
            zero might include situations where Pseudo Wire was unknown,
            or when none or all Pseudo Wires need to be referenced."
       SYNTAX  Unsigned32 (0..4294967295)

   PwVlanCfg ::= TEXTUAL-CONVENTION
      DISPLAY-HINT "d"
      STATUS      current
      DESCRIPTION
           "VLAN configuration for Ethernet PW.
            Values between 0 and 4095 indicate the actual VLAN field
            value.
            A value of 4096 indicates that the object refers to
            untagged frames, i.e. frames without a 802.1Q field.
            A value of 4097 indicates that the object is not
            relevant."
      SYNTAX  Unsigned32 (0..4097)

   PwOperStatusTC ::= TEXTUAL-CONVENTION
      STATUS      current
      DESCRIPTION
        "Indicates the operational status of the PW.

        - up(1):            Ready to pass packets.
        - down(2):          If PW signaling is not yet finished, or
                            indications available at the service
                            level indicate that the PW is not
                            passing packets.
        - testing(3):       If AdminStatus at the PW level is set to
                            test.
        - dormant(4):       The PW is not in a condition to pass
                            packets, but is in a 'pending' state,
                            waiting for some external event.
        - notPresent(5):    Some component is missing to accomplish
                            the setup of the PW. It can be configuration
                            error, incomplete configuration or missing
                            of H/W component.
        - lowerLayerDown(6):One or more of the lower-layer interfaces
                            responsible for running the underlying PSN
                            is not in OperStatus 'up' state."
    SYNTAX   INTEGER {
        up(1),
        down(2),
        testing(3),
        dormant(4),
        notPresent(5),
        lowerLayerDown(6)
        }

   PwAttachmentIdentifierType ::= TEXTUAL-CONVENTION
      STATUS      current
      DESCRIPTION
         "An octet string used in the generalized FEC element for
          identifying attachment forwarder and groups. A NULL
          identifier is of zero length.
         "
     SYNTAX    OCTET STRING (SIZE (0..255))

   PwCwStatusTC ::= TEXTUAL-CONVENTION
      STATUS      current
      DESCRIPTION
         "Indicates the status of the control word negotiation based
          on the local configuration and the indications received from
          the peer node.

          waitingForNextMsg(1) indicates that the node is waiting for
          another label mapping from the peer.

          sentWrongBitErrorCode(2) indicates that the local node has
          notified the peer about a mismatch in the C bit.

          rxWithdrawWithWrongBitErrorCode(3) indicates that a withdraw
          message has been received with the wrong C-bit error code.

          illegalReceivedBit(4) indicates a C-bit configuration with
          the peer which is not compatible with the PW type.

          cwPresent(5) indicates that the CW is present for this PW:
          If signaling is used - the C bit is set and agreed between the
          nodes, and for manualy-configured PW the local configuration
          requires the use of the CW.

          cwNotPresent(6) indicates that the CW is not present for
          this PW: If signaling is used - the C bit is reset and agreed
          between the nodes, and for manualy-configured PW the local
          configuration requires that the CW not be used.

          notYetKnown(7) indicates that a label mapping has not yet
          been received from the peer.
         "
      REFERENCE
         "Martini, et al, 'Pseudowire Setup and Maintenance using
          the Label Distribution Protocol', [RFC4447]."

      SYNTAX    INTEGER {
                 waitingForNextMsg (1),
                 sentWrongBitErrorCode (2),
                 rxWithdrawWithWrongBitErrorCode (3),
                 illegalReceivedBit (4),
                 cwPresent (5),
                 cwNotPresent (6),
                 notYetKnown(7)
                 }

   PwStatus ::= TEXTUAL-CONVENTION
      STATUS      current
      DESCRIPTION
         "Indicates the status of the PW and the interfaces affecting
          this PW. If none of the bits are set, it indicates no faults
          are reported.
         "
      SYNTAX   BITS {
        pwNotForwarding (0),
        servicePwRxFault (1),
        servicePwTxFault (2),
        psnPwRxFault  (3),
        psnPwTxFault  (4)
        }

   PwFragSize ::= TEXTUAL-CONVENTION
      DISPLAY-HINT "d"
      STATUS      current
      DESCRIPTION
         "If set to a value other than zero, it indicates the desired
          fragmentation length in bytes. If set to zero,
          fragmentation is not desired for PSN bound packets.
         "
      SYNTAX   Unsigned32

   PwFragStatus ::= TEXTUAL-CONVENTION
      STATUS      current
      DESCRIPTION
         "Indicates the status of the fragmentation process based on
          local configuration and peer capability.

          noFrag(0) bit indicates that local configuration is for no
          fragmentation.

          cfgFragGreaterThanPsnMtu(1) bit indicates the local node
          is set to fragment, but the fragmentation size is greater
          than the MTU available at the PSN between the nodes.
          Fragmentation is not done in this case.

          cfgFragButRemoteIncapable(2) bit indicates that the local
          configuration indicates the desire for fragmentation but
          the peer is not capable of fragmentation.

          remoteFragCapable(3) bit indicates that the remote node
          is capable to accept fragmented PDUs.

          fragEnabled(4) bit indicates that fargmenteation will be used
          on this PW. Fragmentation can be used if the local node was
          configured for fragmentation, the peer has the cabability
          to accept fragmented packets, and the CW is in use for this
          PW."

      REFERENCE
          "Malis, A. and M. Townsley, 'Pseudowire Emulation Edge-to-
           Edge (PWE3) Fragmentation and Reassembly', [RFC4623]."
      SYNTAX   BITS {
         noFrag (0),
         cfgFragGreaterThanPsnMtu (1),
         cfgFragButRemoteIncapable (2),
         remoteFragCapable (3),
         fragEnabled (4)
         }

   PwCfgIndexOrzero ::= TEXTUAL-CONVENTION
      DISPLAY-HINT "d"
      STATUS      current
      DESCRIPTION
           "Index in any of the relevant configuration tables for
           supplement information regarding configuration of the
           specific technology. Value 0 implies no additional
           configuration information is applicable."
      SYNTAX  Unsigned32 (0..4294967295)
   END
   IANA-PWE3-MIB DEFINITIONS ::= BEGIN

   IMPORTS
       MODULE-IDENTITY
          FROM SNMPv2-SMI -- [RFC2578]
       pwe3
          FROM FOUNDRY-SN-ROOT-MIB
       TEXTUAL-CONVENTION
          FROM SNMPv2-TC; -- [RFC2579]

   ianaPwe3MIB  MODULE-IDENTITY
       LAST-UPDATED "200702041200Z"  -- 4 February 2006 12:00:00 GMT
       ORGANIZATION "IANA"
       CONTACT-INFO
            "Internet Assigned Numbers Authority
            Internet Corporation for Assigned Names and Numbers
            4676 Admiralty Way, Suite 330
            Marina del Rey, CA 90292-6601

            Phone: +1 310 823 9358
            EMail: iana@iana.org"
       DESCRIPTION
           "This MIB module defines the IANAPwTypeTC and
           IANAPwPsnTypeTC textual conventions for use in PWE3
           MIB modules.

           Any additions or changes to the contents of this MIB
           module require either publication of an RFC, Designated
           Expert Review as defined in RFC 2434, Guidelines for
           Writing an IANA Considerations Section in RFCs, and should
           be based on the procedures defined in [RFC4446]. The
           Designated Expert will be selected by the IESG Area
           Director(s) of the internet Area.

           Copyright (C) The IETF Trust (2007).  The initial
           version of this MIB module was published in RFC yyyy;
           for full legal notices see the RFC itself.  Supplementary
           information may be available at:
           http://www.ietf.org/copyrights/ianamib.html."
      -- RFC Ed.: replace yyyy with actual RFC number & remove this note

       REVISION     "200702041200Z"  -- 4 February 2006 12:00:00 GMT
       DESCRIPTION  "Original version, published as part of RFC yyyy."
   -- RFC Editor: please fill the yyyy and remove this note.

       ::= { pwe3 3 }
       -- ::= { transmission XXXX }
   -- RFC Editor: please fill the XXXX based on the IANA allocation
   -- and remove this note.

   IANAPwTypeTC ::= TEXTUAL-CONVENTION
      STATUS     current
      DESCRIPTION
         "Indicates the PW type (i.e. the carried service). "
    SYNTAX   INTEGER {
       other(0),
       frameRelayDlciMartiniMode(1),
       atmAal5SduVcc(2),
       atmTransparent(3),
       ethernetTagged(4),
       ethernet(5),
       hdlc(6),
       ppp(7),
       cem(8),  -- Historic type
       atmCellNto1Vcc(9),
       atmCellNto1Vpc(10),
       ipLayer2Transport(11),
       atmCell1to1Vcc(12),
       atmCell1to1Vpc(13),
       atmAal5PduVcc(14),
       frameRelayPortMode(15),
       cep(16),
       e1Satop(17),
       t1Satop(18),
       e3Satop(19),
       t3Satop(20),
       basicCesPsn(21),
       basicTdmIp(22),
       tdmCasCesPsn(23),
       tdmCasTdmIp(24),
       frDlci(25),
       wildcard (32767)
        }

   IANAPwPsnTypeTC ::= TEXTUAL-CONVENTION
      STATUS      current
      DESCRIPTION
         "Identifies the PSN type which the PW will use over the
          network."
      SYNTAX   INTEGER {
         mpls        (1),
         l2tp        (2),
         udpOverIp   (3),
         mplsOverIp  (4),
         mplsOverGre (5),
         other       (6)
         }

   IANAPwCapabilities ::= TEXTUAL-CONVENTION
      STATUS      current
      DESCRIPTION
         "This TC describes a collection of cabailities related to
          a specific PW.
          Values may be added in the future based on new capabilities
          introduced in IETF documents.
         "
     SYNTAX   BITS {
       pwStatusIndication (0), -- Applicable only if maintenence
                               -- protocol is in use.
       pwVCCV             (1)
     }

   END


  PW-STD-MIB DEFINITIONS ::= BEGIN

  IMPORTS
     NOTIFICATION-TYPE, MODULE-IDENTITY, OBJECT-TYPE,
     Integer32, Unsigned32, Counter32, Counter64, TimeTicks
        FROM SNMPv2-SMI                    -- [RFC2578]

     pwe3
        FROM FOUNDRY-SN-ROOT-MIB
     snAgGblTrapMessage
        FROM FOUNDRY-SN-AGENT-MIB -- [snagent.mib]

     MODULE-COMPLIANCE, OBJECT-GROUP, NOTIFICATION-GROUP
        FROM SNMPv2-CONF                   -- [RFC2580]

     TruthValue, RowStatus, StorageType,
     TimeStamp, TEXTUAL-CONVENTION
        FROM SNMPv2-TC                     -- [RFC2579]

     SnmpAdminString
        FROM SNMP-FRAMEWORK-MIB            -- [RFC3411]

     InterfaceIndexOrZero
        FROM IF-MIB                        -- [RFC2863]

     InetAddressType, InetAddress
        FROM INET-ADDRESS-MIB              -- [RFC4001]

     PerfCurrentCount, PerfIntervalCount
        FROM PerfHist-TC-MIB               -- [RFC3593]

     HCPerfCurrentCount, HCPerfIntervalCount, HCPerfTimeElapsed,
     HCPerfValidIntervals
        FROM HC-PerfHist-TC-MIB            -- [RFC3705]

     PwIndexType, PwIndexOrZeroType, PwGroupID, PwIDType,
     PwOperStatusTC, PwAttachmentIdentifierType, PwCwStatusTC,
     PwStatus, PwFragSize, PwFragStatus
        FROM PW-TC-STD-MIB                 -- [PWTC]
  -- RFC Editor: Please replace [PWTC] with RFC number and remove this
  -- note.

     IANAPwTypeTC, IANAPwPsnTypeTC, IANAPwCapabilities
        FROM IANA-PWE3-MIB                 -- Reference will be added
                                           -- When IANA will create the
                                           -- MIB module
  ;

  pwStdMIB MODULE-IDENTITY
     LAST-UPDATED "200705311200Z"  -- 31 May 2007 12:00:00 GMT
     ORGANIZATION "Pseudo Wire Edge-to-Edge Emulation (PWE3) Working
                   Group"
     CONTACT-INFO
         "
          David Zelig
          E-mail: davidz@corrigent.com

          Thomas D. Nadeau
          Email:  tnadeau@cisco.com

          The PWE3 Working Group (email distribution pwe3@ietf.org,
          http://www.ietf.org/html.charters/pwe3-charter.html)
          "

     DESCRIPTION
         "This MIB module contains managed object definitions for
          pseudo-wire operation as in Bryant, S. and P. Pate, 'Pseudo
          Wire Emulation Edge-to-Edge (PWE3) Architecture' [RFC3985],
          Martini, L., et al, 'Pseudowire Setup and Maintenance Using
          the Label Distribution Protocol (LDP)' [RFC4447], and
          Townsley, M., et al, 'Layer Two Tunneling Protocol
          (Version 3)' [RFC3931].

          This MIB module enables the use of any underlying packet
          switched network (PSN). MIB nodules that will support
          PW operations over specific PSN types are defined in
          separate memos.

          The indexes for this MIB module are also used to index the
          PSN-specific tables and the PW-specific tables. The PW Type
          dictates which PW-specific MIB module to use.

          Copyright (C) The IETF Trust (2007).  This version
          of this MIB module is part of RFC XXX;
          For full legal notices see the RFC itself or
          http://www.ietf.org/copyrights/ianamib.html
     -- RFC Ed.: replace XXX with actual RFC number & remove this note
          "

     -- Revision history.

     REVISION
         "200705311200Z"  -- 31 May 2007 12:00:00 GMT
     DESCRIPTION "Initial version published as part of RFC YYYY."
  -- RFC Editor: please replace YYYY with IANA assigned value, and
  -- delete this note.

        ::= { pwe3 2 }
      -- ::= { transmission ZZZZ }
  -- RFC Editor: please replace ZZZZ with IANA assigned value, and
  -- delete this note.

  -- Top-level components of this MIB.

  -- Notifications
  pwNotifications OBJECT IDENTIFIER
                                ::= { pwStdMIB 0 }
  -- Tables, Scalars
  pwObjects       OBJECT IDENTIFIER
                                ::= { pwStdMIB 1 }
  -- Conformance
  pwConformance   OBJECT IDENTIFIER
                                ::= { pwStdMIB 2 }

-- Foundry Proprietary extension

   FdryPwServiceType ::= TEXTUAL-CONVENTION
   STATUS        current
   DESCRIPTION
       "MPLS pseudo-wire service types."
   SYNTAX        INTEGER{
                          vll(1),
                          vllLocal(2),
                          vpls(3)
                       }

  -- PW Virtual Connection Table

  pwIndexNext OBJECT-TYPE
     SYNTAX            Unsigned32
     MAX-ACCESS        read-only
     STATUS            current
     DESCRIPTION
         "This object contains an appropriate value to be used
          for pwIndex when creating entries in the
          pwTable. The value 0 indicates that no
          unassigned entries are available.  To obtain the
          value of pwIndex for a new entry in the
          pwTable, the manager issues a management
          protocol retrieval operation. The agent will determine
          through its local policy when this index value will be made
          available for reuse."
     ::= { pwObjects 1 }

  pwTable   OBJECT-TYPE
     SYNTAX        SEQUENCE OF PwEntry
     MAX-ACCESS    not-accessible
     STATUS        current
     DESCRIPTION
         "This table specifies information for configuring and
          status monitoring which are common to all service types
          and PSN types."
     ::= { pwObjects 2 }

  pwEntry   OBJECT-TYPE
     SYNTAX        PwEntry
     MAX-ACCESS    not-accessible
     STATUS        current
     DESCRIPTION
          "A row in this table represents a pseudo-wire (PW) virtual
           connection across a packet network. It is indexed by
           pwIndex, which uniquely identifies a singular
           connection.
           A row can be created by an operator command from a
           management plan of a PE, by signaling or due to autodiscovery
           process. Operator's command can be issued via non SNMP
           application; in such case a row will be created implicitly
           by the agent.
           The read-create objects in this tables are divided into
           three categories:
           1) Objects that MUST NOT be changed after row activation.
           These are objects that define basic properties of the
           PW (for example type, destination, etc.).
           2) Objects that MAY be changed when the PW is
           defined as not active. A change of these objects involves
           re-signaling of the PW or it might be traffic affecting.
           PW not active is defined as one of the following
           conditions:
                  a) The pwRowStatus is notInService(2).
                  b) The pwRowStatus is notReady(3).
                  c) The pwAdminStatus is down(2).
           If the operator needs to change one of the values for an
           active row, the operator can either set the pwRowStatus to
           notInService(2) or set pwAdminStatus to down(2).
           Signaling (or traffic) is initiated again upon setting
           the pwRowStatus to active(1) or setting the pwAdminStatus
           to up(1) or testing(3) respectively.
           3) Objects that MAY be changed at any time.

           By default, all the read-create objects MUST NOT be
           changed after row activation, unless specifically indicated
           in the individual object description.

           Manual entries in this table SHOULD be preserved after a
           re-boot, the agent MUST ensure the integrity of those
           entries. If the set of entires of a specific row are found to
           be non consistent after reboot, the PW pwOperStatus MUST be
           declared as notPresent(5).
           "
     INDEX  { pwIndex }

            ::= { pwTable 1 }

  PwEntry ::= SEQUENCE {
        pwIndex               PwIndexType,
        pwType                IANAPwTypeTC,
        pwOwner               INTEGER,
        pwPsnType             IANAPwPsnTypeTC,
        pwSetUpPriority       Integer32,
        pwHoldingPriority     Integer32,
        pwPeerAddrType        InetAddressType,
        pwPeerAddr            InetAddress,
        pwAttachedPwIndex     PwIndexOrZeroType,
        pwIfIndex             InterfaceIndexOrZero,

        pwID                  PwIDType,
        pwLocalGroupID        PwGroupID,
        pwGroupAttachmentID   PwAttachmentIdentifierType,
        pwLocalAttachmentID   PwAttachmentIdentifierType,
        pwPeerAttachmentID    PwAttachmentIdentifierType,

        pwCwPreference        TruthValue,
        pwLocalIfMtu          Unsigned32,


        pwLocalIfString       TruthValue,
        pwLocalCapabAdvert    IANAPwCapabilities,
        pwRemoteGroupID       PwGroupID,
        pwCwStatus            PwCwStatusTC,
        pwRemoteIfMtu         Unsigned32,
        pwRemoteIfString      SnmpAdminString,
        pwRemoteCapabilities  IANAPwCapabilities,

        pwFragmentCfgSize     PwFragSize,
        pwRmtFragCapability   PwFragStatus,
        pwFcsRetentionCfg     INTEGER,
        pwFcsRetentionStatus  BITS,

        pwOutboundLabel       Unsigned32,
        pwInboundLabel        Unsigned32,

        pwName                SnmpAdminString,
        pwDescr               SnmpAdminString,
        pwCreateTime          TimeStamp,
        pwUpTime              TimeTicks,
        pwLastChange          TimeTicks,
        pwAdminStatus         INTEGER,
        pwOperStatus          PwOperStatusTC,
        pwLocalStatus         PwStatus,
        pwRemoteStatusCapable INTEGER,
        pwRemoteStatus        PwStatus,
        pwTimeElapsed         HCPerfTimeElapsed,
        pwValidIntervals      HCPerfValidIntervals,
        pwRowStatus           RowStatus,
        pwStorageType         StorageType,
        pwOamEnable           TruthValue
     }

  pwIndex OBJECT-TYPE
     SYNTAX        PwIndexType
     MAX-ACCESS    not-accessible
     STATUS        current
     DESCRIPTION
         "A unique index for the conceptual row identifying a PW within
          this table."
     ::= { pwEntry 1 }

  pwType OBJECT-TYPE
     SYNTAX        IANAPwTypeTC
     MAX-ACCESS    read-create
     STATUS        current
     DESCRIPTION
         "This value indicates the emulated service to be carried over
          this PW.
         "
     ::= { pwEntry 2 }

  pwOwner OBJECT-TYPE
     SYNTAX   INTEGER {
            manual                (1),
            pwIdFecSignaling      (2), -- PW signaling with PW ID FEC
            genFecSignaling       (3), -- Generalized attachment FEC
            l2tpControlProtocol   (4),
            other                 (5)
                      }
     MAX-ACCESS    read-create
     STATUS        current
     DESCRIPTION
          "This object is set by the operator to indicate the protocol
           responsible for establishing this PW.
           'manual' is used in all cases where no maintenance
           protocol (PW signaling) is used to set-up the PW, i.e.
           require configuration of entries in the PW tables including
           PW labels, etc.
           'pwIdFecSignaling' is used in case of signaling with the
           Pwid FEC element with LDP signaling.
           'genFecSignaling' is used in case of LDP signaling with
           the generalized FEC.
           'l2tpControlProtocol' indicates the use of L2TP
           control protocol.
           'other' is used for other types of signaling."
     ::= { pwEntry 3 }

  pwPsnType OBJECT-TYPE
     SYNTAX   IANAPwPsnTypeTC
     MAX-ACCESS    read-create
     STATUS        current
     DESCRIPTION
          "This object is set by the operator to indicate the PSN type.
           Based on this object, the relevant PSN table's entry is
           created in the PSN specific MIB modules.
          "
     ::= { pwEntry 4 }

  pwSetUpPriority  OBJECT-TYPE
     SYNTAX         Integer32 (0..7)
     MAX-ACCESS     read-create
     STATUS         current
     DESCRIPTION
          "This object defines the relative priority of the PW
           during set-up in a lowest-to-highest fashion, where 0
           is the highest priority. PWs with the same priority
           are treated with equal priority. PW that have not yet
           succeeded to set-up will report 'dormant' in the
           pwOperStatus.
           This value is significant if there are competing resources
           among PWs and the implementation support this feature.
           Equal priority handling with competing resources is
           implementation specific.
           This object MAY be changed at any time."
     DEFVAL { 0 }
     ::= { pwEntry 5 }

  pwHoldingPriority  OBJECT-TYPE
     SYNTAX         Integer32 (0..7)
     MAX-ACCESS     read-create
     STATUS         current
     DESCRIPTION
          "This object defines the relative holding priority of the
           PW in a lowest-to-highest fashion, where 0 is the highest
           priority. PWs with the same priority are treated equally.
           This value is significant if there are competing resources
           among PWs and the implementation support this feature.
           Equal priority handling with competing resources is
           implementation specific.
           This object MAY be changed only if the PW is not active."
     DEFVAL { 0 }
     ::= { pwEntry 6 }

  pwPeerAddrType OBJECT-TYPE
     SYNTAX        InetAddressType
     MAX-ACCESS    read-create
     STATUS        current
     DESCRIPTION
          "Denotes the address type of the peer node. It should be
           set to 'unknown' if PE/PW maintenance protocol is not used
           and the address is unknown."
     DEFVAL { ipv4 }
     ::= { pwEntry 8 }

  pwPeerAddr OBJECT-TYPE
     SYNTAX        InetAddress
     MAX-ACCESS    read-create
     STATUS        current
     DESCRIPTION
          "This object contains the value of the peer node address
           of the PW/PE maintenance protocol entity. This object
           SHOULD contain a value of all zeroes if not applicable
           (pwPeerAddrType is 'unknown')."
     ::= { pwEntry 9 }

  pwAttachedPwIndex OBJECT-TYPE
     SYNTAX        PwIndexOrZeroType
     MAX-ACCESS    read-create
     STATUS        current
     DESCRIPTION
         "If the PW is attached to another PW instead of a local
          native service, this item indicates the pwIndex of the
          attached PW. Otherwise, this object MUST
          be set to zero. Attachement to another PW will have no
          PW specific entry in any of the service MIB modules. "
     DEFVAL { 0 }
     ::= { pwEntry 10 }

  pwIfIndex OBJECT-TYPE
     SYNTAX        InterfaceIndexOrZero
     MAX-ACCESS    read-create
     STATUS        current
     DESCRIPTION
         "This object indicates the ifIndex of the PW if the PW is
          represented in the ifTable. Otherwise, it MUST be set
          to zero."
     DEFVAL { 0 }
     ::= { pwEntry 11 }

  pwID OBJECT-TYPE
     SYNTAX        PwIDType
     MAX-ACCESS    read-create
     STATUS        current
     DESCRIPTION
         "Pseudo Wire identifier.

          If the pwOwner object is 'pwIdFecSignaling' or
          'l2tpControlProtocol', then this object is signaled in the
          outgoing PW ID field within the 'Virtual Circuit FEC
          Element'. For other values of pwOwner, this object is not
          signaled and it MAY be set to zero.

          For implementations that support the pwIndexMappingTable,
          a non-zero value is RECOMMENDED, even if this
          identifier is not signaled.  This is so that reverse
          mappings can be provided by pwIndexMappingTable and
          pwPeerMappingTable.  It is therefore RECOMMENDED that the
          value of this pwID be unique (or if pwPeerAddrType is not
          'unknown', at least [pwType,pwID,pwPeerAddrType,pwPeerAddr]
          is unique.)"
      REFERENCE
         "Martini, et al, 'Pseudowire Setup and Maintenance using
          the Label Distribution Protocol', RFC 4447."
     ::= { pwEntry 12 }

  pwLocalGroupID OBJECT-TYPE
     SYNTAX        PwGroupID
     MAX-ACCESS    read-create
     STATUS        current
     DESCRIPTION
         "Used in the Group ID field sent to the peer PWES
          within the maintenance protocol used for PW setup.
          It SHOULD be set to zero if maintenance protcol is
          not used."
     REFERENCE
         "Martini, et al, 'Pseudowire Setup and Maintenance using
          the Label Distribution Protocol', RFC 4447."
     ::= { pwEntry 13 }

  pwGroupAttachmentID OBJECT-TYPE
     SYNTAX        PwAttachmentIdentifierType
     MAX-ACCESS    read-create
     STATUS        current
     DESCRIPTION
         "This object is an octet string representing the attachment
          group identifier (AGI) that this PW belongs too, which
          typically identifies the VPN ID.
          Applicable if pwOwner equal 'genFecSignaling'."
     REFERENCE
         "Martini, et al, 'Pseudowire Setup and Maintenance using
          the Label Distribution Protocol', RFC 4447."
     ::= { pwEntry 14 }

  pwLocalAttachmentID   OBJECT-TYPE
     SYNTAX        PwAttachmentIdentifierType
     MAX-ACCESS    read-create
     STATUS        current
     DESCRIPTION
         "This object is an octet string representing the local
          forwarder attachment individual identifier (AII) to be
          used by this PW. It is used as the SAII for outgoing
          signaling messages and the TAII in the incoming messages
          from the peer.
          Applicable if pwOwner equal 'genFecSignaling'."
      REFERENCE
         "Martini, et al, 'Pseudowire Setup and Maintenance using
          the Label Distribution Protocol', RFC 4447."
     ::= { pwEntry 15 }

  pwPeerAttachmentID   OBJECT-TYPE
     SYNTAX        PwAttachmentIdentifierType
     MAX-ACCESS    read-create
     STATUS        current
     DESCRIPTION
         "This object is an octet string representing the peer
          forwarder attachment individual identifier (AII) to be
          used by this PW. It is used as the TAII for outgoing
          signaling messages and the SAII in the incoming messages
          from the peer.
          Applicable if pwOwner equal 'genFecSignaling'."
      REFERENCE
         "Martini, et al, 'Pseudowire Setup and Maintenance using
          the Label Distribution Protocol', RFC 4447."
     ::= { pwEntry 16 }

  pwCwPreference OBJECT-TYPE
     SYNTAX        TruthValue
     MAX-ACCESS    read-create
     STATUS        current
     DESCRIPTION
         "Defines if the control word will be sent with each packet
          by the local node. Some PW types mandate the use of a
          control word, and in such cases the value configured for
          this object has no effect on the existence of the control
          word.
          This object MAY be changed only if the PW is not active."
     REFERENCE
         "Martini, et al, 'Pseudowire Setup and Maintenance using
          the Label Distribution Protocol.', RFC 4447."
     DEFVAL { false }
     ::= { pwEntry 17 }

  pwLocalIfMtu OBJECT-TYPE
     SYNTAX        Unsigned32 (0..65535)
     MAX-ACCESS    read-create
     STATUS        current
     DESCRIPTION
         "If not equal to zero, the optional IfMtu object in the
          signaling protocol will be sent with this value, which
          represents the locally-supported MTU size over the
          interface (or the virtual interface) associated with the
          PW.
          This object MAY be changed only if the PW is not active."
     REFERENCE
         "Martini, et al, 'Pseudowire Setup and Maintenance using
          the Label Distribution Protocol', RFC 4447."
     DEFVAL { 0 }
     ::= { pwEntry 18 }

  pwLocalIfString OBJECT-TYPE
     SYNTAX        TruthValue
     MAX-ACCESS    read-create
     STATUS        current
     DESCRIPTION
         "A PW MAY be associated to an interface (or a virtual
          interface) in the ifTable of the node as part of the
          service configuration. This object defines if the
          maintenance protocol will send the interface's name
          (ifAlias) as appears in the ifTable. If set to false,
          the optional element will not be sent.
          This object MAY be changed only if the PW is not active."
     REFERENCE
         "Martini, et al, 'Pseudowire Setup and Maintenance using
          the Label Distribution Protocol', RFC 4447, section 5.5."
     DEFVAL { false }
     ::= { pwEntry 19 }

  pwLocalCapabAdvert OBJECT-TYPE
     SYNTAX        IANAPwCapabilities
     MAX-ACCESS    read-create
     STATUS        current
     DESCRIPTION
         "If maintenance protcol is used, it indicates the
          capabilities the local node will advertize to the
          peer. The operator MAY selectively assign partial set
          of capabilities. In case of manual configuration of the PW,
          the operator SHOULD set non conflicting options (for example
          only a single type of OAM) out of the available options
          in the implementation.
          It is possible to change the value of this object when the
          PW is not active. The agent MUST reject any attempt to set
          a capability that is not supported.

          The default value MUST be the full set of local node
          capabilities."
     REFERENCE
         "Martini, et al, 'Pseudowire Setup and Maintenance using
          the Label Distribution Protocol', RFC 4447."
     ::= { pwEntry 20 }

  pwRemoteGroupID OBJECT-TYPE
     SYNTAX        PwGroupID
     MAX-ACCESS    read-only
     STATUS        current
     DESCRIPTION
         "This object is obtained from the Group ID field as
          received via the maintenance protocol used for PW setup.
          Value zero will be reported if not used.
          Value of 0xFFFFFFFF shall be used if the object is yet to be
          defined by the PW maintenance protocol."
     REFERENCE
         "Martini, et al, 'Pseudowire Setup and Maintenance using
          the Label Distribution Protocol', RFC 4447."
     ::= { pwEntry 21 }

  pwCwStatus OBJECT-TYPE
     SYNTAX        PwCwStatusTC
     MAX-ACCESS    read-only
     STATUS        current
     DESCRIPTION
         "If signaling is used for PW establishment, this object
          indicates the status of the control word negotiation,
          and in both; signaling or manual configuration it indicates
          if CW is to be present for this PW."
     REFERENCE
         "Martini, et al, 'Pseudowire Setup and Maintenance using
          the Label Distribution Protocol', RFC 4447."
     ::= { pwEntry 22 }

  pwRemoteIfMtu OBJECT-TYPE
     SYNTAX        Unsigned32
     MAX-ACCESS    read-only
     STATUS        current
     DESCRIPTION
         "The remote interface MTU as (optionally) received from the
          remote node via the maintenance protocol. The object SHOULD
          report zero if MTU is not available."
     REFERENCE
         "Martini, et al, 'Pseudowire Setup and Maintenance using
          the Label Distribution Protocol', RFC 4447."
     ::= { pwEntry 23 }

  pwRemoteIfString OBJECT-TYPE
     SYNTAX        SnmpAdminString (SIZE (0..80))
     MAX-ACCESS    read-only
     STATUS        current
     DESCRIPTION
         "Indicates the interface description string as received by
          the maintenance protocol. It MUST be a NULL string if
          maintenance protocol is not used or the value is not known
          yet."
     REFERENCE
         "Martini, et al, 'Pseudowire Setup and Maintenance using
          the Label Distribution Protocol', RFC 4447, section 5.5."
     ::= { pwEntry 24 }

  pwRemoteCapabilities OBJECT-TYPE
     SYNTAX        IANAPwCapabilities
     MAX-ACCESS    read-only
     STATUS        current
     DESCRIPTION
         "Indicates the capabilities as recieved from the peer."
     REFERENCE
         "Martini, et al, 'Pseudowire Setup and Maintenance using
          the Label Distribution Protocol', RFC 4447."
     ::= { pwEntry 25 }

  pwFragmentCfgSize OBJECT-TYPE
     SYNTAX        PwFragSize
     UNITS         "bytes"
     MAX-ACCESS    read-create
     STATUS        current
     DESCRIPTION
         "If set to a value other than zero, indicates that
          fragmentation is desired for this PW.
          This object MAY be changed only if the PW is not active."
     REFERENCE
         "Malis A., Townsley M., 'PWE3 Fragmentation and Reassembly',
          RFC 4623."
     DEFVAL { 0 } -- i.e. fragmentation not desired
     ::= { pwEntry 26 }

  pwRmtFragCapability OBJECT-TYPE
     SYNTAX        PwFragStatus
     MAX-ACCESS    read-only
     STATUS        current
     DESCRIPTION
         "The status of the fragmentation based on the local
          configuration and the peer capabilities as recieved from
          the peer when control protocol is used."
     REFERENCE
         "Malis A., Townsley M., 'PWE3 Fragmentation and Reassembly',
          RFC 4623."
     ::= { pwEntry 27 }

  pwFcsRetentionCfg OBJECT-TYPE
     SYNTAX        INTEGER {
                   fcsRetentionDisable  (1),
                   fcsRetentionEnable   (2)
     }
     MAX-ACCESS    read-create
     STATUS        current
     DESCRIPTION
         "The local configuration of FCS retention for this PW. FCS
          retention can be configured for PW types HDLC, PPP and
          Ethernet only. If the implementation does not support
          FCS retention, error MUST be reported in pwFcsRetentionStatus.
          This object MAY be changed only if the PW is not active."
     REFERENCE
         "Malis A., et al.,  'PWE3 Frame Check Sequence Retention',
          RFC 4720."
     DEFVAL { fcsRetentionDisable }
     ::= { pwEntry 28 }

  pwFcsRetentionStatus OBJECT-TYPE
     SYNTAX   BITS {
              remoteIndicationUnknown     (0),
              remoteRequestFcsRetention   (1),
              fcsRetentionEnabled         (2),
              fcsRetentionDisabled        (3),
              localFcsRetentionCfgErr     (4),
              fcsRetentionFcsSizeMismatch (5)
              }
     MAX-ACCESS    read-only
     STATUS        current
     DESCRIPTION
        "The status of the FCS retention negotiation process based on
         local configuration and the remote advertisement.

         remoteIndicationUnknown - set if a FEC has not been received
         from the remote.

         remoteRequestFcsRetention - indicates that the peer has
         requested for FCS retention. FCS retention will be used if
         the local node is capable and configured to use it for this
         PW.

         fcsRetentionEnabled - FCS retention is enabled (both peers
         were configured for FCS retention for signaled PW, or the
         local node is configured and capable for FCS retention for
         manually assigned PW).

         fcsRetentionDisabled - FCS retention is disabled (not
         configured locally or not advertised by the peer).

         localFcsRetentionCfgErr - Set if the local node has been
         configured for FCS retention but is not capable to support
         it.

         fcsRetentionFcsSizeMismatch - Set if there is an FCS size
         mismatch between the local and the peer node.
        "
     REFERENCE
         "Malis A., et al.,  'PWE3 Frame Check Sequence Retention',
          RFC 4720"
     ::= { pwEntry 29 }

  pwOutboundLabel OBJECT-TYPE
     SYNTAX        Unsigned32
     MAX-ACCESS    read-create
     STATUS        current
     DESCRIPTION
         "The PW label used in the outbound direction (i.e. toward
          the PSN). It might be set manually if pwOwner is 'manual',
          otherwise setting done automatically.
          For MPLS, MPLS over IP or MPLS over GRE PSN, it represents
          the 20 bits of PW tag, for L2TP it represents the 32 bits
          Session ID and for IP PSN it represents the destination
          UDP port number.
          If the label is not yet known (signaling in process), the
          object SHOULD return a value of 0xFFFFFFFF.
          For manual configuration, this object MAY be changed only
          if the PW is not active."
     ::= { pwEntry 30 }

  pwInboundLabel OBJECT-TYPE
     SYNTAX        Unsigned32
     MAX-ACCESS    read-create
     STATUS        current
     DESCRIPTION
         "The PW label used in the inbound direction (i.e. packets
          received from the PSN). It may be set manually if pwOwner
          is 'manual',otherwise setting done automatically.
          For MPLS, MPLS over IP or MPLS over GRE PSN, it represents
          the 20 bits of PW tag, for L2TP it represents the 32 bits
          Session ID and for IP PSN it represents the source
          UDP port number.
          If the label is not yet known (signaling in process), the
          object SHOULD return a value of 0xFFFFFFFF.
          For manual configuration, this object MAY be changed only
          if the PW is not active."
     ::= { pwEntry 31 }

  pwName  OBJECT-TYPE
     SYNTAX        SnmpAdminString
     MAX-ACCESS    read-create
     STATUS        current
     DESCRIPTION
         "The canonical name assigned to the PW. This object MAY be
          changed at any time."
     ::= { pwEntry 32 }

  pwDescr OBJECT-TYPE
     SYNTAX        SnmpAdminString
     MAX-ACCESS    read-create
     STATUS        current
     DESCRIPTION
         "A textual string containing information about the PW.
          If there is no description this object contains a zero
          length string. This object MAY be changed at any time."
     ::= { pwEntry 33 }

  pwCreateTime OBJECT-TYPE
     SYNTAX        TimeStamp
     MAX-ACCESS    read-only
     STATUS        current
     DESCRIPTION
         "The value of sysUpTime at the time this PW was created."
     ::= { pwEntry 34 }

  pwUpTime  OBJECT-TYPE
     SYNTAX        TimeTicks
     MAX-ACCESS    read-only
     STATUS        current
     DESCRIPTION
         "Specifies the time since last change of pwOperStatus to
          Up(1)."
     ::= { pwEntry 35 }

  pwLastChange OBJECT-TYPE
     SYNTAX        TimeTicks
     MAX-ACCESS    read-only
     STATUS        current
     DESCRIPTION
        "The value of sysUpTime at the time the PW entered
         its current operational state.  If the current state was
         entered prior to the last re-initialization of the local
         network management subsystem, then this object contains a
         zero value."
     ::= { pwEntry 36 }

  pwAdminStatus OBJECT-TYPE
     SYNTAX   INTEGER {
                  up(1),     -- ready to pass packets
                  down(2),
                  testing(3) -- in a test mode
     }
     MAX-ACCESS    read-create
     STATUS        current
     DESCRIPTION
         "The desired operational status of this PW. This object MAY
          be set at any time."
     ::= { pwEntry 37 }

  pwOperStatus OBJECT-TYPE
     SYNTAX        PwOperStatusTC
     MAX-ACCESS    read-only
     STATUS        current
     DESCRIPTION
          "This object indicates the operational status of the PW, it
           does not reflect the status of the CE bound interface.
           It is set to down only if pwNotForwarding,
           psnFacingPwRxFault, or psnFacingPwTxFault indications are
           set in pwLocalStatus or pwRemoteStatus.
           It indicates 'lowerLayerDown' if the only reason for
           not being in the 'up' state is either outer tunnel
           or physical layer down of the network side is in the down
           state.
           All other states are declared based on the description in
           the textual convention.
           "
     ::= { pwEntry 38 }

  pwLocalStatus OBJECT-TYPE
     SYNTAX        PwStatus
     MAX-ACCESS    read-only
     STATUS        current
     DESCRIPTION
          "Indicates the status of the PW in the local node.
           The various indications in this object SHOULD be
           available independent of the ability of the local node to
           advertise them or the remote node to accept these status
           indications through the control protocol.
          "
     ::= { pwEntry 39 }

  pwRemoteStatusCapable OBJECT-TYPE
     SYNTAX        INTEGER {
            notApplicable    (1),
            notYetKnown      (2),
            remoteCapable    (3),
            remoteNotCapable (4)
     }
     MAX-ACCESS    read-only
     STATUS        current
     DESCRIPTION
          "Indicates the remote node capability to advertise the
           PW status notification.
           notAppicable SHOULD be reported for manually set PW, or
           if the local node is not capable of accepting the status
           notification object.
           notYetKnown SHOULD be reported if the signaling protocol
           has not yet finished the process of capability
           determination.
           remoteCapable and remoteNotcapable SHOULD be reported
           based on the initial signaling exchange that has
           determined the remote node capability.
         "
     ::= { pwEntry 40 }

  pwRemoteStatus OBJECT-TYPE
     SYNTAX        PwStatus
     MAX-ACCESS    read-only
     STATUS        current
     DESCRIPTION
          "Indicates the status of the PW as was advertised by the
           remote. If the remote is not capable of advertising the
           status object, or the local node is not able to accept
           the status object through signaling, then the applicable
           bit is 'pwNotForwarding' which is set if the remote has
           sent label release or label withdraw for this PW.
          "
     ::= { pwEntry 41 }

  pwTimeElapsed OBJECT-TYPE
      SYNTAX  HCPerfTimeElapsed
      MAX-ACCESS  read-only
      STATUS  current
      DESCRIPTION
           "The number of seconds, including partial seconds,
            that have elapsed since the beginning of the current
            interval measurement period."
     ::= { pwEntry 42 }

  pwValidIntervals OBJECT-TYPE
      SYNTAX  HCPerfValidIntervals
      MAX-ACCESS  read-only
      STATUS  current
      DESCRIPTION
         "The number of previous 15-minute intervals
         for which data was collected."
     ::= { pwEntry 43 }

  pwRowStatus OBJECT-TYPE
     SYNTAX        RowStatus
     MAX-ACCESS    read-create
     STATUS        current
     DESCRIPTION
         "For creating, modifying, and deleting this row.
          This object MAY be changed at any time."
     ::= { pwEntry 44 }

  pwStorageType OBJECT-TYPE
     SYNTAX        StorageType
     MAX-ACCESS    read-create
     STATUS        current
     DESCRIPTION
         "This variable indicates the storage type for this
          object."
     DEFVAL { nonVolatile }
     ::= { pwEntry 45 }

  pwOamEnable  OBJECT-TYPE
     SYNTAX        TruthValue
     MAX-ACCESS    read-create
     STATUS        current
     DESCRIPTION
         "This variable indicates if OAM is enabled for this
          PW. It MAY be changed at any time."
     DEFVAL { true }
     ::= { pwEntry 46 }

  -- End of PW Virtual Connection Table

  -- PW Performance Table.

  pwPerfCurrentTable  OBJECT-TYPE
     SYNTAX        SEQUENCE OF PwPerfCurrentEntry
     MAX-ACCESS    not-accessible
     STATUS        current
     DESCRIPTION
          "This table provides per-PW performance information for
           the current interval."
     ::= { pwObjects 3 }

  pwPerfCurrentEntry OBJECT-TYPE
     SYNTAX        PwPerfCurrentEntry
     MAX-ACCESS    not-accessible
     STATUS        current
     DESCRIPTION
          "An entry in this table is created by the agent for
           every PW."
     INDEX  { pwIndex }
     ::= { pwPerfCurrentTable 1 }

  PwPerfCurrentEntry ::= SEQUENCE {
        pwPerfCurrentInHCPackets         HCPerfCurrentCount,
        pwPerfCurrentInHCBytes           HCPerfCurrentCount,
        pwPerfCurrentOutHCPackets        HCPerfCurrentCount,
        pwPerfCurrentOutHCBytes          HCPerfCurrentCount,
        pwPerfCurrentInPackets           PerfCurrentCount,
        pwPerfCurrentInBytes             PerfCurrentCount,
        pwPerfCurrentOutPackets          PerfCurrentCount,
        pwPerfCurrentOutBytes            PerfCurrentCount
        }

  pwPerfCurrentInHCPackets OBJECT-TYPE
     SYNTAX        HCPerfCurrentCount
     MAX-ACCESS    read-only
     STATUS        current
     DESCRIPTION
          "High capacity counter for number of packets received by
           the PW (from the PSN) in the current 15-minute interval.
           This is the 64 bit version of pwPerfCurrentInPackets,
           if pwPerfCurrentInHCPackets is supported according to
           the rules spelled out in RFC2863."
     ::= { pwPerfCurrentEntry 1 }

  pwPerfCurrentInHCBytes OBJECT-TYPE
     SYNTAX        HCPerfCurrentCount
     MAX-ACCESS    read-only
     STATUS        current
     DESCRIPTION
          "High capacity counter for number of bytes received by the
           PW (from the PSN) in the current 15-minute interval.
           This is the 64 bit version of pwPerfCurrentInBytes, if
           pwPerfCurrentInHCBytes is supported according to the
           rules spelled out in RFC2863."
     ::= { pwPerfCurrentEntry 2 }

  pwPerfCurrentOutHCPackets OBJECT-TYPE
     SYNTAX        HCPerfCurrentCount
     MAX-ACCESS    read-only
     STATUS        current
     DESCRIPTION
          "High capacity counter for number of packets forwarded by
           the PW (to the PSN) in the current 15-minute interval.
           This is the 64 bit version of pwPerfCurrentOutPackets,
           if pwPerfCurrentOutHCPackets is supported according to
           the rules spelled out in RFC2863."
     ::= { pwPerfCurrentEntry 3 }

  pwPerfCurrentOutHCBytes OBJECT-TYPE
     SYNTAX        HCPerfCurrentCount
     MAX-ACCESS    read-only
     STATUS        current
     DESCRIPTION
          "High capacity counter for number of bytes forwarded by
           the PW (to the PSN) in the current 15-minute interval.
           This is the 64 bit version of pwPerfCurrentOutBytes,
           if pwPerfCurrentOutHCBytes is supported according to
           the rules spelled out in RFC2863."
     ::= { pwPerfCurrentEntry 4 }

  pwPerfCurrentInPackets OBJECT-TYPE
     SYNTAX        PerfCurrentCount
     MAX-ACCESS    read-only
     STATUS        current
     DESCRIPTION
          "The counter for number of packets received by the PW (from
           the PSN) in the current 15-minute interval.
           This is the 32 bit version of pwPerfCurrentInHCPackets,
           if pwPerfCurrentInHCPackets is supported according to
           the rules spelled out in RFC2863."
     ::= { pwPerfCurrentEntry 5 }

  pwPerfCurrentInBytes OBJECT-TYPE
     SYNTAX        PerfCurrentCount
     MAX-ACCESS    read-only
     STATUS        current
     DESCRIPTION
          "The counter for number of bytes received by the
           PW (from the PSN) in the current 15-minute interval.
           It MUST be equal to the least significant 32 bits of
           pwPerfCurrentInHCBytes, if pwPerfCurrentInHCBytes is
           supported according to the rules spelled out in RFC2863."
     ::= { pwPerfCurrentEntry 6 }

  pwPerfCurrentOutPackets OBJECT-TYPE
     SYNTAX        PerfCurrentCount
     MAX-ACCESS    read-only
     STATUS        current
     DESCRIPTION
          "The counter for number of packets forwarded by
           the PW (to the PSN) in the current 15-minute interval.
           It MUST be equal to the least significant 32 bits of
           pwPerfCurrentOutHCPackets, if
           pwPerfCurrentOutHCPackets is supported according to the
           rules spelled out in RFC2863."
     ::= { pwPerfCurrentEntry 7 }

  pwPerfCurrentOutBytes OBJECT-TYPE
     SYNTAX        PerfCurrentCount
     MAX-ACCESS    read-only
     STATUS        current
     DESCRIPTION
          "The counter for number of bytes forwarded by
           the PW (to the PSN) in the current 15-minute interval.
           It MUST be equal to the least significant 32 bits of
           pwPerfCurrentOutHCBytes, if pwPerfCurrentOutHCBytes is
           supported according to the rules spelled out in RFC2863."
     ::= { pwPerfCurrentEntry 8 }

  -- End of PW Perf current Table

  -- PW Performance Interval Table.

  pwPerfIntervalTable  OBJECT-TYPE
     SYNTAX        SEQUENCE OF PwPerfIntervalEntry
     MAX-ACCESS    not-accessible
     STATUS        current
     DESCRIPTION
          "This table provides per-PW performance information for
           each interval."
     ::= { pwObjects 4 }

  pwPerfIntervalEntry OBJECT-TYPE
     SYNTAX        PwPerfIntervalEntry
     MAX-ACCESS    not-accessible
     STATUS        current
     DESCRIPTION
          "An entry in this table is created by the agent for every
           PW."
     INDEX  { pwIndex, pwPerfIntervalNumber }
     ::= { pwPerfIntervalTable 1 }

  PwPerfIntervalEntry ::= SEQUENCE {
        pwPerfIntervalNumber               Integer32,
        pwPerfIntervalValidData            TruthValue,
        pwPerfIntervalTimeElapsed          HCPerfTimeElapsed,
        pwPerfIntervalInHCPackets          HCPerfIntervalCount,
        pwPerfIntervalInHCBytes            HCPerfIntervalCount,
        pwPerfIntervalOutHCPackets         HCPerfIntervalCount,
        pwPerfIntervalOutHCBytes           HCPerfIntervalCount,
        pwPerfIntervalInPackets            PerfIntervalCount,
        pwPerfIntervalInBytes              PerfIntervalCount,
        pwPerfIntervalOutPackets           PerfIntervalCount,
        pwPerfIntervalOutBytes             PerfIntervalCount
                          }

  pwPerfIntervalNumber OBJECT-TYPE
     SYNTAX  Integer32 (1..96)
     MAX-ACCESS  not-accessible
     STATUS  current
     DESCRIPTION
          "A number N, between 1 and 96, which identifies the
           interval for which the set of statistics is available.
           The interval identified by 1 is the most recently
           completed 15 minute interval, and the interval identified
           by N is the interval immediately preceding the one
           identified by N-1.
           The minimum range of N is 1 through 4. The default range
           is 1 to 32. The maximum range of N is 1 through 96. "
     REFERENCE
         "Tesink, K. 'Definitions of Managed Objects for the
          SONET/SDH Interface Type', RFC 2558"
     ::= { pwPerfIntervalEntry 1 }

  pwPerfIntervalValidData OBJECT-TYPE
     SYNTAX        TruthValue
     MAX-ACCESS    read-only
     STATUS        current
     DESCRIPTION
         "This variable indicates if the data for this interval
          is valid."
     ::= { pwPerfIntervalEntry 2 }

  pwPerfIntervalTimeElapsed OBJECT-TYPE
     SYNTAX      HCPerfTimeElapsed
     MAX-ACCESS  read-only
     STATUS      current
     DESCRIPTION
        "The duration of this interval in seconds."
     ::= { pwPerfIntervalEntry 3 }

  pwPerfIntervalInHCPackets OBJECT-TYPE
     SYNTAX        HCPerfIntervalCount
     MAX-ACCESS    read-only
     STATUS        current
     DESCRIPTION
          "High capacity counter for number of packets received by
           the PW (from the PSN) during the interval. This is the 64
           bit version of pwPerfIntervalInPackets, if
           pwPerfIntervalInHCPackets is supported according to the
           rules spelled out in RFC2863."
     ::= { pwPerfIntervalEntry 4 }

  pwPerfIntervalInHCBytes OBJECT-TYPE
     SYNTAX        HCPerfIntervalCount
     MAX-ACCESS    read-only
     STATUS        current
     DESCRIPTION
          "High capacity counter for number of bytes received by the
           PW (from the PSN) during the interval.
           This is the 64 bit version of pwPerfIntervalInBytes, if
           pwPerfIntervalInHCBytes is supported according to the
           rules spelled out in RFC2863."
     ::= { pwPerfIntervalEntry 5 }

  pwPerfIntervalOutHCPackets OBJECT-TYPE
     SYNTAX        HCPerfIntervalCount
     MAX-ACCESS    read-only
     STATUS        current
     DESCRIPTION
          "High capacity counter for number of packets forwarded by
           the PW (to the PSN) during the interval.
           This is the 64 bit version of pwPerfIntervalOutPackets,
           if pwPerfIntervalOutHCPackets is supported according to
           the rules spelled out in RFC2863."
     ::= { pwPerfIntervalEntry 6 }

  pwPerfIntervalOutHCBytes OBJECT-TYPE
     SYNTAX        HCPerfIntervalCount
     MAX-ACCESS    read-only
     STATUS        current
     DESCRIPTION
          "High capacity counter for number of bytes forwarded by
           the PW (to the PSN) during the interval.
           This is the 64 bit version of pwPerfIntervalOutBytes,
           if pwPerfIntervalOutHCBytes is supported according to
           the rules spelled out in RFC2863."
     ::= { pwPerfIntervalEntry 7 }

  pwPerfIntervalInPackets OBJECT-TYPE
     SYNTAX        PerfIntervalCount
     MAX-ACCESS    read-only
     STATUS        current
     DESCRIPTION
         "This value represents the number of packets received
          by this PW during the interval.
          It MUST be equal to the least significant 32 bits of
          pwPerfIntervalInHCPackets if pwPerfIntervalInHCPackets
          is supported according to the rules spelled out in
          RFC2863."
     ::= { pwPerfIntervalEntry 8 }

  pwPerfIntervalInBytes OBJECT-TYPE
     SYNTAX        PerfIntervalCount
     MAX-ACCESS    read-only
     STATUS        current
     DESCRIPTION
         "This value represents the number of bytes received
          by this PW during the interval.
          It MUST be equal to the least significant 32 bits of
          if pwPerfIntervalInHCBytes is supported according to
          the rules spelled out in RFC2863."
     ::= { pwPerfIntervalEntry 9 }

  pwPerfIntervalOutPackets OBJECT-TYPE
     SYNTAX        PerfIntervalCount
     MAX-ACCESS    read-only
     STATUS        current
     DESCRIPTION
         "This value represents the number of packets sent by this
          PW during the interval.
          It MUST be equal to the least significant 32 bits of
          pwPerfIntervalOutHCPackets if
          pwPerfIntervalOutHCPackets is supported according to the
          rules spelled out in RFC2863."
     ::= { pwPerfIntervalEntry 10 }

  pwPerfIntervalOutBytes OBJECT-TYPE
     SYNTAX        PerfIntervalCount
     MAX-ACCESS    read-only
     STATUS        current
     DESCRIPTION
         "This value represents the number of bytes sent by this
          PW during the interval.
          It MUST be equal to the least significant 32
          bits of pwPerfIntervalOutHCBytes
          if pwPerfIntervalOutHCBytes is supported according to
          the rules spelled out in RFC2863."
     ::= { pwPerfIntervalEntry 11 }

  -- End of PW Performance Interval Table


   -- PW Performance Total Table. 
    
   pwPerfTotalTable  OBJECT-TYPE 
      SYNTAX        SEQUENCE OF PwPerfTotalEntry 
      MAX-ACCESS    not-accessible 
      STATUS        current 
      DESCRIPTION 
           "This table provides per-PW Performance information from  
            PW start time or management application reset.
            
            This table has been obsoleted from draft v.11 and a new
            table pwPerf1DayIntervalTable has been introduced.  However,
            due to better support, pwPerfTotalTable is supported in the
            place of pwPerf1DayIntervalTable."
      ::= { pwObjects 5 } 
    
   pwPerfTotalEntry OBJECT-TYPE 
      SYNTAX        PwPerfTotalEntry 
      MAX-ACCESS    not-accessible 
      STATUS        current 
      DESCRIPTION 
           "An entry in this table is created by the agent for every  
            PW. 
             
            pwPerfTotalDiscontinuityTime indicates the time of the 
            last discontinuity in any of these objects." 
    
      INDEX  { pwIndex } 
      ::= { pwPerfTotalTable 1 } 
       
   PwPerfTotalEntry ::= SEQUENCE { 
         pwPerfTotalInHCPackets          Counter64, 
         pwPerfTotalInHCBytes            Counter64, 
         pwPerfTotalOutHCPackets         Counter64, 
         pwPerfTotalOutHCBytes           Counter64, 
         pwPerfTotalInPackets            Counter32, 
         pwPerfTotalInBytes              Counter32, 
         pwPerfTotalOutPackets           Counter32, 
         pwPerfTotalOutBytes             Counter32, 
         pwPerfTotalDiscontinuityTime    TimeStamp 
                           } 
    
   pwPerfTotalInHCPackets OBJECT-TYPE 
      SYNTAX        Counter64 
      MAX-ACCESS    read-only 
      STATUS        current 
      DESCRIPTION 
           "High capacity counter for the total number of packets  
            received by the PW (from the PSN).  
            This is the 64 bit version of pwPerfTotalInPackets, if  
            pwPerfTotalInHCPackets is supported according to the 
            rules spelled out in RFC2863." 
      ::= { pwPerfTotalEntry 1 } 
    
   pwPerfTotalInHCBytes OBJECT-TYPE 
      SYNTAX        Counter64 
      MAX-ACCESS    read-only 
      STATUS        current 
      DESCRIPTION 
           "High capacity counter for the total number of bytes 
            received by the PW (from the PSN).  
            This is the 64 bit version of pwPerfTotalInBytes, if  
            pwPerfTotalInHCBytes is supported according to the  
            rules spelled out in RFC2863." 
      ::= { pwPerfTotalEntry 2 } 
    
   pwPerfTotalOutHCPackets OBJECT-TYPE 
      SYNTAX        Counter64 
      MAX-ACCESS    read-only 
      STATUS        current 
      DESCRIPTION 
           "High capacity counter for the total number of packets  
            forwarded by the PW (to the PSN). 
            This is the 64 bit version of pwPerfTotalOutPackets,  
            if pwPerfTotalOutHCPackets is supported according to  
            the rules spelled out in RFC2863." 
      ::= { pwPerfTotalEntry 3 } 
    
   pwPerfTotalOutHCBytes OBJECT-TYPE 
      SYNTAX        Counter64 
      MAX-ACCESS    read-only 
      STATUS        current 
      DESCRIPTION 
           "High capacity counter for the total number of bytes  
            forwarded by the PW (to the PSN). 
            This is the 64 bit version of pwPerfTotalOutBytes,  
            if pwPerfTotalOutHCBytes is supported according to  
            the rules spelled out in RFC2863." 
      ::= { pwPerfTotalEntry 4 } 
    
   pwPerfTotalInPackets OBJECT-TYPE 
      SYNTAX        Counter32 
      MAX-ACCESS    read-only 
      STATUS        current 
      DESCRIPTION 
          "This value represents the total number of packets received  
           by this PW.  

           It MUST be equal to the least significant 32 bits of  
           pwPerfTotalInHCPackets if pwPerfTotalInHCPackets  
           is supported according to the rules spelled out in  
           RFC2863." 
      ::= { pwPerfTotalEntry 5 } 
    
   pwPerfTotalInBytes OBJECT-TYPE 
      SYNTAX        Counter32 
      MAX-ACCESS    read-only 
      STATUS        current 
      DESCRIPTION 
          "This value represents the total number of bytes received  
           by this PW.  
           It MUST be equal to the least significant 32 bits of  
           if pwPerfTotalInHCBytes is supported according to 
           the rules spelled out in RFC2863." 
      ::= { pwPerfTotalEntry 6 } 
    
   pwPerfTotalOutPackets OBJECT-TYPE 
      SYNTAX        Counter32 
      MAX-ACCESS    read-only 
      STATUS        current 
      DESCRIPTION 
          "This value represents the total number of packets sent by  
           this PW.  
           It MUST be equal to the least significant 32 bits of  
           pwPerfTotalOutHCPackets if pwPerfTotalOutHCPackets 
           is supported according to the rules spelled out in  
           RFC2863." 
      ::= { pwPerfTotalEntry 7 } 
    
   pwPerfTotalOutBytes OBJECT-TYPE 
      SYNTAX        Counter32 
      MAX-ACCESS    read-only 
      STATUS        current 
      DESCRIPTION 
          "This value represents the total number of bytes sent by  
           this PW. 
           It MUST be equal to the least significant 32  
           bits of pwPerfTotalOutHCBytes 
           if pwPerfTotalOutHCBytes is supported according to 
           the rules spelled out in RFC2863." 
      ::= { pwPerfTotalEntry 8 } 
    
   pwPerfTotalDiscontinuityTime OBJECT-TYPE 
      SYNTAX      TimeStamp 
      MAX-ACCESS  read-only 
      STATUS      current 
      DESCRIPTION 
          "The value of sysUpTime on the most recent occasion at 
           which any one or more of this row Counter32 or 
           Counter64 suffered a discontinuity. If no such 
           discontinuities have occurred since the last re- 
           initialization of the local management subsystem, then 
           this object contains a zero value." 
      ::= { pwPerfTotalEntry 9 } 
    
   -- End of PW Perf Total Table 

  -- Error counter scalar

  pwPerfTotalErrorPackets OBJECT-TYPE
     SYNTAX        Counter32
     MAX-ACCESS    read-only
     STATUS        current
     DESCRIPTION
          "Counter for number of error at the PW processing level,
           for example packets received with unknown PW label."
     ::= { pwObjects 6 }

  -- Reverse mapping tables

  -- The PW ID mapping table
  pwIndexMappingTable  OBJECT-TYPE
     SYNTAX        SEQUENCE OF PwIndexMappingEntry
     MAX-ACCESS    not-accessible
     STATUS        current
     DESCRIPTION
          "This table enables the reverse mapping the unique PWid
           parameters [peer IP, PW type and PW ID] and the
           pwIndex. The table is not applicable for PW created
           manually or by using the generalized FEC."
     ::= { pwObjects 7 }

  pwIndexMappingEntry OBJECT-TYPE
     SYNTAX        PwIndexMappingEntry
     MAX-ACCESS    not-accessible
     STATUS        current
     DESCRIPTION
          "An entry in this table MUST be created by the agent for
           every PW created by the pwTable for which pwOwner
           equals pwIdFecSignaling and pwID is not zero.

           Implementors need to be aware that if the value of
           the pwIndexMappingPeerAddr (an OID) has more than
           112 sub-identifiers, then OIDs of column  instances
           in this table will have more than 128
           sub-identifiers and cannot be accessed using SNMPv1,
           SNMPv2c, or SNMPv3."
     INDEX  { pwIndexMappingPwType,  pwIndexMappingPwID,
              pwIndexMappingPeerAddrType, pwIndexMappingPeerAddr
              }
     ::= { pwIndexMappingTable 1 }

  PwIndexMappingEntry ::= SEQUENCE {
        pwIndexMappingPwType        IANAPwTypeTC,
        pwIndexMappingPwID          PwIDType,
        pwIndexMappingPeerAddrType  InetAddressType,
        pwIndexMappingPeerAddr      InetAddress,
        pwIndexMappingPwIndex       PwIndexType
                         }

  pwIndexMappingPwType OBJECT-TYPE
     SYNTAX        IANAPwTypeTC
     MAX-ACCESS    not-accessible
     STATUS        current
     DESCRIPTION
          "The PW type (indicates the service) of this PW."
     ::= { pwIndexMappingEntry 1 }

  pwIndexMappingPwID OBJECT-TYPE
     SYNTAX        PwIDType
     MAX-ACCESS    not-accessible
     STATUS        current
     DESCRIPTION
          "The PW ID of this PW. Zero if the PW is configured
           manually."
     ::= { pwIndexMappingEntry 2 }

  pwIndexMappingPeerAddrType OBJECT-TYPE
     SYNTAX        InetAddressType
     MAX-ACCESS    not-accessible
     STATUS        current
     DESCRIPTION
          "IP address type of the peer node."
     ::= { pwIndexMappingEntry 3 }

  pwIndexMappingPeerAddr OBJECT-TYPE
     SYNTAX        InetAddress
     MAX-ACCESS    not-accessible
     STATUS        current
     DESCRIPTION
          "IP address of the peer node."
     ::= { pwIndexMappingEntry 4 }

  pwIndexMappingPwIndex  OBJECT-TYPE
     SYNTAX        PwIndexType
     MAX-ACCESS    read-only
     STATUS        current
     DESCRIPTION
         "The value that represents the PW in the pwTable."
     ::= { pwIndexMappingEntry 5 }

  -- End of the PW ID mapping table

  -- The peer mapping table

  pwPeerMappingTable  OBJECT-TYPE
     SYNTAX        SEQUENCE OF PwPeerMappingEntry
     MAX-ACCESS    not-accessible
     STATUS        current
     DESCRIPTION
          "This table provides reverse mapping of the existing PW
           based on PW type and PW ID ordering. This table is
           typically useful for EMS ordered query of existing PWs."
     ::= { pwObjects 8 }

  pwPeerMappingEntry OBJECT-TYPE
     SYNTAX        PwPeerMappingEntry
     MAX-ACCESS    not-accessible
     STATUS        current
     DESCRIPTION
          "An entry in this table is created by the agent for every
           PW entry in pwTable.

          Implementors need to be aware that if the value of the
          pwPeerMappingPeerAddr (an OID) has more than 112
          sub-identifiers, then OIDs of column instances in this
          table will have more than 128 sub-identifiers and cannot
          be accessed using SNMPv1, SNMPv2c, or SNMPv3."
     INDEX  { pwPeerMappingPeerAddrType, pwPeerMappingPeerAddr,
              pwPeerMappingPwType,  pwPeerMappingPwID }

     ::= { pwPeerMappingTable 1 }

  PwPeerMappingEntry ::= SEQUENCE {
        pwPeerMappingPeerAddrType         InetAddressType,
        pwPeerMappingPeerAddr             InetAddress,
        pwPeerMappingPwType               IANAPwTypeTC,
        pwPeerMappingPwID                 PwIDType,
        pwPeerMappingPwIndex              PwIndexType
                         }

  pwPeerMappingPeerAddrType OBJECT-TYPE
     SYNTAX        InetAddressType
     MAX-ACCESS    not-accessible
     STATUS        current
     DESCRIPTION
          "IP address type of the peer node."
     ::= { pwPeerMappingEntry 1 }

  pwPeerMappingPeerAddr OBJECT-TYPE
     SYNTAX        InetAddress
     MAX-ACCESS    not-accessible
     STATUS        current
     DESCRIPTION
          "IP address of the peer node."
     ::= { pwPeerMappingEntry 2 }

  pwPeerMappingPwType OBJECT-TYPE
     SYNTAX        IANAPwTypeTC
     MAX-ACCESS    not-accessible
     STATUS        current
     DESCRIPTION
          "The PW type (indicates the emulated service) of this PW."
     ::= { pwPeerMappingEntry 3 }

  pwPeerMappingPwID OBJECT-TYPE
     SYNTAX        PwIDType
     MAX-ACCESS    not-accessible
     STATUS        current
     DESCRIPTION
          "The PW ID of this PW. Zero if the PW is configured
           manually."
     ::= { pwPeerMappingEntry 4 }

  pwPeerMappingPwIndex  OBJECT-TYPE
     SYNTAX        PwIndexType
     MAX-ACCESS    read-only
     STATUS        current
     DESCRIPTION
         "The value that represents the PW in the pwTable."
     ::= { pwPeerMappingEntry 5 }

  -- End of the peer mapping table

  -- End of reverse mapping tables

  pwUpDownNotifEnable  OBJECT-TYPE
     SYNTAX      TruthValue
     MAX-ACCESS  read-write
     STATUS      current
     DESCRIPTION
        "If this object is set to true(1), then it enables
         the emission of pwUp and pwDown
         notifications; otherwise these notifications are not
         emitted."
     REFERENCE
        "See also [RFC3413] for explanation that
         notifications are under the ultimate control of the
         MIB module in this document."
     DEFVAL { false }
     ::= { pwObjects 9 }

  pwDeletedNotifEnable  OBJECT-TYPE
     SYNTAX      TruthValue
     MAX-ACCESS  read-write
     STATUS      current
     DESCRIPTION
        "If this object is set to true(1), then it enables the
         emission of pwDeleted notification; otherwise this
         notification is not emitted."
     REFERENCE
        "See also [RFC3413] for explanation that
         notifications are under the ultimate control of the
         MIB module in this document."
     DEFVAL { false }
     ::= { pwObjects 10 }

  pwNotifRate  OBJECT-TYPE
     SYNTAX      Unsigned32
     MAX-ACCESS  read-write
     STATUS      current
     DESCRIPTION
        "This object defines the maximum number of PW notifications
         that can be emitted from the device per second."
     ::= { pwObjects 11 }

-- Foundry Proprietary extension

  fdryPwServiceType OBJECT-TYPE
     SYNTAX        FdryPwServiceType
     MAX-ACCESS    accessible-for-notify
     STATUS        current
     DESCRIPTION
         "A L2VPN service type, used only for notification.
         "
     ::= { pwObjects 20 }

  -- Notifications - PW

  pwDown NOTIFICATION-TYPE
     OBJECTS { pwOperStatus, --start of range
               pwOperStatus,  --end of range
               fdryPwServiceType,  -- properietary extension
               snAgGblTrapMessage  -- properietary extension
     }
     STATUS  current
     DESCRIPTION
         "This notification is generated when the
          pwOperStatus object for one or more contiguous
          entries in pwTable are about to enter the
          down(2) state from some other state. The included values
          of pwOperStatus MUST all be set equal to this
          down(2) state.  The two instances of pwOperStatus
          in this notification indicate the range of indexes
          that are affected.  Note that all the indexes of the
          two ends of the range can be derived from the
          instance identifiers of these two objects.  For
          cases where a contiguous range of cross-connects
          have transitioned into the down(2) state at roughly
          the same time, the device SHOULD issue a single
          notification for each range of contiguous indexes in
          an effort to minimize the emission of a large number
          of notifications.  If a notification has to be
          issued for just a single cross-connect entry, then
          the instance identifier (and values) of the two
          pwOperStatus objects MUST be identical.
             The varbind fdryPwServiceType, specifies the 
          service that originated this notification.
             The varbind snAgGblTrapMessage displays the corresponding
          SYSLOG content for this notification, which is more descriptive.
          "
         --#TYPE "Foundry Trap: MPLS Pseudo-Wire Down"
         --#SUMMARY "%s."
         --#ARGUMENTS { 3 }
         --#SEVERITY WARNING
         --#STATE OPERATIONAL
     ::= { pwNotifications  1 }

  pwUp NOTIFICATION-TYPE
     OBJECTS { pwOperStatus, --start of range
               pwOperStatus,  --end of range
               fdryPwServiceType,  -- properietary extension
               snAgGblTrapMessage  -- properietary extension
     }
     STATUS  current
     DESCRIPTION
         "This notification is generated when the
          pwOperStatus object for one or more contiguous
          entries in pwTable are about to enter the up(1)
          state from some other state. The included values of
          pwOperStatus MUST both be set equal to this
          new state (i.e: up(1)).  The two instances of
          pwOperStatus in this notification indicate the range
          of indexes that are affected.  Note that all the indexes
          of the two ends of the range can be derived from the
          instance identifiers of these two objects.  For
          cases where a contiguous range of cross-connects
          have transitioned into the up(1) state at roughly
          the same time, the device SHOULD issue a single
          notification for each range of contiguous indexes in
          an effort to minimize the emission of a large number
          of notifications.  If a notification has to be
          issued for just a single cross-connect entry, then
          the instance identifier (and values) of the two
          pwOperStatus objects MUST be the identical.
             The varbind fdryPwServiceType, specifies the 
          service that originated this notification.
             The varbind snAgGblTrapMessage displays the corresponding
          SYSLOG content for this notification, which is more descriptive.
          "
         --#TYPE "Foundry Trap: MPLS Pseudo-Wire Up"
         --#SUMMARY "%s."
         --#ARGUMENTS { 3 }
         --#SEVERITY WARNING
         --#STATE OPERATIONAL
     ::= { pwNotifications 2 }

  pwDeleted NOTIFICATION-TYPE
     OBJECTS { pwType,
               pwID,
               pwPeerAddrType,
               pwPeerAddr,
               fdryPwServiceType,  -- properietary extension
               pwName --proprietary extension
     }
     STATUS  current
     DESCRIPTION
         "This notification is generated when the PW has been
          deleted, i.e. when the pwRowStatus has been set to
          destroy(6), the PW has been deleted by a non-MIB
          application or due to auto-discovery process.
            pwName varbind has been added as a proprietary extension
          to provide a name, in addition to the pwID, which has the VC ID.
          For VPLS PW, name is the VPLS instance name.
          For VLL PW, it is the VLL instance name. Similarly, for VLL-Local PW,
          it is the VLL-Local's instance name.
             The varbind fdryPwServiceType, specifies the 
          service that originated this notification.
         "
         --#TYPE "Foundry Trap: MPLS Pseudo-Wire Deleted"
         --#SUMMARY "PW %s (ID %d) with peer %s has been deleted."
         --#ARGUMENTS { 5, 1, 3 }
         --#SEVERITY WARNING
         --#STATE OPERATIONAL
     ::= { pwNotifications  3 }

  -- End of notifications.

  -- Conformance information

  pwGroups      OBJECT IDENTIFIER ::= { pwConformance   1 }
  pwCompliances OBJECT IDENTIFIER ::= { pwConformance   2 }

  -- Compliance requirement for fully compliant implementations.

  pwModuleFullCompliance MODULE-COMPLIANCE
      STATUS  current
      DESCRIPTION
              "The compliance statement for agents that provide full
               support for PW MIB Module. Such devices can
               then be monitored and configured using
               this MIB module."

      MODULE  -- this module
          MANDATORY-GROUPS { pwBasicGroup,
                             pwPerformanceGeneralGroup,
                             pwPeformanceTotalGroup
                           }

     GROUP pwNotificationGroup
     DESCRIPTION "This group is only mandatory for implementations
                  which can efficiently implement the notifications
                  contained in this group.
                 "

     GROUP        pwPwIdGroup
     DESCRIPTION "This group is only mandatory for implementations
                  that support the PW ID FEC.
                 "

     GROUP        pwGeneralizedFecGroup
     DESCRIPTION "This group is only mandatory for implementations
                  that support the generalized PW FEC.
                 "

     GROUP        pwFcsGroup
     DESCRIPTION "This group is only mandatory for implementations
                  that support FCS retention."

     GROUP        pwFragGroup
     DESCRIPTION "This group is only mandatory for implementations
                  that support PW fragmentation.
                 "

     GROUP        pwPwStatusGroup
     DESCRIPTION "This group is only mandatory for implementations
                  that support PW status notification.
                 "

     GROUP        pwGetNextGroup
     DESCRIPTION "This group is only mandatory for implementations
                  where the pwIndex may be any arbitrary value
                  and the EMS would require retrieval of the next
                  free index."

     GROUP        pwPriorityGroup
     DESCRIPTION "This group is only mandatory for implementations
                  that support the controlling the PW setup and
                  holding priority."

     GROUP        pwAttachmentGroup
     DESCRIPTION "This group is only mandatory for implementations
                  that support attachment of two PWs (PW stitching)."

     GROUP        pwPerformanceIntervalGeneralGroup
     DESCRIPTION "This group is only mandatory for implementations
                  that support PW performance gathering in 15
                  minute intervals."

     GROUP        pwPeformanceIntervalGroup
     DESCRIPTION "This group is only mandatory for implementations
                  that support PW performance gathering in 15
                  minute intervals."

     GROUP        pwHCPeformanceIntervalGroup
     DESCRIPTION "This group is only mandatory for implementations
                  where at least one of the interval performance
                  counters wraps around too quickly based on the
                  criteria specified in RFC 2863 for high-capacity
                  counters."

     GROUP        pwMappingTablesGroup
     DESCRIPTION "This group is only mandatory for implementations
                  that support reverse mapping of PW indexes to
                  the pwIndex and the peer mapping table."

     GROUP        pwSignalingGroup
     DESCRIPTION "This group is only mandatory for implementations
                  that support the PW signaling."

     GROUP        pwNotificationControlGroup
     DESCRIPTION "This group is only mandatory for implementations
                  that support the PW notifications."

     OBJECT       pwAdminStatus
     SYNTAX       INTEGER { up(1), down(2) }
     DESCRIPTION "The support of the value testing(3) is not
                  required."

     OBJECT       pwOperStatus
     SYNTAX       INTEGER { up(1), down(2), notPresent(5),
                  lowerLayerDown(6) }
     DESCRIPTION "The support of the values testing(3) and dormant(4)
                  is not required."

     OBJECT       pwRowStatus
     SYNTAX       INTEGER { active(1), notInService(2),
                              notReady(3) }
     WRITE-SYNTAX INTEGER { active(1), notInService(2),
                              createAndGo(4), destroy(6)
                            }
     DESCRIPTION "Support for createAndWait is not required. Support
                  of notReady is not required for implementations
                  that do not support signaling, or if it is
                  guaranteed that the conceptual row has all the
                  required information to create the PW when the
                  row has been created by the agent or written by
                  the operator."

     OBJECT       pwPeerAddrType
     SYNTAX       INTEGER { unknown(0), ipv4(1) }
     MIN-ACCESS   read-only
     DESCRIPTION "Only unknown(0) and ipv4(1) is required.
                  Implementation that support only IPv4 MAY support
                  read-only access."

     OBJECT       pwPeerAddr
     SYNTAX       InetAddress (SIZE(0|4))
     DESCRIPTION "An implementation is only required to support
                  0, 4 address sizes."

     OBJECT       pwStorageType
     MIN-ACCESS   read-only
     DESCRIPTION "Write access is not required."

     OBJECT       pwNotifRate
     MIN-ACCESS   read-only
     DESCRIPTION "Write access is not required."

       ::= { pwCompliances 1 }

  -- Compliance requirement for read-only compliant implementations.

  pwModuleReadOnlyCompliance MODULE-COMPLIANCE
      STATUS  current
      DESCRIPTION
              "The compliance statement for agents that provide read-
               only support for PW MIB Module. Such devices can
               then be monitored but cannot be configured using this
               MIB module."

      MODULE  -- this module
          MANDATORY-GROUPS { pwBasicGroup,
						     pwPeformanceTotalGroup
                           }

     GROUP pwNotificationGroup
     DESCRIPTION "This group is only mandatory for implementations
                  which can efficiently implement the notifications
                  contained in this group."

     GROUP        pwPwIdGroup
     DESCRIPTION "This group is only mandatory for implementations
                  that support the PW ID FEC.
                 "

     GROUP        pwGeneralizedFecGroup
     DESCRIPTION "This group is only mandatory for implementations
                  that support the generalized PW FEC.
                 "

     GROUP        pwFcsGroup
     DESCRIPTION "This group is only mandatory for implementations
                  that support FCS retention."

     GROUP        pwFragGroup


     DESCRIPTION "This group is only mandatory for implementations
                  that support PW fragmentation.
                 "

     GROUP        pwPwStatusGroup
     DESCRIPTION "This group is only mandatory for implementations
                  that support PW status notification.
                 "

     GROUP        pwGetNextGroup
     DESCRIPTION "This group is only mandatory for implementations
                  where the pwIndex may be any arbitary value
                  and the EMS would require retrieval of the next
                  free index."

     GROUP        pwPriorityGroup
     DESCRIPTION "This group is only mandatory for implementations
                  that support the controling the PW setup and
                  holding priority."

     GROUP        pwAttachmentGroup
     DESCRIPTION "This group is only mandatory for implementations
                  that support attachment of two PWs (PW stitching)."

     GROUP        pwPerformanceIntervalGeneralGroup
     DESCRIPTION "This group is only mandatory for implementations
                  that support PW performance gathering in 15
                  minute intervals."

     GROUP        pwPeformanceIntervalGroup
     DESCRIPTION "This group is only mandatory for implementations
                  that support PW performance gathering in 15
                  minute intervals."

     GROUP        pwHCPeformanceIntervalGroup
     DESCRIPTION "This group is only mandatory for implementations
                  where at least one of the interval performance
                  counters wraps around too quickly based on the
                  criteria specified in RFC 2863 for high-capacity
                  counters."

     GROUP        pwMappingTablesGroup
     DESCRIPTION "This group is only mandatory for implementations
                  that support reverse mapping of PW indexes to
                  the pwIndex and the peer mapping table."

     GROUP        pwSignalingGroup
     DESCRIPTION "This group is only mandatory for implementations
                  that support the PW signaling."

     GROUP        pwNotificationControlGroup
     DESCRIPTION "This group is only mandatory for implementations
                  that support the PW notifications."

     OBJECT       pwType
     MIN-ACCESS   read-only
     DESCRIPTION "Write access is not required."

     OBJECT       pwOwner
     MIN-ACCESS   read-only
     DESCRIPTION "Write access is not required."

     OBJECT       pwPsnType
     MIN-ACCESS   read-only
     DESCRIPTION "Write access is not required."

     OBJECT       pwSetUpPriority
     MIN-ACCESS   read-only
     DESCRIPTION "Write access is not required."

     OBJECT       pwHoldingPriority
     MIN-ACCESS   read-only
     DESCRIPTION "Write access is not required."

     OBJECT       pwPeerAddrType
     SYNTAX       INTEGER { unknown(0), ipv4(1) }
     MIN-ACCESS   read-only
     DESCRIPTION "Write access is not required. Only unknown(0) and
                  ipv4(1) is required."

     OBJECT       pwPeerAddr
     SYNTAX       InetAddress (SIZE(0|4))
     MIN-ACCESS   read-only
     DESCRIPTION "Write access is not required. An implementation
                  is only required to support 0, 4 address sizes."

     OBJECT       pwAttachedPwIndex
     MIN-ACCESS   read-only
     DESCRIPTION "Write access is not required."

     OBJECT       pwIfIndex
     MIN-ACCESS   read-only
     DESCRIPTION "Write access is not required."

     OBJECT       pwID
     MIN-ACCESS   read-only
     DESCRIPTION "Write access is not required."

     OBJECT       pwLocalGroupID
     MIN-ACCESS   read-only
     DESCRIPTION "Write access is not required."

     OBJECT       pwGroupAttachmentID
     MIN-ACCESS   read-only
     DESCRIPTION "Write access is not required."

     OBJECT       pwLocalAttachmentID
     MIN-ACCESS   read-only
     DESCRIPTION "Write access is not required."

     OBJECT       pwPeerAttachmentID
     MIN-ACCESS   read-only
     DESCRIPTION "Write access is not required."

     OBJECT       pwCwPreference
     MIN-ACCESS   read-only
     DESCRIPTION "Write access is not required."

     OBJECT       pwLocalIfMtu
     MIN-ACCESS   read-only
     DESCRIPTION "Write access is not required."

     OBJECT       pwLocalIfString
     MIN-ACCESS   read-only
     DESCRIPTION "Write access is not required."

     OBJECT       pwLocalCapabAdvert
     MIN-ACCESS   read-only
     DESCRIPTION "Write access is not required."

     OBJECT       pwFragmentCfgSize
     MIN-ACCESS   read-only
     DESCRIPTION "Write access is not required."

     OBJECT       pwFcsRetentionCfg
     MIN-ACCESS   read-only
     DESCRIPTION "Write access is not required."

     OBJECT       pwOutboundLabel
     MIN-ACCESS   read-only
     DESCRIPTION "Write access is not required."

     OBJECT       pwInboundLabel
     MIN-ACCESS   read-only


     DESCRIPTION "Write access is not required."

     OBJECT       pwName
     MIN-ACCESS   read-only
     DESCRIPTION "Write access is not required."

     OBJECT       pwDescr
     MIN-ACCESS   read-only
     DESCRIPTION "Write access is not required."

     OBJECT       pwAdminStatus
     SYNTAX       INTEGER { up(1), down(2) }
     MIN-ACCESS   read-only
     DESCRIPTION "Write access is not required. The support of value
                  testing(3) is not required."

     OBJECT       pwOperStatus
     SYNTAX       INTEGER { up(1), down(2), notPresent(5),
                  lowerLayerDown(6) }
     DESCRIPTION "The support of the values testing(3) and dormant(4)
                  is not required."

     OBJECT       pwRowStatus
     SYNTAX       INTEGER { active(1) }
     MIN-ACCESS   read-only
     DESCRIPTION "Write access is not required."

     OBJECT       pwStorageType
     MIN-ACCESS   read-only
     DESCRIPTION "Write access is not required."

     OBJECT       pwUpDownNotifEnable
     MIN-ACCESS   read-only
     DESCRIPTION "Write access is not required."

     OBJECT       pwDeletedNotifEnable
     MIN-ACCESS   read-only
     DESCRIPTION "Write access is not required."

     OBJECT       pwNotifRate
     MIN-ACCESS   read-only
     DESCRIPTION "Write access is not required."

       ::= { pwCompliances 2 }

  -- Units of conformance.

  pwBasicGroup   OBJECT-GROUP
     OBJECTS {
              pwType,
              pwOwner,
              pwPsnType,
              pwIfIndex,
              pwCwPreference,
              pwLocalIfMtu,
              pwOutboundLabel,
              pwInboundLabel,
              pwName,
              pwDescr,
              pwCreateTime,
              pwUpTime,
              pwLastChange,
              pwAdminStatus,
              pwOperStatus,
              pwLocalStatus,
              pwRowStatus,
              pwStorageType,
              pwOamEnable
            }

     STATUS  current
     DESCRIPTION
         "Collection of objects that are required in all
          implementations that support the PW MIB module."
     ::= { pwGroups 1 }

  pwPwIdGroup   OBJECT-GROUP
     OBJECTS {
              pwID
             }

     STATUS  current
     DESCRIPTION
         "Collection of objects required for PW ID configuration
          and signaling."
     ::= { pwGroups 2 }

  pwGeneralizedFecGroup   OBJECT-GROUP
     OBJECTS {
              pwGroupAttachmentID,
              pwLocalAttachmentID,
              pwPeerAttachmentID
            }

     STATUS  current
     DESCRIPTION
         "Collection of objects required for generalized FEC
          configuration and signaling."
     ::= { pwGroups 3 }

  pwFcsGroup   OBJECT-GROUP
     OBJECTS {
              pwFcsRetentionCfg,
              pwFcsRetentionStatus
            }

     STATUS  current
     DESCRIPTION
         "Collection of objects required for FCS retention
          configuration and signaling."
     ::= { pwGroups 4 }

  pwFragGroup   OBJECT-GROUP
     OBJECTS {
              pwFragmentCfgSize,
              pwRmtFragCapability
            }

     STATUS  current
     DESCRIPTION
         "Collection of objects required for fragmentation
          configuration and signaling."
     ::= { pwGroups 5 }

  pwPwStatusGroup   OBJECT-GROUP
     OBJECTS {
              pwRemoteCapabilities,
              pwRemoteStatusCapable,
              pwRemoteStatus
            }

     STATUS  current
     DESCRIPTION
         "Collection of objects required for PW status configuration
          and signaling."
     ::= { pwGroups 6 }


  pwGetNextGroup   OBJECT-GROUP
     OBJECTS {
              pwIndexNext
              }

     STATUS  current
     DESCRIPTION
         "Collection of objects for getting the next available
          index."
     ::= { pwGroups 7 }

  pwPriorityGroup   OBJECT-GROUP
     OBJECTS {
              pwSetUpPriority,
              pwHoldingPriority
              }

     STATUS  current
     DESCRIPTION
         "Collection of objects for controlling the PW setup and
          holding priority."
     ::= { pwGroups 8 }

  pwAttachmentGroup   OBJECT-GROUP
     OBJECTS {
              pwAttachedPwIndex
              }

     STATUS  current
     DESCRIPTION
         "Collection of objects for PW configuration as ifIndex"
     ::= { pwGroups 9 }

  pwPerformanceGeneralGroup OBJECT-GROUP
     OBJECTS {
              pwPerfTotalErrorPackets
            }

     STATUS  current
     DESCRIPTION
         "Collection of general objects needed for managing the
          total running performance parameters."
     ::= { pwGroups 10 }

   pwPeformanceTotalGroup OBJECT-GROUP  
      OBJECTS { 
               pwPerfTotalInPackets, 
               pwPerfTotalInBytes, 
               pwPerfTotalOutPackets, 
               pwPerfTotalOutBytes 
             } 
                 
      STATUS  current 
      DESCRIPTION 
          "Collection of 32 bits objects needed for PW running total  
           performance collection." 
      ::= { pwGroups 11 } 
    
  pwPerformanceIntervalGeneralGroup OBJECT-GROUP
     OBJECTS {
              pwTimeElapsed,
              pwValidIntervals,
              pwPerfIntervalValidData,
              pwPerfIntervalTimeElapsed
            }

     STATUS  current
     DESCRIPTION
         "Collection of general objects needed for managing the
          interval performance parameters."
     ::= { pwGroups 12 }

  pwPeformanceIntervalGroup OBJECT-GROUP
     OBJECTS {
              pwPerfCurrentInPackets,
              pwPerfCurrentInBytes,
              pwPerfCurrentOutPackets,
              pwPerfCurrentOutBytes,

              pwPerfIntervalInPackets,
              pwPerfIntervalInBytes,
              pwPerfIntervalOutPackets,
              pwPerfIntervalOutBytes
            }

     STATUS  current
     DESCRIPTION
         "Collection of 32 bits objects needed for PW performance
          collection in 15 minutes intervals."
     ::= { pwGroups 13 }

  pwHCPeformanceIntervalGroup OBJECT-GROUP
     OBJECTS {
              pwPerfCurrentInHCPackets,
              pwPerfCurrentInHCBytes,
              pwPerfCurrentOutHCPackets,
              pwPerfCurrentOutHCBytes,

              pwPerfIntervalInHCPackets,
              pwPerfIntervalInHCBytes,
              pwPerfIntervalOutHCPackets,
              pwPerfIntervalOutHCBytes
            }

     STATUS  current
     DESCRIPTION
         "Collection of HC objects needed for PW performance
          collection in 15 minutes intervals."
     ::= { pwGroups 14 }

  pwMappingTablesGroup OBJECT-GROUP
     OBJECTS {
              pwIndexMappingPwIndex,
              pwPeerMappingPwIndex
            }

     STATUS  current
     DESCRIPTION
         "Collection of objects contained in the reverse
          mapping tables."
     ::= { pwGroups 15 }

  pwNotificationControlGroup OBJECT-GROUP
     OBJECTS {
              pwUpDownNotifEnable,
              pwDeletedNotifEnable,
              pwNotifRate
            }

     STATUS  current
     DESCRIPTION
         "Collection of objects for controlling the PW
          notifications."
     ::= { pwGroups 16 }

  pwNotificationGroup NOTIFICATION-GROUP
     NOTIFICATIONS {
              pwUp,
              pwDown,
              pwDeleted
            }

     STATUS  current
     DESCRIPTION
         "Collection PW notifications objects."
     ::= { pwGroups 17 }

  pwSignalingGroup OBJECT-GROUP
     OBJECTS {
              pwPeerAddrType,
              pwPeerAddr,
              pwLocalGroupID,
              pwLocalIfString,
              pwLocalCapabAdvert,
              pwRemoteGroupID,
              pwCwStatus,
              pwRemoteIfMtu,
              pwRemoteIfString
            }

     STATUS  current
     DESCRIPTION
         "Collection of objects for use in implementations that
          support the PW signaling."
     ::= { pwGroups 18 }

  END
  
PW-ENET-STD-MIB DEFINITIONS ::= BEGIN

IMPORTS
   OBJECT-TYPE, MODULE-IDENTITY, Unsigned32
       FROM SNMPv2-SMI                    -- [RFC2578]

   pwe3
       FROM FOUNDRY-SN-ROOT-MIB
       
   MODULE-COMPLIANCE, OBJECT-GROUP
       FROM SNMPv2-CONF                   -- [RFC2580]

   StorageType, RowStatus
       FROM SNMPv2-TC                     -- [RFC2579]

   InterfaceIndexOrZero
       FROM IF-MIB                        -- [RFC2863]

   ZeroBasedCounter32
       FROM RMON2-MIB                     -- [RFC4502]

   pwIndex
       FROM PW-STD-MIB                    -- [PWMIB]
                                 -- RFC Editor: Please replace
                                 -- PWMIB with correct RFC #

   PwVlanCfg
       FROM PW-TC-STD-MIB;                -- [PWTC]
                              -- RFC Editor: Please replace
                              -- PWTC with correct RFC #

pwEnetStdMIB MODULE-IDENTITY
    LAST-UPDATED "200705201200Z"  -- 20 May 2007 12:00:00 GMT
    ORGANIZATION "IETF PWE3 Working group"
    CONTACT-INFO
         "David Zelig
          E-mail: davidz@corrigent.com

          Thomas D. Nadeau
          Email:  tnadeau@cisco.com
        "
    DESCRIPTION
        "This MIB module describes a model for managing Ethernet
        point-to-point pseudo-wire services over a Packet
        Switched Network (PSN).

        Copyright (C) The IETF Trust (2007).  This version
        of this MIB module is part of RFC yyyy;  see the RFC
        itself for full legal notices.
-- RFC Editor: replace yyyy with the actual RFC number and remove
-- this note
        "

   -- Revision history.
   REVISION "200705201200Z"  -- 20 May 2007 12:00:00 GMT
   DESCRIPTION "Initial version published as part of RFC XXXX."
-- RFC Editor: Please replace XXXX with the actual RFC number and
-- remove this note


      ::= { pwe3 4 }
      -- ::= { transmission XXXX }  
                          -- RFC Editor: Please replace
                          -- XXXX with IANA assigned value.
                          -- See IANA considerations section.

pwEnetObjects        OBJECT IDENTIFIER ::= { pwEnetStdMIB 1 }
pwEnetConformance    OBJECT IDENTIFIER ::= { pwEnetStdMIB 2 }

--
-- Ethernet PW table
--

pwEnetTable  OBJECT-TYPE
    SYNTAX SEQUENCE OF PwEnetEntry
    MAX-ACCESS  not-accessible
    STATUS     current
    DESCRIPTION
        "This table contains the index to the Ethernet tables
        associated with this ETH PW, the VLAN configuration and
        VLAN mode."
    ::= { pwEnetObjects 1 }

pwEnetEntry  OBJECT-TYPE
    SYNTAX     PwEnetEntry
    MAX-ACCESS  not-accessible
    STATUS     current
    DESCRIPTION
        "This table is indexed by the same index that was created
        for the associated entry in the PW generic table in the
        PW-STD-MIB module.
        The pwIndex and the pwEnetPwInstance are used as indexes
        to allow multiple VLANs to exist on the same PW.

        An entry is created in this table by the agent for every
        entry in the pwTable with a pwType of 'ethernetTagged'
        or 'ethernet'. Additional rows may be created by the
        operator or the agent if multiple entries are required for
        the same PW.

        The value of pwEnetPwInstance can be arbitrary selected
        to make the row unique, however implementations that know
        the VLAN field value when the row is created MAY use the
        value of the VLAN itself for better readability and
        backward compatibility with older versions of this MIB
        module.

        This table provides Ethernet port mapping and VLAN
        configuration for each Ethernet PW.

        All read-create object in this table MAY be changed at any
        time, however change of some objects (for example
        pwEnetVlanMode) during PW forwarding state MAY cause traffic
        disruption.

        Manual entries in this table SHOULD be preserved after a
        re-boot, the agent MUST ensure the integrity of those
        entries. If the set of entires of a specific row are found to
        be non consistent after reboot, the PW pwOperStatus MUST be
        declared as notPresent(5).
        "

    INDEX { pwIndex, pwEnetPwInstance }
    ::= { pwEnetTable 1 }


PwEnetEntry ::= SEQUENCE {
       pwEnetPwInstance    Unsigned32,
       pwEnetPwVlan        PwVlanCfg,
       pwEnetVlanMode      INTEGER,
       pwEnetPortVlan      PwVlanCfg,

       pwEnetPortIfIndex   InterfaceIndexOrZero,
       pwEnetPwIfIndex     InterfaceIndexOrZero,

       pwEnetRowStatus     RowStatus,
       pwEnetStorageType   StorageType
   }

pwEnetPwInstance  OBJECT-TYPE
    SYNTAX      Unsigned32
    MAX-ACCESS  not-accessible
    STATUS      current
    DESCRIPTION
        "If multiple rows are mapped to the same PW, this index is
         used to uniquely identify the individual row.
         If the value of the VLAN field is known at the time of
         of row creation, the value of pwEnetPwVlan MAY be used
         for better readability and backward compatibility with
         older versions of this MIB module. Otherwise the value
         '1' SHOULD be set to the first row for each pwIndex
         for better readability and in order that the management
         application will know in advance how to access the
         first row when it was created by the agent.
        "
    ::= { pwEnetEntry 1 }

pwEnetPwVlan  OBJECT-TYPE
    SYNTAX      PwVlanCfg
    MAX-ACCESS  read-create
    STATUS      current
    DESCRIPTION
        "This Object defines the (service delimiting) VLAN field
        value on the PW. The value of 4097 MUST be used if the
        object is not applicable, for example when mapping all
        packets from an Ethernet port to this PW (raw mode).
        The value 4096 MUST be set to indicate untagged frames
        (from the PW point of view), i.e. when pwEnetVlanMode
        equals 'noChange' and pwEnetPortVlan equals 4096."
    ::= { pwEnetEntry 2 }

pwEnetVlanMode  OBJECT-TYPE
    SYNTAX     INTEGER {
             other(0),
             portBased(1),
             noChange(2),
             changeVlan(3),
             addVlan(4),
             removeVlan(5)
    }
    MAX-ACCESS  read-create
    STATUS     current
    DESCRIPTION
        "This object indicates the mode of VLAN handling between the
         port or the virtual port associated with the PW and the
         PW encapsulation.

        - 'other' indicates an operation that is not defined by
          this MIB module.

        - 'portBased' indicates that the forwarder will forward
          packets between the port and the PW independent of their
          structure (i.e. there is no service delimiting VLAN tags
          from the PE standpoint).

        - 'noChange' indicates that the PW contains the original
           user VLAN, as specified in pwEnetPortVlan, i.e. the
           VLAN on the PE-CE link is the service delimiting tag
           and is kept 'as is' on the PW.

        - 'changeVlan' indicates that the VLAN field on the PW
          may be different than the VLAN field on the user's
          port. The VLAN on the PE-CE link is the service delimiting
          tag but has a different value on the PW.

        - 'removeVlan' indicates that the encapsulation on the
          PW does not include the service delimiting VLAN field.
          Note that PRI bits transparency is lost in this case.

        - 'addVlan' indicates that a VLAN field will be added
          on the PSN bound direction (i.e. on the PW). pwEnetPwVlan
          indicates the value that will be added.

        - Implementation of 'portsbased', 'removeVlan', 'addVlan'
          'other' and 'changeVlan' is OPTIONAL.
        "
    DEFVAL { noChange }
    ::= { pwEnetEntry 3 }

pwEnetPortVlan  OBJECT-TYPE
    SYNTAX     PwVlanCfg
    MAX-ACCESS read-create
    STATUS     current
    DESCRIPTION
        "This object defines if the mapping between the original port
        (physical port or VPLS virtual port) to the PW is VLAN based
        or not. In case of VLAN mapping, this object indicates the
        the VLAN value on the original port.

        The value of '4097' MUST be used if the whole original port
        traffic is mapped to the same PW. Note that a pwType of
        'ethernetTagged' can still be used if service delimiting tag
        is added on the PW (pwEnetVlanMode equals 'addVlan').

        This object MUST be equal to pwEnetPwVlan if pwEnetVlanMode
        equals 'noChange'.

        The value 4096 indicates packets without VLAN field
        (i.e. untagged frames) on the port are associated to this
        PW. This allows the same behavior as assigning 'Default
        VLAN' to untagged frames.
        "
    DEFVAL  { 4097 }
    ::= { pwEnetEntry 4 }

pwEnetPortIfIndex  OBJECT-TYPE
    SYNTAX      InterfaceIndexOrZero
    MAX-ACCESS  read-create
    STATUS      current
    DESCRIPTION
        "This object is used to specify the ifIndex of the Ethernet
         port associated with this PW for point-to-point Ethernet
         service, or the ifIndex of the virtual interface of the
         VPLS instance associated with the PW if the service is
         VPLS. Two rows in this table can point to the same ifIndex
         only if there is no overlap of VLAN values specified in
         pwEnetPortVlan that are associated with this port.

         A value of zero indicates that association to an ifIndex is
         not yet known."

    ::= { pwEnetEntry 5 }

pwEnetPwIfIndex  OBJECT-TYPE
    SYNTAX     InterfaceIndexOrZero
    MAX-ACCESS read-create
    STATUS     current
    DESCRIPTION
        "If the PW is modeled as an ifIndex in the ifTable, this
         object indicates the value of the ifIndex representing the
         Ethernet PW on the PSN side in the Etherlike-MIB. Note that
         this value may be different from the value of pwIfIndex
         that represents the ifIndex of the PW for ifType 'pw'."

     DEFVAL { 0 }
    ::= { pwEnetEntry 6 }

pwEnetRowStatus  OBJECT-TYPE
    SYNTAX      RowStatus
    MAX-ACCESS  read-create
    STATUS      current
    DESCRIPTION
        "This object enables creating, deleting and modifying this row."
    ::= { pwEnetEntry 7 }

pwEnetStorageType  OBJECT-TYPE
    SYNTAX      StorageType
    MAX-ACCESS  read-create
    STATUS      current
    DESCRIPTION
        "This object indicates the storage type of this row."
    DEFVAL { nonVolatile }
    ::= { pwEnetEntry 8 }

--
-- Ethernet PW Statistics Table
--

pwEnetStatsTable  OBJECT-TYPE
    SYNTAX SEQUENCE OF PwEnetStatsEntry
    MAX-ACCESS  not-accessible
    STATUS      current
    DESCRIPTION
        "This table contains statistical counters specific for
         Ethernet PW."
    ::= { pwEnetObjects 2 }

pwEnetStatsEntry  OBJECT-TYPE
    SYNTAX      PwEnetStatsEntry
    MAX-ACCESS  not-accessible
    STATUS      current
    DESCRIPTION
        "Each entry represents the statistics gathered for the
         PW carrying the Ethernet."
    INDEX { pwIndex }
    ::= { pwEnetStatsTable 1 }


PwEnetStatsEntry ::= SEQUENCE {
    pwEnetStatsIllegalVlan        ZeroBasedCounter32,
    pwEnetStatsIllegalLength      ZeroBasedCounter32
}

pwEnetStatsIllegalVlan  OBJECT-TYPE
    SYNTAX     ZeroBasedCounter32
    MAX-ACCESS  read-only
    STATUS     current
    DESCRIPTION
        "The number of packets received (from the PSN) on this PW
         with either an illegal VLAN field, a missing VLAN field
         when one was expected, or an excessive VLAN field when
         it was not expected. This counter may not be applicable
         in some cases, and MUST return the value of zero in
         such a case."
    ::= { pwEnetStatsEntry 1 }

pwEnetStatsIllegalLength  OBJECT-TYPE
    SYNTAX     ZeroBasedCounter32
    MAX-ACCESS  read-only
    STATUS     current
    DESCRIPTION
        "The number of packets that were received with an illegal
         Ethernet packet length on this PW. An illegal length is
         defined as being greater than the value in the advertised
         MTU supported, or shorter than the allowed Ethernet packet
         size."
    ::= { pwEnetStatsEntry 2 }

---
--- Conformance description
---

pwEnetGroups      OBJECT IDENTIFIER ::= { pwEnetConformance 1 }
pwEnetCompliances OBJECT IDENTIFIER ::= { pwEnetConformance 2 }

-- Compliance requirement for fully compliant implementations.

pwEnetModuleFullCompliance MODULE-COMPLIANCE
    STATUS  current
    DESCRIPTION
            "The compliance statement for agents that provide full
             support for the PW-ENET-STD-MIB Module. Such devices
             can then be monitored and also be configured using
             this MIB module."
    MODULE  -- this module
      MANDATORY-GROUPS {
                         pwEnetGroup,
                         pwEnetStatsGroup
                        }

   OBJECT       pwEnetVlanMode
   DESCRIPTION "An implementation MUST support at least the value
                noChange(2)."

   OBJECT       pwEnetPwIfIndex
   MIN-ACCESS   read-only
   DESCRIPTION "Write access and values other than zero are
                required only for implementations that support
                modeling the Ethernet PW in the Etherlike-MIB."
   
   OBJECT       pwEnetRowStatus
   SYNTAX       INTEGER { active(1), notInService(2),
                            notReady(3) }
   WRITE-SYNTAX INTEGER { active(1), notInService(2),
                            createAndGo(4), destroy(6)
                          }
   MIN-ACCESS   read-only
   DESCRIPTION "Support for createAndWait is not required. Support
                of notReady is not required for implementations that
                do not support signaling.
                Support of read-write is not required for
                implementations that do not support more than one
                VLAN mapping to the same PW."

    ::= { pwEnetCompliances 1 }

-- Compliance requirement for read-only compliant implementations.


pwEnetModuleReadOnlyCompliance MODULE-COMPLIANCE
    STATUS  current
    DESCRIPTION
            "The compliance statement for agents that provide read-
             only support for the PW-ENET-STD-MIB Module. Such
             devices can then be monitored but cannot be configured
             using this MIB module."

    MODULE  -- this module
      MANDATORY-GROUPS { pwEnetGroup,
                         pwEnetStatsGroup
                         }

   OBJECT       pwEnetPwVlan
   MIN-ACCESS   read-only
   DESCRIPTION "Write access is not required."

   OBJECT       pwEnetVlanMode
   MIN-ACCESS   read-only
   DESCRIPTION "Write access is not required. An implementation
                MUST support at least the value noChange(2)."

   OBJECT       pwEnetPortVlan
   MIN-ACCESS   read-only
   DESCRIPTION "Write access is not required."

   OBJECT       pwEnetPortIfIndex
   MIN-ACCESS   read-only
   DESCRIPTION "Write access is not required."

   OBJECT       pwEnetPwIfIndex
   MIN-ACCESS   read-only
   DESCRIPTION "Write access is not required. Values other than
                zero are required only for implementations that
                support modeling the Ethernet PW in the
                Etherlike-MIB."

   OBJECT       pwEnetRowStatus
   SYNTAX       INTEGER { active(1), notInService(2),
                            notReady(3) }
   MIN-ACCESS   read-only
   DESCRIPTION "Write access is not required. Support
                of notReady is not required for implementations that
                do not support signaling."

   OBJECT       pwEnetStorageType
   MIN-ACCESS   read-only
   DESCRIPTION "Write access is not required."

    ::= { pwEnetCompliances 2 }

-- Units of conformance.

pwEnetGroup OBJECT-GROUP
   OBJECTS {
            pwEnetPwVlan,
            pwEnetVlanMode,
            pwEnetPortVlan,
            pwEnetPortIfIndex,
            pwEnetPwIfIndex,
            pwEnetRowStatus,
            pwEnetStorageType
   }
   STATUS  current
   DESCRIPTION
       "Collection of objects for basic Ethernet PW configuration."
   ::= { pwEnetGroups 1 }

pwEnetStatsGroup OBJECT-GROUP
   OBJECTS {
            pwEnetStatsIllegalVlan,
            pwEnetStatsIllegalLength
   }
   STATUS  current
   DESCRIPTION
       "Collection of objects counting various PW level errors."
   ::= { pwEnetGroups 2 }

END


     VPLS-GENERIC-DRAFT-01-MIB DEFINITIONS ::= BEGIN

      IMPORTS
      NOTIFICATION-TYPE, MODULE-IDENTITY, OBJECT-TYPE,
      Unsigned32, Counter32
         FROM SNMPv2-SMI                    -- RFC2578

      MODULE-COMPLIANCE, OBJECT-GROUP, NOTIFICATION-GROUP
         FROM SNMPv2-CONF                   -- RFC2580

      TruthValue, RowStatus, StorageType
         FROM SNMPv2-TC                     -- RFC2579

      SnmpAdminString
         FROM SNMP-FRAMEWORK-MIB            -- RFC3411

       PwIndexType
               FROM PW-TC-STD-MIB

        VPNIdOrZero
               FROM VPN-TC-STD-MIB           -- RFC4265

        vplsRoot
               FROM FOUNDRY-SN-ROOT-MIB          --snroot
;
        
   vplsGenericDraft01MIB MODULE-IDENTITY
      LAST-UPDATED "200608301200Z"  -- 30 Aug 2006 12:00:00 GMT
      ORGANIZATION "Layer 2 Virtual Private Networks (L2VPN)
                                 Working  Group"
      CONTACT-INFO
          "
           Thomas D. Nadeau
           Email:  tnadeau@cisco.com

           The L2VPN Working Group (email distribution l2vpn@ietf.org,
           http://www.ietf.org/html.charters/l2vpn-charter.html)
           "

      DESCRIPTION
          "Copyright (C) The IETF Trust (2008). The initial
           version of this MIB module was published in RFC XXXX.
   -- RFC Editor: Please replace XXXX with RFC number & remove
   --                    this note.

           For full legal notices see the RFC itself or see:
           http://www.ietf.org/copyrights/ianamib.html

           This MIB module contains generic managed object definitions
           for Virtual Private LAN Services as in [L2VPN-VPLS-LDP] and
           [L2VPN-VPLS-BGP]

           This MIB module enables the use of any underlying Pseudo Wire
           network."

      -- Revision history.
      REVISION
          "200608301200Z"  -- 30 August 2006 12:00:00 GMT
      DESCRIPTION
          "Changes from previous version:
           1) Moved LDP Specific information to VPLS-LDP-DRAFT-01-MIB
           2) Created the vplsStatusTable to store status information.
           3)
          "
      REVISION
          "200606041200Z"  -- 4 June 2006 12:00:00 GMT
        

      DESCRIPTION "Initial version published as part of RFC YYYY."
   -- RFC Editor: please replace YYYY with IANA assigned value, and
   -- delete this note.

--         ::= { transmission XXXX }
         ::= { vplsRoot 1 } -- OID assigned under fdry experimental branch.
   -- RFC Editor: please replace XXXX with IANA assigne value, and
   -- delete this note.

   -- Top-level components of this MIB.

   -- Notifications
   vplsNotifications OBJECT IDENTIFIER
                                 ::= { vplsGenericDraft01MIB 0 }
   -- Tables, Scalars
   vplsObjects       OBJECT IDENTIFIER
                                 ::= { vplsGenericDraft01MIB 1 }
   -- Conformance
   vplsConformance   OBJECT IDENTIFIER
                                 ::= { vplsGenericDraft01MIB 2 }

   -- PW Virtual Connection Table

   vplsConfigIndexNext OBJECT-TYPE
      SYNTAX            Unsigned32
      MAX-ACCESS        read-only
      STATUS            current
      DESCRIPTION
          "This object contains an appropriate value to be used
           for vplsConfigIndex when creating entries in the
           vplsConfigTable. The value 0 indicates that no
           unassigned entries are available.  To obtain the
           value of vplsConfigIndex for a new entry in the
           vplsConfigTable, the manager issues a management
           protocol retrieval operation to obtain the current
           value of vplsConfigIndex.  After each retrieval
           operation, the agent should modify the value to
           reflect the next unassigned index.  After a manager
           retrieves a value the agent will determine through
           its local policy when this index value will be made
           available for reuse."
      ::= { vplsObjects 1 }

      vplsConfigTable OBJECT-TYPE
          SYNTAX          SEQUENCE OF VplsConfigEntry
          MAX-ACCESS      not-accessible
          STATUS          current
          DESCRIPTION
               "This table specifies information for configuring
                and monitoring Virtual Private Lan Services(VPLS).
                "
          ::= { vplsObjects 2 }

      vplsConfigEntry OBJECT-TYPE
          SYNTAX          VplsConfigEntry
          MAX-ACCESS      not-accessible
          STATUS          current
          DESCRIPTION
           "A row in this table represents a Virtual Private Lan
            Service(VPLS) in a packet network. It is indexed by
            vplsConfigIndex, which uniquely identifies a single VPLS.

            A row is created by the operator or by the agent if a
            VPLS service is created by non-SNMP application or
            due to autodiscovery process.

            None of the read-create objects values can be
            changed when vplsConfigRowStatus is in the active(1)
            state. Changes are allowed when the vplsConfigRowStatus
            is in notInService(2) or notReady(3) states only.
            If the operator need to change one of the values
            for an active row the vplsConfigRowStatus should be
            first changed to notInService(2), the objects may
            be changed now, and later to active(1) in order to
            re-initiate the signaling process with the new
            values in effect.
            "
          INDEX           { vplsConfigIndex }
          ::= { vplsConfigTable 1 }

     VplsConfigEntry ::=
        SEQUENCE {
         vplsConfigIndex                                Unsigned32,
         vplsConfigName                                 SnmpAdminString,
         vplsConfigDescr                                SnmpAdminString,
         vplsConfigAdminStatus                          INTEGER,
         vplsConfigMacLearning                          TruthValue,
         vplsConfigDiscardUnknownDest                   TruthValue,
         vplsConfigMacAging                             TruthValue,
         vplsConfigFwdFullHighWatermark                 Unsigned32,
         vplsConfigFwdFullLowWatermark                  Unsigned32,
         vplsConfigRowStatus                            RowStatus,
         vplsConfigMtu                                  Unsigned32,
         vplsConfigVpnId                                VPNIdOrZero,
         vplsConfigServiceType                          INTEGER,
         vplsConfigStorageType                          StorageType
          }

      vplsConfigIndex  OBJECT-TYPE
          SYNTAX          Unsigned32 (1.. 2147483647)
        
          MAX-ACCESS      not-accessible
          STATUS          current
          DESCRIPTION
               "Unique index for the conceptual row identifying
                a VPLS service."
          ::= { vplsConfigEntry 1 }

      vplsConfigName  OBJECT-TYPE
          SYNTAX          SnmpAdminString
          MAX-ACCESS      read-create
          STATUS          current
          DESCRIPTION
               "A textual name of the VPLS.
                If there is no local name, or this object is
                otherwise not applicable, then this object MUST
                contain a zero-length octet string."
          DEFVAL           { "" }
          ::= { vplsConfigEntry 2 }

      vplsConfigDescr  OBJECT-TYPE
          SYNTAX          SnmpAdminString
          MAX-ACCESS      read-create
          STATUS          current
          DESCRIPTION
               "A textual string containing information about the
               VPLS service. If there is no information for this VPLS
               service, then this object MUST contain a zero-length
               octet string."
          DEFVAL           { "" }
          ::= { vplsConfigEntry 3 }

      vplsConfigAdminStatus OBJECT-TYPE
          SYNTAX          INTEGER {
                              up(1),
                              down(2),
                              testing(3)   -- in some test mode

                          }
          MAX-ACCESS      read-create
          STATUS          current
          DESCRIPTION
               "The desired administrative state of the VPLS
                service. If the administrative status of the
                Vpls service is changed to enable then this
                service is able to utilize the pseudo wire to
                perform the tasks of a VPLS service.
                The testing(3) state indicates that no operational
                packets can be passed. "
        

          DEFVAL           { down }
          ::= { vplsConfigEntry 4 }

      vplsConfigMacLearning OBJECT-TYPE
          SYNTAX          TruthValue
          MAX-ACCESS      read-create
          STATUS          current
          DESCRIPTION
               "This object specifies if MAC Learning is enabled
                in this service. If this object is true then Mac
                Learning is enabled. If false, then Mac Learning is
                disabled."
          DEFVAL          { true }
          ::= { vplsConfigEntry 6 }

      vplsConfigDiscardUnknownDest OBJECT-TYPE
          SYNTAX          TruthValue
          MAX-ACCESS      read-create
          STATUS          current
          DESCRIPTION
               "If the value of this object is 'true', then frames
                received with an unknown destination MAC are discarded
                in this VPLS. If 'false', then the packets are
                processed."
          DEFVAL          { false }
          ::= { vplsConfigEntry 7 }

      vplsConfigMacAging OBJECT-TYPE
          SYNTAX          TruthValue
          MAX-ACCESS      read-create
          STATUS          current
          DESCRIPTION
               "If the value of this object is 'true'
                then the MAC ageing process is enabled in
                this VPLS. If 'false', then the MAC ageing process
                is disabled"
          DEFVAL          { true }
          ::= { vplsConfigEntry 8 }

      vplsConfigFwdFullHighWatermark OBJECT-TYPE
          SYNTAX          Unsigned32 (0..100)
          UNITS           "percentage"
          MAX-ACCESS      read-create
          STATUS          current
          DESCRIPTION
        
               "This object specifies the utilization of the
                forwarding database for this VPLS instance at
                which the vplsFwdFullAlarmRaised notification
                will be sent."
          DEFVAL          { 95 }
          ::= { vplsConfigEntry 10 }

      vplsConfigFwdFullLowWatermark OBJECT-TYPE
          SYNTAX          Unsigned32 (0..100)
          UNITS           "percentage"
          MAX-ACCESS      read-create
          STATUS          current
          DESCRIPTION
               "This object specifies the utilization of the
                forwarding database for this VPLS instance
                at which the vplsFwdFullAlarmCleared
                notification will be sent."
          DEFVAL          { 90 }
          ::= { vplsConfigEntry 11 }

      vplsConfigRowStatus OBJECT-TYPE
          SYNTAX          RowStatus
          MAX-ACCESS      read-create
          STATUS          current
          DESCRIPTION
               "For creating, modifying, and deleting this row.
                None of the read-create objects in the
                conceptual rows may be changed when this
                object is in the active(1) state."
          ::= { vplsConfigEntry 12 }

      vplsConfigMtu OBJECT-TYPE
          SYNTAX          Unsigned32 (64..1518)
          MAX-ACCESS      read-create
          STATUS          current
          DESCRIPTION
               "The value of this object specifies the MTU of this
                vpls instance."
          DEFVAL          { 1518 }
          ::= { vplsConfigEntry 13 }

      vplsConfigVpnId OBJECT-TYPE
          SYNTAX          VPNIdOrZero
          MAX-ACCESS      read-only
          STATUS          current
          DESCRIPTION
               "This objects indicates the IEEE 802-1990
                VPN ID of the associated VPLS service."
-- Ed note: Should we import the VPNIdOrZero TC or
--              define a new TC?
          ::= { vplsConfigEntry 14 }

      vplsConfigServiceType OBJECT-TYPE
          SYNTAX          INTEGER {
                           vlan     (1),
                           ethernet (2)
                          }
          MAX-ACCESS      read-create
          STATUS          current
          DESCRIPTION
               "The value of this object specifies the type of 
                service emulated by this vpls instance."
          DEFVAL          { vlan }
          ::= { vplsConfigEntry 15 }

  vplsConfigStorageType OBJECT-TYPE   
          SYNTAX        StorageType  
          MAX-ACCESS    read-create  
          STATUS        current  
          DESCRIPTION  
               "This variable indicates the storage type for this row."  
          DEFVAL { volatile }
          ::= { vplsConfigEntry 16 }  

-- VPLS Status table

      vplsStatusTable OBJECT-TYPE
          SYNTAX          SEQUENCE OF VplsStatusEntry
          MAX-ACCESS      not-accessible
          STATUS          current
          DESCRIPTION
        

               "This table provides information for monitoring
                Virtual Private Lan Services(VPLS).
                "
          ::= { vplsObjects 3 }

      vplsStatusEntry OBJECT-TYPE
          SYNTAX          VplsStatusEntry
          MAX-ACCESS      not-accessible
          STATUS          current
          DESCRIPTION
           "A row in this table represents a Virtual Private Lan
            Service(VPLS) in a packet network. It is indexed by
            vplsConfigIndex, which uniquely identifies a single VPLS.

            A row in this table is automatically created by the agent
            when a VPLS service is configured.
            "
          INDEX           { vplsConfigIndex }
          ::= { vplsStatusTable 1 }

     VplsStatusEntry ::=
        SEQUENCE {
         vplsStatusOperStatus                        INTEGER,
         vplsStatusPeerCount                         Counter32
          }

      vplsStatusOperStatus OBJECT-TYPE
          SYNTAX          INTEGER {
                              other(0),
                              up(1),
                              down(2)
                          }
          MAX-ACCESS      read-only
          STATUS          current
          DESCRIPTION
               "The current operational state of this VPLS Service."
          ::= { vplsStatusEntry 1 }

      vplsStatusPeerCount OBJECT-TYPE
          SYNTAX          Counter32
          MAX-ACCESS      read-only
          STATUS          current
          DESCRIPTION
               "This objects specifies the number of peers
                present in this vpls instance."
          ::= { vplsStatusEntry 2 }
        

      -- VPLS PW Binding Table

      vplsPwBindTable OBJECT-TYPE
          SYNTAX          SEQUENCE OF VplsPwBindEntry
          MAX-ACCESS      not-accessible
          STATUS          current
          DESCRIPTION
               "This table provides an association between a
                VPLS service and the corresponding Pseudo
                Wires. A service can have more than one Pseudo
                Wire association. Pseudo Wires are defined in
                the pwTable"
          ::= { vplsObjects 4 }

      vplsPwBindEntry OBJECT-TYPE
          SYNTAX          VplsPwBindEntry
          MAX-ACCESS      not-accessible
          STATUS          current
          DESCRIPTION
               "Each row represents an association between a
                VPLS instance and one or more Pseudo Wires
                defined in the pwTable. Each index is unique
                in describing an entry in this table. However
                both indexes are required to define the one
                to many association of service to
                pseudowire."
          INDEX  { vplsConfigIndex, vplsPwBindIndex }
          ::= { vplsPwBindTable 1 }

      VplsPwBindEntry ::=
          SEQUENCE {
              vplsPwBindIndex                     PwIndexType,
              vplsPwBindConfigType              INTEGER,
              vplsPwBindType                  INTEGER,
              vplsPwBindRowStatus             RowStatus,
              vplsPwBindStorageType             StorageType
          }

      vplsPwBindIndex        OBJECT-TYPE
           SYNTAX        PwIndexType
           MAX-ACCESS    not-accessible
           STATUS        current
           DESCRIPTION
              "Secondary Index for the conceptual row identifying
               a pseudowire within the PwEntry which MUST
               match an entry from the PW-STD-MIB's PwTable
               which represents an already-provisioned
               pseuwowire that is then associated with this
               VPLS instance."
          ::= { vplsPwBindEntry 1 }

      vplsPwBindConfigType   OBJECT-TYPE
           SYNTAX          INTEGER {
                                   manual        (1),
                                   autodiscovery (2)
                           }
           MAX-ACCESS      read-create
           STATUS          current
           DESCRIPTION
                "The value of this object indicates
                 whether the Pseudo Wire binding was created
                 manually or via autodiscovery.

                 The value of this object must be
                 specifed when the row is created and cannot
                 be changed while the row status is active(1)"
          ::= { vplsPwBindEntry 2 }

      vplsPwBindType   OBJECT-TYPE
           SYNTAX          INTEGER {
                                   mesh  (1),
                                   spoke (2)
                           }
           MAX-ACCESS      read-create
           STATUS          current
           DESCRIPTION
                "The value of this object indicates
                 whether the Pseudo Wire binding is of
                 type mesh or spoke.

                 The value of this object must be
                 specifed when the row is created and cannot
                 be changed while the row status is active(1)"
          ::= { vplsPwBindEntry 3 }

      vplsPwBindRowStatus  OBJECT-TYPE
           SYNTAX          RowStatus
           MAX-ACCESS      read-create
           STATUS          current
           DESCRIPTION
                "For creating, modifying, and deleting this row.
                 None of the read-create objects in the
                 conceptual rows may be changed when this
                 object is in the active(1) state"
          ::= { vplsPwBindEntry 4 }

      vplsPwBindStorageType OBJECT-TYPE   
           SYNTAX        StorageType  
           MAX-ACCESS    read-create 
           STATUS        current  
           DESCRIPTION  
                "This variable indicates the storage type for this row."  
           DEFVAL { volatile }
           ::= { vplsPwBindEntry 5 }  

   vplsStatusNotifEnable  OBJECT-TYPE
      SYNTAX      TruthValue
      MAX-ACCESS  read-write
      STATUS      current
      DESCRIPTION
           "If this object is set to true(1), then it enables
            the emission of vplsStatusChanged
            notification; otherwise this notification is not
            emitted."
      REFERENCE
           "See also [RFC3413] for explanation that
            notifications are under the ultimate control of the
            MIB module in this document."
      DEFVAL { false }
      ::= { vplsObjects 5 }

   vplsNotificationMaxRate OBJECT-TYPE
      SYNTAX       Unsigned32
      MAX-ACCESS   read-write
      STATUS       current
      DESCRIPTION
           "This object indicates the maximum number of
            notifications issued per second. If events occur
            more rapidly, the implementation may simply fail to
            emit these notifications during that period, or may
            queue them until an appropriate time. A value of 0
            means no throttling is applied and events may be
            notified at the rate at which they occur."
      DEFVAL       { 0 }
      ::= { vplsObjects 6 }

      -- VPLS Service Notifications

      vplsStatusChanged NOTIFICATION-TYPE
          OBJECTS {
              vplsConfigVpnId,
              vplsConfigAdminStatus,
              vplsStatusOperStatus
          }
          STATUS          current
          DESCRIPTION
               "The vplsStatusChanged notification is generated
                when there is a change in the administrative or
                operating status of a VPLS service.
                  This notification is not supported as VPLS instance is always up."
          ::= { vplsNotifications 1 }

      vplsFwdFullAlarmRaised NOTIFICATION-TYPE
          OBJECTS {
              vplsConfigVpnId,
              vplsConfigFwdFullHighWatermark,
              vplsConfigFwdFullLowWatermark
          }
          STATUS          current
          DESCRIPTION
               "The vplsFwdFullAlarmRaised notification is
                generated when the utilization of the Forwarding
                database is above the value specified by
                vplsConfigFwdFullHighWatermark.
                   This notification is not supported by the device."
          ::= { vplsNotifications 2 }

      vplsFwdFullAlarmCleared NOTIFICATION-TYPE
          OBJECTS {
              vplsConfigVpnId,
              vplsConfigFwdFullHighWatermark,
              vplsConfigFwdFullLowWatermark
          }
          STATUS          current
          DESCRIPTION
               "The vplsFwdFullAlarmCleared notification is
                generated when the utilization of the Forwarding
                database is below the value specified by
                vplsConfigFwdFullLowWatermark.
                   This notification is not supported by the device."
          ::= { vplsNotifications 3 }

   -- Compliance requirement for read-only implementations.

   vplsCompliances
     OBJECT IDENTIFIER ::= { vplsConformance 1 }

   vplsModuleFullCompliance MODULE-COMPLIANCE
      STATUS current
      DESCRIPTION
           "Compliance requirement for implementations that
            provide full support for VPLS-GENERIC-DRAFT-01-MIB.
            Such devices can then be monitored and configured using 
            this MIB module."
      MODULE -- this module

          MANDATORY-GROUPS {
               vplsGroup,
               vplsPwBindGroup,
               vplsNotificationGroup
           }

      ::= { vplsCompliances 1 }


   vplsModuleReadOnlyCompliance MODULE-COMPLIANCE
      STATUS current
      DESCRIPTION
           "Compliance requirement for implementations that only
            provide read-only support for VPLS-GENERIC-DRAFT-01-MIB.
            Such devices can then be monitored but cannot be
            configured using this MIB modules."

      MODULE -- this module

          MANDATORY-GROUPS {
               vplsGroup,
               vplsPwBindGroup,
               vplsNotificationGroup
           }

           OBJECT          vplsConfigName
           MIN-ACCESS      read-only
           DESCRIPTION
               "Write access is not required."
    

           OBJECT          vplsConfigDescr
           MIN-ACCESS      read-only
           DESCRIPTION
               "Write access is not required."

           OBJECT          vplsConfigAdminStatus
           MIN-ACCESS      read-only
           DESCRIPTION
               "Write access is not required."

           OBJECT          vplsConfigMacLearning
           MIN-ACCESS      read-only
           DESCRIPTION
               "Write access is not required."

           OBJECT          vplsConfigDiscardUnknownDest
           MIN-ACCESS      read-only
           DESCRIPTION
               "Write access is not required."

           OBJECT          vplsConfigMacAging
           MIN-ACCESS      read-only
           DESCRIPTION
               "Write access is not required."

           OBJECT          vplsConfigFwdFullHighWatermark
           MIN-ACCESS      read-only
           DESCRIPTION
               "Write access is not required."

           OBJECT          vplsConfigFwdFullLowWatermark
           MIN-ACCESS      read-only
           DESCRIPTION
               "Write access is not required."

           OBJECT          vplsConfigRowStatus
           MIN-ACCESS      read-only
           DESCRIPTION
               "Write access is not required."

           OBJECT          vplsConfigMtu
           MIN-ACCESS      read-only
           DESCRIPTION
               "Write access is not required."

           OBJECT          vplsConfigServiceType
           MIN-ACCESS      read-only
           DESCRIPTION
               "Write access is not required."

           OBJECT          vplsPwBindConfigType
           MIN-ACCESS      read-only
           DESCRIPTION
               "Write access is not required."

           OBJECT          vplsPwBindType
           MIN-ACCESS      read-only
           DESCRIPTION
               "Write access is not required."

           OBJECT          vplsPwBindRowStatus
           MIN-ACCESS      read-only
           DESCRIPTION
               "Write access is not required."

      ::= { vplsCompliances 2 }

-- Units of conformance.

      vplsGroups
        OBJECT IDENTIFIER ::= { vplsConformance 2 }
        

      vplsGroup OBJECT-GROUP
          OBJECTS {
              vplsConfigName,
              vplsConfigDescr,
              vplsConfigAdminStatus,
              vplsConfigMacLearning,
              vplsConfigDiscardUnknownDest,
              vplsConfigMacAging,
              vplsConfigVpnId,
              vplsConfigFwdFullHighWatermark,
              vplsConfigFwdFullLowWatermark,
              vplsConfigRowStatus,
              vplsConfigIndexNext,
              vplsConfigMtu,
              vplsConfigServiceType,
              vplsConfigStorageType,

              vplsStatusOperStatus,
              vplsStatusPeerCount,

              vplsStatusNotifEnable,
              vplsNotificationMaxRate
          }
          STATUS          current
          DESCRIPTION
               "The group of objects supporting
                management of L2VPN VPLS services"
          ::= { vplsGroups 1 }

      vplsPwBindGroup OBJECT-GROUP
          OBJECTS {
              vplsPwBindConfigType,
              vplsPwBindType,
              vplsPwBindRowStatus,
              vplsPwBindStorageType
          }
          STATUS          current
          DESCRIPTION
               "The group of objects supporting
                management of
                Pseudo Wire (PW) Binding to VPLS."
          ::= { vplsGroups 2 }

      vplsNotificationGroup NOTIFICATION-GROUP
          NOTIFICATIONS   {
              vplsStatusChanged,
              vplsFwdFullAlarmRaised,
              vplsFwdFullAlarmCleared
          }
          STATUS          current
          DESCRIPTION
               "The group of notifications supporting
                the  Notifications generated for
                VPLS Services"
          ::= { vplsGroups 3 }
        

       END

FDRY-MPLS-L2VPN-MIB DEFINITIONS ::= BEGIN
IMPORTS
   NOTIFICATION-TYPE, MODULE-IDENTITY, OBJECT-TYPE,
   Unsigned32, Counter64
      FROM SNMPv2-SMI                                     -- [RFC2578]
   TEXTUAL-CONVENTION, RowStatus, TruthValue
      FROM SNMPv2-TC                                      -- [RFC2579]
   InterfaceIndex
      FROM IF-MIB                                         -- [RFC2863]
   VlanTagMode
      FROM FOUNDRY-SN-SWITCH-GROUP-MIB                    -- [snswitch]
   snMpls
      FROM FOUNDRY-SN-ROOT-MIB                            -- [snroot]
   vplsConfigName, vplsConfigIndex, vplsConfigEntry
      FROM VPLS-GENERIC-DRAFT-01-MIB                      -- [draft-ietf-l2vpn-vpls-mib-00]
   PwOperStatusTC, PwVlanCfg
      FROM PW-TC-STD-MIB                                  -- [draft-ietf-pw3-pw-tc-mib-11]
   pwIndex, pwName, pwID, fdryPwServiceType
      FROM PW-STD-MIB                                     -- [draft-ietf-pw3-pw-mib-11]
   pwEnetPwInstance
      FROM PW-ENET-STD-MIB                                -- [draft-ietf-pw3-enet-mib-11]
   ;

fdryMplsL2VpnMIB MODULE-IDENTITY
   LAST-UPDATED "200802070000Z"  -- 7 February 2008
   ORGANIZATION "Foundry Networks, Inc."
   CONTACT-INFO
            "Technical Support Center, Foundry Networks,
            4980 Great America Parkway,
            Santa Clara, CA 95054
            Email: support@foundrynet.com
            Phone: 1-877-TURBO-CALL"
    DESCRIPTION
        "The Foundry proprietary MIB module for L2 VPN.
        This mib is built on the current L2VPN draft mib.
         It has additional information for Virtual Leased Line (VLL),
         VLL-Local and Virtual Private LAN Service (VPLS) Endpoints,
         as well as for VPLS Instance.
         
         Copyright (C) Foundry Networks, Inc, (2008)
         This document and the information contained herein are provided on an
         AS IS basis and FOUNDRY NETWORKS DISCLAIM ALL WARRANTIES, EXPRESS OR IMPLIED,
         INCLUDING BUT NOT LIMITED TO ANY WARRANTY THAT THE USE OF THE
         INFORMATION HEREIN WILL NOT INFRINGE ANY RIGHTS OR ANY IMPLIED
         WARRANTIES OF MERCHANTABILITY OR FITNESS FOR A PARTICULAR PURPOSE.
       "
    REVISION      "200802070000Z"  -- 7 February 2008
    DESCRIPTION
            "Initial revision"
   ::= { snMpls 2 }

--
-- Textual Conventions
--
MplsServiceType ::= TEXTUAL-CONVENTION
   STATUS        current
   DESCRIPTION
       "MPLS VLL service types, VLL, VLL-local or VPLS."
   SYNTAX        INTEGER{
                          vll(1),
                          vllLocal(2),
                          vpls(3)
                       }

AdminStatus ::= TEXTUAL-CONVENTION
   STATUS        current
   DESCRIPTION
       "Administrative status of a given management entity."
     SYNTAX        INTEGER{
                              up(1),      -- ready to pass packets
                              down(2),     -- can't pass packets
                              testing(3)   -- in some test mode
                        }

ClassOfService ::= TEXTUAL-CONVENTION
   STATUS        current
   DESCRIPTION
       "Class Of Service (COS) value of a given management entity.
       Value 255 means that COS is not explicitly configured. Valid COS values
       are between 0 and 7."
   SYNTAX        Unsigned32(0..7 | 255)

Layer2StateTC ::= TEXTUAL-CONVENTION
   STATUS    current
   DESCRIPTION
     "Specifies the layer2 state a given interface can take.."
   SYNTAX  INTEGER{  -- picked from Syntax of dot1dStpPortState
                        disabled(1),
                        blocking(2),
                        listening(3),
                        learning(4),
                        preforwarding(5),
                        forwarding(6)
                 }

--
-- Top level components of this MIB.
--

  fdryMplsVpnNotifications   OBJECT IDENTIFIER ::= { fdryMplsL2VpnMIB 0 }
  fdryMplsVllInfo   OBJECT IDENTIFIER ::= { fdryMplsL2VpnMIB 1 }  -- Includes VLL and VLL-Local
  fdryMplsVplsInfo   OBJECT IDENTIFIER ::= { fdryMplsL2VpnMIB 2 }

--
-- L2 VPN VLL and VLL-Local Endpoint table
--

  fdryVllEndPointTable   OBJECT-TYPE
     SYNTAX        SEQUENCE OF FdryVllEndPointEntry
     MAX-ACCESS    not-accessible
     STATUS        current
     DESCRIPTION
         "This table specifies information about the VLL and VLL-local endpoints which are not
         available in the PW tables."
     ::= { fdryMplsVllInfo 1 }

  fdryVllEndPointEntry   OBJECT-TYPE
     SYNTAX        FdryVllEndPointEntry
     MAX-ACCESS    not-accessible
     STATUS        current
     DESCRIPTION
          "A row in this table represents a VLL or VLL-local end point for a
          pseudo-wire (PW) virtual connection across a packet network. 
          For a VLL, we would have one instance of this table for a given PW.
          For a VLL-local, there would be two instances of this table for a given PW.
          It is indexed by fdryVllEndPointServiceType, pwIndex, and pwEnetPwInstance.
          The pwIndex is the index of pwTable, and {pwIndex, pwEnetPwInstance} together
          provides an instance in the pwEnetTable.
           A row can be created by an operator command after having created a row
           in the pwTable and pwEnetTable.
           1) Objects MUST NOT be changed after row activation.
           2) Objects MAY be changed when the PW is
           defined as not active. A change of these objects involves
           re-signaling of the PW or it might be traffic affecting.
           End point not active is defined as one of the following
           conditions:
                  a) The pwRowStatus is notInService(2).
                  b) The pwRowStatus is notReady(3).
                  c) The pwAdminStatus is down(2).
           "
     INDEX  {fdryVllEndPointServiceType, pwIndex, pwEnetPwInstance}
            ::= { fdryVllEndPointTable 1 }

  FdryVllEndPointEntry ::= SEQUENCE {
        fdryVllEndPointServiceType           MplsServiceType ,
        fdryVllEndPointVlanTagMode               VlanTagMode,
        fdryVllEndPointClassOfService        ClassOfService,
        fdryVllEndPointInHCPkts              Counter64,
        fdryVllEndPointOutHCPkts              Counter64,
        fdryVllEndPointAdminStatus           AdminStatus,
        fdryVllEndPointOperStatus           PwOperStatusTC,
        fdryVllEndPointRowStatus             RowStatus,
        fdryVllEndPointInnerVlanId          PwVlanCfg,
        fdryVllEndPointInHCOctets           Counter64,
        fdryVllEndPointOutHCOctets         Counter64
     }

  fdryVllEndPointServiceType OBJECT-TYPE
     SYNTAX        MplsServiceType
     MAX-ACCESS    not-accessible
     STATUS        current
     DESCRIPTION
         "A service type indicating VLL or VLL-local service for this endpoint.
         The value vpls(3) is not used in this table.
         "
     ::= { fdryVllEndPointEntry 1 }

  fdryVllEndPointVlanTagMode OBJECT-TYPE
     SYNTAX        VlanTagMode
     MAX-ACCESS    read-create
     STATUS        current
     DESCRIPTION
         "This value indicates the vlan mode for this endpoint. The values,
         dual(3) and other(4) is not used in this table.
         "
     ::= { fdryVllEndPointEntry 2 }

  fdryVllEndPointClassOfService OBJECT-TYPE
     SYNTAX        ClassOfService
     MAX-ACCESS    read-create
     STATUS        current
     DESCRIPTION
         "This value indicates the Class Of Service for this endpoint.
         For VLL, this value is used to select the appropriate tunnel
         whose COS value is either same, or almost approaching this value.
         For VLL-local, this value is applied to the ingress packet of an endpoint
         "
     DEFVAL {0}
     ::= { fdryVllEndPointEntry 3 }

  fdryVllEndPointInHCPkts OBJECT-TYPE
     SYNTAX        Counter64
     MAX-ACCESS    read-only
     STATUS        current
     DESCRIPTION
         "This value indicates the number of packets ingressing into this endpoint.
           This counter is not supported in CES/CER platform.
         "
     ::= { fdryVllEndPointEntry 4 }

  fdryVllEndPointOutHCPkts OBJECT-TYPE
     SYNTAX        Counter64
     MAX-ACCESS    read-only
     STATUS        current
     DESCRIPTION
         "This value indicates the number of packets egressing out from this endpoint.
         For VLL-local, this value could be the fdryVllEndPointInHCPkts of the other endpoint
         of this VLL instance. But since rate limit could be applied to the incoming packet,
         the count value will not be accurate. Due to this, the value will be 0 for VLL-local.
           This counter is not supported in CES/CER platform.
         "
     ::= { fdryVllEndPointEntry 5 }

  fdryVllEndPointAdminStatus OBJECT-TYPE
     SYNTAX        AdminStatus
     MAX-ACCESS    read-create
     STATUS        current
     DESCRIPTION
         "The desired administrative status of this endpoint. This object MAY
          be set at any time.
         "
     ::= { fdryVllEndPointEntry 6 }

  fdryVllEndPointOperStatus OBJECT-TYPE
     SYNTAX        PwOperStatusTC
     MAX-ACCESS    read-only
     STATUS        current
     DESCRIPTION
         "This object indicates the operational status of this endpoint.
         Only values up(1), down(2) are used in this table
         "
     ::= { fdryVllEndPointEntry 7 }

  fdryVllEndPointRowStatus OBJECT-TYPE
     SYNTAX        RowStatus
     MAX-ACCESS    read-create
     STATUS        current
     DESCRIPTION
       "This variable is used to create, modify, and/or
        delete a row in this table. When a row in this
        table is in active(1) state, no objects in that row
        can be modified except this object, and the fdryVllEndPointAdminStatus.
        "
     ::= { fdryVllEndPointEntry 8 }

fdryVllEndPointInnerVlanId OBJECT-TYPE
     SYNTAX        PwVlanCfg
     MAX-ACCESS    read-create
     STATUS        current
     DESCRIPTION
         "This value indicates the inner vlan id for this endpoint.
          Returns 0 if not configured or is not supported.
         "
     DEFVAL { 0 }
     ::= { fdryVllEndPointEntry 9 }

  fdryVllEndPointInHCOctets OBJECT-TYPE
     SYNTAX        Counter64
     MAX-ACCESS    read-only
     STATUS        current
     DESCRIPTION
         "This value indicates the number of octets ingressing into this endpoint
         from a Customer Edge (CE) device.
           This counter is supported in CES/CER platform.
         "
     ::= { fdryVllEndPointEntry 10 }

  fdryVllEndPointOutHCOctets OBJECT-TYPE
     SYNTAX        Counter64
     MAX-ACCESS    read-only
     STATUS        current
     DESCRIPTION
         "This value indicates the number of octets egressing out from this endpoint towards
         the Customer Edge (CE) device.
          This counter is not supported in CES/CER platform.
           Within CES/CER, any packet coming in from the tunnel will have its MPLS header as part of the octet count.
         "
     ::= { fdryVllEndPointEntry 11 }


-- Deprecated table fdryVplsEndPointTable

  fdryVplsEndPointTable   OBJECT-TYPE
     SYNTAX        SEQUENCE OF FdryVplsEndPointEntry
     MAX-ACCESS    not-accessible
     STATUS        deprecated
     DESCRIPTION
         "This table specifies information about the VPLS endpoints which are not
         available in the PW mib, or VPLS draft mib."
     ::= { fdryMplsVplsInfo 1 }

  fdryVplsEndPointEntry   OBJECT-TYPE
     SYNTAX        FdryVplsEndPointEntry
     MAX-ACCESS    not-accessible
     STATUS        deprecated
     DESCRIPTION
          "A row in this table represents a VPLS end point for a
          given VPLS instance. The VPLS instance is represented 
          by vplsConfigTable and fdryVplsTable.
          For a given VPLS instance, there could be multiple instances
          of rows within this table, each describing one endpoint.
          For a given endpoint, there will be one VPLS instance.
          A given endpoint is represented by vplsConfigIndex (VPLS instance),
          vlan id, and ifIndex of the physical port which is acting as an endpoint.
          This allows a tagged port to be associated with multiple VPLS instances.
          An untagged port can only be associated with one VPLS instance.
          Note that this table is kept independent of the PW tables to indicate 
          that endpoints terminate on the VPLS instance.
          On the other side, a VPLS instance will have association with the PW MIB.
          This table is indexed by vplsConfigIndex, fdryVplsEndPointPortVlan, 
          and fdryVplsEndPointIfIndex.
           "
     INDEX  {vplsConfigIndex, fdryVplsEndPointPortVlan, fdryVplsEndPointIfIndex}
            ::= { fdryVplsEndPointTable 1 }

  FdryVplsEndPointEntry ::= SEQUENCE {
        fdryVplsEndPointPortVlan           PwVlanCfg ,
        fdryVplsEndPointIfIndex            InterfaceIndex,
        fdryVplsEndPointVlanTagMode        VlanTagMode,
        fdryVplsEndPointOutHCPkts            Counter64,
        fdryVplsEndPointState                INTEGER,
        fdryVplsEndPointAdminStatus           AdminStatus,
        fdryVplsEndPointOperStatus           PwOperStatusTC,
        fdryVplsEndPointRowStatus             RowStatus,
        fdryVplsEndPointInHCOctets           Counter64
     }

  fdryVplsEndPointPortVlan OBJECT-TYPE
     SYNTAX        PwVlanCfg
     MAX-ACCESS    not-accessible
     STATUS        deprecated
     DESCRIPTION
         "This value specifies the VLAN id value of this endpoint.
         "
     ::= { fdryVplsEndPointEntry 1 }

  fdryVplsEndPointIfIndex OBJECT-TYPE
     SYNTAX        InterfaceIndex
     MAX-ACCESS    not-accessible
     STATUS        deprecated
     DESCRIPTION
         "This value specifies the ifIndex value of this endpoint.
         "
     ::= { fdryVplsEndPointEntry 2 }

  fdryVplsEndPointVlanTagMode OBJECT-TYPE
     SYNTAX        VlanTagMode
     MAX-ACCESS    read-create
     STATUS        deprecated
     DESCRIPTION
         "This value indicates the vlan mode for this endpoint. The values,
         dual(3) and other(4) is not used in this table.
         "
     ::= { fdryVplsEndPointEntry 3 }

  fdryVplsEndPointOutHCPkts OBJECT-TYPE
     SYNTAX        Counter64
     MAX-ACCESS    read-only
     STATUS        deprecated
     DESCRIPTION
         "This counter indicates the number of packets egressing 
         out from this endpoint towards the Customer Edge (CE).
         This value counts packets coming from multiple pseudo-wires
         towards the endpoint, as well as locally switched packets
         between other endpoints to this endpoint, all belonging
         to the same VPLS instance.
           The value gives count of known unicast packets only.
         Unknown unicast and broadcast packets are not counted.
           This object is not supported in CES/CER.
         "
     ::= { fdryVplsEndPointEntry 4 }

  fdryVplsEndPointState OBJECT-TYPE
       SYNTAX      INTEGER { -- picked from Syntax of dot1dStpPortState
                            disabled(1),
                            blocking(2),
                            forwarding(5)
                   }
     MAX-ACCESS    read-only
     STATUS        deprecated
     DESCRIPTION
         "A L2 state of this VPLS endpoint.
         "
     ::= { fdryVplsEndPointEntry 5 }

  fdryVplsEndPointAdminStatus OBJECT-TYPE
     SYNTAX        AdminStatus
     MAX-ACCESS    read-create
     STATUS        deprecated
     DESCRIPTION
         "The desired administrative status of this endpoint. This object MAY
          be set at any time.
         "
     ::= { fdryVplsEndPointEntry 6 }

  fdryVplsEndPointOperStatus OBJECT-TYPE
     SYNTAX        PwOperStatusTC
     MAX-ACCESS    read-only
     STATUS        deprecated
     DESCRIPTION
         "This object indicates the operational status of this endpoint.
         Only values up(1), down(2) are used in this table
         "
     ::= { fdryVplsEndPointEntry 7 }

  fdryVplsEndPointRowStatus OBJECT-TYPE
     SYNTAX        RowStatus
     MAX-ACCESS    read-create
     STATUS        deprecated
     DESCRIPTION
       "This variable is used to create, modify, and/or
        delete a row in this table. When a row in this
        table is in active(1) state, no objects in that row
        can be modified except this object and the fdryVplsEndPointAdminStatus.
         "
     ::= { fdryVplsEndPointEntry 8 }

  fdryVplsEndPointInHCOctets OBJECT-TYPE
     SYNTAX        Counter64
     MAX-ACCESS    read-only
     STATUS        deprecated
     DESCRIPTION
         "This counter indicates the number of octets ingressing 
         into this endpoint from the Customer Edge (CE).
           This object is supported in CES/CER only.
         "
     ::= { fdryVplsEndPointEntry 9 }

--
-- L2 VPN VPLS Endpoint table
--
  fdryVplsEndPoint2Table   OBJECT-TYPE
     SYNTAX        SEQUENCE OF FdryVplsEndPoint2Entry
     MAX-ACCESS    not-accessible
     STATUS        current
     DESCRIPTION
         "This table specifies information about the VPLS endpoints which are not
         available in the PW mib, or VPLS draft mib.
           This table deprecates fdryVplsEndPointTable, as inner VLAN and ISID
         has been added as index to this table."
     ::= { fdryMplsVplsInfo 3 }

  fdryVplsEndPoint2Entry   OBJECT-TYPE
     SYNTAX        FdryVplsEndPoint2Entry
     MAX-ACCESS    not-accessible
     STATUS        current
     DESCRIPTION
          "A row in this table represents a VPLS end point for a
          given VPLS instance. The VPLS instance is represented 
          by vplsConfigTable and fdryVplsTable.
          For a given VPLS instance, there could be multiple instances
          of rows within this table, each describing one endpoint.
          For a given endpoint, there will be one VPLS instance.
          A given endpoint is represented by vplsConfigIndex (VPLS instance),
          vlan id, inner-id (inner VLAN or ISID),and ifIndex of the physical port which is acting as an endpoint.
          This allows a tagged port to be associated with multiple VPLS instances, and also many inner VLAN or ISID
          to be associated with a tagged port (outer VLAN tag)
          An untagged port can only be associated with one VPLS instance.
          Note that this table is kept independent of the PW tables to indicate 
          that endpoints terminate on the VPLS instance.
          On the other side, a VPLS instance will have association with the PW MIB.
          This table is indexed by vplsConfigIndex, fdryVplsEndPointPortVlan, 
          and fdryVplsEndPointIfIndex.
           "
     INDEX  {vplsConfigIndex,
             fdryVplsEndPoint2VlanId,
             fdryVplsEndPoint2InnerTagType, --inner vlan or ISID
             fdryVplsEndPoint2InnerTag,
             fdryVplsEndPoint2IfIndex}
            ::= { fdryVplsEndPoint2Table 1 }

  FdryVplsEndPoint2Entry ::= SEQUENCE {
        fdryVplsEndPoint2VlanId           PwVlanCfg ,
        fdryVplsEndPoint2InnerTagType        INTEGER,
        fdryVplsEndPoint2InnerTag            Unsigned32,
        fdryVplsEndPoint2IfIndex            InterfaceIndex,
        fdryVplsEndPoint2VlanTagMode        VlanTagMode,
        fdryVplsEndPoint2InHCOctets           Counter64,
        fdryVplsEndPoint2Layer2State          Layer2StateTC,
        fdryVplsEndPoint2OperStatus           PwOperStatusTC,
        fdryVplsEndPoint2RowStatus             RowStatus
     }

  fdryVplsEndPoint2VlanId OBJECT-TYPE
     SYNTAX        PwVlanCfg
     MAX-ACCESS    not-accessible
     STATUS        current
     DESCRIPTION
         "This value specifies the VLAN id value of this endpoint.
         "
     ::= { fdryVplsEndPoint2Entry 1 }

  fdryVplsEndPoint2InnerTagType OBJECT-TYPE
     SYNTAX        INTEGER {invalid(1),innerVlan(2), isid(3)}
     MAX-ACCESS    not-accessible
     STATUS        current
     DESCRIPTION
         "This value indicates the inner id for this endpoint. 
         If no inner tag is specified, value invalid(1) is returned.
         "
     ::= { fdryVplsEndPoint2Entry 2 }

  fdryVplsEndPoint2InnerTag OBJECT-TYPE
     SYNTAX        Unsigned32
     MAX-ACCESS    not-accessible
     STATUS        current
     DESCRIPTION
         "This value indicates the inner tag for this endpoint. 
          If the index fdryVplsEndPoint2InnerTagType has 
          value isid(3), then this object will have the 
          ISID value for that endpoint. Valid ISID value 
          is between 256 (0x100) and 16777214 (0xFFFFFE).
         If no inner tag is specified, value 0 is returned.
         "
     ::= { fdryVplsEndPoint2Entry 3 }

  fdryVplsEndPoint2IfIndex OBJECT-TYPE
     SYNTAX        InterfaceIndex
     MAX-ACCESS    not-accessible
     STATUS        current
     DESCRIPTION
         "This value specifies the ifIndex value of this endpoint.
         "
     ::= { fdryVplsEndPoint2Entry 4 }

  fdryVplsEndPoint2VlanTagMode OBJECT-TYPE
     SYNTAX        VlanTagMode
     MAX-ACCESS    read-create
     STATUS        current
     DESCRIPTION
         "This value indicates the vlan mode for this endpoint. The values,
         dual(3) and other(4) is not used in this table.
         "
     ::= { fdryVplsEndPoint2Entry 5 }

  fdryVplsEndPoint2InHCOctets OBJECT-TYPE
     SYNTAX        Counter64
     MAX-ACCESS    read-only
     STATUS        current
     DESCRIPTION
         "This counter indicates the number of octets ingressing 
         into this endpoint from the Customer Edge (CE).
           This object is supported in CES/CER only.
         "
     ::= { fdryVplsEndPoint2Entry 6 }

  fdryVplsEndPoint2Layer2State OBJECT-TYPE
     SYNTAX      Layer2StateTC
     MAX-ACCESS    read-only
     STATUS        current
     DESCRIPTION
         "The L2 state of this VPLS endpoint.
         "
     ::= { fdryVplsEndPoint2Entry 7 }

  fdryVplsEndPoint2OperStatus OBJECT-TYPE
     SYNTAX        PwOperStatusTC
     MAX-ACCESS    read-only
     STATUS        current
     DESCRIPTION
         "This object indicates the operational status of this endpoint.
         Only values up(1), down(2) are used in this table
         "
     ::= { fdryVplsEndPoint2Entry 8 }

  fdryVplsEndPoint2RowStatus OBJECT-TYPE
     SYNTAX        RowStatus
     MAX-ACCESS    read-create
     STATUS        current
     DESCRIPTION
       "This variable is used to create, modify, and/or
        delete a row in this table. When a row in this
        table is in active(1) state, no objects in that row
        can be modified except this object.
         "
     ::= { fdryVplsEndPoint2Entry 9 }



--
-- L2 VPN VPLS Instance Table
--

  fdryVplsTable   OBJECT-TYPE
     SYNTAX        SEQUENCE OF FdryVplsEntry
     MAX-ACCESS    not-accessible
     STATUS        current
     DESCRIPTION
         "This table specifies additional information about the VPLS instance configuration
          which is not available in the VplsConfigTable. Some of these
          objects are configuration specific, some are commands specific 
          to that VPLS instance."
     ::= { fdryMplsVplsInfo 2 }

  fdryVplsEntry   OBJECT-TYPE
     SYNTAX        FdryVplsEntry
     MAX-ACCESS    not-accessible
     STATUS        current
     DESCRIPTION
          "A row in this table represents a VPLS instance. It augments 
          the vplsConfigTable in the VPLS draft mib.
           "
     AUGMENTS    { vplsConfigEntry }
            ::= { fdryVplsTable 1 }

  FdryVplsEntry ::= SEQUENCE {
        fdryVplsClassOfService           ClassOfService ,
        fdryVplsMaxMacLearned            Unsigned32,
        fdryVplsClearMac        TruthValue,
        fdryVplsVcId            Unsigned32
     }

  fdryVplsClassOfService OBJECT-TYPE
     SYNTAX        ClassOfService
     MAX-ACCESS    read-create
     STATUS        current
     DESCRIPTION
         "This value indicates the Class Of Service for this VPLS instance.
         This value is used to select the appropriate tunnel
         whose COS value is either same, or almost approaching this value.
         "
     DEFVAL {0}
     ::= { fdryVplsEntry 1 }

  fdryVplsMaxMacLearned OBJECT-TYPE
     SYNTAX        Unsigned32
     MAX-ACCESS    read-only
     STATUS        current
     DESCRIPTION
         "This value indicates the maximum number of MAC addresses
         that can be learned by this VPLS instance.
         "
     ::= { fdryVplsEntry 2}

  fdryVplsClearMac OBJECT-TYPE
     SYNTAX        TruthValue
     MAX-ACCESS    read-create
     STATUS        current
     DESCRIPTION
         "The Set value of TRUE tells the system to clear all the MAC addresses
         learned by this VPLS instance. Setting value of FALSE will return an error.
         During read operations, value FALSE will be returned at all times.
         "
     ::= { fdryVplsEntry 3}

  fdryVplsVcId OBJECT-TYPE
     SYNTAX        Unsigned32
     MAX-ACCESS    read-only
     STATUS        current
     DESCRIPTION
         "The VPLS Instance ID of a given VPLS session.
         "
     ::= { fdryVplsEntry 4}

--
  -- L2 VPN Service Notifications
--

  fdryVplsCreated NOTIFICATION-TYPE
      OBJECTS {
          vplsConfigName, --VPLS name
          fdryVplsVcId --VPLS VC ID
      }
      STATUS          current
      DESCRIPTION
           "This notification is generated when an entry is created in
            fdryVplsTable, indicating creation of a new VPLS instance.
              This notification is not generated during system boot up time."
      --#TYPE "Foundry Trap: MPLS VPLS Instance Created"
      --#SUMMARY "VPLS %s (VC ID %d) has been created."
      --#ARGUMENTS { 0, 1 }
      --#SEVERITY INFORMATIONAL
      --#STATE OPERATIONAL
      ::= { fdryMplsVpnNotifications 1 }

  fdryVplsDeleted NOTIFICATION-TYPE
      OBJECTS {
          vplsConfigName, --VPLS name
          fdryVplsVcId --VPLS VC ID
      }
      STATUS          current
      DESCRIPTION
           "This notification is generated when one entry in the
            fdryVplsTable have been marked for deletion, indicating 
           deletion of an existing VPLS instance."
      --#TYPE "Foundry Trap: MPLS VPLS Instance Deleted"
      --#SUMMARY "VPLS %s (VC ID %d) has been deleted."
      --#ARGUMENTS { 0, 1 }
      --#SEVERITY INFORMATIONAL
      --#STATE OPERATIONAL
      ::= { fdryMplsVpnNotifications 2 }

  fdryPwCreated NOTIFICATION-TYPE
      OBJECTS {
          fdryPwServiceType,
          pwName, --VLL or VLL-Local name
          pwID       --VLL VC ID, value 0 for VLL-Local
      }
      STATUS          current
      DESCRIPTION
           "This notification is generated when an instance of VLL or VLL-Local
           pseudo-wire entry is created in the pwTable.
             The varbind fdryPwServiceType has the service type which
           originated this notification.
             This notification is not used for VPLS service.
             This notification is not generated during system boot up time"
      --#TYPE "Foundry Trap: MPLS L2VPN Instance Created"
      --#SUMMARY "L2VPN %d (1=VLL, 2=VLL-Local) Instance %s (VC ID %d) has been created."
      --#ARGUMENTS { 0, 1, 2 }
      --#SEVERITY INFORMATIONAL
      --#STATE OPERATIONAL
      ::= { fdryMplsVpnNotifications 3 }

END


FOUNDRY-BFD-STD-MIB DEFINITIONS ::= BEGIN  
   IMPORTS 
      MODULE-IDENTITY, OBJECT-TYPE,  
      Unsigned32, Counter32, Counter64,  
      NOTIFICATION-TYPE
         FROM SNMPv2-SMI                        -- [RFC2578]
    
      TEXTUAL-CONVENTION, TruthValue, 
      RowStatus, StorageType, TimeStamp 
         FROM SNMPv2-TC                         -- [RFC2579]

      MODULE-COMPLIANCE, OBJECT-GROUP, 
      NOTIFICATION-GROUP     
          FROM SNMPv2-CONF                      -- [RFC2580]
        
      InetAddress, InetAddressType, InetPortNumber 
         FROM INET-ADDRESS-MIB                  -- [RFC3291]
      bfd
        FROM FOUNDRY-SN-ROOT-MIB

   ; 
    
   bfdMIB MODULE-IDENTITY 
      LAST-UPDATED "200507221200Z"  -- 04 July 2005 12:00:00 EST 
      ORGANIZATION "IETF" 
      CONTACT-INFO 
          "        Thomas D. Nadeau 
                   Cisco Systems, Inc. 
           Email:  tnadeau@cisco.com 
    
                   Zafar Ali  
                   Cisco Systems, Inc. 
           Email:  zali@cisco.com 
          " 
      DESCRIPTION 
          "Bidirectional Forwarding Management Information Base." 
    
      -- Revision history. 
      REVISION 
          "200508221200Z"  -- 04 August 2005 12:00:00 EST 
      DESCRIPTION 
      "Initial version. Published as RFC xxxx." -- RFC-editor pls fill 
                                                -- in xxxx
   ::= { bfd 1 }
--   ::= { mib-2 XXX }
   
   -- Top level components of this MIB module. 

   bfdNotifications OBJECT IDENTIFIER ::= { bfdMIB 0 } 
    
   bfdObjects       OBJECT IDENTIFIER ::= { bfdMIB 1 } 
    
   bfdConformance   OBJECT IDENTIFIER ::= { bfdMIB 3 } 
    
   bfdScalarObjects OBJECT IDENTIFIER ::= { bfdObjects 1 } 
    
    
   --  Textual Conventions 
    
      BfdSessIndexTC ::= TEXTUAL-CONVENTION 
      DISPLAY-HINT "d" 
      STATUS        current 
      DESCRIPTION 
          "An index used to uniquely identify BFD sessions." 
      SYNTAX Unsigned32 (1..4294967295) 

      BfdInterval ::= TEXTUAL-CONVENTION 
      STATUS        current 
      DESCRIPTION 
          "The BFD interval delay in microseconds." 
      SYNTAX        Unsigned32 (1..4294967295) 
    
      BfdDiag ::=      TEXTUAL-CONVENTION 
      STATUS        current 
      DESCRIPTION 
          "A common BFD diagnostic code." 
    
      SYNTAX INTEGER { noDiagnostic(1),  
                       controlDetectionTimeExpired(2),  
                       echoFunctionFailed(3),  
                       neighborSignaledSessionDown(4),  
                       forwardingPlaneReset(5), 
                       pathDown(6),  
                       concatenatedPathDown(7), 
                       administrativelyDown(8),  
                       reverseConcatenatedPathDown (9) 
                     } 
    
        --  BFD General Variables 
    
        --  These parameters apply globally to the Router's 
        --  BFD Process. 
    
        bfdAdminStatus OBJECT-TYPE 
           SYNTAX   INTEGER { enabled(1), disabled(2) }         
           MAX-ACCESS   read-write 
           STATUS   current 
           DESCRIPTION 
              "The global administrative status of BFD in this router.  
               The value 'enabled' denotes that the BFD Process is 
               active on at least one interface; 'disabled' disables  
               it on all interfaces." 
           DEFVAL { enabled }  
           ::= { bfdScalarObjects 1 } 
    
        bfdVersionNumber OBJECT-TYPE 
            SYNTAX   Unsigned32 
            MAX-ACCESS   read-only 
            STATUS   current 
            DESCRIPTION 
               "The current version number of the BFD protocol." 
            REFERENCE 
               " BFD Version 0 (draft-katz-ward-bfd-02.txt)" 
            DEFVAL { 0 } 
            ::= { bfdScalarObjects 3 } 
    
    
        --  BFD Session Table 
        --  The BFD Session Table specifies BFD session specific 
        --  information.  
    
        bfdSessTable OBJECT-TYPE 
            SYNTAX   SEQUENCE OF BfdSessEntry 
            MAX-ACCESS   not-accessible 
            STATUS   current 
            DESCRIPTION 
               "The BFD Session Table describes the BFD sessions." 
            REFERENCE 
               "BFD Version 0 (draft-katz-ward-bfd-02.txt)" 
            ::= { bfdObjects 2 } 
    
        bfdSessEntry OBJECT-TYPE 
            SYNTAX      BfdSessEntry 
            MAX-ACCESS  not-accessible 
            STATUS      current 
            DESCRIPTION 
               "The BFD Session Entry describes BFD session." 
            INDEX { bfdSessIndex } 
            ::= { bfdSessTable 1 } 
    
        BfdSessEntry ::= SEQUENCE { 
          bfdSessIndex                    BfdSessIndexTC, 
          bfdSessApplicationId            Unsigned32, 
          bfdSessDiscriminator            Unsigned32, 
          bfdSessRemoteDiscr              Unsigned32,  
          bfdSessUdpPort                  InetPortNumber, 
          bfdSessState                    INTEGER, 
          bfdSessRemoteHeardFlag          TruthValue,   
          bfdSessDiag                     Unsigned32, 
          bfdSessOperMode                 INTEGER, 
          bfdSessDemandModeDesiredFlag    TruthValue, 
          bfdSessEchoFuncModeDesiredFlag  TruthValue, 
          bfdSessControlPlanIndepFlag     TruthValue, 
          bfdSessAddrType                 InetAddressType, 
          bfdSessAddr                     InetAddress,  
          bfdSessDesiredMinTxInterval     BfdInterval, 
          bfdSessReqMinRxInterval         BfdInterval, 
          bfdSessReqMinEchoRxInterval     BfdInterval, 
          bfdSessDetectMult               Unsigned32, 
          bfdSessStorType                 StorageType, 
          bfdSessRowStatus                RowStatus, 
          bfdSessAuthPresFlag             TruthValue, 
          bfdSessAuthenticationType       INTEGER 
      } 
    
      bfdSessIndex  OBJECT-TYPE 
      SYNTAX        BfdSessIndexTC 
      MAX-ACCESS    not-accessible
      STATUS        current 
      DESCRIPTION 
          "This object contains an index used to represent a 
           unique BFD session on this device." 
      ::= { bfdSessEntry 1 } 
    
   bfdSessApplicationId  OBJECT-TYPE 
      SYNTAX        Unsigned32 
      MAX-ACCESS    read-only 
      STATUS        current 
      DESCRIPTION 
          "This object contains an index used to indicate 
           a local application which owns or maintains this 
           BFD session. For instance, the MPLS VPN process may 
           maintain a subset of the total number of BFD 
           sessions.  This application ID provides a convenient 
           way to segregate sessions by the applications which 
           maintain them." 
      ::= { bfdSessEntry 2 } 
     
      bfdSessDiscriminator            OBJECT-TYPE 
      SYNTAX        Unsigned32 (1..4294967295) 
      MAX-ACCESS    read-only 
      STATUS        current 
      DESCRIPTION 
          "This object specifies the local discriminator for this BFD  
        session, used to uniquely identify it." 
      ::= { bfdSessEntry 3 } 
    
      bfdSessRemoteDiscr OBJECT-TYPE 
          SYNTAX        Unsigned32 (1..4294967295) 
          MAX-ACCESS    read-only 
          STATUS        current 
          DESCRIPTION 
            "This object specifies the session discriminator chosen  
             by the remote system for this BFD session." 
      ::= { bfdSessEntry 4 } 
    
      bfdSessUdpPort OBJECT-TYPE 
          SYNTAX      InetPortNumber 
          MAX-ACCESS  read-create 
          STATUS      current 
          DESCRIPTION 
              "The UDP Port for BFD. The default value is the 
              well-known value for this port." 
            REFERENCE 
                "draft-katz-ward-bfd-02.txt and 
                draft-raggarwa-mpls-bfd-00.txt" 
            DEFVAL { 0 } 
            ::= { bfdSessEntry 5 } 
    
      bfdSessState OBJECT-TYPE 
            SYNTAX   INTEGER { 
                  adminDown(1),  
                  down(2),  
                  init(3),  
                  up(4)
            } 
            MAX-ACCESS   read-only 
            STATUS   current 
            DESCRIPTION 
               "The perceived state of the BFD session." 
            ::= { bfdSessEntry 6 } 
    
   bfdSessRemoteHeardFlag OBJECT-TYPE 
      SYNTAX        TruthValue 
      MAX-ACCESS    read-only 
      STATUS        current 
      DESCRIPTION 
            "This object specifies status of BFD packet reception from  
             the remote system. Specifically, it is set to true(1) if 
             the local system is actively receiving BFD packets from the  
             remote system, and is set to false(0) if the local system  
             has not received BFD packets recently (within the detection  
             time) or if the local system is attempting to tear down 
             the BFD session." 
      ::= { bfdSessEntry 7 } 
    
   bfdSessDiag OBJECT-TYPE 
            SYNTAX      Unsigned32 
            MAX-ACCESS  accessible-for-notify 
            STATUS      current 
            DESCRIPTION 
               "A diagnostic code specifying the local system's reason  
                for the last transition of the session from up(1)  
                to some other state." 
      ::= { bfdSessEntry 8 } 
    
   bfdSessOperMode OBJECT-TYPE 
            SYNTAX   INTEGER { asyncModeWEchoFun(1),  
                               asynchModeWOEchoFun(2),  
                               demandModeWEchoFunction(3),  
                               demandModeWOEchoFunction(4)  
             } 
           MAX-ACCESS   read-only 
           STATUS   current 
           DESCRIPTION 
               "This object specifies current operating mode that BFD  
                session is operating in. 
    
                A value of AsyncModeWEchoFun(1) ... 
                A value of AsynchModeWOEchoFun(2) ... 
                A value of DemandModeWEchoFunction(3) ... 
                A value of DemandModeWOEchoFunction(4) ... 
            " 
            ::= { bfdSessEntry 9 } 
    
   bfdSessDemandModeDesiredFlag OBJECT-TYPE 
      SYNTAX        TruthValue 
      MAX-ACCESS    read-create 
      STATUS        current 
      DESCRIPTION 
              "This object indicates that the local system's  
               desire to use Demand mode. Specifically, it is set  
               to true(1) if the local system wishes to use  
               Demand mode or false(0) if not" 
      DEFVAL { false } 
      ::= { bfdSessEntry 10 } 
    
   bfdSessEchoFuncModeDesiredFlag OBJECT-TYPE 
      SYNTAX        TruthValue 
      MAX-ACCESS    read-create 
      STATUS        current 
      DESCRIPTION 
              "This object indicates that the local system's  
               desire to use Echo mode. Specifically, it is set  
               to true(1) if the local system wishes to use  
               Echo mode or false(0) if not" 
      DEFVAL { false } 
      ::= { bfdSessEntry 11 } 
    
   bfdSessControlPlanIndepFlag     OBJECT-TYPE 
      SYNTAX        TruthValue 
      MAX-ACCESS    read-create 
      STATUS        current 
      DESCRIPTION 
          "This object indicates that the local system's  
           ability to continue to function through a disruption of  
           the control plane. Specifically, it is set  
           to true(1) if the local system BFD implementation is 
           independent of the control plane. Otherwise, the  
           value is set to false(0)" 
      DEFVAL { false } 
      ::= { bfdSessEntry 12 } 
    
   bfdSessAddrType  OBJECT-TYPE 
      SYNTAX        InetAddressType 
      MAX-ACCESS    read-create 
      STATUS        current 
      DESCRIPTION 
           "This object specifies IP address of the interface  
            associated with this BFD session.  
    
            Only values unknown(0), ipv4(1) or ipv6(2) 
            have to be supported.  
    
            A value of unknown(0) is allowed only when  
            the outgoing interface is of type point-to-point, or 
            when the BFD session is not associated with a specific  
            interface. 
    
            If any other unsupported values are attempted in a set 
            operation, the agent MUST return an inconsistentValue  
            error. 
      " 
      ::= { bfdSessEntry 13 } 
    
   bfdSessAddr OBJECT-TYPE 
      SYNTAX        InetAddress 
      MAX-ACCESS    read-create 
      STATUS        current 
      DESCRIPTION 
           "This object specifies IP address of the interface  
            associated with this BFD session.  
            It can also be used to enabled BFD on a specific  
            interface. The value is set to zero when BFD session is not  
            associated with a specific interface. " 
      ::= { bfdSessEntry 14 } 
    
   bfdSessDesiredMinTxInterval OBJECT-TYPE 
      SYNTAX    BfdInterval 
      MAX-ACCESS   read-create 
      STATUS    current 
      DESCRIPTION 
       "This object specifies the minimum interval, in  
        microseconds, that the local system would like to use when 
             transmitting BFD Control packets." 
      ::= { bfdSessEntry 15 } 
    
   bfdSessReqMinRxInterval     OBJECT-TYPE 
      SYNTAX        BfdInterval 
      MAX-ACCESS    read-create 
      STATUS        current 
      DESCRIPTION 
            "This object specifies the minimum interval, in  
             microseconds, between received  BFD Control packets the  
             local system is capable of supporting." 
      ::= { bfdSessEntry 16 } 
    
   bfdSessReqMinEchoRxInterval  OBJECT-TYPE 
      SYNTAX        BfdInterval 
      MAX-ACCESS    read-create 
      STATUS        current 
      DESCRIPTION 
            "This object specifies the minimum interval, in  
             microseconds, between received BFD Echo packets that this 
             system is capable of supporting." 
      ::= { bfdSessEntry 17 } 
    
   bfdSessDetectMult OBJECT-TYPE 
      SYNTAX        Unsigned32 
      MAX-ACCESS    read-create 
      STATUS        current 
      DESCRIPTION 
            "This object specifies the Detect time multiplier." 
      ::= { bfdSessEntry 18 } 
    
   bfdSessStorType  OBJECT-TYPE 
      SYNTAX        StorageType 
      MAX-ACCESS    read-create 
      STATUS        current 
      DESCRIPTION 
          "This variable indicates the storage type for this 
           object. Conceptual rows having the value  
           'permanent' need not allow write-access to any  
           columnar objects in the row."          
      ::= { bfdSessEntry 19 } 
    
   bfdSessRowStatus OBJECT-TYPE 
      SYNTAX        RowStatus 
      MAX-ACCESS    read-create 
      STATUS        current 
      DESCRIPTION 
            "This variable is used to create, modify, and/or 
             delete a row in this table. When a row in this 
             table has a row in the active(1) state, no  
             objects in this row can be modified except the 
             bfdSessRowStatus and bfdSessStorageType." 
      ::= { bfdSessEntry 20 } 
    
   bfdSessAuthPresFlag OBJECT-TYPE 
      SYNTAX        TruthValue 
      MAX-ACCESS    read-create 
      STATUS        current 
      DESCRIPTION 
              "This object indicates that the local system's  
               desire to use Authentication. Specifically, it is set  
               to true(1) if the local system wishes the session  
               to be authenticated or false(0) if not" 
      DEFVAL { false } 
      ::= { bfdSessEntry 21 } 
 
   bfdSessAuthenticationType OBJECT-TYPE 
            SYNTAX      INTEGER { simplePassword(1),  
                                  keyedMD5(2),  
                                  meticulousKeyedMD5(3),  
                                  keyedSHA1(4),  
                                  meticulousKeyedSHA1(5) 
             } 
            MAX-ACCESS  read-create 
            STATUS      current 
            DESCRIPTION 
               "The Authentication Type used for this BFD session. This 
   field is valid only when the Authentication Present bit is set" 
      ::= { bfdSessEntry 22 } 
 
   -- BFD Session Performance Table 
    
   bfdSessPerfTable OBJECT-TYPE 
      SYNTAX        SEQUENCE OF BfdSessPerfEntry 
      MAX-ACCESS    not-accessible 
      STATUS        current 
      DESCRIPTION 
          "This table specifies BFD Session performance counters." 
      ::= { bfdObjects 3 } 
    
   bfdSessPerfEntry OBJECT-TYPE 
      SYNTAX        BfdSessPerfEntry 
      MAX-ACCESS    not-accessible 
      STATUS        current 
      DESCRIPTION 
          "An entry in this table is created by a BFD-enabled node for  
           every BFD Session. bfdCounterDiscontinuityTime is used to  
           indicate potential discontinuity for all counter objects  
           in this table." 
      AUGMENTS    { bfdSessEntry } 
      ::= { bfdSessPerfTable 1 } 
    
   BfdSessPerfEntry ::= SEQUENCE { 
     bfdSessPerfPktIn               Counter32,  
     bfdSessPerfPktOut              Counter32, 
     bfdSessPerfUpTime                  TimeStamp,  
     bfdSessPerfLastSessDownTime    TimeStamp, 
     bfdSessPerfLastCommLostDiag    BfdDiag, 
     bfdSessPerfSessUpCount         Counter32, 
     bfdSessPerfDiscTime            TimeStamp, 
    
     -- High Capacity Counters 
     bfdSessPerfPktInHC             Counter64,  
     bfdSessPerfPktOutHC            Counter64 
     } 
    
   -- Ed Note: should we add per-diag code counts here,  
    
   bfdSessPerfPktIn OBJECT-TYPE  
       SYNTAX      Counter32 
       MAX-ACCESS  read-only 
       STATUS      current 
       DESCRIPTION 
           "The total number of BFD messages received for this BFD 
   session." 
       ::= { bfdSessPerfEntry 1 } 
    
   bfdSessPerfPktOut OBJECT-TYPE 
       SYNTAX      Counter32 
       MAX-ACCESS  read-only 
       STATUS      current 
       DESCRIPTION 
           "The total number of BFD messages sent for this BFD session." 
       ::= { bfdSessPerfEntry 2 } 
    
   bfdSessPerfUpTime OBJECT-TYPE 
       SYNTAX       TimeStamp 
       MAX-ACCESS   read-only 
       STATUS       current 
       DESCRIPTION 
           "The value of sysUpTime on the most recent occasion at which 
            the session came up. If no such up event exists this object 
            contains a zero value." 
       ::= { bfdSessPerfEntry 3 } 
 
   bfdSessPerfLastSessDownTime OBJECT-TYPE 
       SYNTAX       TimeStamp 
       MAX-ACCESS   read-only 
       STATUS       current 
       DESCRIPTION 
           "The value of sysUpTime on the most recent occasion at which 
            the last time communication was lost with the neighbor. If  
            no such down event exist this object contains a zero value." 
       ::= { bfdSessPerfEntry 4 } 
    
   bfdSessPerfLastCommLostDiag  OBJECT-TYPE 
       SYNTAX       BfdDiag 
       MAX-ACCESS   read-only 
       STATUS       current 
       DESCRIPTION 
           "The BFD diag code for the last time communication was lost  
            with the neighbor. If no such down event exists this object  
            contains a zero value." 
       ::= { bfdSessPerfEntry 5 }     
    
   bfdSessPerfSessUpCount OBJECT-TYPE 
       SYNTAX       Counter32 
       MAX-ACCESS   read-only 
       STATUS       current 
       DESCRIPTION 
           "The number of times this session has gone into the Up 
            state since the router last rebooted." 
       ::= { bfdSessPerfEntry 6 } 
    
   bfdSessPerfDiscTime OBJECT-TYPE 
       SYNTAX       TimeStamp 
       MAX-ACCESS   read-only 
       STATUS       current 
       DESCRIPTION 
         "The value of sysUpTime on the most recent occasion at 
          which any one or more of the session counters suffered 
          a discontinuity.  

          The relevant counters are the specific instances associated  
          with this BFD session of any Counter32 object contained in 
          the BfdSessPerfTable. If no such discontinuities have occurred  
          since the last re-initialization of the local management 
          subsystem, then this object contains a zero value." 
       ::= { bfdSessPerfEntry 7 } 
    

   bfdSessPerfPktInHC OBJECT-TYPE  
       SYNTAX       Counter64 
       MAX-ACCESS   read-only 
       STATUS       current 
       DESCRIPTION 
           "This value represents the total number of BFD messages 
            received for this BFD session. It MUST be equal to the 
            least significant 32 bits of bfdSessPerfPktIn 
            if bfdSessPerfPktInHC is supported according to 
            the rules spelled out in RFC2863." 
       ::= { bfdSessPerfEntry 8 } 
    
   bfdSessPerfPktOutHC OBJECT-TYPE 
       SYNTAX       Counter64 
       MAX-ACCESS   read-only 
       STATUS       current 
       DESCRIPTION 
           "This value represents the total number of  
            total number of BFD messages transmitted for this  
            BFD session. It MUST be equal to the 
           least significant 32 bits of bfdSessPerfPktIn 
           if bfdSessPerfPktOutHC is supported according to 
           the rules spelled out in RFC2863." 
       ::= { bfdSessPerfEntry 9 } 
    
    
   -- BFD Session Mapping Table 
    
        bfdSessMapTable OBJECT-TYPE 
            SYNTAX   SEQUENCE OF BfdSessMapEntry 
            MAX-ACCESS   not-accessible 
            STATUS   current 
            DESCRIPTION 
               "The BFD Session Mapping Table maps the complex 
                indexing of the BFD sessions to the flat 
                BFDIndex used in the BfdSessionTable. 
    
                Implementors need to be aware that if the value of 
                the bfdSessAddr (an OID) has more  
                that 111 sub-identifiers, then OIDs of column 
                instances in this table will have more than 128 
                sub-identifiers and cannot be accessed using SNMPv1, 
                SNMPv2c, or SNMPv3. 
               " 
            REFERENCE 
               "BFD Version 0 (draft-katz-ward-bfd-02.txt)" 
            ::= { bfdObjects 4 } 
    
        bfdSessMapEntry OBJECT-TYPE 
            SYNTAX   BfdSessMapEntry 
            MAX-ACCESS   not-accessible 
            STATUS   current 
            DESCRIPTION 
               "The BFD Session Entry describes BFD session 
                that is mapped to this index.

                Implementors need to be aware that if the value of
                the mplsInSegmentMapLabelPtrIndex (an OID) has more
                that 111 sub-identifiers, then OIDs of column
                instances in this table will have more than 128
                sub-identifiers and cannot be accessed using SNMPv1,
                SNMPv2c, or SNMPv3." 
            INDEX { bfdSessApplicationId, 
                    bfdSessDiscriminator, 
                    bfdSessAddrType, 
                    bfdSessAddr 
             } 
            ::= { bfdSessMapTable 1 } 
    
        BfdSessMapEntry ::= SEQUENCE { 
          bfdSessMapBfdIndex            BfdSessIndexTC 
        } 
    
   bfdSessMapBfdIndex OBJECT-TYPE 
      SYNTAX        BfdSessIndexTC 
      MAX-ACCESS    read-only 
      STATUS        current 
      DESCRIPTION 
          "This object specifies the BfdIndex referred to by 
           the indexes of this row. In essence, a mapping is 
           provided between these indexes and the BfdSessTable." 
      ::= { bfdSessMapEntry 1 } 
    
   -- Notification Configuration 
    
   bfdSessNotificationsEnable OBJECT-TYPE 
      SYNTAX        TruthValue 
      MAX-ACCESS    read-write 
      STATUS        current 
      DESCRIPTION 
          "If this object is set to true(1), then it enables 
           the emission of bfdSessUp and bfdSessDown 
           notifications; otherwise these notifications are not 
           emitted." 
      REFERENCE 
          "See also RFC3413 for explanation that  
           notifications are under the ultimate control of the  
           MIB modules in this document." 
      DEFVAL { false } 
      ::= { bfdScalarObjects 4 } 
    
   bfdSessUp NOTIFICATION-TYPE 
      OBJECTS     { bfdSessDiag, -- low range value 
                    bfdSessDiag  -- high range value 
      } 
      STATUS      current 
      DESCRIPTION 
          "This notification is generated when the 
           bfdSessState object for one or more contiguous 
           entries in bfdSessTable are about to enter the up(2) 
           state from some other state. The included values of 
           bfdSessDiag MUST both be set equal to this 
           new state (i.e: up(1)).  The two instances of  
           bfdSessDiag in this notification indicate the range  
           of indexes that are affected.  Note that all the indexes  
           of the two ends of the range can be derived from the 
           instance identifiers of these two objects.  For the 
           cases where a contiguous range of sessions 
           have transitioned into the up(1) state at roughly 
           the same time, the device SHOULD issue a single 
           notification for each range of contiguous indexes in 
           an effort to minimize the emission of a large number 
           of notifications.  If a notification has to be 
           issued for just a single bfdSessEntry, then 
           the instance identifier (and values) of the two 
           bfdSessDiag objects MUST be the identical." 
         --#TYPE "Foundry Trap: BFD Session Up"
         --#SUMMARY "BFD session up for specified sessions in varbind indexes."
         --#ARGUMENTS {}
         --#SEVERITY INFORMATIONAL
         --#STATE OPERATIONAL
      ::= { bfdNotifications 1 } 
    
   bfdSessDown NOTIFICATION-TYPE 
      OBJECTS     { bfdSessDiag, -- low range value 
                    bfdSessDiag  -- high range value 
      } 
      STATUS      current 
      DESCRIPTION 
          "This notification is generated when the 
           bfdSessState object for one or more contiguous 
           entries in bfdSessTable are about to enter the down(4) 
           or adminDown(5) states from some other state. The included  
           values of bfdSessDiag MUST both be set equal to this 
           new state (i.e: down(4) or adminDown(5)).  The two instances  
           of bfdSessDiag in this notification indicate the range  
           of indexes that are affected.  Note that all the indexes  
           of the two ends of the range can be derived from the 
           instance identifiers of these two objects.  For 
           cases where a contiguous range of sessions 
           have transitioned into the down(4) or adminDown(5) states  
           at roughly the same time, the device SHOULD issue a single 
           notification for each range of contiguous indexes in 
           an effort to minimize the emission of a large number 
           of notifications.  If a notification has to be 
           issued for just a single bfdSessEntry, then 
           the instance identifier (and values) of the two 
           bfdSessDiag objects MUST be the identical." 
         --#TYPE "Foundry Trap: BFD Session Down"
         --#SUMMARY "BFD session down due to code %d for specified sessions in varbind indexes."
         --#ARGUMENTS { 0 }
         --#SEVERITY INFORMATIONAL
         --#STATE OPERATIONAL
      ::= { bfdNotifications 2 } 
    
   -- Ed Note: We need to add notification for changes  
   -- when the two ends automatically negotiate to a new detection time 
   -- value or when detection multiplier changes.  
   -- Similarly, changes in the operating mode (bfdSessOperMode)  
   -- also need to be notified.  
    
   -- Module compliance. 
 
   bfdGroups 
      OBJECT IDENTIFIER ::= { bfdConformance 1 } 
    
   bfdCompliances 
      OBJECT IDENTIFIER ::= { bfdConformance 2 } 
    
   -- Compliance requirement for fully compliant implementations.  
    
   bfdModuleFullCompliance MODULE-COMPLIANCE 
      STATUS       current 
      DESCRIPTION "Compliance statement for agents that provide full 
                   support for BFD-MIB. Such devices can 
                   then be monitored and also be configured using 
                   this MIB module." 
    
      MODULE -- This module. 
      MANDATORY-GROUPS { 
            bfdSessionGroup, 
            bfdSessionPerfGroup, 
            bfdSessionPerfHCGroup, 
            bfdNotificationGroup 
      } 
    
      GROUP        bfdSessionPerfHCGroup 
      DESCRIPTION "This group is mandatory for those bfdPerfTable  
                   entries for which any of the objects  
                   bfdSessPerfPktInHC or bfdSessPerfPktOutHC  
                   wraps around too quickly  
                   based on the criteria specified in RFC 2863 for  
                   high-capacity counters." 
    
      GROUP        bfdNotificationGroup 
      DESCRIPTION "This group is only mandatory for those  
                   implementations which can efficiently implement  
                   the notifications contained in this group." 
    
      OBJECT       bfdSessAddrType 
      SYNTAX       INTEGER { unknown(0), ipv4(1), ipv6(2) } 
--      SYNTAX       InetAddressType { unknown(0), ipv4(1), ipv6(2) } 
      DESCRIPTION "Only unknown(0), ipv4(1) and ipv6(2) support  
                   is required." 
    
      OBJECT       bfdSessAddr 
      SYNTAX       InetAddress (SIZE(0|4|16)) 
      DESCRIPTION "An implementation is only required to support  
                   unknown(0), ipv4(1) and ipv6(2) sizes." 
 
      ::= { bfdCompliances 1 } 
    
   -- Read-Only Conformance TBD... 
    
    
   -- Units of conformance. 
    
   bfdSessionGroup OBJECT-GROUP 
      OBJECTS { 
                bfdSessNotificationsEnable, 
                bfdAdminStatus, 
                bfdVersionNumber, 
                bfdSessApplicationId,  
                bfdSessDiscriminator,             
                bfdSessAddrType, 
                bfdSessAddr,                      
                bfdSessRemoteDiscr,               
                bfdSessUdpPort,
                bfdSessState,                     
                bfdSessRemoteHeardFlag,           
                bfdSessDiag,                      
                bfdSessOperMode,                  
                bfdSessDemandModeDesiredFlag,     
                bfdSessEchoFuncModeDesiredFlag, 
                bfdSessControlPlanIndepFlag, 
                bfdSessDesiredMinTxInterval,      
                bfdSessReqMinRxInterval,      
                bfdSessReqMinEchoRxInterval,  
                bfdSessDetectMult,                
                bfdSessStorType,                 
                bfdSessRowStatus, 
                bfdSessMapBfdIndex,  
                bfdSessAuthPresFlag,  
                bfdSessAuthenticationType 
      } 
      STATUS  current 
      DESCRIPTION 
             "Collection of objects needed for BFD sessions." 
      ::= { bfdGroups 1 } 
    
    
   bfdSessionPerfGroup OBJECT-GROUP 
      OBJECTS { 
                bfdSessPerfPktIn, 
                bfdSessPerfPktOut, 
                bfdSessPerfUpTime,
                bfdSessPerfLastSessDownTime, 
                bfdSessPerfLastCommLostDiag, 
                bfdSessPerfSessUpCount,
                bfdSessPerfDiscTime 
      } 
      STATUS  current 
      DESCRIPTION 
             "Collection of objects needed to monitor the 
              performance of BFD sessions." 
      ::= { bfdGroups 2 } 
    
   bfdSessionPerfHCGroup OBJECT-GROUP 
      OBJECTS { 
               bfdSessPerfPktInHC, 
               bfdSessPerfPktOutHC  
      } 
      STATUS  current 
      DESCRIPTION 
             "Collection of objects needed to monitor the 
              performance of BFD sessions for which the 
              values of bfdSessPerfPktIn, bfdSessPerfPktOut  
              wrap around too quickly." 
      ::= { bfdGroups 3 } 
    
   bfdNotificationGroup NOTIFICATION-GROUP 
      NOTIFICATIONS { 
                bfdSessUp, 
                bfdSessDown 
      } 
      STATUS  current 
      DESCRIPTION 
             "Set of notifications implemented in this  
              module." 
      ::= { bfdGroups 4 }          
    
   END

FDRY-RADIUS-MIB DEFINITIONS ::= BEGIN

IMPORTS
	MODULE-IDENTITY, OBJECT-TYPE, 
			Unsigned32	   	FROM SNMPv2-SMI	  			-- [RFC2578]
	RowStatus, TEXTUAL-CONVENTION		FROM SNMPv2-TC 				-- [RFC2579]
	DisplayString		 				FROM SNMPv2-TC 		 		-- [RFC2579]
	
	InetAddressType, InetAddress		FROM INET-ADDRESS-MIB		-- [RFC 4001]
	fdryRadius	 					   	FROM FOUNDRY-SN-ROOT-MIB	-- [snroo101]
	;
   
fdryRadiusMIB MODULE-IDENTITY
	LAST-UPDATED "200802250000Z"  -- 25 February 2008
	ORGANIZATION "Foundry Networks, Inc."
	CONTACT-INFO
			"Technical Support Center, Foundry Networks,
			4980 Great America Parkway,
			Santa Clara, CA 95054
			Email: support@foundrynet.com
			Phone: 1-877-TURBO-CALL"
	DESCRIPTION
			"The Foundry proprietary MIB module for Radius Authentication Servers
			It has new table combines Ipv4 and Ipv6 Radius Authentication Servers configuration.
			
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.
			"
   
	REVISION 	"200802250000Z"  -- 25 February 2008
	DESCRIPTION	"Initial version, obsoletes the earlier snRadiusServerTable."
		  
	::= { fdryRadius 1 }

	--
	-- Textual Conventions
	--
	ServerUsage ::= TEXTUAL-CONVENTION
		STATUS	  current
		DESCRIPTION
			"Represents usage of the server for Authentication, Authorization or Accounting purpose."
		SYNTAX	INTEGER{
			default(1),
			authenticationOnly(2),
			authorizationOnly(3),
			accountingOnly(4) }

	--
	-- Top level components of this MIB.
	--

	fdryRadiusServer OBJECT IDENTIFIER ::= { fdryRadiusMIB 1 }

	--
	-- Ipv4/Ipv6  Radius server table
	--
	
fdryRadiusServerTable        OBJECT-TYPE
	SYNTAX  SEQUENCE OF FdryRadiusServerEntry
	MAX-ACCESS  not-accessible
	STATUS  current
	DESCRIPTION
		"Radius server table, listing the RADIUS authentication servers"
	::= { fdryRadiusServer 1 }

fdryRadiusServerEntry        OBJECT-TYPE
	SYNTAX  FdryRadiusServerEntry
	MAX-ACCESS  not-accessible
	STATUS  current
	DESCRIPTION
		"An entry in the Radius server table. This table uses running index as the Index to the table.
		  Reasons to go for running index Scheme than IP addresses:
		  1.  The table will be Virtual Routing and Forwarding(VRF) independent
			  that multiple VRFs could share the same address type and address.
		  2.  Index with address type and address could be potentially 17 unsigned integer, parsing and finding next index takes CPU time. 
			  The PDU gets to be huge too! 
		  3.  IP address is just another attribute, they are supposed to be list of servers."
	INDEX   { fdryRadiusServerIndex }
	::= { fdryRadiusServerTable 1 }

FdryRadiusServerEntry ::= SEQUENCE {
	fdryRadiusServerIndex
		Unsigned32,
	fdryRadiusServerAddrType
		InetAddressType,
	fdryRadiusServerAddr
		InetAddress,
	fdryRadiusServerAuthPort
		Unsigned32,
	fdryRadiusServerAcctPort
		Unsigned32,
	fdryRadiusServerRowKey
		DisplayString,
	fdryRadiusServerUsage
		ServerUsage,
	fdryRadiusServerRowStatus
		RowStatus
	}

fdryRadiusServerIndex OBJECT-TYPE
	SYNTAX	Unsigned32
	MAX-ACCESS	not-accessible
	STATUS	current
	DESCRIPTION
		"The index to the Radius server Table. Maximum 8 Radius servers are supported."
	::= { fdryRadiusServerEntry 1 }

fdryRadiusServerAddrType			 OBJECT-TYPE
	SYNTAX	InetAddressType
	MAX-ACCESS	read-create
	STATUS	current
	DESCRIPTION
		  "Radius server IP address Type. Supported address types are ipv4(1) and ipv6(2)"
	DEFVAL	{ ipv4 }
	::= { fdryRadiusServerEntry 2 }

fdryRadiusServerAddr			 OBJECT-TYPE
	SYNTAX	InetAddress
	MAX-ACCESS	read-create
	STATUS	current
	DESCRIPTION
		  "Radius server IP address."
	::= { fdryRadiusServerEntry 3 }

fdryRadiusServerAuthPort     OBJECT-TYPE
	SYNTAX  Unsigned32
	MAX-ACCESS  read-create
	STATUS  current
	DESCRIPTION
		"Authentication UDP port number."
    DEFVAL  { 1645 }
	::= { fdryRadiusServerEntry 4 }

fdryRadiusServerAcctPort     OBJECT-TYPE
	SYNTAX  Unsigned32
	MAX-ACCESS  read-create
	STATUS  current
	DESCRIPTION
		"Account UDP port number."
    DEFVAL  { 1646 }
	::= { fdryRadiusServerEntry 5 }

fdryRadiusServerRowKey       OBJECT-TYPE
	SYNTAX  DisplayString (SIZE(0..32))
	MAX-ACCESS  read-create
	STATUS  current
	DESCRIPTION
		"Authentication key displayed as encrypted text."
	::= { fdryRadiusServerEntry 6 }

fdryRadiusServerUsage    OBJECT-TYPE
	SYNTAX	ServerUsage
	MAX-ACCESS  read-create
	STATUS  current
	DESCRIPTION
		"To allow this server to be dedicated for a particular AAA activity."
	DEFVAL  { default }
	::= { fdryRadiusServerEntry 7 }

fdryRadiusServerRowStatus    OBJECT-TYPE
	SYNTAX	RowStatus
	MAX-ACCESS  read-create
	STATUS  current
	DESCRIPTION
		"This variable is used to create, modify, or
			delete a row in this table. When a row in this
			table is in active(1) state, no objects in that row
			can be modified except this object.
			 "
	::= { fdryRadiusServerEntry 8 }

	END
FDRY-ACL-MIB DEFINITIONS ::= BEGIN

IMPORTS
   MODULE-IDENTITY, OBJECT-TYPE, 
					 Unsigned32 	FROM SNMPv2-SMI	   -- [RFC2578]
   TEXTUAL-CONVENTION, RowStatus, 
   DisplayString, TruthValue		FROM SNMPv2-TC			-- [RFC2579]
   Ipv6Address						FROM IPV6-TC			-- [RFC2465]
   fdryAcl							FROM FOUNDRY-SN-ROOT-MIB -- [snroo101]
   ;

fdryAclMIB MODULE-IDENTITY
   LAST-UPDATED "200802140000Z"  -- 14 February 2008
   ORGANIZATION "Foundry Networks, Inc."
   CONTACT-INFO
			"Technical Support Center, Foundry Networks,
			4980 Great America Parkway,
			Santa Clara, CA 95054
			Email: support@foundrynet.com
			Phone: 1-877-TURBO-CALL"
	DESCRIPTION
		"The Foundry proprietary MIB module for Ipv6 Access Control List. 
		 It has new tables for Ipv6 Access Control List.
		 
		 Copyright (C) Foundry Networks, Inc, (2008)
		 This document and the information contained herein are provided on an
		 AS IS basis and FOUNDRY NETWORKS DISCLAIM ALL WARRANTIES, EXPRESS OR IMPLIED,
		 INCLUDING BUT NOT LIMITED TO ANY WARRANTY THAT THE USE OF THE
		 INFORMATION HEREIN WILL NOT INFRINGE ANY RIGHTS OR ANY IMPLIED
		 WARRANTIES OF MERCHANTABILITY OR FITNESS FOR A PARTICULAR PURPOSE.
	   "

	REVISION	 "200802140000Z"  -- 14 February 2008
	DESCRIPTION  "Initial version"
	   
   ::= { fdryAcl 1 }

--
-- Textual Conventions
--
RtrStatus ::= TEXTUAL-CONVENTION
	STATUS	  current
	DESCRIPTION
		"Represents a status value such as disabled or enabled."
	SYNTAX	INTEGER { 
						disabled(0), 
						enabled (1) 
					}

Action ::= TEXTUAL-CONVENTION
	STATUS	  current
	DESCRIPTION
		"Represents a action value such as deny or permit."
	SYNTAX	INTEGER { 
						deny(0), 
						permit (1) 
					}

Operator ::= TEXTUAL-CONVENTION
	STATUS	  current
	DESCRIPTION
		"Represents a operators value, such as equal, not-equal, lesser than,
		greater than, range and undefined."
	SYNTAX	INTEGER { 
						eq(0), 
						neq (1), 
						lt (2), 
						gt (3), 
						range (4), 
						undefined (7) 
					}

IpProtocol ::= TEXTUAL-CONVENTION
	STATUS	  current
	DESCRIPTION
		"Represents a transport protocol value."
	SYNTAX	Unsigned32 (0..255)

--
-- Top level components of this MIB.
--

fdryIpv6Acl		OBJECT IDENTIFIER ::= { fdryAclMIB 1 }

--
-- Ipv6 Access Control List Table
--
fdryIpv6AclTable       OBJECT-TYPE
	SYNTAX  SEQUENCE OF FdryIpv6AclEntry
	MAX-ACCESS  not-accessible
	STATUS  current
	DESCRIPTION
		"Table of Ipv6 Access Control List"
	::= { fdryIpv6Acl 1 }

fdryIpv6AclEntry       OBJECT-TYPE
	SYNTAX  FdryIpv6AclEntry
	MAX-ACCESS  not-accessible
	STATUS  current
	DESCRIPTION
		"An entry in the Ipv6 Access Control List table."
	INDEX   { fdryIpv6AclIndex }
	::= { fdryIpv6AclTable 1 }

FdryIpv6AclEntry ::= SEQUENCE {
	fdryIpv6AclIndex
		Unsigned32,
	fdryIpv6AclName
		DisplayString,
	fdryIpv6AclAction              
		Action,
	fdryIpv6AclProtocol            
		IpProtocol,
	fdryIpv6AclSourceIp
		Ipv6Address,
	fdryIpv6AclSourcePrefixLen
		Unsigned32,
	fdryIpv6AclSourceOperator
		Operator,
	fdryIpv6AclSourceOperand1
		Unsigned32,
	fdryIpv6AclSourceOperand2
		Unsigned32,
	fdryIpv6AclDestinationIp
		Ipv6Address,
	fdryIpv6AclDestinationPrefixLen
		Unsigned32,
	fdryIpv6AclDestinationOperator
		Operator,
	fdryIpv6AclDestinationOperand1
		Unsigned32,
	fdryIpv6AclDestinationOperand2
		Unsigned32,
	fdryIpv6AclEstablished
		RtrStatus,
	fdryIpv6AclLogOption
		TruthValue,
	fdryIpv6AclComments
		DisplayString,
	fdryIpv6AclRowStatus
		RowStatus
	}

fdryIpv6AclIndex       OBJECT-TYPE
	SYNTAX  Unsigned32
	MAX-ACCESS  not-accessible
	STATUS  current
	DESCRIPTION
		"The access control list item number for an entry.
		This is a unique number that identifies different
		Access list entries. This one has to be 
		unique even though the name is not unique
		for a give access list with same or different source
		address, prefix length, destination address and destination
		prefix length, protocol type, action (permit/deny) type and the
		operator (neq, eq, gt and , lt)."
	::= { fdryIpv6AclEntry 1 }

fdryIpv6AclName		OBJECT-TYPE
	SYNTAX  DisplayString (SIZE (0..199))
	MAX-ACCESS  read-create
	STATUS  current
	DESCRIPTION
		"Access Control List name for an entry."
	::= { fdryIpv6AclEntry 2 }

fdryIpv6AclAction      OBJECT-TYPE
	SYNTAX  Action 
	MAX-ACCESS  read-create
	STATUS  current
	DESCRIPTION
		"Action to take if the ip packet matches
		with this access control list."
	::= { fdryIpv6AclEntry 3 }

fdryIpv6AclProtocol    OBJECT-TYPE
	SYNTAX  IpProtocol
	MAX-ACCESS  read-create
	STATUS  current
	DESCRIPTION
		"Transport protocols. 0 means any protocol."
	::= { fdryIpv6AclEntry 4 }

fdryIpv6AclSourceIp    OBJECT-TYPE
	SYNTAX  Ipv6Address
	MAX-ACCESS  read-create
	STATUS  current
	DESCRIPTION
		"Source Ipv6 address."
	::= { fdryIpv6AclEntry 5 }

fdryIpv6AclSourcePrefixLen  OBJECT-TYPE
	SYNTAX  Unsigned32
	MAX-ACCESS  read-create
	STATUS  current
	DESCRIPTION
		"Source IPv6 address prefix length."
    DEFVAL  {64}
 	::= { fdryIpv6AclEntry 6 }

fdryIpv6AclSourceOperator    OBJECT-TYPE
	SYNTAX  Operator
	MAX-ACCESS  read-create
	STATUS  current
	DESCRIPTION
		"Type of comparison to perform.
		for now, this only applys to tcp or udp
		to compare the port number"
	::= { fdryIpv6AclEntry 7 }

fdryIpv6AclSourceOperand1     OBJECT-TYPE
	SYNTAX  Unsigned32(0..65535)
	MAX-ACCESS  read-create
	STATUS  current
	DESCRIPTION
		"For now this only refers to transport 
		protocol port number."
	::= { fdryIpv6AclEntry 8 }

fdryIpv6AclSourceOperand2     OBJECT-TYPE
	SYNTAX  Unsigned32(0..65535)
	MAX-ACCESS  read-create
	STATUS  current
	DESCRIPTION
		"For now this only refers to transport 
		protocol port number."
	::= { fdryIpv6AclEntry 9 }

fdryIpv6AclDestinationIp      OBJECT-TYPE
	SYNTAX  Ipv6Address
	MAX-ACCESS  read-create
	STATUS  current
	DESCRIPTION
		"Destination Ipv6 address."
	::= { fdryIpv6AclEntry 10 }

fdryIpv6AclDestinationPrefixLen    OBJECT-TYPE
	SYNTAX  Unsigned32
	MAX-ACCESS  read-create
	STATUS  current
	DESCRIPTION
		"Destination IPv6 address prefix length."
		
    DEFVAL  {64}
 	::= { fdryIpv6AclEntry 11 }

fdryIpv6AclDestinationOperator    OBJECT-TYPE
	SYNTAX  Operator
	MAX-ACCESS  read-create
	STATUS  current
	DESCRIPTION
		"Type of comparison to perform.
		for now, this only applys to tcp or udp
		to compare the port number"
	::= { fdryIpv6AclEntry 12 }

fdryIpv6AclDestinationOperand1     OBJECT-TYPE
	SYNTAX  Unsigned32(0..65535)
	MAX-ACCESS  read-create
	STATUS  current
	DESCRIPTION
		"For now this only refers to transport 
		protocol port number."
	::= { fdryIpv6AclEntry 13 }

fdryIpv6AclDestinationOperand2     OBJECT-TYPE
	SYNTAX  Unsigned32(0..65535)
	MAX-ACCESS  read-create
	STATUS  current
	DESCRIPTION
		"For now this only refers to transport 
		protocol port number."
	::= { fdryIpv6AclEntry 14 }

fdryIpv6AclEstablished OBJECT-TYPE
	SYNTAX  RtrStatus
	MAX-ACCESS  read-create
	STATUS  current
	DESCRIPTION
		"Enable/Disable the filtering of established TCP
		packets of which the ACK or RESET flag is on. This
		additional filter only applies to TCP transport
		protocol."
	::= { fdryIpv6AclEntry 15 }

fdryIpv6AclLogOption OBJECT-TYPE
	SYNTAX  TruthValue
	MAX-ACCESS  read-create
	STATUS  current
	DESCRIPTION
		"Log flag, should be set to one to enable logging"
	::= { fdryIpv6AclEntry 16 }

fdryIpv6AclComments   OBJECT-TYPE
	SYNTAX  DisplayString (SIZE (0..255))
	MAX-ACCESS  read-create
	STATUS  current
	DESCRIPTION
		"Remark description of individual Access Control List entry."
	::= { fdryIpv6AclEntry 17 }

fdryIpv6AclRowStatus   OBJECT-TYPE
	SYNTAX	RowStatus
	MAX-ACCESS	read-create
	STATUS	current
	DESCRIPTION
			"To create or delete a access list
			entry."
		::= { fdryIpv6AclEntry 18 }
	END


FDRY-TACACS-MIB DEFINITIONS ::= BEGIN

IMPORTS
	MODULE-IDENTITY, OBJECT-TYPE, 
			Unsigned32	   	FROM SNMPv2-SMI	  			-- [RFC2578]
	RowStatus							FROM SNMPv2-TC 				-- [RFC2579]
	DisplayString		 				FROM SNMPv2-TC 		 		-- [RFC2579]
	
	InetAddressType, InetAddress		FROM INET-ADDRESS-MIB
	fdryTacacs	 					   	FROM FOUNDRY-SN-ROOT-MIB	-- [snroo101]
	ServerUsage							FROM FDRY-RADIUS-MIB		-- [fdryradius]
	;
   
fdryTacacsMIB MODULE-IDENTITY
	LAST-UPDATED "200802250000Z"  -- 25 February 2008
	ORGANIZATION "Foundry Networks, Inc."
	CONTACT-INFO
			"Technical Support Center, Foundry Networks,
			4980 Great America Parkway,
			Santa Clara, CA 95054
			Email: support@foundrynet.com
			Phone: 1-877-TURBO-CALL"
	DESCRIPTION
			"The Foundry proprietary MIB module for Tacacs Authentication Servers
			It has new table combines Ipv4 and Ipv6 Tacacs Authentication Servers configuration.
			
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.
			"
   
	REVISION 	"200802250000Z"  -- 25 February 2008
	DESCRIPTION	"Initial version, obsoletes the earlier snTacacsServerTable."
		  
	::= { fdryTacacs 1 }

--
-- Top level components of this MIB.
--

fdryTacacsServer OBJECT IDENTIFIER ::= { fdryTacacsMIB 1 }

--
-- Ipv4/Ipv6  Tacacs server table
--
	
	fdryTacacsServerTable 	   OBJECT-TYPE
		SYNTAX	SEQUENCE OF FdryTacacsServerEntry
		MAX-ACCESS	not-accessible
		STATUS	current
		DESCRIPTION
			"Tacacs server table, listing the Tacacs authentication servers"
		::= { fdryTacacsServer 1 }
	
	fdryTacacsServerEntry 	   OBJECT-TYPE
		SYNTAX	FdryTacacsServerEntry
		MAX-ACCESS	not-accessible
		STATUS	current
		DESCRIPTION
			"An entry in the Tacacs server table. This table uses running index as the Index to the table.
			  Reasons to go for running index Scheme than IP addresses:
			  1.  The table will be Virtual Routing and Forwarding(VRF) independent
				  that multiple VRFs could share the same address type and address.
			  2.  Index with address type and address could be potentially 17 unsigned integer, parsing and finding next index takes CPU time. 
				  The PDU gets to be huge too! 
			  3.  IP address is just another attribute, they are supposed to be list of servers."
		INDEX	{ fdryTacacsServerIndex }
		::= { fdryTacacsServerTable 1 }
	
	FdryTacacsServerEntry ::= SEQUENCE {
		fdryTacacsServerIndex
			Unsigned32,
		fdryTacacsServerAddrType
			InetAddressType,
		fdryTacacsServerAddr
			InetAddress,
		fdryTacacsServerAuthPort
			Unsigned32,
		fdryTacacsServerRowKey
			DisplayString,
		fdryTacacsServerUsage
			ServerUsage,
		fdryTacacsServerRowStatus
			RowStatus
		}
	
	fdryTacacsServerIndex OBJECT-TYPE
		SYNTAX  Unsigned32
		MAX-ACCESS  not-accessible
		STATUS  current
		DESCRIPTION
		"The index to the Tacacs server Table, Maximum 8 Tacacs servers are supported."
		::= { fdryTacacsServerEntry 1 }
	
	fdryTacacsServerAddrType 			 OBJECT-TYPE
		SYNTAX  InetAddressType
		MAX-ACCESS  read-create
		STATUS  current
		DESCRIPTION
			  "Tacacs server IP address Type. Supported address types are ipv4(1) and ipv6(2)"
		DEFVAL	{ ipv4 }
		::= { fdryTacacsServerEntry 2 }
	
	fdryTacacsServerAddr 			 OBJECT-TYPE
		SYNTAX  InetAddress
		MAX-ACCESS  read-create
		STATUS  current
		DESCRIPTION
			  "Tacacs server IP address."
		::= { fdryTacacsServerEntry 3 }
	
	fdryTacacsServerAuthPort	   OBJECT-TYPE
		SYNTAX	Unsigned32
		MAX-ACCESS	read-create
		STATUS	current
		DESCRIPTION
			"Authentication UDP port number."
		DEFVAL	{ 49 }
		::= { fdryTacacsServerEntry 4 }
	
	fdryTacacsServerRowKey	   OBJECT-TYPE
		SYNTAX	DisplayString (SIZE(0..32))
		MAX-ACCESS	read-create
		STATUS	current
		DESCRIPTION
			"Authentication key displayed as encrypted text."
		::= { fdryTacacsServerEntry 5 }
	
	fdryTacacsServerUsage    OBJECT-TYPE
		SYNTAX	ServerUsage
		MAX-ACCESS	read-create
		STATUS	current
		DESCRIPTION
			"To allow this server to be dedicated for a particular AAA activity."
		DEFVAL	{ default }
		::= { fdryTacacsServerEntry 6 }

	fdryTacacsServerRowStatus    OBJECT-TYPE
		SYNTAX	RowStatus
		MAX-ACCESS	read-create
		STATUS	current
		DESCRIPTION
			"This variable is used to create, modify, or
			delete a row in this table. When a row in this
			table is in active(1) state, no objects in that row
			can be modified except this object.
			 "
		::= { fdryTacacsServerEntry 7 }
	
	END
FDRY-SNTP-MIB DEFINITIONS ::= BEGIN

IMPORTS
	MODULE-IDENTITY, OBJECT-TYPE, 
			Integer32, Unsigned32	   	FROM SNMPv2-SMI	  			-- [RFC2578]
	RowStatus							FROM SNMPv2-TC 				-- [RFC2579]
	InetAddressType, InetAddress		FROM INET-ADDRESS-MIB		-- [RFC 4001]
	fdrySntp	 					   	FROM FOUNDRY-SN-ROOT-MIB 	-- [snroo101]
	;
   
fdrySntpMIB MODULE-IDENTITY
	LAST-UPDATED "200802250000Z"  -- 25 February 2008
	ORGANIZATION "Foundry Networks, Inc."
	CONTACT-INFO
			"Technical Support Center, Foundry Networks,
			4980 Great America Parkway,
			Santa Clara, CA 95054
			Email: support@foundrynet.com
			Phone: 1-877-TURBO-CALL"
	DESCRIPTION
			"The Foundry proprietary MIB module for Simple Network Time Protocol(SNTP)
			It has new table combines Ipv4 and Ipv6 Simple Network Time Protocol server configuration.
			
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.
			"
   
	REVISION 	"200802250000Z"  -- 25 February 2008
	DESCRIPTION	"Initial version, obsoletes the earlier snNTPServerTable."
		  
	::= { fdrySntp 1 }

	--
	-- Top level components of this MIB.
	--

	fdrySntpServer OBJECT IDENTIFIER ::= { fdrySntpMIB 1 }

	--
	-- Ipv4/Ipv6  SNTP server table
	--
	
	fdrySntpServerTable			 OBJECT-TYPE
		SYNTAX  SEQUENCE OF FdrySntpServerTable
		MAX-ACCESS  not-accessible
		STATUS  current
		DESCRIPTION
			  "Simple Network Time Protocol(SNTP) server table."
		::= { fdrySntpServer 1 }
	
	fdrySntpServerEntry			 OBJECT-TYPE
		SYNTAX  FdrySntpServerTable
		MAX-ACCESS  not-accessible
		STATUS  current
		DESCRIPTION
			  "An entry in the SNTP server table. This table uses running index as the Index to the table.
			  	Reasons to go for running index Scheme than IP addresses:
				1.	The table will be Virtual Routing and Forwarding(VRF) independent
					that multiple VRFs could share the same address type and address.
				2.	Index with address type and address could be potentially 17 unsigned integer, parsing and finding next index takes CPU time. 
					The PDU gets to be huge too! 
				3. 	IP address is just another attribute, they are supposed to be list of servers."
				
		INDEX   { fdrySntpServerIndex }
		::= { fdrySntpServerTable 1 }
	
	FdrySntpServerTable ::= SEQUENCE {
		fdrySntpServerIndex
			Unsigned32,
		fdrySntpServerAddrType
			InetAddressType,
		fdrySntpServerAddr
			InetAddress,
		fdrySntpServerVersion
			Integer32,
		fdrySntpServerRowStatus
			RowStatus
		}

	fdrySntpServerIndex OBJECT-TYPE
		SYNTAX  Unsigned32
		MAX-ACCESS  not-accessible
		STATUS  current
		DESCRIPTION
			  "The index to the SNTP server Table. Maximum 3 Sntp servers are supported."
		::= { fdrySntpServerEntry 1 }
	
	fdrySntpServerAddrType 			 OBJECT-TYPE
		SYNTAX  InetAddressType
		MAX-ACCESS  read-create
		STATUS  current
		DESCRIPTION
			  "SNTP server IP address Type. Supported address types are ipv4(1) and ipv6(2)"
		DEFVAL  { ipv4 }
		::= { fdrySntpServerEntry 2 }
	
	fdrySntpServerAddr 			 OBJECT-TYPE
		SYNTAX  InetAddress
		MAX-ACCESS  read-create
		STATUS  current
		DESCRIPTION
			  "SNTP server IP address."
		::= { fdrySntpServerEntry 3 }
	
	fdrySntpServerVersion		 OBJECT-TYPE
		SYNTAX  Integer32 (1..4)
		MAX-ACCESS  read-create
		STATUS  current
		DESCRIPTION
			"SNTP server version."
		DEFVAL  { 3 }
		::= { fdrySntpServerEntry 4 }
	
	fdrySntpServerRowStatus		 OBJECT-TYPE
		SYNTAX  RowStatus
		MAX-ACCESS  read-create
		STATUS  current
		DESCRIPTION
			"This variable is used to create, modify, or
			delete a row in this table. When a row in this
			table is in active(1) state, no objects in that row
			can be modified except this object.
			 "
		::= { fdrySntpServerEntry 5 }

END




FDRY-TRAP-MIB DEFINITIONS ::= BEGIN

IMPORTS
	MODULE-IDENTITY, OBJECT-TYPE, 
			Integer32, Unsigned32	   	FROM SNMPv2-SMI	  			-- [RFC2578]
	RowStatus, TEXTUAL-CONVENTION		FROM SNMPv2-TC 				-- [RFC2579]
	
	InetAddressType, InetAddress		FROM INET-ADDRESS-MIB
	fdryTrap	 					   	FROM FOUNDRY-SN-ROOT-MIB	-- [snroo101]
	;
   
fdryTrapMIB MODULE-IDENTITY
	LAST-UPDATED "200802250000Z"  -- 25 February 2008
	ORGANIZATION "Foundry Networks, Inc."
	CONTACT-INFO
			"Technical Support Center, Foundry Networks,
			4980 Great America Parkway,
			Santa Clara, CA 95054
			Email: support@foundrynet.com
			Phone: 1-877-TURBO-CALL"
	DESCRIPTION
			"The Foundry proprietary MIB module for Traps.
			It has new table combines Ipv4 and Ipv6 configuration of 
			trap Receiver/managers which to send traps.
			
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.
			"
   
	REVISION 	"200802250000Z"  -- 25 February 2008
	DESCRIPTION	"Initial version, obsoletes the earlier snAgTrpRcvrTable."
		  
	::= { fdryTrap 1 }

--
-- Textual Conventions
--
SecurityModel ::= TEXTUAL-CONVENTION
	STATUS	  current
	DESCRIPTION
		"Represents version of trap format to be used."
	SYNTAX	INTEGER{
		v1(1),
		v2c(2),
		usm(3)
		}

SecurityLevel ::= TEXTUAL-CONVENTION
	STATUS	  current
	DESCRIPTION
		"Represents security levels to be used."
	SYNTAX	INTEGER {
		noAuth(1),
		auth(2),
		authPriv(3)
		}
	
--
-- Top level components of this MIB.
--

fdryTrapReceiver OBJECT IDENTIFIER ::= { fdryTrapMIB 1 }

--
-- Ipv4/Ipv6  trap receiver table
--
	
	fdryTrapReceiverTable 	   OBJECT-TYPE
		SYNTAX	SEQUENCE OF FdryTrapReceiverEntry
		MAX-ACCESS	not-accessible
		STATUS	current
		DESCRIPTION
			"Trap Receiver table."
		::= { fdryTrapReceiver 1 }
	
	fdryTrapReceiverEntry 	   OBJECT-TYPE
		SYNTAX	FdryTrapReceiverEntry
		MAX-ACCESS	not-accessible
		STATUS	current
		DESCRIPTION
			"An entry in the Trap Receiver table. This table uses running index as the Index to the table.
			  Reasons to go for running index Scheme than IP addresses:
			  1.  The table will be Virtual Routing and Forwarding(VRF) independent
				  that multiple VRFs could share the same address type and address.
			  2.  Index with address type and address could be potentially 17 unsigned integer, parsing and finding next index takes CPU time. 
				  The PDU gets to be huge too! 
			  3.  IP address is just another attribute, they are supposed to be list of servers."
		INDEX	{ fdryTrapReceiverIndex }
		::= { fdryTrapReceiverTable 1 }
	
	FdryTrapReceiverEntry ::= SEQUENCE {
		fdryTrapReceiverIndex
			Unsigned32,
		fdryTrapReceiverAddrType
			InetAddressType,
		fdryTrapReceiverAddr
			InetAddress,
		fdryTrapReceiverCommunityOrSecurityName
			OCTET STRING,
		fdryTrapReceiverUDPPort
			Integer32,
		fdryTrapReceiverSecurityModel
			SecurityModel,
		fdryTrapReceiverSecurityLevel
			SecurityLevel,
		fdryTrapReceiverRowStatus
			RowStatus
		}
	
	fdryTrapReceiverIndex OBJECT-TYPE
		SYNTAX  Unsigned32
		MAX-ACCESS  not-accessible
		STATUS  current
		DESCRIPTION
		"The index to the Trap Receiver Table."
		::= { fdryTrapReceiverEntry 1 }
	
	fdryTrapReceiverAddrType 			 OBJECT-TYPE
		SYNTAX  InetAddressType
		MAX-ACCESS  read-create
		STATUS  current
		DESCRIPTION
			  "Trap Receiver IP address Type. Supported address types are ipv4(1) and ipv6(2)"
		DEFVAL	{ ipv4 }
		::= { fdryTrapReceiverEntry 2 }
	
	fdryTrapReceiverAddr 			 OBJECT-TYPE
		SYNTAX  InetAddress
		MAX-ACCESS  read-create
		STATUS  current
		DESCRIPTION
			  "Trap Receiver IP address."
		::= { fdryTrapReceiverEntry 3 }
	
	fdryTrapReceiverCommunityOrSecurityName OBJECT-TYPE
		SYNTAX	OCTET STRING (SIZE(0..32))
		MAX-ACCESS	read-create
		STATUS	current
		DESCRIPTION
			"Community string to use. In case of USM (SNMPv3) security model,
			this object is used to provide the security name."
		::= { fdryTrapReceiverEntry 4 }
	
	fdryTrapReceiverUDPPort		 OBJECT-TYPE
		SYNTAX	Integer32  (0..65535)
		MAX-ACCESS	read-create
		STATUS	current
		DESCRIPTION
			"UDP port number of the trap receiver."
		DEFVAL { 162 }
		::= { fdryTrapReceiverEntry 5 }
	
	fdryTrapReceiverSecurityModel	   OBJECT-TYPE
		SYNTAX	SecurityModel
		MAX-ACCESS	read-create
		STATUS	current
		DESCRIPTION
			"Version of trap format to be used."
		DEFVAL { v1 }
		::= { fdryTrapReceiverEntry 6 }
	
	fdryTrapReceiverSecurityLevel	   OBJECT-TYPE
		SYNTAX	SecurityLevel
		MAX-ACCESS	read-create
		STATUS	current
		DESCRIPTION
			"Used for USM (SNMPv3) security model to specify the level of security.
			The security name is provided by fdryTrapReceiverCommunityOrSecurityName."
		DEFVAL { noAuth }
		::= { fdryTrapReceiverEntry 7 }

	fdryTrapReceiverRowStatus    OBJECT-TYPE
		SYNTAX	RowStatus
		MAX-ACCESS	read-create
		STATUS	current
		DESCRIPTION
			"This variable is used to create, modify, or
			delete a row in this table. When a row in this
			table is in active(1) state, no objects in that row
			can be modified except this object.
			 "
		::= { fdryTrapReceiverEntry 8 }

	
	END
--
-- FDRY-DNS2-MIB
--

FDRY-DNS2-MIB DEFINITIONS ::= BEGIN

IMPORTS
    MODULE-IDENTITY, Unsigned32,
    OBJECT-TYPE         FROM SNMPv2-SMI                 -- [RFC2578]
    DisplayString, RowStatus    
                        FROM SNMPv2-TC                  -- [RFC2579]
    InetAddressType, InetAddress        
                        FROM INET-ADDRESS-MIB           -- [RFC 4001]
    ;
   
fdryDns2MIB MODULE-IDENTITY
    LAST-UPDATED "200901300000Z"  -- 30 January 2009
    ORGANIZATION "Foundry Networks, Inc."
    CONTACT-INFO
            "Technical Support Center, Foundry Networks,
             4980 Great America Parkway,
             Santa Clara, CA 95054
             Email: support@foundrynet.com
             Phone: 1-877-TURBO-CALL"
    DESCRIPTION
            "The Foundry proprietary MIB module for Domain Name Service(DNS)
             It has new IPv4/IPv6 combined tables for Domain Name Service Address List and Name configuration.

             Copyright 1996-2008 Foundry Networks, Inc.
             All rights reserved.
             This Foundry Networks SNMP Management Information Base Specification
             embodies Foundry Networks' confidential and proprietary
             intellectual property. Foundry Networks retains all
             title and ownership in the Specification, including any
             revisions.

             This Specification is supplied AS IS, and Foundry Networks makes
             no warranty, either express or implied, as to the use,
             operation, condition, or performance of the Specification."
   
	REVISION 	"200901300000Z"  -- 30 Jan 2009
    DESCRIPTION "Initial version, obsoletes the earlier mib groups to resolve the mib conflicts.
    			fdryDns2MIB obsoletes fdryDnsMIB,
				fdryDns2DomainName obsoletes fdryDnsDomainName,
				fdryDnsServer obsoletes fdryDnsServerAddress"
         
    ::= { iso(1) org(3) dod(6) internet(1) private(4) enterprises(1) foundry(1991) products(1) switch(1) snSwitch(3) 34 }

    --
    -- Top level components of this MIB.
    --

    fdryDns2DomainName      OBJECT IDENTIFIER ::= { fdryDns2MIB 1 }
    fdryDnsServer           OBJECT IDENTIFIER ::= { fdryDns2MIB 2 }

    --
    -- Ipv4/Ipv6  mib table for Domain Name Service (DNS) Domain Name
    --

    fdryDns2DomainNameTable      OBJECT-TYPE
        SYNTAX  SEQUENCE OF FdryDns2DomainNameEntry
        MAX-ACCESS  not-accessible
        STATUS  current
        DESCRIPTION
            "Domain Name Service domain name table."
        ::= { fdryDns2DomainName 1 }
    
    fdryDns2DomainNameEntry      OBJECT-TYPE
        SYNTAX  FdryDns2DomainNameEntry
        MAX-ACCESS  not-accessible
        STATUS  current
        DESCRIPTION
            "An entry in the DNS domain name table."
        INDEX   { fdryDns2DomainNameIndex }
        ::= { fdryDns2DomainNameTable 1 }
    
    FdryDns2DomainNameEntry ::= SEQUENCE {
        fdryDns2DomainNameIndex         Unsigned32,
        fdryDns2DomainNameAddrType      InetAddressType,
        fdryDns2DomainNameName          DisplayString,
        fdryDns2DomainNameRowStatus     RowStatus
        }
    
    fdryDns2DomainNameIndex OBJECT-TYPE
        SYNTAX  Unsigned32
        MAX-ACCESS  not-accessible
        STATUS  current
        DESCRIPTION
            "The index to the DNS name table."
        ::= { fdryDns2DomainNameEntry 1 }
    
    fdryDns2DomainNameAddrType           OBJECT-TYPE
        SYNTAX  InetAddressType
        MAX-ACCESS  read-create
        STATUS  current
        DESCRIPTION
              "DNS IP address Type. Supported address types are ipv4(1) and ipv6(2)"
        DEFVAL  { ipv4 }
        ::= { fdryDns2DomainNameEntry 2 }
    
    fdryDns2DomainNameName OBJECT-TYPE
        SYNTAX  DisplayString (SIZE(0..64))
        MAX-ACCESS  read-create
        STATUS  current
        DESCRIPTION
            "Domain Name Service Domain Name string."
        ::= { fdryDns2DomainNameEntry 3 }
    
    fdryDns2DomainNameRowStatus  OBJECT-TYPE
        SYNTAX  RowStatus
        MAX-ACCESS  read-create
        STATUS  current
        DESCRIPTION
            "This variable is used to create, modify, or
             delete a row in this table. When a row in this
             table is in active(1) state, no objects in that row
             can be modified except this object."
        ::= { fdryDns2DomainNameEntry 4 }

    --
    -- IPv4/IPv6 MIB table for DNS servers
    --

    fdryDnsServerTable       OBJECT-TYPE
        SYNTAX      SEQUENCE OF FdryDnsServerEntry
        MAX-ACCESS  not-accessible
        STATUS      current
        DESCRIPTION
            "DNS server table, listing the Ipv4/Ipv6 DNS server addresses"
        ::= { fdryDnsServer 1 }
    
    fdryDnsServerEntry       OBJECT-TYPE
        SYNTAX      FdryDnsServerEntry
        MAX-ACCESS  not-accessible
        STATUS      current
        DESCRIPTION
            "An entry in the DNS server table."

        INDEX   {fdryDnsServerAddrType, fdryDnsServerIndex}
        ::= { fdryDnsServerTable 1 }
    
    FdryDnsServerEntry ::= SEQUENCE {
        fdryDnsServerAddrType
            InetAddressType,
        fdryDnsServerIndex
            Unsigned32,
        fdryDnsServerAddr
            InetAddress,
        fdryDnsServerRowStatus
            RowStatus
        }
    fdryDnsServerAddrType OBJECT-TYPE
        SYNTAX      InetAddressType
        MAX-ACCESS  not-accessible
        STATUS      current
        DESCRIPTION
              "The index to the DNS server table. DNS server IP address type. Supported address types are ipv4(1) and ipv6(2)"
        DEFVAL  { ipv4 }
        ::= { fdryDnsServerEntry 1 }

    fdryDnsServerIndex OBJECT-TYPE
        SYNTAX      Unsigned32
        MAX-ACCESS  not-accessible
        STATUS      current
        DESCRIPTION
            "The index to the DNS server table.  Currently, up to 4 DNS server
             entries each are supported for IPv4 and IPv6."
        ::= { fdryDnsServerEntry 2 }
    
    fdryDnsServerAddr OBJECT-TYPE
        SYNTAX      InetAddress
        MAX-ACCESS  read-create
        STATUS      current
        DESCRIPTION
              "DNS server IP address."
        ::= { fdryDnsServerEntry 3 }
    
    fdryDnsServerRowStatus OBJECT-TYPE
        SYNTAX      RowStatus
        MAX-ACCESS  read-create
        STATUS      current
        DESCRIPTION
            "This variable is used to create, modify, or
             delete a row in this table. When a row in this
             table is in active(1) state, no objects in that row
             can be modified except this object."
        ::= { fdryDnsServerEntry 4 }

END
FDRY-POE-MIB DEFINITIONS ::= BEGIN

IMPORTS
	MODULE-IDENTITY, OBJECT-TYPE, 
			Integer32, Unsigned32	   	FROM SNMPv2-SMI	  			-- [RFC2578]
	DisplayString		 				FROM SNMPv2-TC 		 		-- [RFC2579]
	InterfaceIndex						FROM IF-MIB
	snAgentSys	 						FROM FOUNDRY-SN-ROOT-MIB
	;
   
snAgentPoe MODULE-IDENTITY
	LAST-UPDATED "200909300000Z" -- September 30, 2009
	ORGANIZATION "Foundry Networks, Inc."
	CONTACT-INFO
			"Technical Support Center, Foundry Networks,
			4980 Great America Parkway,
			Santa Clara, CA 95054
			Email: support@foundrynet.com
			Phone: 1-877-TURBO-CALL"
	DESCRIPTION
			"The Foundry proprietary MIB module for Power Over Ethernet(PoE)
			It has PoE port and module configuring information.
			
			Copyright 1996-2008 Foundry Networks, Inc.
			All rights reserved.
			This Foundry Networks SNMP Management Information Base Specification
			embodies Foundry Networks confidential and proprietary
			intellectual property. Foundry Networks retains all
			title and ownership in the Specification, including any
			revisions.
			
			This Specification is supplied AS IS, and Foundry Networks makes
			no warranty, either express or implied, as to the use,
			operation, condition, or performance of the Specification.
			"
   
	REVISION     "200909300000Z" -- September 30, 2009
	DESCRIPTION	"Changed INTEGER to Integer32"
	REVISION 	"200904030000Z"  -- 3 April 2009
	DESCRIPTION	"Initial version, snAgentPoePortTable which was in SNMPv1 written in SNMPv2-SMI."
		  
 ::= { snAgentSys 14 }

-- Power Over Ethernet MIB Group

snAgentPoeGbl  OBJECT IDENTIFIER ::= { snAgentPoe 1 }
snAgentPoePort OBJECT IDENTIFIER ::= { snAgentPoe 2 }
snAgentPoeModule OBJECT IDENTIFIER ::= { snAgentPoe 3 }
snAgentPoeUnit OBJECT IDENTIFIER ::= { snAgentPoe 4 }


-- Power Over Ethernet Global Objects

snAgentPoeGblPowerCapacityTotal  OBJECT-TYPE
	SYNTAX Unsigned32
	MAX-ACCESS	read-only
	STATUS	current
	DESCRIPTION
		"This object shows the total inline power capacity available in the device, measured in mWatts. "
	::= { snAgentPoeGbl 1 }

snAgentPoeGblPowerCapacityFree  OBJECT-TYPE
	SYNTAX Unsigned32
	MAX-ACCESS	read-only
	STATUS	current
	DESCRIPTION
		"This object shows the inline power capacity currently available in the device which is unallocated, measured in mWatts."
	::= { snAgentPoeGbl 2 }

snAgentPoeGblPowerAllocationsRequestsHonored   OBJECT-TYPE
	SYNTAX Unsigned32
	MAX-ACCESS	read-only
	STATUS	current
	DESCRIPTION
		"This object shows number of times the inline power allocations requests honored."
	::= { snAgentPoeGbl 3}


-- Power Over Ethernet Port Table

snAgentPoePortTable       OBJECT-TYPE
	SYNTAX	SEQUENCE OF SnAgentPoePortEntry
	MAX-ACCESS	not-accessible
	STATUS	current
	DESCRIPTION
		"A table of POE port information."
	::= { snAgentPoePort 2 }

snAgentPoePortEntry       OBJECT-TYPE
	SYNTAX	SnAgentPoePortEntry
	MAX-ACCESS	not-accessible
	STATUS	current
	DESCRIPTION
		"A row in the POE port table."
	INDEX	{ snAgentPoePortNumber }
	::= { snAgentPoePortTable 1 }

SnAgentPoePortEntry ::= SEQUENCE {
	snAgentPoePortNumber
		InterfaceIndex,
	snAgentPoePortControl
		INTEGER,
	snAgentPoePortWattage
		Integer32,
	snAgentPoePortClass
		Integer32,
	snAgentPoePortPriority
		INTEGER,
	snAgentPoePortConsumed
		Integer32,
	snAgentPoePortType
		DisplayString
	}

snAgentPoePortNumber OBJECT-TYPE
    SYNTAX  InterfaceIndex
	MAX-ACCESS	read-only
	STATUS	current
	DESCRIPTION
		"The port number in ifIndex value."
	::= { snAgentPoePortEntry 1 }

snAgentPoePortControl OBJECT-TYPE
	SYNTAX	INTEGER {
              other(1),
              disable(2),
              enable(3),
              enableLegacyDevice(4)
            }
	MAX-ACCESS  read-create
	STATUS	current
	DESCRIPTION
		"Control inline power on/off to a port. If a port does not
		have inline power capability, reading this object returns
		'other(1)'."
	::= { snAgentPoePortEntry 2 }

snAgentPoePortWattage OBJECT-TYPE
	SYNTAX	Integer32
	MAX-ACCESS  read-create
	STATUS	current
    DESCRIPTION
		"Adjust the inline power wattage. Valid value between 1000
		to 15400(IEEE802_3AF)/30000(IEEE802_3AT). Each unit is milliwatts. This object can only be
		set after snSwIfInLinePowerControl has been set to 'enable(3)'
		or 'enableLegacyDevice(4)'. If a port does not have inline
		power capability, reading this object returns undefined value."
    ::= { snAgentPoePortEntry 3 }

snAgentPoePortClass OBJECT-TYPE
	SYNTAX	Integer32
	MAX-ACCESS  read-create
	STATUS	current
    DESCRIPTION
		"Adjust the inline power class. Valid value between 0 to 3(IEEE802_3AF)/4(IEEE802_3AT).
		This object can only be set after snSwIfInLinePowerControl
		has been set to 'enable(3)' or 'enableLegacyDevice(4)'. If
		a port does not have inline power capability, reading this
		object returns undefined value."
    ::= { snAgentPoePortEntry 4 }

snAgentPoePortPriority OBJECT-TYPE
	SYNTAX	INTEGER	{
              invalid(0),
              critical(1),
              high(2),
              low(3),
              medium(4),
              other(5)
            }
	MAX-ACCESS  read-create
	STATUS	current
	DESCRIPTION
		"Inline power allocation priority for the power device
		 0- Not a POE port, 1- Critical, 2- High, 3- Low,
		 4- Medium, 5- other."
	::= { snAgentPoePortEntry 5 }

snAgentPoePortConsumed OBJECT-TYPE
	SYNTAX	Integer32
	MAX-ACCESS	read-only
	STATUS	current
	DESCRIPTION
		"Inline power consumed by the port. Each unit is milliwatts."
	::= { snAgentPoePortEntry 6 }

snAgentPoePortType OBJECT-TYPE
	SYNTAX	DisplayString
	MAX-ACCESS	read-only
	STATUS	current
	DESCRIPTION
		"Inline Power device type	802.3af, 802.3at or Legacy device."
	::= { snAgentPoePortEntry 7 }

-- Power Over Module Table

snAgentPoeModuleTable       OBJECT-TYPE
	SYNTAX	SEQUENCE OF SnAgentPoeModuleEntry
	MAX-ACCESS	not-accessible
	STATUS	current
	DESCRIPTION
		"A table of POE Module configuration."
	::= { snAgentPoeModule 1 }

snAgentPoeModuleEntry       OBJECT-TYPE
	SYNTAX	SnAgentPoeModuleEntry
	MAX-ACCESS	not-accessible
	STATUS	current
	DESCRIPTION
		"A row in the POE Module table."
	INDEX	{ snAgentPoeModuleNumber }
	::= { snAgentPoeModuleTable 1 }

SnAgentPoeModuleEntry ::= SEQUENCE {
	snAgentPoeModuleNumber
		Unsigned32,
	snAgentPoeModuleBudget
		Unsigned32,
	snAgentPoeModuleMaxPDTypeSupport
		INTEGER
	}

snAgentPoeModuleNumber OBJECT-TYPE
    SYNTAX  Unsigned32
	MAX-ACCESS	read-only
	STATUS	current
	DESCRIPTION
		"This objects talks about POE module number."
	::= { snAgentPoeModuleEntry 1 }

snAgentPoeModuleBudget OBJECT-TYPE
	SYNTAX	Unsigned32
	MAX-ACCESS  read-create
	STATUS	current
    DESCRIPTION
		"This objects talks about module power budget in watts."
    ::= { snAgentPoeModuleEntry 2 }

snAgentPoeModuleMaxPDTypeSupport  OBJECT-TYPE
	SYNTAX	INTEGER	{
              ieee802dot3af(0),
              ieee802dot3at(1)
            }
	MAX-ACCESS  read-only
	STATUS	current
    DESCRIPTION
		"This object talks about the POE module type which is capable to support Power Device (PD) type 
		ieee802.3af or ieee802.3at(also called POE plus)type. Module which support ieee802.3at can also
		support ieee802.3af but reverse is not true."

    ::= { snAgentPoeModuleEntry 3 }



-- Power Over Unit Table (stacking system)

snAgentPoeUnitTable       OBJECT-TYPE
	SYNTAX	SEQUENCE OF SnAgentPoeUnitEntry
	MAX-ACCESS	not-accessible
	STATUS	current
	DESCRIPTION
		"A table of POE informaion for each unit. Only the unit 
		that has POE capability appears in a table row"
	::= { snAgentPoeUnit 1 }

snAgentPoeUnitEntry       OBJECT-TYPE
	SYNTAX	SnAgentPoeUnitEntry
	MAX-ACCESS	not-accessible
	STATUS	current
	DESCRIPTION
		"A row in the POE Unit table."
	INDEX	{ snAgentPoeUnitIndex }
	::= { snAgentPoeUnitTable 1 }

SnAgentPoeUnitEntry ::= SEQUENCE {
	snAgentPoeUnitIndex
		Unsigned32,
	snAgentPoeUnitPowerCapacityTotal
		Unsigned32,
	snAgentPoeUnitPowerCapacityFree
		Unsigned32,
	snAgentPoeUnitPowerAllocationsRequestsHonored
		Unsigned32
	}

snAgentPoeUnitIndex OBJECT-TYPE
    SYNTAX  Unsigned32
	MAX-ACCESS	read-only
	STATUS	current
	DESCRIPTION
		"The Index to POE unit Table."
	::= { snAgentPoeUnitEntry 1 }

snAgentPoeUnitPowerCapacityTotal  OBJECT-TYPE
	SYNTAX Unsigned32
	MAX-ACCESS	read-only
	STATUS	current
	DESCRIPTION
		"This object shows the total inline power capacity available on that unit (device), measured in mWatts. "
	::= { snAgentPoeUnitEntry 2 }

snAgentPoeUnitPowerCapacityFree  OBJECT-TYPE
	SYNTAX Unsigned32
	MAX-ACCESS	read-only
	STATUS	current
	DESCRIPTION
		"This object shows the inline power capacity currently available on that unit (device) which is unallocated, measured in mWatts."
	::= { snAgentPoeUnitEntry 3 }

snAgentPoeUnitPowerAllocationsRequestsHonored   OBJECT-TYPE
	SYNTAX Unsigned32
	MAX-ACCESS	read-only
	STATUS	current
	DESCRIPTION
		"This object shows number of times the inline power allocations requests honored on that unit (device)."
	::= { snAgentPoeUnitEntry 4}
 
END

FDRY-DAI-MIB DEFINITIONS ::= BEGIN

IMPORTS
	MODULE-IDENTITY, OBJECT-TYPE, Unsigned32, IpAddress
	   FROM SNMPv2-SMI
	snSwitch
	   FROM FOUNDRY-SN-SWITCH-GROUP-MIB
	MacAddress, TruthValue, RowStatus, TEXTUAL-CONVENTION
	   FROM SNMPv2-TC
	VlanIndex
	   FROM Q-BRIDGE-MIB
	DisplayString
	   FROM FOUNDRY-SN-AGENT-MIB
	ifIndex
	   FROM IF-MIB;
	  
fdryDaiMIB MODULE-IDENTITY
	LAST-UPDATED "201007260000Z" -- July 26, 2010
	ORGANIZATION "Brocade Communications Systems, Inc."
	CONTACT-INFO
		"Technical Support Center
              130 Holger Way,
              San Jose, CA  95134
              Email:  ipsupport@brocade.com
              Phone: 1-800-752-8061
              URL:  www.brocade.com"
	DESCRIPTION
		"Management Information for configuration of Dynamic ARP Inspection feature. 
		Dynamic ARP Inspection is a security mechanism which validates all ARP packets
		in a subnet and discard those packets with invalid IP to MAC address bindings.
			
		Copyright 1996-2010 Brocade Communications Systems, Inc.  
  		All rights reserved.
  		This Brocade Communications Systems SNMP Management Information Base Specification
 		embodies Brocade Communications Systems' confidential and proprietary
 		intellectual property. Brocade Communications Systems retains all
  		title and ownership in the Specification, including any revisions.
                                                
 		This Specification is supplied AS IS, and Brocade Communications Systems makes
 		no warranty, either express or implied, as to the use,
 		operation, condition, or performance of the specification, and any unintended 
 		consequence it may on the user environment."
 		
 	REVISION        "201007260000Z" -- July 26, 2010
 	DESCRIPTION  
 		"Changed the ORGANIZATION, CONTACT-INFO and DESCRIPTION fields."
 	
	REVISION     "201002220000Z" -- February 22, 2010
	DESCRIPTION
		""
   ::= { snSwitch 35}

--
-- Textual Conventions
--

ArpType ::= TEXTUAL-CONVENTION
	STATUS	  current
	DESCRIPTION
		"Represents type of ARP entry to be used."
	SYNTAX	INTEGER{
		other(1),
		static(2),
		dynamic(3),
		inspect(4),
		dhcp(5),
		dynamicDhcp(6),
		staticDhcp(7),
		host(8)
		}
		
ArpState ::= TEXTUAL-CONVENTION
	STATUS	  current
	DESCRIPTION
		"Represents state of ARP entry to be used."
	SYNTAX	INTEGER{
		other(1),
		valid(2),
		pend(3)
		}

fdryDaiVlan  OBJECT IDENTIFIER ::= { fdryDaiMIB 1 }
fdryDaiInterface  OBJECT IDENTIFIER ::= { fdryDaiMIB 2 }
fdryDaiArpInspect OBJECT IDENTIFIER ::= { fdryDaiMIB 3 }

--
-- Dynamic ARP Inspection VLAN configuration table
--

fdryDaiVlanConfigTable OBJECT-TYPE
	SYNTAX SEQUENCE OF FdryDaiVlanConfigEntry
	MAX-ACCESS not-accessible
	STATUS current
	DESCRIPTION
		"A table provides the mechanism to control Dynamic ARP
		Inspection per VLAN. When a VLAN is created in a device
		supporting this table, a corresponding entry of this table
		will be added."
	::= { fdryDaiVlan 1 }

fdryDaiVlanConfigEntry OBJECT-TYPE
	SYNTAX FdryDaiVlanConfigEntry
	MAX-ACCESS not-accessible
	STATUS current
	DESCRIPTION
		"A row instance contains the configuration to enable
		or disable Dynamic ARP Inspection at the existing VLAN."
	INDEX { fdryDaiVlanVLanId }
	::= { fdryDaiVlanConfigTable 1 }

FdryDaiVlanConfigEntry ::= SEQUENCE {
	fdryDaiVlanVLanId 
		VlanIndex,
	fdryDaiVlanDynArpInspEnable 
		TruthValue
	}

fdryDaiVlanVLanId  OBJECT-TYPE
	SYNTAX		VlanIndex
	MAX-ACCESS	not-accessible
	STATUS 		current
	DESCRIPTION
		"This object indicates the VLAN number on which Dynamic ARP
		Inspection feature is configured."
	::= { fdryDaiVlanConfigEntry 1 }

fdryDaiVlanDynArpInspEnable	 OBJECT-TYPE
	SYNTAX 		TruthValue
	MAX-ACCESS 	read-write
	STATUS 		current
	DESCRIPTION
		"This object indicates whether Dynamic ARP Inspection is
		enabled in this VLAN.
		If this object is set to 'true', Dynamic ARP Inspection is enabled.
		If this object is set to 'false', Dynamic ARP Inspection is disabled."
	::= { fdryDaiVlanConfigEntry 2 }

--
-- Dynamic ARP Inspection Interface configuration table
--

fdryDaiIfConfigTable OBJECT-TYPE
	SYNTAX SEQUENCE OF FdryDaiIfConfigEntry
	MAX-ACCESS not-accessible
	STATUS current
	DESCRIPTION
		"A table provides the mechanism to configure the trust
		state for Dynamic ARP Inspection purpose at each physical
		interface."
	::= { fdryDaiInterface 1 }

fdryDaiIfConfigEntry OBJECT-TYPE
	SYNTAX FdryDaiIfConfigEntry
	MAX-ACCESS not-accessible
	STATUS current
	DESCRIPTION
		"A row instance contains the configuration to enable or
		disable trust state for Dynamic ARP Inspection at each
		physical interface capable of this feature."
	INDEX { ifIndex }
	::= { fdryDaiIfConfigTable 1 }

FdryDaiIfConfigEntry ::= SEQUENCE {
	fdryDaiIfTrustValue 
		TruthValue
	}

fdryDaiIfTrustValue  OBJECT-TYPE
	SYNTAX		TruthValue
	MAX-ACCESS	read-write
	STATUS		current
	DESCRIPTION
		"This object indicates whether the interface is trusted for
		Dynamic ARP Inspection.
		If this object is set to 'true', the interface is trusted.
		ARP packets coming to this interface will be forwarded
		without checking.
		If this object is set to 'false', the interface is not trusted. 
		ARP packets received on this interface will be subjected 
		to ARP inspection."
	::= { fdryDaiIfConfigEntry 1 }

--
-- Dynamic ARP Inspection entry table
-- Use this table to configure and display the inspection ARP entries
--

fdryDaiArpInspectTable OBJECT-TYPE
	SYNTAX SEQUENCE OF FdryDaiArpInspectEntry
	MAX-ACCESS not-accessible
	STATUS current
	DESCRIPTION
		"A table provides the mechanism to control Dynamic ARP
		Inspection entries. When an IP-MAC mapping entry is created 
		in a device supporting this table, a corresponding entry of this 
		table will be added."
	::= { fdryDaiArpInspect 1 }

fdryDaiArpInspectEntry OBJECT-TYPE
	SYNTAX FdryDaiArpInspectEntry
	MAX-ACCESS not-accessible
	STATUS current
	DESCRIPTION
		"A row instance contains the configuration to map a device
		IP address with its MAC address."
	INDEX { fdryDaiArpInspectIpAddr }
	::= { fdryDaiArpInspectTable 1 }

FdryDaiArpInspectEntry ::= SEQUENCE {
	fdryDaiArpInspectIpAddr 
		IpAddress,
	fdryDaiArpInspectMacAddr 
		MacAddress,
	fdryDaiArpInspectRowStatus 
		RowStatus,
	fdryDaiArpInspectType
		ArpType,
	fdryDaiArpInspectState
		ArpState,
	fdryDaiArpInspectAge
		Unsigned32,
	fdryDaiArpInspectPort
		DisplayString
	}
	
fdryDaiArpInspectIpAddr  OBJECT-TYPE
	SYNTAX		IpAddress
	MAX-ACCESS	not-accessible
	STATUS		current
	DESCRIPTION
		"The device IP address."
	::= { fdryDaiArpInspectEntry 1}

fdryDaiArpInspectMacAddr  OBJECT-TYPE
	SYNTAX		MacAddress
	MAX-ACCESS	read-create
	STATUS		current
	DESCRIPTION
		"The device MAC address."
	::= { fdryDaiArpInspectEntry 2 }
	
fdryDaiArpInspectRowStatus  OBJECT-TYPE
 	SYNTAX  RowStatus
 	MAX-ACCESS  read-create
 	STATUS  current
 	DESCRIPTION
 		"This variable is used to create, or
 		delete a row in this table. When a row in this
 		table is in active(1) state, no objects in that row
 		can be modified except this object."
 	::= { fdryDaiArpInspectEntry 3 }

fdryDaiArpInspectType OBJECT-TYPE
	SYNTAX     ArpType
	MAX-ACCESS read-only
	STATUS     current
	DESCRIPTION
		"The type of the ARP entry"
	::= { fdryDaiArpInspectEntry 4 }

fdryDaiArpInspectState OBJECT-TYPE
	SYNTAX     ArpState
	MAX-ACCESS read-only
	STATUS     current
	DESCRIPTION
		"The state of the ARP entry"
	::= { fdryDaiArpInspectEntry 5 }

fdryDaiArpInspectAge OBJECT-TYPE
	SYNTAX    Unsigned32
	MAX-ACCESS read-only
	STATUS     current
	DESCRIPTION
		"The timer of the ARP entry"
	::= { fdryDaiArpInspectEntry 6 }

fdryDaiArpInspectPort OBJECT-TYPE
	SYNTAX    DisplayString
	MAX-ACCESS read-only
	STATUS     current
	DESCRIPTION
		"The port of the ARP entry"
	::= { fdryDaiArpInspectEntry 7 }

   END

FDRY-DHCP-SNOOPING-MIB DEFINITIONS ::= BEGIN

IMPORTS
	MODULE-IDENTITY, OBJECT-TYPE, Unsigned32, IpAddress
	   FROM SNMPv2-SMI
	snSwitch
	   FROM FOUNDRY-SN-SWITCH-GROUP-MIB
	ArpType, ArpState
	   FROM FDRY-DAI-MIB
	MacAddress, TruthValue, TEXTUAL-CONVENTION
	   FROM SNMPv2-TC
	VlanIndex
	   FROM Q-BRIDGE-MIB
	DisplayString
	   FROM FOUNDRY-SN-AGENT-MIB
	ifIndex
	   FROM IF-MIB;
	  
fdryDhcpSnoopMIB MODULE-IDENTITY
	LAST-UPDATED "201007260000Z" -- July 26, 2010
	ORGANIZATION "Brocade Communications Systems, Inc."
	CONTACT-INFO
		"Technical Support Center
              130 Holger Way,
              San Jose, CA  95134
              Email:  ipsupport@brocade.com
              Phone: 1-800-752-8061
              URL:  www.brocade.com"
	DESCRIPTION
		"Management Information for configuration of DHCP Snooping feature. 
		DHCP Snooping  is a security feature which enables the device to filter
		untrusted DHCP packets in a subnet. It can also stop unauthorized DHCP 
		serves and prevent errors due to user mis-configuration servers.
			
		Copyright 1996-2010 Brocade Communications Systems, Inc.  
  		All rights reserved.
  		This Brocade Communications Systems SNMP Management Information Base Specification
 		embodies Brocade Communications Systems' confidential and proprietary
 		intellectual property. Brocade Communications Systems retains all
  		title and ownership in the Specification, including any revisions.
                                                
 		This Specification is supplied AS IS, and Brocade Communications Systems makes
 		no warranty, either express or implied, as to the use,
 		operation, condition, or performance of the specification, and any unintended 
 		consequence it may on the user environment."
 		
 	REVISION        "201007260000Z" -- July 26, 2010
 	DESCRIPTION  
 		"Changed the ORGANIZATION, CONTACT-INFO and DESCRIPTION fields."
 		
	REVISION     "201003220000Z" -- March 22, 2010
	DESCRIPTION
		""
   ::= { snSwitch 36}

--
-- Textual Conventions
--

ClearAction ::= TEXTUAL-CONVENTION
	STATUS	  current
	DESCRIPTION
		"Represents action of Clear operation to be used."
	SYNTAX	INTEGER{
		valid(0),
		clear(1)
		}

fdryDhcpSnoopGlobalObjects  OBJECT IDENTIFIER ::= { fdryDhcpSnoopMIB 1 }
fdryDhcpSnoopVlan  OBJECT IDENTIFIER ::= { fdryDhcpSnoopMIB 2 }
fdryDhcpSnoopInterface  OBJECT IDENTIFIER ::= { fdryDhcpSnoopMIB 3 }
fdryDhcpSnoopBind OBJECT IDENTIFIER ::= { fdryDhcpSnoopMIB 4 }

--
-- DHCP Snooping global Scalar Object
--

fdryDhcpSnoopGlobalClearOper OBJECT-TYPE
    SYNTAX     ClearAction
    MAX-ACCESS read-write
    STATUS     current
    DESCRIPTION
        "valid(0) - this value is always returned when the variable is read. 
         clear(1) - setting the variable to this value clears all entries in the 
         DHCP binding database."
    ::= { fdryDhcpSnoopGlobalObjects 1 }

--
-- DHCP Snooping VLAN configuration table
--

fdryDhcpSnoopVlanConfigTable OBJECT-TYPE
	SYNTAX SEQUENCE OF FdryDhcpSnoopVlanConfigEntry
	MAX-ACCESS not-accessible
	STATUS current
	DESCRIPTION
		"A table provides the mechanism to control DHCP Snooping
		per VLAN. When a VLAN is created in a device
		supporting this table, a corresponding entry of this table
		will be added."
	::= { fdryDhcpSnoopVlan 1 }

fdryDhcpSnoopVlanConfigEntry OBJECT-TYPE
	SYNTAX FdryDhcpSnoopVlanConfigEntry
	MAX-ACCESS not-accessible
	STATUS current
	DESCRIPTION
		"A row instance contains the configuration to enable
		or disable DHCP Snooping at the existing VLAN."
	INDEX { fdryDhcpSnoopVlanVLanId }
	::= { fdryDhcpSnoopVlanConfigTable 1 }

FdryDhcpSnoopVlanConfigEntry ::= SEQUENCE {
	fdryDhcpSnoopVlanVLanId 
		VlanIndex,
	fdryDhcpSnoopVlanDhcpSnoopEnable 
		TruthValue
	}

fdryDhcpSnoopVlanVLanId  OBJECT-TYPE
	SYNTAX		VlanIndex
	MAX-ACCESS	not-accessible
	STATUS 		current
	DESCRIPTION
		"This object indicates the VLAN number on which DHCP
		Snooping feature is configured."
	::= { fdryDhcpSnoopVlanConfigEntry 1 }

fdryDhcpSnoopVlanDhcpSnoopEnable	 OBJECT-TYPE
	SYNTAX 		TruthValue
	MAX-ACCESS 	read-write
	STATUS 		current
	DESCRIPTION
		"This object indicates whether DHCP Snooping is enabled in this VLAN.
		
		If this object is set to 'true', DHCP Snooping is enabled.
		If this object is set to 'false', DHCP Snooping is disabled."
	::= { fdryDhcpSnoopVlanConfigEntry 2 }

--
-- DHCP Snooping Interface configuration table
--

fdryDhcpSnoopIfConfigTable OBJECT-TYPE
	SYNTAX SEQUENCE OF FdryDhcpSnoopIfConfigEntry
	MAX-ACCESS not-accessible
	STATUS current
	DESCRIPTION
		"A table provides the mechanism to configure the trust
		state for DHCP Snooping purpose at each physical
		interface."
	::= { fdryDhcpSnoopInterface 1 }

fdryDhcpSnoopIfConfigEntry OBJECT-TYPE
	SYNTAX FdryDhcpSnoopIfConfigEntry
	MAX-ACCESS not-accessible
	STATUS current
	DESCRIPTION
		"A row instance contains the configuration to enable or
		disable trust state for DHCP Snooping at each
		physical interface capable of this feature."
	INDEX { ifIndex }
	::= { fdryDhcpSnoopIfConfigTable 1 }

FdryDhcpSnoopIfConfigEntry ::= SEQUENCE {
	fdryDhcpSnoopIfTrustValue 
		TruthValue
	}

fdryDhcpSnoopIfTrustValue  OBJECT-TYPE
	SYNTAX		TruthValue
	MAX-ACCESS	read-write
	STATUS		current
	DESCRIPTION
		"This object indicates whether the interface is trusted for
		DHCP Snooping.
		If this object is set to 'true', the interface is trusted.
		DHCP packets coming to this interface will be forwarded
		without checking.
		If this object is set to 'false', the interface is not trusted. 
		DHCP packets received on this interface will be subjected 
		to DHCP checks."
	::= { fdryDhcpSnoopIfConfigEntry 1 }

--
-- DHCP Snooping binding database table
-- Use this table to display DHCP Snooping entries
--

fdryDhcpSnoopBindTable OBJECT-TYPE
	SYNTAX SEQUENCE OF FdryDhcpSnoopBindEntry
	MAX-ACCESS not-accessible
	STATUS current
	DESCRIPTION
		"A table provides the information of DHCP snooping 
		binding database learnt by the device"
	::= { fdryDhcpSnoopBind 1 }

fdryDhcpSnoopBindEntry OBJECT-TYPE
	SYNTAX FdryDhcpSnoopBindEntry
	MAX-ACCESS not-accessible
	STATUS current
	DESCRIPTION
		"A row instance contains the information of DHCP snoonping entry."
	INDEX { fdryDhcpSnoopBindIpAddr }
	::= { fdryDhcpSnoopBindTable 1 }

FdryDhcpSnoopBindEntry ::= SEQUENCE {
	fdryDhcpSnoopBindIpAddr 
		IpAddress,
	fdryDhcpSnoopBindMacAddr 
		MacAddress,
	fdryDhcpSnoopBindType
		ArpType,
	fdryDhcpSnoopBindState
		ArpState,
	fdryDhcpSnoopBindPort
		DisplayString,
	fdryDhcpSnoopBindVlanId
		VlanIndex,
	fdryDhcpSnoopBindClearOper
		ClearAction
	}
	
fdryDhcpSnoopBindIpAddr  OBJECT-TYPE
	SYNTAX		IpAddress
	MAX-ACCESS	not-accessible
	STATUS		current
	DESCRIPTION
		"The device IP address."
	::= { fdryDhcpSnoopBindEntry 1}

fdryDhcpSnoopBindMacAddr  OBJECT-TYPE
	SYNTAX		MacAddress
	MAX-ACCESS	read-only
	STATUS		current
	DESCRIPTION
		"The device MAC address."
	::= { fdryDhcpSnoopBindEntry 2 }

fdryDhcpSnoopBindType OBJECT-TYPE
	SYNTAX     ArpType
	MAX-ACCESS read-only
	STATUS     current
	DESCRIPTION
		"The type of the ARP entry"
	::= { fdryDhcpSnoopBindEntry 3 }

fdryDhcpSnoopBindState OBJECT-TYPE
	SYNTAX    ArpState
	MAX-ACCESS read-only
	STATUS     current
	DESCRIPTION
		"The state of the ARP entry"
	::= { fdryDhcpSnoopBindEntry 4 }

fdryDhcpSnoopBindPort OBJECT-TYPE
	SYNTAX    DisplayString
	MAX-ACCESS read-only
	STATUS     current
	DESCRIPTION
		"The port of the ARP entry"
	::= { fdryDhcpSnoopBindEntry 5 }

fdryDhcpSnoopBindVlanId  OBJECT-TYPE
	SYNTAX		VlanIndex
	MAX-ACCESS	read-only
	STATUS 		current
	DESCRIPTION
		"This object indicates the VLAN number on which DHCP snooping
		feature is configured."
	::= { fdryDhcpSnoopBindEntry 6 }

fdryDhcpSnoopBindClearOper OBJECT-TYPE
	SYNTAX    ClearAction
	MAX-ACCESS read-write
	STATUS     current
	DESCRIPTION
		 "valid(0) - this value is always returned when the variable is read. 
         	clear(1) - setting the variable to this value clears this entry in the 
        	 DHCP binding database."
	::= {fdryDhcpSnoopBindEntry 7 }


   END

FDRY-IP-SOURCE-GUARD-MIB DEFINITIONS ::= BEGIN

IMPORTS
	MODULE-IDENTITY, OBJECT-TYPE, Unsigned32, IpAddress
	   FROM SNMPv2-SMI
	snSwitch
	   FROM FOUNDRY-SN-SWITCH-GROUP-MIB
	TruthValue, RowStatus, TEXTUAL-CONVENTION
	   FROM SNMPv2-TC
	VlanIndex
	   FROM Q-BRIDGE-MIB
	ifIndex, InterfaceIndex
	   FROM IF-MIB;
	  
fdryIpSrcGuardMIB MODULE-IDENTITY
	LAST-UPDATED "201007260000Z" -- July 26, 2010
	ORGANIZATION "Brocade Communications Systems, Inc."
	CONTACT-INFO
		"Technical Support Center
              130 Holger Way,
              San Jose, CA  95134
              Email:  ipsupport@brocade.com
              Phone: 1-800-752-8061
              URL:  www.brocade.com"
	DESCRIPTION
		"Management Information for configuration of IP Source Guard feature. 
		IP Source Guard is a security feature that restricts IP traffic on untrusted 
		ports by filtering traffic based on the DHCP snooping binding database or 
		manually configured IP source bindings.
			
		Copyright 1996-2010 Brocade Communications Systems, Inc.  
  		All rights reserved.
  		This Brocade Communications Systems SNMP Management Information Base Specification
 		embodies Brocade Communications Systems' confidential and proprietary
 		intellectual property. Brocade Communications Systems retains all
  		title and ownership in the Specification, including any revisions.
                                                
 		This Specification is supplied AS IS, and Brocade Communications Systems makes
 		no warranty, either express or implied, as to the use,
 		operation, condition, or performance of the specification, and any unintended 
 		consequence it may on the user environment."
 		
 	REVISION        "201007260000Z" -- July 26, 2010
 	DESCRIPTION  
 		"Changed the ORGANIZATION, CONTACT-INFO and DESCRIPTION fields."
 		
	REVISION     "201002220000Z" -- February 22, 2010
	DESCRIPTION
		""
   ::= { snSwitch 37}

BindMode ::= TEXTUAL-CONVENTION
	STATUS	  current
	DESCRIPTION
		"Represents mode of the IP Source Guard entry."
	SYNTAX     INTEGER {
		other(1),
		active(2),
		inactive(3)
		}

BindType ::= TEXTUAL-CONVENTION
	STATUS	  current
	DESCRIPTION
		"Represents type of the IP Source Guard entry."
	SYNTAX     INTEGER {
		other(1),
		ip(2)
		}
		
fdryIpSrcGuardInterface  OBJECT IDENTIFIER ::= { fdryIpSrcGuardMIB 1 }
fdryIpSrcGuardPortVlan OBJECT IDENTIFIER ::= { fdryIpSrcGuardMIB 2 }
fdryIpSrcGuardBind OBJECT IDENTIFIER ::= { fdryIpSrcGuardMIB 3 }

--
-- IP Source Guard Interface configuration table
--

fdryIpSrcGuardIfConfigTable OBJECT-TYPE
	SYNTAX SEQUENCE OF FdryIpSrcGuardIfConfigEntry
	MAX-ACCESS not-accessible
	STATUS current
	DESCRIPTION
		"A table provides the mechanism to configure enabling or disabling 
		IP Source Guard purpose at each physical interface."
	::= { fdryIpSrcGuardInterface 1 }

fdryIpSrcGuardIfConfigEntry OBJECT-TYPE
	SYNTAX FdryIpSrcGuardIfConfigEntry
	MAX-ACCESS not-accessible
	STATUS current
	DESCRIPTION
		"A row instance contains the configuration to enable or disable IP 
		Source Guard at each physical interface capable of this feature."
	INDEX { ifIndex }
	::= { fdryIpSrcGuardIfConfigTable 1 }

FdryIpSrcGuardIfConfigEntry ::= SEQUENCE {
	fdryIpSrcGuardIfEnable 
		TruthValue
	}

fdryIpSrcGuardIfEnable  OBJECT-TYPE
	SYNTAX		TruthValue
	MAX-ACCESS	read-write
	STATUS		current
	DESCRIPTION
		"This object indicates whether IP Source Guard is 
		enabled  at this interface.
		If this object is set to 'true', IP Source Guard is enabled.
		Traffic  coming to this interface will be forwarded. If it is 
		 from the list of IP addresses obtained from DHCP snooping.
		 Otherwise it is denied.
		If this object is set to 'false', IP Source Guard is disabled."
	::= { fdryIpSrcGuardIfConfigEntry 1 }

--
-- IP Source Guard per-port-per-VLAN configuration table
--

fdryIpSrcGuardPortVlanConfigTable OBJECT-TYPE
	SYNTAX SEQUENCE OF FdryIpSrcGuardPortVlanConfigEntry
	MAX-ACCESS not-accessible
	STATUS current
	DESCRIPTION
		"A table provides the mechanism to configure enabling or disabling 
		IP Source Guard purpose per port per VLAN."
	::= { fdryIpSrcGuardPortVlan 1 }

fdryIpSrcGuardPortVlanConfigEntry OBJECT-TYPE
	SYNTAX FdryIpSrcGuardPortVlanConfigEntry
	MAX-ACCESS not-accessible
	STATUS current
	DESCRIPTION
		"A row instance contains the configuration to enable or disable IP 
		Source Guard per port per VLAN of this feature."
	INDEX { fdryIpSrcGuardPortVlanPortId, fdryIpSrcGuardPortVlanVlanId }
	::= { fdryIpSrcGuardPortVlanConfigTable 1 }

FdryIpSrcGuardPortVlanConfigEntry ::= SEQUENCE {
	fdryIpSrcGuardPortVlanPortId
		InterfaceIndex,
	fdryIpSrcGuardPortVlanVlanId
		VlanIndex,
	fdryIpSrcGuardPortVlanEnable 
		TruthValue
	}

fdryIpSrcGuardPortVlanPortId OBJECT-TYPE
    SYNTAX     InterfaceIndex
    MAX-ACCESS not-accessible
    STATUS     current
    DESCRIPTION
        "The ifIndex of the port for IP Source Guard purpose per port per VLAN."
    ::= { fdryIpSrcGuardPortVlanConfigEntry 1 }

fdryIpSrcGuardPortVlanVlanId OBJECT-TYPE
    SYNTAX     VlanIndex
    MAX-ACCESS not-accessible
    STATUS     current
    DESCRIPTION
        "The number of VLAN for IP Source Guard purpose per port per VLAN."
    ::= { fdryIpSrcGuardPortVlanConfigEntry 2 }

fdryIpSrcGuardPortVlanEnable  OBJECT-TYPE
	SYNTAX		TruthValue
	MAX-ACCESS	read-write
	STATUS		current
	DESCRIPTION
		"This object indicates whether IP Source Guard is 
		enabled at this interface and this VLAN number.
		If this object is set to 'true', IP Source Guard per-port-per-VLAN is enabled.
		If this object is set to 'false', IP Source Guard per-port-per-VLAN is disabled."
	::= { fdryIpSrcGuardPortVlanConfigEntry 3 }

--
-- IP Source Guard binding table
-- Use this table to configure Ip source entries
--

fdryIpSrcGuardBindTable OBJECT-TYPE
	SYNTAX SEQUENCE OF FdryIpSrcGuardBindEntry
	MAX-ACCESS not-accessible
	STATUS current
	DESCRIPTION
		"A table provides the information of IP addresses used IP Source 
		Guard purpose at each physical interface with or without specific VLAN 
		memberships  "
	::= { fdryIpSrcGuardBind 1 }

fdryIpSrcGuardBindEntry OBJECT-TYPE
	SYNTAX FdryIpSrcGuardBindEntry
	MAX-ACCESS not-accessible
	STATUS current
	DESCRIPTION
		"A row instance contains IP address used for IP Source Guard purpose 
		at each physical interface with or without specific VLAN memberships ."
	INDEX { ifIndex, fdryIpSrcGuardBindIpAddr }
	::= { fdryIpSrcGuardBindTable 1 }

FdryIpSrcGuardBindEntry ::= SEQUENCE {
	fdryIpSrcGuardBindIpAddr 
		IpAddress,
	fdryIpSrcGuardBindVlanId
		Unsigned32,
	fdryIpSrcGuardBindRowStatus
		RowStatus,
	fdryIpSrcGuardBindMode
		BindMode,
	fdryIpSrcGuardBindType
		BindType
	}
	
fdryIpSrcGuardBindIpAddr  OBJECT-TYPE
	SYNTAX		IpAddress
	MAX-ACCESS	not-accessible
	STATUS		current
	DESCRIPTION
		"The device IP address."
	::= { fdryIpSrcGuardBindEntry 1}

fdryIpSrcGuardBindVlanId  OBJECT-TYPE
	SYNTAX		Unsigned32
	MAX-ACCESS	read-create
	STATUS 		current
	DESCRIPTION
		"This object indicates the specific VLAN memberships on this interface.
		The VLAN number is optional. If you configure a VLAN number, the bindings
		applies to that VLAN only. If you do not configure a VLAN number, the static 
		applies to all VLANs associated with the port. In this case, the VLAN number 
		will be displayed as 0."
	::= { fdryIpSrcGuardBindEntry 2 }

fdryIpSrcGuardBindRowStatus  OBJECT-TYPE
 	SYNTAX  RowStatus
 	MAX-ACCESS  read-create
 	STATUS  current
 	DESCRIPTION
 		"This variable is used to create, or
 		delete a row in this table. When a row in this
 		table is in active(1) state, no objects in that row
 		can be modified except this object."
 	::= { fdryIpSrcGuardBindEntry 3 }

fdryIpSrcGuardBindMode OBJECT-TYPE
	SYNTAX    BindMode 
	MAX-ACCESS read-only
	STATUS     current
	DESCRIPTION
		"The mode of the IP Source Guard entry"
	::= { fdryIpSrcGuardBindEntry 4 }

fdryIpSrcGuardBindType OBJECT-TYPE
	SYNTAX    BindType 
	MAX-ACCESS read-only
	STATUS     current
	DESCRIPTION
		"The type of the IP Source Guard entry"
	::= { fdryIpSrcGuardBindEntry 5 }

	
   END

FOUNDRY-SN-NOTIFICATION-MIB DEFINITIONS ::= BEGIN

IMPORTS
   MODULE-IDENTITY, NOTIFICATION-TYPE	FROM SNMPv2-SMI
   foundry				FROM FOUNDRY-SN-ROOT-MIB   
   ifIndex                          FROM IF-MIB
   dot3OamLoopbackStatus	FROM DOT3-OAM-MIB
   snVLanByPortCfgVLanId 		  FROM FOUNDRY-SN-SWITCH-GROUP-MIB
   snChasPwrSupplyStatus,
   snAgGblTrapMessage,
   snAgentBrdIndex,
   snAgentBrdModuleStatus,
   snChasPwrSupplyIndex,
   snChasPwrSupplyDescription,
   snChasUnitIndex,
   snChasFanIndex,
   snChasFanDescription   FROM FOUNDRY-SN-AGENT-MIB
   fdryLicenseType			FROM FOUNDRY-SN-AGENT-MIB
   snSwViolatorPortNumber,
   snSwViolatorMacAddress FROM FOUNDRY-SN-SWITCH-GROUP-MIB
   snL4TrapLinkName,
   snL4LinkVirtualInterface,
   snL4MaxSessionLimit,
   snL4TcpSynLimit,
   snL4TrapRealServerIP, 
   snL4TrapRealServerName,
   snL4TrapRealServerPort,
   snL4TrapRealServerCurConnections FROM FOUNDRY-SN-SW-L4-SWITCH-GROUP-MIB
   wgPnPStatus FROM FOUNDRY-SN-WIRELESS-GROUP-MIB
   snOspfRouterId,
   snOspfIfStatusIpAddress,
   snOspfIfStatusState,
   snOspfVirtIfStatusAreaID,
   snOspfVirtIfStatusNeighbor,
   snOspfVirtIfStatusState,
   snOspfNbrIpAddr,
   snOspfNbrRtrId,
   snOspfNbrState,
   snOspfVirtNbrArea,
   snOspfVirtNbrRtrId, 
   snOspfVirtNbrState, 
   snOspfPacketSrc,
   snOspfConfigErrorType,
   snOspfPacketType,
   snOspfLsdbAreaId,
   snOspfLsdbType,
   snOspfLsdbLsId,
   snOspfLsdbRouterId,
   snOspfExtLsdbLimit	  FROM FOUNDRY-SN-OSPF-GROUP-MIB
   snStackingGlobalMixedMode FROM FOUNDRY-SN-STACKING-MIB
   ;
   
snTraps MODULE-IDENTITY
	LAST-UPDATED "200909300000Z" -- September 30, 2009
	ORGANIZATION "Foundry Networks, Inc"
	CONTACT-INFO
			"
			Technical Support Center, Foundry Networks,
			4980 Great America Parkway,
			Santa Clara, CA 95054
			Email: support@foundrynet.com
			Phone: 1-877-TURBO-CALL
			"
	DESCRIPTION
			"
			The MIB module describes proprietery SNMP Trap information 
			of Foundry Networks' router/switch product.
			
			Copyright 1996-2008 Foundry Networks, Inc.
			All rights reserved.
			This Foundry Networks SNMP Management Information Base Specification
			embodies Foundry Networks' confidential and proprietary
			intellectual property. Foundry Networks retains all
			title and ownership in the Specification, including any
			revisions.
			
			This Specification is supplied AS IS, and Foundry Networks makes
			no warranty, either express or implied, as to the use,
			operation, condition, or performance of the Specification.			
			"            
	REVISION     "200909300000Z" -- September 30, 2009
	DESCRIPTION
			"convert from SMIv1 to SMIv2"                        
	::= { foundry 0 }			

-- Trap Information
-- Foundry Networks, Inc. Specific Traps

snTrapChasPwrSupply NOTIFICATION-TYPE
   OBJECTS { snChasPwrSupplyStatus }
   STATUS current
   DESCRIPTION
	   "The SNMP trap that is generated when a power supply fails
		to operate normally. The value is a packed bit string;
		the 2 power supplies status are encoded into 4 bits
		(a nibble). 
		The following shows the meaning of each bit:
		(bit 0 is the least significant bit).

		bit position   meaning
		------------   -------
		4-31	 reserved
		3		 Power  Supply 2 DC (0=bad, 1=good).
		2		 Power  Supply 1 DC (0=bad, 1=good).
		1		 Power  Supply 2 present status (0=present, 1=not-present).
		0		 Power  Supply 1 present status (0=present, 1=not-present)."
		--#TYPE "Foundry Trap: Power Supply Failure"
		--#SUMMARY "Power supply fails, error status %d."
		--#ARGUMENTS { 0 }
		--#SEVERITY MINOR
		--#STATE OPERATIONAL
   ::= { snTraps 1 }

snTrapLockedAddressViolation NOTIFICATION-TYPE
   OBJECTS { snSwViolatorPortNumber, snSwViolatorMacAddress }
   STATUS current
   DESCRIPTION
	   "The SNMP trap that is generated when more source MAC addresses
		are received from a port than the maximum number of addresses
		configured to that port."
		--#TYPE "Foundry Trap: MAC Addresses Violation"
		--#SUMMARY "Lock address violation on Port %d with MAC Address %s."
		--#ARGUMENTS { 0, 1 }
		--#SEVERITY MINOR
		--#STATE OPERATIONAL
   ::= { snTraps 2 }

snTrapOspfIfStateChange NOTIFICATION-TYPE
   OBJECTS {
                snOspfRouterId, -- The originator of the trap
                snOspfIfStatusIpAddress,
                snOspfIfStatusState   -- The new state
              }
   STATUS current
   DESCRIPTION
      "An ospfIfStateChange trap signifies that there
      has been a change in the state of a non-virtual
      OSPF interface. This trap should  be  generated
      when  the interface state regresses (e.g., goes
      from Dr to Down) or progresses  to  a  terminal
      state  (i.e.,  Point-to-Point, DR Other, Dr, or
      Backup)."
      --#TYPE "Foundry Trap: OSPF Interface State Change"
      --#SUMMARY "OSPF router id %s, interface %s state changed to %d."
      --#ARGUMENTS { 0, 1, 2 }
      --#SEVERITY INFORMATIONAL
      --#STATE OPERATIONAL
   ::= { snTraps 3 }

snTrapOspfVirtIfStateChange NOTIFICATION-TYPE
   OBJECTS {
                snOspfRouterId, -- The originator of the trap
                snOspfVirtIfStatusAreaID,
                snOspfVirtIfStatusNeighbor,
                snOspfVirtIfStatusState  -- The new state
              }
   STATUS current
   DESCRIPTION
      "An ospfIfStateChange trap signifies that there
      has  been a change in the state of an OSPF vir-
      tual interface.
      This trap should be generated when  the  inter-
      face  state  regresses  (e.g., goes from Point-
      to-Point to Down) or progresses to  a  terminal
      state (i.e., Point-to-Point)."
      --#TYPE "Foundry Trap: OSPF Virtual Interface State Change"
      --#SUMMARY "OSPF router id %s, virtual interface area id %s  neighbor %s state changed to %d."
      --#ARGUMENTS { 0, 1, 2, 3 }
      --#SEVERITY INFORMATIONAL
      --#STATE OPERATIONAL
   ::= { snTraps 4 }


snOspfNbrStateChange NOTIFICATION-TYPE
   OBJECTS {
                snOspfRouterId, -- The originator of the trap
                snOspfNbrIpAddr,
                snOspfNbrRtrId,
                snOspfNbrState  -- The new state
              }
    STATUS current
    DESCRIPTION
       "An  ospfNbrStateChange  trap  signifies   that
       there  has been a change in the state of a non-
       virtual OSPF neighbor.   This  trap  should  be
       generated  when  the  neighbor  state regresses
       (e.g., goes from Attempt or Full  to  1-Way  or
       Down)  or progresses to a terminal state (e.g.,
       2-Way or Full).  When an  neighbor  transitions
       from  or  to Full on non-broadcast multi-access
       and broadcast networks, the trap should be gen-
       erated  by the designated router.  A designated
       router transitioning to Down will be  noted  by
       ospfIfStateChange."
       --#TYPE "Foundry Trap: OSPF Neighbour State Change"
       --#SUMMARY "OSPF  router id %s neighbor area %s, neighbor router id  %s state changed to %d."
       --#ARGUMENTS { 0, 1, 2, 3 }
       --#SEVERITY INFORMATIONAL
       --#STATE OPERATIONAL
   ::= { snTraps 5 }


snOspfVirtNbrStateChange NOTIFICATION-TYPE
   OBJECTS {
                snOspfRouterId, -- The originator of the trap
                snOspfVirtNbrArea,
                snOspfVirtNbrRtrId,
                snOspfVirtNbrState  -- The new state
              }
    STATUS current
    DESCRIPTION
       "An ospfIfStateChange trap signifies that there
       has  been a change in the state of an OSPF vir-
       tual neighbor.  This trap should  be  generated
       when  the  neighbor state regresses (e.g., goes
       from Attempt or  Full  to  1-Way  or  Down)  or
       progresses to a terminal state (e.g., Full)."
       --#TYPE "Foundry Trap: OSPF Virtual Neighbour State Change"
       --#SUMMARY "OSPF router id %s virtual neighbor area %s, virtual neighbor router id  %s state changed to %d."
       --#ARGUMENTS { 0, 1, 2, 3 }
       --#SEVERITY INFORMATIONAL
       --#STATE OPERATIONAL
   ::= { snTraps 6 }



snOspfIfConfigError NOTIFICATION-TYPE
   OBJECTS {
                snOspfRouterId, -- The originator of the trap
                snOspfIfStatusIpAddress,
                snOspfPacketSrc,  -- The source IP address
                snOspfConfigErrorType, -- Type of error
                snOspfPacketType
              }
    STATUS current
    DESCRIPTION
       "An ospfIfConfigError  trap  signifies  that  a
       packet  has  been received on a non-virtual in-
       terface  from  a  router  whose   configuration
       parameters  conflict  with this router's confi-
       guration parameters.  Note that the  event  op-
       tionMismatch  should  cause  a  trap only if it
       prevents an adjacency from forming."
       --#TYPE "Foundry Trap: OSPF Interface Configuration Error"
       --#SUMMARY "configuration error type %d with  packet type %d has been received on interface %s, router id %s from  %s."
       --#ARGUMENTS { 3, 4, 1, 0, 2 }
       --#SEVERITY MAJOR
       --#STATE OPERATIONAL
   ::= { snTraps 7 }


snOspfVirtIfConfigError NOTIFICATION-TYPE
   OBJECTS {
                snOspfRouterId, -- The originator of the trap
                snOspfVirtIfStatusAreaID,
                snOspfVirtIfStatusNeighbor,
                snOspfConfigErrorType, -- Type of error
                snOspfPacketType
              }
    STATUS current
    DESCRIPTION
       "An ospfConfigError trap signifies that a pack-
       et  has  been  received  on a virtual interface
       from a router  whose  configuration  parameters
       conflict   with   this  router's  configuration
       parameters.  Note that the event optionMismatch
       should  cause a trap only if it prevents an ad-
       jacency from forming."
       --#TYPE "Foundry Trap: OSPF Virtual Interface Configuration Error"
       --#SUMMARY "configuration error type %d with  packet type %d has been received on virtual interface area id %s, router id %s from neighbor %s."
       --#ARGUMENTS { 3, 4, 1, 0, 2 }
       --#SEVERITY MAJOR
       --#STATE OPERATIONAL
   ::= { snTraps 8 }


snOspfIfAuthFailure NOTIFICATION-TYPE
   OBJECTS {
                snOspfRouterId, -- The originator of the trap
                snOspfIfStatusIpAddress,
                snOspfPacketSrc,  -- The source IP address
                snOspfConfigErrorType, -- authTypeMismatch or
                                     -- authFailure
                snOspfPacketType
              }
    STATUS current
    DESCRIPTION
       "An ospfIfAuthFailure  trap  signifies  that  a
       packet  has  been received on a non-virtual in-
       terface from a router whose authentication  key
       or  authentication  type  conflicts  with  this
       router's authentication key  or  authentication
       type."
       --#TYPE "Foundry Trap: OSPF Interface Authentication Failure"
       --#SUMMARY "OSPF authentication failed. Router ID %s,Interface %s, packet src %s, error type %d and packet type %d."
       --#ARGUMENTS { 0, 1, 2, 3, 4 }
       --#SEVERITY MINOR
       --#STATE OPERATIONAL
   ::= { snTraps 9 }


snOspfVirtIfAuthFailure NOTIFICATION-TYPE
   OBJECTS {
                snOspfRouterId, -- The originator of the trap
                snOspfVirtIfStatusAreaID,
                snOspfVirtIfStatusNeighbor,
                snOspfConfigErrorType, -- authTypeMismatch or
                                     -- authFailure
                snOspfPacketType
              }
    STATUS current
    DESCRIPTION
       "An ospfVirtIfAuthFailure trap signifies that a
       packet has been received on a virtual interface
       from a router whose authentication key  or  au-
       thentication  type conflicts with this router's
       authentication key or authentication type."
       --#TYPE "Foundry Trap: OSPF Virtual Interface Authentication Failure"
       --#SUMMARY "OSPF authentication failed. Router ID %s,virtual interface %s, Neigbor %s, Error type %d and packet type %d."
       --#ARGUMENTS { 0, 1, 2, 3, 4 }
       --#SEVERITY MINOR
       --#STATE OPERATIONAL
   ::= { snTraps 10 }


snOspfIfRxBadPacket NOTIFICATION-TYPE
   OBJECTS {
                snOspfRouterId, -- The originator of the trap
                snOspfIfStatusIpAddress,
                snOspfPacketSrc,  -- The source IP address
                snOspfPacketType
              }
    STATUS current
    DESCRIPTION
       "An ospfIfRxBadPacket trap  signifies  that  an
       OSPF  packet has been received on a non-virtual
       interface that cannot be parsed."
       --#TYPE "Foundry Trap: OSPF Interface Receive Bad Packet"
       --#SUMMARY "OSPF Router Id %s, interface %s  receive bad packet (type %d) from %s."
       --#ARGUMENTS { 0, 1, 3, 2 }
       --#SEVERITY WARNING
       --#STATE OPERATIONAL
   ::= { snTraps 11 }


snOspfVirtIfRxBadPacket NOTIFICATION-TYPE
   OBJECTS {
                snOspfRouterId, -- The originator of the trap
                snOspfVirtIfStatusAreaID,
                snOspfVirtIfStatusNeighbor,
                snOspfPacketType
              }
    STATUS current
    DESCRIPTION
       "An ospfRxBadPacket trap signifies that an OSPF
       packet has been received on a virtual interface
       that cannot be parsed."
       --#TYPE "Foundry Trap: OSPF Virt Interface Receive Bad Packet"
       --#SUMMARY "OSPF router id %s, virtual interface %s received bad packet (type %d) from neighbor %s."
       --#ARGUMENTS { 0, 1, 3, 2 }
       --#SEVERITY WARNING
       --#STATE OPERATIONAL
   ::= { snTraps 12 }


snOspfTxRetransmit NOTIFICATION-TYPE
   OBJECTS {
                snOspfRouterId, -- The originator of the trap
                snOspfIfStatusIpAddress,
                snOspfNbrRtrId, -- Destination
                snOspfPacketType,
                snOspfLsdbType,
                snOspfLsdbLsId,
                snOspfLsdbRouterId
              }
    STATUS current
    DESCRIPTION
       "An ospfTxRetransmit  trap  signifies  than  an
       OSPF  packet  has  been retransmitted on a non-
       virtual interface.  All packets that may be re-
       transmitted  are associated with an LSDB entry.
       The LS type, LS ID, and Router ID are  used  to
       identify the LSDB entry."
       --#TYPE "Foundry Trap: OSPF Retransmit"
       --#SUMMARY "OSPF router id %s, interface %s retransmited packet type %d,LSDB type %d, LSDB LS ID %s and LSDB router id %s to neightbor router id %s."
       --#ARGUMENTS { 0, 1, 3, 4, 5, 6, 2 }
       --#SEVERITY WARNING
       --#STATE OPERATIONAL
   ::= { snTraps 13 }


ospfVirtIfTxRetransmit NOTIFICATION-TYPE
   OBJECTS {
                snOspfRouterId, -- The originator of the trap
                snOspfVirtIfStatusAreaID,
                snOspfVirtIfStatusNeighbor,
                snOspfPacketType,
                snOspfLsdbType,
                snOspfLsdbLsId,
                snOspfLsdbRouterId
              }

    STATUS current
    DESCRIPTION
       "An ospfTxRetransmit  trap  signifies  than  an
       OSPF packet has been retransmitted on a virtual
       interface.  All packets that may be retransmit-
       ted  are  associated with an LSDB entry. The LS
       type, LS ID, and Router ID are used to identify
       the LSDB entry."
       --#TYPE "Foundry Trap: OSPF Virt Interface Retransmit"
       --#SUMMARY "OSPF router id %s, virtual interface area id %s retransmited packet type %d,LSDB type %d, LSDB LS ID %s and LSDB router id %s to neightbor %s."
       --#ARGUMENTS { 0, 1, 3, 4, 5, 6, 2 }
       --#SEVERITY WARNING
       --#STATE OPERATIONAL
   ::= { snTraps 14 }


snOspfOriginateLsa NOTIFICATION-TYPE
   OBJECTS {
                snOspfRouterId, -- The originator of the trap
                snOspfLsdbAreaId,  -- 0.0.0.0 for AS Externals
                snOspfLsdbType,
                snOspfLsdbLsId,
                snOspfLsdbRouterId
              }
    STATUS current
    DESCRIPTION
       "An ospfOriginateLsa trap signifies that a  new
       LSA  has  been originated by this router.  This
       trap should not be invoked for simple refreshes
       of  LSAs  (which happesn every 30 minutes), but
       instead will only be invoked  when  an  LSA  is
       (re)originated due to a topology change.  Addi-
       tionally, this trap does not include LSAs  that
       are  being  flushed  because  they have reached
       MaxAge."
       --#TYPE "Foundry Trap: OSPF Originate LSA"
       --#SUMMARY "New LSA (area id %s, type %d, LS Id %s and router id %s) has been originated by router id %s."
       --#ARGUMENTS { 1, 2, 3, 4, 0 }
       --#SEVERITY INFORMATIONAL
       --#STATE OPERATIONAL
   ::= { snTraps 15 }


snOspfMaxAgeLsa NOTIFICATION-TYPE
   OBJECTS {
                snOspfRouterId, -- The originator of the trap
                snOspfLsdbAreaId,  -- 0.0.0.0 for AS Externals
                snOspfLsdbType,
                snOspfLsdbLsId,
                snOspfLsdbRouterId
              }
    STATUS current
    DESCRIPTION
       "An ospfMaxAgeLsa trap signifies  that  one  of
       the LSA in the router's link-state database has
       aged to MaxAge."
       --#TYPE "Foundry Trap: OSPF MaxAge LSA"
       --#SUMMARY "The LSA (area id %s, type %d, LS Id %s and router id %s) in router id %s link-state database has aged to maximum age."
       --#ARGUMENTS { 1, 2, 3, 4, 0 }
       --#SEVERITY WARNING
       --#STATE OPERATIONAL
   ::= { snTraps 16 }



snOspfLsdbOverflow NOTIFICATION-TYPE
   OBJECTS {
                snOspfRouterId, -- The originator of the trap
                snOspfExtLsdbLimit
              }
    STATUS current
    DESCRIPTION
       "An ospfLsdbOverflow trap  signifies  that  the
       number of LSAs in the router's link-state data-
       base has exceeded ospfExtLsdbLimit."
       --#TYPE "Foundry Trap: OSPF LS DB Overflow"
       --#SUMMARY "The number of LSAs in the OSPF router id %s link-state database has exceeded %d."
       --#ARGUMENTS { 0, 1 }
       --#SEVERITY WARNING
       --#STATE OPERATIONAL
   ::= { snTraps 17 }


snOspfLsdbApproachingOverflow NOTIFICATION-TYPE
   OBJECTS {
                snOspfRouterId, -- The originator of the trap
                snOspfExtLsdbLimit
              }
    STATUS current
    DESCRIPTION
       "An ospfLsdbApproachingOverflow trap  signifies
       that  the  number of LSAs in the router's link-
       state database has exceeded ninety  percent  of
       ospfExtLsdbLimit."
       --#TYPE "Foundry Trap: OSPF LS DB Near Full"
       --#SUMMARY "The number of LSAs in the OSPF router id %s link-state database has exceeded ninety percent of  %d."
       --#ARGUMENTS { 0, 1 }
       --#SEVERITY INFORMATIONAL
       --#STATE OPERATIONAL
   ::= { snTraps 18 }


snTrapL4MaxSessionLimitReached NOTIFICATION-TYPE
   OBJECTS { snL4MaxSessionLimit }
   STATUS current
   DESCRIPTION
	   "The SNMP trap that is generated when the maximum number
	   of connections reached."
	   --#TYPE "Foundry Trap: L4 Session Limit"
	   --#SUMMARY "SLB maximum number of connections  %d has been reached."
	   --#ARGUMENTS { 0 }
	   --#SEVERITY WARNING
	   --#STATE OPERATIONAL
   ::= { snTraps 19 }


snTrapL4TcpSynLimitReached NOTIFICATION-TYPE
   OBJECTS { snL4TcpSynLimit }
   STATUS current
   DESCRIPTION
	   "The SNMP trap that is generated when the number of TCP
	   SYN limits reached."
	   --#TYPE "Foundry Trap: L4 TCP Syn Limit"
	   --#SUMMARY "SLB TCP Syn limits %d has been reached."
	   --#ARGUMENTS { 0 }
	   --#SEVERITY WARNING
	   --#STATE OPERATIONAL
   ::= { snTraps 20 }


snTrapL4RealServerUp NOTIFICATION-TYPE
   OBJECTS { snL4TrapRealServerIP, snL4TrapRealServerName }
   STATUS current
   DESCRIPTION
	   "The SNMP trap that is generated when the load balancing
	   real server is up."
	   --#TYPE "Foundry Trap: L4 Real Server Up"
	   --#SUMMARY "SLB real server %s %s is up."
	   --#ARGUMENTS { 0, 1 }
	   --#SEVERITY INFORMATIONAL
	   --#STATE OPERATIONAL
   ::= { snTraps 21 }


snTrapL4RealServerDown NOTIFICATION-TYPE
   OBJECTS { snL4TrapRealServerIP, snL4TrapRealServerName }
   STATUS current
   DESCRIPTION
	   "The SNMP trap that is generated when the load balancing
	   real server is down."
	   --#TYPE "Foundry Trap: L4 Real Server Down"
	   --#SUMMARY "SLB real server %s %s is down."
	   --#ARGUMENTS { 0, 1 }
	   --#SEVERITY INFORMATIONAL
	   --#STATE OPERATIONAL
   ::= { snTraps 22 }


snTrapL4RealServerPortUp NOTIFICATION-TYPE
   OBJECTS { snL4TrapRealServerIP, snL4TrapRealServerName, snL4TrapRealServerPort }
   STATUS current
   DESCRIPTION
	   "The SNMP trap that is generated when the load balancing
	   real server TCP port is up."
	   --#TYPE "Foundry Trap: L4 Real Server Port Up"
	   --#SUMMARY "SLB real server port %s %s %d is up."
	   --#ARGUMENTS { 0, 1, 2 }
	   --#SEVERITY INFORMATIONAL
	   --#STATE OPERATIONAL
   ::= { snTraps 23 }


snTrapL4RealServerPortDown NOTIFICATION-TYPE
   OBJECTS { snL4TrapRealServerIP, snL4TrapRealServerName, snL4TrapRealServerPort }
   STATUS current
   DESCRIPTION
	   "The SNMP trap that is generated when the load balancing
	   real server TCP port is down."
	   --#TYPE "Foundry Trap: L4 Real Server Port Down"
	   --#SUMMARY "SLB real server port %s %s %d is down."
	   --#ARGUMENTS { 0, 1, 2 }
	   --#SEVERITY INFORMATIONAL
	   --#STATE OPERATIONAL
   ::= { snTraps 24 }


snTrapL4RealServerMaxConnectionLimitReached NOTIFICATION-TYPE
   OBJECTS { snL4TrapRealServerIP, snL4TrapRealServerName, snL4TrapRealServerCurConnections }
   STATUS current
   DESCRIPTION
	   "The SNMP trap that is generated when the real server reaches
	   maximum number of connections."
	   --#TYPE "Foundry Trap: L4 Real Server Max Connection Limit"
	   --#SUMMARY "SLB real server %s %s maximum connection %d has been reached."
	   --#ARGUMENTS { 0, 1, 2 }
	   --#SEVERITY WARNING
	   --#STATE OPERATIONAL
   ::= { snTraps 25 }


snTrapL4BecomeStandby NOTIFICATION-TYPE
   STATUS current
   DESCRIPTION
	   "The SNMP trap that is generated when the server load
	   balancing switch changes state from active to standby."
	   --#TYPE "Foundry Trap: L4 Server On Standby"
	   --#SUMMARY "SLB changes state from active to standby."
	   --#ARGUMENTS { }
	   --#SEVERITY WARNING
	   --#STATE OPERATIONAL
   ::= { snTraps 26 }


snTrapL4BecomeActive NOTIFICATION-TYPE
   STATUS current
   DESCRIPTION
	   "The SNMP trap that is generated when the server load
	   balancing switch changes state from standby to active."
	   --#TYPE "Foundry Trap: L4 Server Active"
	   --#SUMMARY "SLB changes state from standby to active."
	   --#ARGUMENTS { }
	   --#SEVERITY WARNING
	   --#STATE OPERATIONAL
   ::= { snTraps 27 }


snTrapModuleInserted NOTIFICATION-TYPE
   OBJECTS { snAgentBrdIndex }
   STATUS current
   DESCRIPTION
	   "The SNMP trap that is generated when a module was inserted
	   to the chassis during system running."
	   --#TYPE "Foundry Trap: Module Inserted"
	   --#SUMMARY "Module %d was inserted to the chassis during system running."
	   --#ARGUMENTS { 0 }
	   --#SEVERITY INFORMATIONAL
	   --#STATE OPERATIONAL
   ::= { snTraps 28 }


snTrapModuleRemoved NOTIFICATION-TYPE
   OBJECTS { snAgentBrdIndex }
   STATUS current
   DESCRIPTION
	   "The SNMP trap that is generated when a module was removed
	   from the chassis during system running."
	   --#TYPE "Foundry Trap: Module Removed"
	   --#SUMMARY "Module %d was removed from the chassis during system running."
	   --#ARGUMENTS { 0 }
	   --#SEVERITY INFORMATIONAL
	   --#STATE OPERATIONAL
   ::= { snTraps 29 }


snTrapChasPwrSupplyFailed NOTIFICATION-TYPE
   OBJECTS { snChasPwrSupplyIndex, snChasPwrSupplyDescription }
   STATUS current
   DESCRIPTION
	   "The SNMP trap that is generated when a power supply operational
		status changed from normal to failure."
		--#TYPE "Foundry Trap: Power Supply Failure"
		--#SUMMARY "Power supply %d (%s)  failed."
		--#ARGUMENTS { 0, 1 }
		--#SEVERITY MINOR
		--#STATE OPERATIONAL
   ::= { snTraps 30 }


snTrapChasFanFailed NOTIFICATION-TYPE
   OBJECTS { snChasFanIndex, snChasFanDescription }
   STATUS current
   DESCRIPTION
	   "The SNMP trap that is generated when a fan fails
		to operate normally."
		--#TYPE "Foundry Trap: Fan Failure"
		--#SUMMARY "Fan  %d (%s)  failed."
		--#ARGUMENTS { 0, 1 }
		--#SEVERITY MINOR
		--#STATE OPERATIONAL
   ::= { snTraps 31 }


snTrapLockedAddressViolation2 NOTIFICATION-TYPE
   OBJECTS { snAgGblTrapMessage }
   STATUS current
   DESCRIPTION
	   "The SNMP trap that is generated when more source MAC addresses
		are received from a port than the maximum number of addresses
		configured to that port."
		--#TYPE "Foundry Trap: Lock Address Violation"
		--#SUMMARY "%s."
		--#ARGUMENTS { 0 }
		--#SEVERITY MINOR
		--#STATE OPERATIONAL
   ::= { snTraps 32 }


snTrapFsrpIfStateChange NOTIFICATION-TYPE
   OBJECTS { snAgGblTrapMessage }
   STATUS current
   DESCRIPTION
	   "The SNMP trap that is generated when a FSRP routing device
	   changed state from active to standby or vice-versa."
	   --#TYPE "Foundry Trap: FSRP Interface Change"
	   --#SUMMARY "%s."
	   --#ARGUMENTS { 0 }
	   --#SEVERITY INFORMATIONAL
	   --#STATE OPERATIONAL
   ::= { snTraps 33 }

snTrapVrrpIfStateChange NOTIFICATION-TYPE
   OBJECTS { snAgGblTrapMessage }
   STATUS current
   DESCRIPTION
	   "The SNMP trap that is generated when a VRRP routing device
	   switched between states master, backup, intialized or uknown."
	   --#TYPE "Foundry Trap: VRRP Interface Change"
	   --#SUMMARY "%s."
	   --#ARGUMENTS { 0 }
	   --#SEVERITY WARNING
	   --#STATE OPERATIONAL
   ::= { snTraps 34 }


snTrapMgmtModuleRedunStateChange NOTIFICATION-TYPE
   OBJECTS { snAgGblTrapMessage }
   STATUS current
   DESCRIPTION
	   "The SNMP trap that is generated when the management module
	   changes redundancy state."
	   --#TYPE "Foundry Trap: Management Module Change State"
	   --#SUMMARY "%s."
	   --#ARGUMENTS { 0 }
	   --#SEVERITY WARNING
	   --#STATE OPERATIONAL
   ::= { snTraps 35 }


snTrapTemperatureWarning NOTIFICATION-TYPE
   OBJECTS { snAgGblTrapMessage }
   STATUS current
   DESCRIPTION
	   "The SNMP trap that is generated when the actual temperature
	   reading is above the warning temperature threshold."
	   --#TYPE "Foundry Trap: Temperature Warning"
	   --#SUMMARY "%s."
	   --#ARGUMENTS { 0 }
	   --#SEVERITY CRITICAL
	   --#STATE OPERATIONAL
   ::= { snTraps 36 }

snTrapAccessListDeny NOTIFICATION-TYPE
   OBJECTS { snAgGblTrapMessage }
   STATUS current
   DESCRIPTION
	   "The SNMP trap that is generated when a packet was denied
	   by an access list."
	   --#TYPE "Foundry Trap: Deny from ACL"
	   --#SUMMARY "%s."
	   --#ARGUMENTS { 0 }
	   --#SEVERITY WARNING
	   --#STATE OPERATIONAL
   ::= { snTraps 37 }

snTrapMacFilterDeny NOTIFICATION-TYPE
   OBJECTS { snAgGblTrapMessage }
   STATUS current
   DESCRIPTION
	   "The SNMP trap that is generated when a packet was denied
	   by a MAC address filter."
	   --#TYPE "Foundry Trap: Deny from MAC Filter"
	   --#SUMMARY "%s."
	   --#ARGUMENTS { 0 }
	   --#SEVERITY WARNING
	   --#STATE OPERATIONAL
   ::= { snTraps 38 }

snTrapL4GslbRemoteUp NOTIFICATION-TYPE
   OBJECTS { snAgGblTrapMessage }
   STATUS current
   DESCRIPTION
	   "The SNMP trap that is generated when the connection to the remote SI is established."
		--#TYPE "Foundry Trap: Remote SI Up"
		--#SUMMARY "%s."
		--#ARGUMENTS { 0 }
		--#SEVERITY WARNING
		--#STATE OPERATIONAL
   ::= { snTraps 39 }

snTrapL4GslbRemoteDown NOTIFICATION-TYPE
   OBJECTS { snAgGblTrapMessage }
   STATUS current
   DESCRIPTION
	   "The SNMP trap that is generated when the connection to the remote SI is down."
		--#TYPE "Foundry Trap: Remote SI Down"
		--#SUMMARY "%s."
		--#ARGUMENTS { 0 }
		--#SEVERITY WARNING
		--#STATE OPERATIONAL
   ::= { snTraps 40 }

snTrapL4GslbRemoteControllerUp NOTIFICATION-TYPE
   OBJECTS { snAgGblTrapMessage }
   STATUS current
   DESCRIPTION
	   "The SNMP trap that is generated when the connection to the GSLB SI is established."
	   --#TYPE "Foundry Trap: Remote GSLB SI Up"
	   --#SUMMARY "%s."
	   --#ARGUMENTS { 0 }
	   --#SEVERITY WARNING
	   --#STATE OPERATIONAL
   ::= { snTraps 41 }

snTrapL4GslbRemoteControllerDown NOTIFICATION-TYPE
   OBJECTS { snAgGblTrapMessage }
   STATUS current
   DESCRIPTION
	   "The SNMP trap that is generated when the connection to the GSLB SI is down."
	   --#TYPE "Foundry Trap: Remote GSLB SI Down"
	   --#SUMMARY "%s."
	   --#ARGUMENTS { 0 }
	   --#SEVERITY WARNING
	   --#STATE OPERATIONAL
   ::= { snTraps 42 }

snTrapL4GslbHealthCheckIpUp NOTIFICATION-TYPE
   OBJECTS { snAgGblTrapMessage }
   STATUS current
   DESCRIPTION
	   "The SNMP trap that is generated when GSLB health check for an address transitions
		from down to active state."
	 --#TYPE "Foundry Trap: GSLB HealtCheck Up"
	 --#SUMMARY "%s."
	 --#ARGUMENTS { 0 }
	 --#SEVERITY WARNING
	 --#STATE OPERATIONAL
   ::= { snTraps 43 }

snTrapL4GslbHealthCheckIpDown NOTIFICATION-TYPE
   OBJECTS { snAgGblTrapMessage }
   STATUS current
   DESCRIPTION
	   "The SNMP trap that is generated when GSLB health check for an address transitions
		from active to down state."
	 --#TYPE "Foundry Trap: GSLB HealthCheck Down"
	 --#SUMMARY "%s."
	 --#ARGUMENTS { 0 }
	 --#SEVERITY WARNING
	 --#STATE OPERATIONAL
   ::= { snTraps 44 }

snTrapL4GslbHealthCheckIpPortUp NOTIFICATION-TYPE
   OBJECTS { snAgGblTrapMessage }
   STATUS current
   DESCRIPTION
	   "The SNMP trap that is generated when a given port for a health check address is up."
	--#TYPE "Foundry Trap: GSLB HealthCheck Port Up"
	--#SUMMARY "%s."
	--#ARGUMENTS { 0 }
	--#SEVERITY WARNING
	--#STATE OPERATIONAL
   ::= { snTraps 45 }

snTrapL4GslbHealthCheckIpPortDown NOTIFICATION-TYPE
   OBJECTS { snAgGblTrapMessage }
   STATUS current
   DESCRIPTION
	   "The SNMP trap that is generated when a given port for a health check address is down."
	 --#TYPE "Foundry Trap: GSLB HealthCheck Port Down"
	 --#SUMMARY "%s."
	 --#ARGUMENTS { 0 }
	 --#SEVERITY WARNING
	 --#STATE OPERATIONAL
   ::= { snTraps 46 }

snTrapL4FirewallBecomeStandby NOTIFICATION-TYPE
   STATUS current
   DESCRIPTION
	   "The SNMP trap that is generated when the server load
	   balancing switch Firewall changes state from active to standby."
	--#TYPE "Foundry Trap: Firewall Standby"
	--#SUMMARY "Firewall changes state from active to standby."
	--#ARGUMENTS { }
	--#SEVERITY MAJOR
	--#STATE OPERATIONAL
   ::= { snTraps 47 }

snTrapL4FirewallBecomeActive NOTIFICATION-TYPE
   STATUS current
   DESCRIPTION
	   "The SNMP trap that is generated when the server load
	   balancing switch Firewall changes state from standby to active."
	--#TYPE "Foundry Trap: Firewall Active"
	--#SUMMARY "Firewall changes state from standby to active."
	--#ARGUMENTS { }
	--#SEVERITY MAJOR
	--#STATE OPERATIONAL
   ::= { snTraps 48 }

snTrapL4FirewallPathUp NOTIFICATION-TYPE
   STATUS current
   DESCRIPTION
	   "The SNMP trap that is generated when the server load
	   balancing switch Firewall path is up."
	--#TYPE "Foundry Trap: Firewall Path Up"
	--#SUMMARY "Firewall path is up."
	--#ARGUMENTS { }
	--#SEVERITY MINOR
	--#STATE OPERATIONAL
   ::= { snTraps 49 }


snTrapL4FirewallPathDown NOTIFICATION-TYPE
   STATUS current
   DESCRIPTION
	   "The SNMP trap that is generated when the server load
	   balancing switch Firewall path is down."
	--#TYPE "Foundry Trap: Firewall Path Down"
	--#SUMMARY "Firewall path is down."
	--#ARGUMENTS { }
	--#SEVERITY MINOR
	--#STATE OPERATIONAL
   ::= { snTraps 50 }

snTrapIcmpLocalExceedBurst NOTIFICATION-TYPE
   OBJECTS { snAgGblTrapMessage }
   STATUS current
   DESCRIPTION
	   "The SNMP trap that is generated when incoming ICMP exceeds burst-MAX."
	--#TYPE "Foundry Trap: ICMP Burst Exceeded"
	--#SUMMARY "%s."
	--#ARGUMENTS { 0 }
	--#SEVERITY WARNING
	--#STATE OPERATIONAL
   ::= { snTraps 51 }

snTrapIcmpTransitExceedBurst NOTIFICATION-TYPE
   OBJECTS { snAgGblTrapMessage }
   STATUS current
   DESCRIPTION
	   "The SNMP trap that is generated when transit ICMP exceeds burst-MAX."
	--#TYPE "Foundry Trap: Transit ICMP Burst Exceeded"
	--#SUMMARY "%s."
	--#ARGUMENTS { 0 }
	--#SEVERITY WARNING
	--#STATE OPERATIONAL
   ::= { snTraps 52 }

snTrapTcpLocalExceedBurst NOTIFICATION-TYPE
   OBJECTS { snAgGblTrapMessage }
   STATUS current
   DESCRIPTION
	   "The SNMP trap that is generated when incoming TCP SYN exceeds burst-MAX."
	--#TYPE "Foundry Trap: TCP SYN Burst Exceeded"
	--#SUMMARY "%s."
	--#ARGUMENTS { 0 }
	--#SEVERITY WARNING
	--#STATE OPERATIONAL
   ::= { snTraps 53 }

snTrapTcpTransitExceedBurst NOTIFICATION-TYPE
   OBJECTS { snAgGblTrapMessage }
   STATUS current
   DESCRIPTION
	   "The SNMP trap that is generated when transit TCP exceeds burst-MAX."
	--#TYPE "Foundry Trap: Transit TCP SYN Burst Exceeded"
	--#SUMMARY "%s."
	--#ARGUMENTS { 0 }
	--#SEVERITY WARNING
	--#STATE OPERATIONAL
   ::= { snTraps 54 }

snTrapL4ContentVerification NOTIFICATION-TYPE
   STATUS current
   DESCRIPTION
	   "The SNMP trap that is generated when the HTTP match-list pattern
	   is found."
   --#TYPE "Foundry Trap: HTTP Match"
   --#SUMMARY "HTTP match-list pattern is found."
   --#ARGUMENTS { }
   --#SEVERITY INFORMATIONAL
   --#STATE OPERATIONAL
   ::= { snTraps 55 }

snTrapDuplicateIp NOTIFICATION-TYPE
   STATUS current
   DESCRIPTION
	   "Duplicate IP address detected."
	--#TYPE "Foundry Trap: Duplicate IP"
	--#SUMMARY "Duplicate IP address detect."
	--#ARGUMENTS { }
	--#SEVERITY MAJOR
	--#STATE OPERATIONAL
   ::= { snTraps 56 }

snTrapMplsProblem NOTIFICATION-TYPE
   STATUS obsolete
   DESCRIPTION
	   "NOT IMPLEMENTED: MPLS Problem Detected."
	--#TYPE "Foundry Trap: MPLS Problem"
	--#SUMMARY "MPLS Problem detect."
	--#ARGUMENTS { }
	--#SEVERITY MAJOR
	--#STATE OPERATIONAL
   ::= { snTraps 57 }

snTrapMplsException NOTIFICATION-TYPE
   STATUS obsolete
   DESCRIPTION
	   "NOT IMPLEMENTED: MPLS Exception Detected."
	--#TYPE "Foundry Trap: MPLS Exception"
	--#SUMMARY "MPLS Exception detect."
	--#ARGUMENTS { }
	--#SEVERITY MAJOR
	--#STATE OPERATIONAL
   ::= { snTraps 58 }
   
snTrapMplsAudit NOTIFICATION-TYPE
   STATUS obsolete
   DESCRIPTION
	   "NOT IMPLEMENTED: MPLS Audit Trap."
	--#TYPE "Foundry Trap: MPLS Audit"
	--#SUMMARY "MPLS Audit Trap."
	--#ARGUMENTS { }
	--#SEVERITY INFORMATIONAL
	--#STATE OPERATIONAL
   ::= { snTraps 59 }
   
snTrapMplsDeveloper NOTIFICATION-TYPE
   STATUS obsolete
   DESCRIPTION
	   "NOT IMPLEMENTED: MPLS Developer Trap."
	--#TYPE "Foundry Trap: MPLS Developer"
	--#SUMMARY "MPLS Developer Trap."
	--#ARGUMENTS { }
	--#SEVERITY INFORMATIONAL
	--#STATE OPERATIONAL
   ::= { snTraps 60 }

snTrapNoBmFreeQueue NOTIFICATION-TYPE
   OBJECTS { snAgGblTrapMessage }
   STATUS current
   DESCRIPTION
	   "The SNMP trap that is generated when no free queue is available in buffer manager."
	--#TYPE "Foundry Trap: No BM Free Queue"
	--#SUMMARY "%s."
	--#ARGUMENTS { 0 }
	--#SEVERITY WARNING
	--#STATE OPERATIONAL
   ::= { snTraps 61 }

snTrapSmcDmaDrop NOTIFICATION-TYPE
   OBJECTS { snAgGblTrapMessage }
   STATUS current
   DESCRIPTION
	   "The SNMP trap that is generated when SMC DMA packet is dropped."
	--#TYPE "Foundry Trap: SMC DMA Packet Dropped"
	--#SUMMARY "%s."
	--#ARGUMENTS { 0 }
	--#SEVERITY INFORMATIONAL
	--#STATE OPERATIONAL
   ::= { snTraps 62 }

snTrapSmcBpDrop NOTIFICATION-TYPE
   OBJECTS { snAgGblTrapMessage }
   STATUS current
   DESCRIPTION
	   "The SNMP trap that is generated when SMC BackPlane packet is dropped."
	--#TYPE "Foundry Trap: SMC BP Packet Dropped"
	--#SUMMARY "%s."
	--#ARGUMENTS { 0 }
	--#SEVERITY INFORMATIONAL
	--#STATE OPERATIONAL
   ::= { snTraps 63 }

snTrapBmWriteSeqDrop NOTIFICATION-TYPE
   OBJECTS { snAgGblTrapMessage }
   STATUS current
   DESCRIPTION
	   "The SNMP trap that is generated when BM write sequence packet is dropped."
	--#TYPE "Foundry Trap: BM Write Sequence Packet Dropped"
	--#SUMMARY "%s."
	--#ARGUMENTS { 0 }
	--#SEVERITY INFORMATIONAL
	--#STATE OPERATIONAL
   ::= { snTraps 64 }

snTrapBgpPeerUp NOTIFICATION-TYPE
   OBJECTS { snAgGblTrapMessage }
   STATUS current
   DESCRIPTION
	   "The SNMP trap that is generated when the bgp peer is up."
   --#TYPE "Foundry Trap: BGP Peer Up"
   --#SUMMARY "%s."
   --#ARGUMENTS { 0 }
   --#SEVERITY INFORMATIONAL
   --#STATE OPERATIONAL
   ::= { snTraps 65 }

snTrapBgpPeerDown NOTIFICATION-TYPE
   OBJECTS { snAgGblTrapMessage }
   STATUS current
   DESCRIPTION
	   "The SNMP trap that is generated when the bgp peer is down."
	--#TYPE "Foundry Trap: BGP Peer Down"
	--#SUMMARY "%s."
	--#ARGUMENTS { 0 }
	--#SEVERITY INFORMATIONAL
	--#STATE OPERATIONAL
   ::= { snTraps 66 }

snTrapL4RealServerResponseTimeLowerLimit NOTIFICATION-TYPE
   OBJECTS { snAgGblTrapMessage }
   STATUS current
   DESCRIPTION
	   "The SNMP trap that is generated when the real server average response time exceeds lower threshold."
   --#TYPE "Foundry Trap: L4 Real Server Response Exceeds Lower Threshold"
   --#SUMMARY "%s."
   --#ARGUMENTS { 0 }
   --#SEVERITY WARNING
   --#STATE OPERATIONAL
   ::= { snTraps 67 }

snTrapL4RealServerResponseTimeUpperLimit NOTIFICATION-TYPE
   OBJECTS { snAgGblTrapMessage }
   STATUS current
   DESCRIPTION
	   "The SNMP trap that is generated when the real server average response time exceeds upper threshold."
   --#TYPE "Foundry Trap: L4 Real Server Response Exceeds Upper Threshold"
   --#SUMMARY "%s."
   --#ARGUMENTS { 0 }
   --#SEVERITY WARNING
   --#STATE OPERATIONAL
   ::= { snTraps 68 }

snTrapL4TcpAttackRateExceedMax NOTIFICATION-TYPE
   OBJECTS { snAgGblTrapMessage }
   STATUS current
   DESCRIPTION
	   "The SNMP trap that is generated when the TCP attack rate exceeds configured maximum."
	--#TYPE "Foundry Trap: L4 TCP Attack Rate Exceed Max"
	--#SUMMARY "%s."
	--#ARGUMENTS { 0 }
	--#SEVERITY CRITICAL
	--#STATE OPERATIONAL
   ::= { snTraps 69 }

snTrapL4TcpAttackRateExceedThreshold NOTIFICATION-TYPE
   OBJECTS { snAgGblTrapMessage }
   STATUS current
   DESCRIPTION
	   "The SNMP trap that is generated when the TCP attack rate exceeds 80% of configured maximum."
   --#TYPE "Foundry Trap: L4 TCP Attack Rate Exceed Threshold"
   --#SUMMARY "%s."
   --#ARGUMENTS { 0 }
   --#SEVERITY WARNING
   --#STATE OPERATIONAL
   ::= { snTraps 70 }

snTrapL4ConnectionRateExceedMax NOTIFICATION-TYPE
   OBJECTS { snAgGblTrapMessage }
   STATUS current
   DESCRIPTION
	   "The SNMP trap that is generated when the L4 connection rate exceeds configured maximum."
   --#TYPE "Foundry Trap: L4 Connection Rate Exceed Max"
   --#SUMMARY "%s."
   --#ARGUMENTS { 0 }
   --#SEVERITY CRITICAL
   --#STATE OPERATIONAL
   ::= { snTraps 71 }

snTrapL4ConnectionRateExceedThreshold NOTIFICATION-TYPE
   OBJECTS { snAgGblTrapMessage }
   STATUS current
   DESCRIPTION
	   "The SNMP trap that is generated when the L4 connection rate exceeds 80% of configured maximum"
	--#TYPE "Foundry Trap: L4 Connection Rate Exceed Threshold"
	--#SUMMARY "%s."
	--#ARGUMENTS { 0 }
	--#SEVERITY WARNING
	--#STATE OPERATIONAL
   ::= { snTraps 72 }

snTrapRunningConfigChanged NOTIFICATION-TYPE
   OBJECTS { snAgGblTrapMessage }
   STATUS current
   DESCRIPTION
	   "The SNMP trap that is generated when the running configuration
		was changed."
   --#TYPE "Foundry Trap: Running Configuration Changed"
   --#SUMMARY "%s."
   --#ARGUMENTS { 0 }
   --#SEVERITY INFORMATIONAL
   --#STATE OPERATIONAL
   ::= { snTraps 73 }

snTrapStartupConfigChanged NOTIFICATION-TYPE
   OBJECTS { snAgGblTrapMessage }
   STATUS current
   DESCRIPTION
	   "The SNMP trap that is generated when the startup configuration
		was changed."
   --#TYPE "Foundry Trap: Startup Configuration Changed"
   --#SUMMARY "%s."
   --#ARGUMENTS { 0 }
   --#SEVERITY INFORMATIONAL
   --#STATE OPERATIONAL
   ::= { snTraps 74 }

snTrapUserLogin NOTIFICATION-TYPE
   OBJECTS { snAgGblTrapMessage }
   STATUS current
   DESCRIPTION
	   "The SNMP trap that is generated when user login."
   --#TYPE "Foundry Trap: User Login"
   --#SUMMARY "%s."
   --#ARGUMENTS { 0 }
   --#SEVERITY INFORMATIONAL
   --#STATE OPERATIONAL
   ::= { snTraps 75 }

snTrapUserLogout NOTIFICATION-TYPE
   OBJECTS { snAgGblTrapMessage }
   STATUS current
   DESCRIPTION
	   "The SNMP trap that is generated when user logout."
   --#TYPE "Foundry Trap: User Logout"
   --#SUMMARY "%s."
   --#ARGUMENTS { 0 }
   --#SEVERITY INFORMATIONAL
   --#STATE OPERATIONAL
   ::= { snTraps 76 }

snTrapPortSecurityViolation NOTIFICATION-TYPE
   OBJECTS { snAgGblTrapMessage }
   STATUS current
   DESCRIPTION
	   "The SNMP trap that is generated when insecure MAC addresses
		are received from a port with MAC security feature enabled."
  --#TYPE "Foundry Trap: Port Security Violation"
  --#SUMMARY "%s."
  --#ARGUMENTS { 0 }
  --#SEVERITY MINOR
  --#STATE OPERATIONAL
   ::= { snTraps 77 }

snTrapPortSecurityShutdown NOTIFICATION-TYPE
   OBJECTS { snAgGblTrapMessage }
   STATUS current
   DESCRIPTION
	   "The SNMP trap that is generated when insecure MAC addresses
		are received from a port caused the port to shutdown."
   --#TYPE "Foundry Trap: Port Security Violation Cause Shutdown"
   --#SUMMARY "%s."
   --#ARGUMENTS { 0 }
   --#SEVERITY MINOR
   --#STATE OPERATIONAL
   ::= { snTraps 78 }

snTrapMrpStateChange NOTIFICATION-TYPE
   OBJECTS { snAgGblTrapMessage }
   STATUS current
   DESCRIPTION
	   "The SNMP trap that is generated when a MRP switching and routing device
	   changed state to  disabled, blocking, preforwarding, forwarding, uknown."
   --#TYPE "Foundry Trap: MRP Interface Change"
   --#SUMMARY "%s."
   --#ARGUMENTS { 0 }
   --#SEVERITY WARNING
   --#STATE OPERATIONAL
   ::= { snTraps 79 }

snTrapMrpCamError NOTIFICATION-TYPE
   OBJECTS { snAgGblTrapMessage }
   STATUS current
   DESCRIPTION
	   "The SNMP trap that is generated when a MRP Cam Error occurs."
   --#TYPE "Foundry Trap: MRP Cam Error"
   --#SUMMARY "%s."
   --#ARGUMENTS { 0 }
   --#SEVERITY WARNING
   --#STATE OPERATIONAL
   ::= { snTraps 80 }

snTrapChasPwrSupplyOK NOTIFICATION-TYPE
   OBJECTS { snChasPwrSupplyIndex, snChasPwrSupplyDescription }
   STATUS current
   DESCRIPTION
	   "The SNMP trap that is generated when a power supply operational
		status changed from failure to normal."
  --#TYPE "Foundry Trap: Power Supply OK"
  --#SUMMARY "Power supply %d (%s)  OK."
  --#ARGUMENTS { 0, 1 }
  --#SEVERITY MINOR
  --#STATE OPERATIONAL
   ::= { snTraps 81 }


snTrapVrrpeIfStateChange NOTIFICATION-TYPE
   OBJECTS { snAgGblTrapMessage }
   STATUS current
   DESCRIPTION
	   "The SNMP trap that is generated when a VRRPE routing device
	   switched between states master, backup, intialized or uknown."
  --#TYPE "Foundry Trap: VRRPE Interface Change"
  --#SUMMARY "%s."
  --#ARGUMENTS { 0 }
  --#SEVERITY WARNING
  --#STATE OPERATIONAL
   ::= { snTraps 82 }

snTrapVsrpIfStateChange NOTIFICATION-TYPE
   OBJECTS { snAgGblTrapMessage }
   STATUS current
   DESCRIPTION
	   "The SNMP trap that is generated when a VSRP switching and routing device
	   switched between states master, backup, intialized or uknown."
   --#TYPE "Foundry Trap: VSRP Interface Change"
   --#SUMMARY "%s."
   --#ARGUMENTS { 0 }
   --#SEVERITY WARNING
   --#STATE OPERATIONAL
   ::= { snTraps 83 }

snTrapSrcIpAddressViolation NOTIFICATION-TYPE
   OBJECTS { snAgGblTrapMessage }
   STATUS current
   DESCRIPTION
	   "The SNMP trap that is generated when a rogue device spoofs source
	   IP address for denial of service attack."
   --#TYPE "Foundry Trap: Intruder Source IP Address"
   --#SUMMARY "%s."
   --#ARGUMENTS { 0 }
   --#SEVERITY WARNING
   --#STATE OPERATIONAL
   ::= { snTraps 84 }

snTrapMacAuthEnable NOTIFICATION-TYPE
   OBJECTS { snAgGblTrapMessage }
   STATUS current
   DESCRIPTION
	   "The SNMP trap that is generated when MAC-Authentication is enabled 
	   on an interface."
   --#TYPE "Foundry Trap: MAC-Authentication enabled"
   --#SUMMARY "%s."
   --#ARGUMENTS { 0 }
   --#SEVERITY INFORMATIONAL
   --#STATE OPERATIONAL
   ::= { snTraps 85 }

snTrapMacAuthDisable NOTIFICATION-TYPE
   OBJECTS { snAgGblTrapMessage }
   STATUS current
   DESCRIPTION
	   "The SNMP trap that is generated when MAC-Authentication is disabled 
	   on an interface."
   --#TYPE "Foundry Trap: MAC-Authentication disabled"
   --#SUMMARY "%s."
   --#ARGUMENTS { 0 }
   --#SEVERITY INFORMATIONAL
   --#STATE OPERATIONAL
   ::= { snTraps 86 }

snTrapMacAuthMACAccepted NOTIFICATION-TYPE
   OBJECTS { snAgGblTrapMessage }
   STATUS current
   DESCRIPTION
	   "The SNMP trap that is generated when MAC-Authentication is successful 
	   on an interface."
   --#TYPE "Foundry Trap: MAC-Authentication success"
   --#SUMMARY "%s."
   --#ARGUMENTS { 0 }
   --#SEVERITY INFORMATIONAL
   --#STATE OPERATIONAL
   ::= { snTraps 87 }

snTrapMacAuthMACRejected NOTIFICATION-TYPE
   OBJECTS { snAgGblTrapMessage }
   STATUS current
   DESCRIPTION
	   "The SNMP trap that is generated when MAC-Authentication is failed 
	   on an interface."
   --#TYPE "Foundry Trap: MAC-Authentication failure"
   --#SUMMARY "%s."
   --#ARGUMENTS { 0 }
   --#SEVERITY WARNING
   --#STATE OPERATIONAL
   ::= { snTraps 88 }

snTrapMacAuthPortDisabled NOTIFICATION-TYPE
   OBJECTS { snAgGblTrapMessage }
   STATUS current
   DESCRIPTION
	   "The SNMP trap that is generated when an interface is disabled due to
	   MAC-Authentication detecting a DOS attack on that interface."
   --#TYPE "Foundry Trap: MAC-Authentication port disabled"
   --#SUMMARY "%s."
   --#ARGUMENTS { 0 }
   --#SEVERITY CRITICAL
   --#STATE OPERATIONAL
   ::= { snTraps 89 }

-- 90 through 103 are OSPFv3 traps

snTrapClientLoginReject NOTIFICATION-TYPE
   OBJECTS { snAgGblTrapMessage }
   STATUS current
   DESCRIPTION
	   "The SNMP trap that is generated when a login attempt by a 
	   telnet or SSH client fails."
   --#TYPE "Foundry Trap: Client Login Reject"
   --#SUMMARY "%s."
   --#ARGUMENTS { 0 }
   --#SEVERITY INFORMATIONAL
   --#STATE OPERATIONAL
   ::= { snTraps 110 }

snTrapLocalUserConfigChange NOTIFICATION-TYPE
   OBJECTS { snAgGblTrapMessage }
   STATUS current
   DESCRIPTION
	   "The SNMP trap that is generated when a local user configuration is changed."
   --#TYPE "Foundry Trap: Local User Config Change"
   --#SUMMARY "%s."
   --#ARGUMENTS { 0 }
   --#SEVERITY INFORMATIONAL
   --#STATE OPERATIONAL
   ::= { snTraps 111 }

snTrapVlanConfigChange NOTIFICATION-TYPE
   OBJECTS { snAgGblTrapMessage }
   STATUS current
   DESCRIPTION
	   "The SNMP trap that is generated when a vlan configuration is changed."
   --#TYPE "Foundry Trap: Vlan Config Change"
   --#SUMMARY "%s."
   --#ARGUMENTS { 0 }
   --#SEVERITY INFORMATIONAL
   --#STATE OPERATIONAL
   ::= { snTraps 112 }

snTrapAclConfigChange NOTIFICATION-TYPE
   OBJECTS { snAgGblTrapMessage }
   STATUS current
   DESCRIPTION
	   "The SNMP trap that is generated when a ACL configuration is changed."
   --#TYPE "Foundry Trap: ACL Config Change"
   --#SUMMARY "%s."
   --#ARGUMENTS { 0 }
   --#SEVERITY INFORMATIONAL
   --#STATE OPERATIONAL
   ::= { snTraps 113 }

snTrapMacFilterConfigChange NOTIFICATION-TYPE
   OBJECTS { snAgGblTrapMessage }
   STATUS current
   DESCRIPTION
	   "The SNMP trap that is generated when a MAC Filter configuration is changed."
   --#TYPE "Foundry Trap: MAC Filter Config Change"
   --#SUMMARY "%s."
   --#ARGUMENTS { 0 }
   --#SEVERITY INFORMATIONAL
   --#STATE OPERATIONAL
   ::= { snTraps 114 }

snTrapSNMPConfigChange NOTIFICATION-TYPE
   OBJECTS { snAgGblTrapMessage }
   STATUS current
   DESCRIPTION
	   "The SNMP trap that is generated when a SNMP configuration is changed."
   --#TYPE "Foundry Trap: SNMP Config Change"
   --#SUMMARY "%s."
   --#ARGUMENTS { 0 }
   --#SEVERITY INFORMATIONAL
   --#STATE OPERATIONAL
   ::= { snTraps 115 }

snTrapSyslogConfigChange NOTIFICATION-TYPE
   OBJECTS { snAgGblTrapMessage }
   STATUS current
   DESCRIPTION
	   "The SNMP trap that is generated when a Syslog configuration is changed."
   --#TYPE "Foundry Trap: Syslog Config Change"
   --#SUMMARY "%s."
   --#ARGUMENTS { 0 }
   --#SEVERITY INFORMATIONAL
   --#STATE OPERATIONAL
   ::= { snTraps 116 }

snTrapPasswordConfigChange NOTIFICATION-TYPE
   OBJECTS { snAgGblTrapMessage }
   STATUS current
   DESCRIPTION
	   "The SNMP trap that is generated when enable or line password is changed."
   --#TYPE "Foundry Trap: Password Config Change"
   --#SUMMARY "%s."
   --#ARGUMENTS { 0 }
   --#SEVERITY INFORMATIONAL
   --#STATE OPERATIONAL
   ::= { snTraps 117 }

snTrapServerStatusChange NOTIFICATION-TYPE
   OBJECTS { snAgGblTrapMessage }
   STATUS current
   DESCRIPTION
	   "The SNMP trap that is generated when a server is disabled or enabled."
   --#TYPE "Foundry Trap: Server Status Change"
   --#SUMMARY "%s."
   --#ARGUMENTS { 0 }
   --#SEVERITY INFORMATIONAL
   --#STATE OPERATIONAL
   ::= { snTraps 118 }

snTrapL4RealServerPortMaxConnectionLimitReached NOTIFICATION-TYPE
   OBJECTS { snAgGblTrapMessage }
   STATUS current
   DESCRIPTION
	   "The SNMP trap that is generated when the real server's port reaches
	   maximum number of connections."
   --#TYPE "Foundry Trap: L4 Real Server Port Max Connection Limit"
   --#SUMMARY "%s."
   --#ARGUMENTS { 0 }
   --#SEVERITY WARNING
   --#STATE OPERATIONAL
   ::= { snTraps 119 }

snTrapL4LinkDown NOTIFICATION-TYPE
   OBJECTS { snL4TrapLinkName, snL4LinkVirtualInterface }
   STATUS current
   DESCRIPTION
	   "The SNMP trap that is generated when the ISP link goes down."
   --#TYPE "Foundry Trap: L4 "
   --#SUMMARY "ISP Link %s bound to ve %d is down."
   --#ARGUMENTS { 0, 1 }
   --#SEVERITY WARNING
   --#STATE OPERATIONAL
   ::= { snTraps 120 }

snTrapL4LinkUp NOTIFICATION-TYPE
   OBJECTS { snL4TrapLinkName, snL4LinkVirtualInterface }
   STATUS current
   DESCRIPTION
	   "The SNMP trap that is generated when the ISP link goes up."
   --#TYPE "Foundry Trap: L4 "
   --#SUMMARY "ISP Link %s bound to ve %d is up."
   --#ARGUMENTS { 0, 1 }
   --#SEVERITY WARNING
   --#STATE OPERATIONAL
   ::= { snTraps 121 }

snTrapPortPriorityChange NOTIFICATION-TYPE
   OBJECTS { snAgGblTrapMessage }
   STATUS current
   DESCRIPTION
	   "The SNMP trap that is generated when the priority of a port is changed."
   --#TYPE "Foundry Trap: Port Priority Change"
   --#SUMMARY "%s."
   --#ARGUMENTS { 0 }
   --#SEVERITY INFORMATIONAL
   --#STATE OPERATIONAL
   ::= { snTraps 122 }

snTrapAutoPortDisableTrigger NOTIFICATION-TYPE
   OBJECTS { snAgGblTrapMessage }
   STATUS current
   DESCRIPTION
	   "The SNMP trap that is generated when automatic port disable was triggered."
   --#TYPE "Foundry Trap: Automatic Port Disable Triggered "
   --#SUMMARY "%s."
   --#ARGUMENTS { 0 }
   --#SEVERITY ALERTS
   --#STATE OPERATIONAL
   ::= { snTraps 123 }

snTrapAutoPortDisableRelease NOTIFICATION-TYPE
   OBJECTS { snAgGblTrapMessage }
   STATUS current
   DESCRIPTION
	   "The SNMP trap that is generated when automatic port disable was released."
   --#TYPE "Foundry Trap: Automatic Port Disable Released "
   --#SUMMARY "%s."
   --#ARGUMENTS { 0 }
   --#SEVERITY ALERTS
   --#STATE OPERATIONAL
   ::= { snTraps 124 }

snTrapPnPStatusChange NOTIFICATION-TYPE
   OBJECTS { wgPnPStatus, wgPnPStatus, snAgGblTrapMessage }
   STATUS current
   DESCRIPTION
	   "The SNMP trap that is generated when plug-and-play status change."
   --#TYPE "Foundry Trap: Plug-and-play Status Change "
   --#SUMMARY "Plug and Play status changed from  %d to %d due to %s."
   --#ARGUMENTS { 0, 1, 2 }
   --#SEVERITY NOTIFICATIONS
   --#STATE OPERATIONAL
   ::= { snTraps 125 }

snTrapWirelessIsrpPeerStateChange NOTIFICATION-TYPE
   OBJECTS { snAgGblTrapMessage }
   STATUS current
   DESCRIPTION
	   "The SNMP trap that is generated when ISRP Peer changes state."
   --#TYPE "Foundry Trap: ISRP Peer's state has changed  "
   --#SUMMARY "%s."
   --#ARGUMENTS { 0 }
   --#SEVERITY NOTIFICATIONS
   --#STATE OPERATIONAL
   ::= { snTraps 126 }

snTrapWirelessStationStateChange NOTIFICATION-TYPE
   OBJECTS { snAgGblTrapMessage }
   STATUS current
   DESCRIPTION
	   "The SNMP trap that is generated when a wireless station's state changes."
   --#TYPE "Foundry Trap: Wireless Station's state has changed."
   --#SUMMARY "%s."
   --#ARGUMENTS { 0 }
   --#SEVERITY NOTIFICATIONS
   --#STATE OPERATIONAL
   ::= { snTraps 127 }

snTrapWirelessStationRoamingEventTriggered NOTIFICATION-TYPE
   OBJECTS { snAgGblTrapMessage }
   STATUS current
   DESCRIPTION
	   "The SNMP trap that is generated when we received a MOVE request from
   the AP"
   --#TYPE "Foundry Trap: Station has roamed "
   --#SUMMARY "%s."
   --#ARGUMENTS { 0 }
   --#SEVERITY NOTIFICATIONS
   --#STATE OPERATIONAL
   ::= { snTraps 128 }

snTrapWirelessSappStateChange NOTIFICATION-TYPE
   OBJECTS { snAgGblTrapMessage }
   STATUS current
   DESCRIPTION
	   "The SNMP trap that is generated when SAPP between an AP and a FIPS
   changes state."
   --#TYPE "Foundry Trap: SAPP between AP and FIPS changes state. "
   --#SUMMARY "%s."
   --#ARGUMENTS { 0 }
   --#SEVERITY NOTIFICATIONS
   --#STATE OPERATIONAL
   ::= { snTraps 129 }

snTrapExternalPowerConnectionStatus NOTIFICATION-TYPE
   OBJECTS { snAgGblTrapMessage }
   STATUS current
   DESCRIPTION
	   "The SNMP trap that is generated when the external power supply
	   connecting or disconnecting to a power over ethernet module."
   --#TYPE "Foundry Trap: External Power Supply Change"
   --#SUMMARY "%s."
   --#ARGUMENTS { 0 }
   --#SEVERITY ALERTS
   --#STATE OPERATIONAL
   ::= { snTraps 130 }

snTrapDot1xSecurityViolation NOTIFICATION-TYPE
   OBJECTS { snAgGblTrapMessage }
   STATUS current
   DESCRIPTION
	   "The SNMP trap that is generated when a malicious mac
	   address was detected."
   --#TYPE "Foundry Trap: 802.1x Security Violation"
   --#SUMMARY "%s."
   --#ARGUMENTS { 0 }
   --#SEVERITY ALERTS
   --#STATE OPERATIONAL
   ::= { snTraps 131 }

snTrapDot1xPortLinkChange NOTIFICATION-TYPE
   OBJECTS { snAgGblTrapMessage }
   STATUS current
   DESCRIPTION
	   "The SNMP trap that is generated when software port link status
	   has changed to up or down."
   --#TYPE "Foundry Trap: 802.1x Port Link Change"
   --#SUMMARY "%s."
   --#ARGUMENTS { 0 }
   --#SEVERITY NOTIFICATIONS
   --#STATE OPERATIONAL
   ::= { snTraps 132 }

snTrapDot1xPortControlChange NOTIFICATION-TYPE
   OBJECTS { snAgGblTrapMessage }
   STATUS current
   DESCRIPTION
	   "The SNMP trap that is generated when software port control status
	   has changed to authorize or unauthorize."
   --#TYPE "Foundry Trap: 802.1x Port Control Change"
   --#SUMMARY "%s."
   --#ARGUMENTS { 0 }
   --#SEVERITY NOTIFICATIONS
   --#STATE OPERATIONAL
   ::= { snTraps 133 }

snTrapDot1xVlanIdChange NOTIFICATION-TYPE
   OBJECTS { snAgGblTrapMessage }
   STATUS current
   DESCRIPTION
	   "The SNMP trap that is generated when VLAN ID of a port
	   has changed."
   --#TYPE "Foundry Trap: 802.1x VLAN ID Change"
   --#SUMMARY "%s."
   --#ARGUMENTS { 0 }
   --#SEVERITY NOTIFICATIONS
   --#STATE OPERATIONAL
   ::= { snTraps 134 }

snTrapDot1xFilterSetupFailure NOTIFICATION-TYPE
   OBJECTS { snAgGblTrapMessage }
   STATUS current
   DESCRIPTION
	   "The SNMP trap that is generated when software failed
	   to setup a filter to a mac address of a port."
   --#TYPE "Foundry Trap: 802.1x Filter Setup Failure"
   --#SUMMARY "%s."
   --#ARGUMENTS { 0 }
   --#SEVERITY NOTIFICATIONS
   --#STATE OPERATIONAL
   ::= { snTraps 135 }

snTrapDot1xError NOTIFICATION-TYPE
   OBJECTS { snAgGblTrapMessage }
   STATUS current
   DESCRIPTION
	   "The SNMP trap that is generated when software detected
	   system error."
   --#TYPE "Foundry Trap: 802.1x Error"
   --#SUMMARY "%s."
   --#ARGUMENTS { 0 }
   --#SEVERITY DEBUGGING
   --#STATE OPERATIONAL
   ::= { snTraps 136 }

snTrapPortConfigChange NOTIFICATION-TYPE
   OBJECTS { snAgGblTrapMessage }
   STATUS current
   DESCRIPTION
	   "The SNMP trap that is generated when a port configuration is changed."
   --#TYPE "Foundry Trap: Port Config Change"
   --#SUMMARY "%s."
   --#ARGUMENTS { 0 }
   --#SEVERITY INFORMATIONAL
   --#STATE OPERATIONAL
   ::= { snTraps 137 }

snTrapMacAuthVlanIdChange NOTIFICATION-TYPE
   OBJECTS { snAgGblTrapMessage }
   STATUS current
   DESCRIPTION
	   "The SNMP trap that is generated when VLAN ID of a port
	   has changed."
   --#TYPE "Foundry Trap: MAC-Authentication VLAN ID Change"
   --#SUMMARY "%s."
   --#ARGUMENTS { 0 }
   --#SEVERITY NOTIFICATIONS
   --#STATE OPERATIONAL
   ::= { snTraps 138 }

snTrapWebAuthEnabled NOTIFICATION-TYPE
   OBJECTS { snAgGblTrapMessage }
   STATUS current
   DESCRIPTION
	   "The SNMP trap that is generated when web authentication is enabled."
	--#TYPE "Foundry Trap: Web Authentication Enabled"
	--#SUMMARY "%s."
	--#ARGUMENTS { 0 }
	--#SEVERITY INFORMATIONAL
	--#STATE OPERATIONAL
   ::= { snTraps 139 }

snTrapWebAuthDisabled NOTIFICATION-TYPE
   OBJECTS { snAgGblTrapMessage }
   STATUS current
   DESCRIPTION
	   "The SNMP trap that is generated when web authentication is disabled."
	--#TYPE "Foundry Trap: Web Authentication Disabled"
	--#SUMMARY "%s."
	--#ARGUMENTS { 0 }
	--#SEVERITY INFORMATIONAL
	--#STATE OPERATIONAL
   ::= { snTraps 140 }

snTrapIpConfigChange NOTIFICATION-TYPE
   OBJECTS { snAgGblTrapMessage }
   STATUS current
   DESCRIPTION
	   "The SNMP trap that is generated when IP system address changes."
	--#TYPE "Foundry Trap: IP Configuration Change"
	--#SUMMARY "%s."
	--#ARGUMENTS { 0 }
	--#SEVERITY INFORMATIONAL
	--#STATE OPERATIONAL
   ::= { snTraps 141 }

snTrapIpv6ConfigChange NOTIFICATION-TYPE
   OBJECTS { snAgGblTrapMessage }
   STATUS current
   DESCRIPTION
	   "The SNMP trap that is generated when IPv6 system address changes."
	--#TYPE "Foundry Trap: IPv6 Configuration Change"
	--#SUMMARY "%s."
	--#ARGUMENTS { 0 }
	--#SEVERITY INFORMATIONAL
	--#STATE OPERATIONAL
   ::= { snTraps 142 }

snTrapMacAuthRadiusTimeout NOTIFICATION-TYPE
   OBJECTS { snAgGblTrapMessage }
   STATUS current
   DESCRIPTION
	   "The SNMP trap that is generated when a request from Mac-Auth
	   to RADIUS has not been answered within the retry and time limit."
	--#TYPE "Foundry Trap: MAC-Authentication RADIUS timeout"
	--#SUMMARY "%s."
	--#ARGUMENTS { 0 }
	--#SEVERITY NOTIFICATIONS
	--#STATE OPERATIONAL
   ::= { snTraps 143 }

snTrapDot1xRadiusTimeout NOTIFICATION-TYPE
   OBJECTS { snAgGblTrapMessage }
   STATUS current
   DESCRIPTION
	   "The SNMP trap that is generated when a request from 802.1x
	   to RADIUS has not been answered within the retry and time limit."
	--#TYPE "Foundry Trap: MAC-Authentication RADIUS timeout"
	--#SUMMARY "%s."
	--#ARGUMENTS { 0 }
	--#SEVERITY NOTIFICATIONS
	--#STATE OPERATIONAL
   ::= { snTraps 144 }

snTrapUDLDLinkDown NOTIFICATION-TYPE
   OBJECTS { ifIndex, snAgGblTrapMessage }
   STATUS current
   DESCRIPTION
	   "The SNMP trap that is generated when UDLD port link status
	   has changed to down."
	--#TYPE "Foundry Trap: UDLD Port Link Down"
	--#SUMMARY "%s."
	--#ARGUMENTS { 1 }
	--#SEVERITY NOTIFICATIONS
	--#STATE OPERATIONAL
   ::= { snTraps 145 }

snTrapUDLDLinkUp NOTIFICATION-TYPE
   OBJECTS { ifIndex, snAgGblTrapMessage }
   STATUS current
   DESCRIPTION
	   "The SNMP trap that is generated when UDLD port link status
	   has changed to up."
	--#TYPE "Foundry Trap: UDLD Port Link Up"
	--#SUMMARY "%s."
	--#ARGUMENTS { 1 }
	--#SEVERITY NOTIFICATIONS
	--#STATE OPERATIONAL
   ::= { snTraps 146 }

snTrapMacBasedVlanEnabled NOTIFICATION-TYPE
   OBJECTS { snAgGblTrapMessage }
   STATUS current
   DESCRIPTION
	   "The SNMP trap that is generated when MAC based VLAN is enabled."
	--#TYPE "Foundry Trap: MAC based VLAN enabled"
	--#SUMMARY "%s."
	--#ARGUMENTS { 0 }
	--#SEVERITY NOTIFICATIONS
	--#STATE OPERATIONAL
   ::= { snTraps 147 }

snTrapMacBasedVlanDisabled NOTIFICATION-TYPE
   OBJECTS { snAgGblTrapMessage }
   STATUS current
   DESCRIPTION
	   "The SNMP trap that is generated when MAC based VLAN is disabled."
	--#TYPE "Foundry Trap: MAC based VLAN disabled"
	--#SUMMARY "%s."
	--#ARGUMENTS { 0 }
	--#SEVERITY NOTIFICATIONS
	--#STATE OPERATIONAL
   ::= { snTraps 148 }

snTrapChasFanNormal NOTIFICATION-TYPE
   OBJECTS { snChasFanIndex, snChasFanDescription }
   STATUS current
   DESCRIPTION
	   "The SNMP trap that is generated when a fan operational status
		changed from failure to normal."
	--#TYPE "Foundry Trap: Fan OK"
	--#SUMMARY "Fan  %d (%s)  OK."
	--#ARGUMENTS { 0, 1 }
	--#SEVERITY MINOR
	--#STATE OPERATIONAL
   ::= { snTraps 149 }

snTrapStpRootGuardDetect NOTIFICATION-TYPE
	OBJECTS {ifIndex, snVLanByPortCfgVLanId, snAgGblTrapMessage}
	STATUS current
	DESCRIPTION
	   "The SNMP trap that is generated when VLAN's Root-Guarded port received superior BPDU."
	--#TYPE "Foundry Trap:  Stp root guard detect"
	--#SUMMARY "%s."
	--#ARGUMENTS {  2  }
	--#SEVERITY NOTIFICATIONS
	--#STATE OPERATIONAL
   ::= { snTraps 150 } 

snTrapStpRootGuardExpire NOTIFICATION-TYPE
   OBJECTS {ifIndex, snVLanByPortCfgVLanId, snAgGblTrapMessage}
   STATUS current
   DESCRIPTION
		   "The SNMP trap that is generated when VLAN's ports's Root-Guard expire."
	 --#TYPE "Foundry Trap:  Stp root guard expire"
	 --#SUMMARY "%s."
	 --#ARGUMENTS { 2 }
	 --#SEVERITY NOTIFICATIONS
	 --#STATE OPERATIONAL
   ::= { snTraps 151 }
 
snTrapStpBPDUGuardDetect NOTIFICATION-TYPE
   OBJECTS {ifIndex, snVLanByPortCfgVLanId, snAgGblTrapMessage}
   STATUS current
   DESCRIPTION
	   "The SNMP trap that is generated when VLAN's BPDU-guarded port received BPDU . "
	 --#TYPE "Foundry Trap: STP BPDU guard "
	 --#SUMMARY "%s."
	 --#ARGUMENTS { 2 }
	 --#SEVERITY NOTIFICATIONS
	 --#STATE OPERATIONAL
   ::= { snTraps 152 }

snTrapMstpBPDUGuardDetect NOTIFICATION-TYPE
   OBJECTS {ifIndex, snAgGblTrapMessage}
   STATUS current
   DESCRIPTION
	   "The SNMP trap that is generated when BPDU-guarded port received BPDU . "
	 --#TYPE "Foundry Trap: MSTP BPDU guard "
	 --#SUMMARY "%s."
	 --#ARGUMENTS { 1 }
	 --#SEVERITY NOTIFICATIONS
	 --#STATE OPERATIONAL
   ::= { snTraps 153 }

snTrapErrorDisableAction NOTIFICATION-TYPE
   OBJECTS {ifIndex, snAgGblTrapMessage}
   STATUS current
   DESCRIPTION
	   "The SNMP trap that is generated when  Interface error-disable is hit or recovery times out . "
	 --#TYPE "Foundry Trap:  Error-disable hit or recovery times out"
	 --#SUMMARY "%s."
	 --#ARGUMENTS {  1  }
	 --#SEVERITY NOTIFICATIONS
	 --#STATE OPERATIONAL
   ::= { snTraps 154 }

snTrapLACPLinkStateChange NOTIFICATION-TYPE
   OBJECTS {ifIndex, snAgGblTrapMessage}
   STATUS current
   DESCRIPTION
	   "The SNMP trap that is generated when LACP port changes its state. "
	 --#TYPE "Foundry Trap:  LACP port state change"
	 --#SUMMARY "%s."
	 --#ARGUMENTS {  1  }
	 --#SEVERITY NOTIFICATIONS
	 --#STATE OPERATIONAL
   ::= { snTraps 155 }

snTrapOpticalMonitoringNotFoundryOptics NOTIFICATION-TYPE
   OBJECTS {snAgGblTrapMessage}
   STATUS current
   DESCRIPTION
	   "The SNMP trap that is generated if optical monitoring is enabled but optics vendor is not Foundry Networks."
	--#TYPE "Foundry Trap: Optical Monitoring Not Foundry Networks Optics"
	--#SUMMARY "%s."
	--#ARGUMENTS { 0 }
	--#SEVERITY ALERTS
	--#STATE OPERATIONAL
   ::= { snTraps 156 }

snTrapOpticalMonitoringFoundryOpticsNotCapable NOTIFICATION-TYPE
   OBJECTS {snAgGblTrapMessage}
   STATUS current
   DESCRIPTION
	   "The SNMP trap that is generated if optical monitoring is enabled but the Foundry optic is not capable."
	--#TYPE "Foundry Trap: Optical Monitoring Optics Not Capable"
	--#SUMMARY "%s."
	--#ARGUMENTS { 0 }
	--#SEVERITY ALERTS
	--#STATE OPERATIONAL
   ::= { snTraps 157 }

snTrapStaticMulticastMacConfigAdd NOTIFICATION-TYPE
   OBJECTS {snAgGblTrapMessage}
   STATUS current
   DESCRIPTION
	   "The SNMP trap that is generated if a new entry is added to static multicast mac configuration table.
		Format 1: Static Mac entry with Mac Address <xxxx:xxxx:xxxx> is added to portnumber <port> on VLAN <id>
		Format 2: Static Mac entry with Mac Address <xxxx:xxxx:xxxx> is added to portmask <0xXXXXXXXX-XXXXXXXX> on VLAN <id>"
	--#TYPE "Foundry Trap: New Entry is Added To Static Multicast Mac Configuration Table."
	--#SUMMARY "%s."
	--#ARGUMENTS { 0 }
	--#SEVERITY NOTIFICATIONS
	--#STATE OPERATIONAL
   ::= { snTraps 158 }

snTrapStaticMulticastMacConfigRemove NOTIFICATION-TYPE
   OBJECTS {snAgGblTrapMessage}
   STATUS current
   DESCRIPTION
	   "The SNMP trap that is generated if an entry is removed from static multicast mac configuration table .
		Format 1: Static Mac entry with Mac Address <xxxx:xxxx:xxxx> is deleted from portnumber <port> on VLAN <id>
		Format 2: Static Mac entry with Mac Address <xxxx:xxxx:xxxx> is deleted from portmask <0xXXXXXXXX-XXXXXXXX> on VLAN <id>"
	--#TYPE "Foundry Trap:  Entry is Removed From Static Multicast Mac Configuration Table."
	--#SUMMARY "%s."
	--#ARGUMENTS { 0 }
	--#SEVERITY NOTIFICATIONS
	--#STATE OPERATIONAL
   ::= { snTraps 159 }

snTrapSTPBPDUGuardExpire NOTIFICATION-TYPE
   OBJECTS { ifIndex, snVLanByPortCfgVLanId, snAgGblTrapMessage }
   STATUS current
   DESCRIPTION
	   "The SNMP notification that is generated when a port is re-enabled after being disabled due to BPDU Guard Violation.
		Format: STP: BPDU Guard re-enabled on VLAN <id> port <slot>/<port>"
		--#TYPE "Foundry Trap: STP BPDU Guard Expire"
		--#SUMMARY "%s."
		--#ARGUMENTS { 2 }
		--#SEVERITY NOTIFICATIONS
		--#STATE OPERATIONAL
::= { snTraps 160 }

snTrapPortLoopDetection NOTIFICATION-TYPE
   OBJECTS { ifIndex, snVLanByPortCfgVLanId, snAgGblTrapMessage }
   STATUS current
   DESCRIPTION
	   "The SNMP notification is generated when a port loop is detected.
	   Format: LOOP DETECTION: VLAN <id>,  port <slot>/<port> detect, putting into err-disable state"
			--#TYPE "Foundry Trap: Port Loop Detection"
			--#SUMMARY "%s."
			--#ARGUMENTS { 2 }
			--#SEVERITY NOTIFICATIONS
			--#STATE OPERATIONAL
   ::= { snTraps 161 }

snTrapNoFreeTcamEntry NOTIFICATION-TYPE
   OBJECTS { snAgGblTrapMessage }
   STATUS current
   DESCRIPTION
	   "The SNMP trap that is generated when system is running out of TCAM spaces allocated for routing entries. "
		--#TYPE "Foundry Trap: No TCAM free entry"
		--#SUMMARY "%s."
		--#ARGUMENTS { 0 }
		--#SEVERITY ALERTS
		--#STATE OPERATIONAL
   ::= { snTraps 162 }

-- Stacking traps

snTrapStackingMasterElected NOTIFICATION-TYPE
   OBJECTS { snChasUnitIndex,  snAgGblTrapMessage }
   STATUS current
   DESCRIPTION
	   "The SNMP trap that is generated when a unit is elected as Master unit for the stacking system."
  --#TYPE "Foundry Trap: Unit is elected as Master"
  --#SUMMARY "%s."
  --#ARGUMENTS { 1 }
  --#SEVERITY MINOR
  --#STATE OPERATIONAL
   ::= { snTraps 163 }

 snTrapStackingUnitAdded NOTIFICATION-TYPE
   OBJECTS { snChasUnitIndex,  snAgGblTrapMessage }
   STATUS current
   DESCRIPTION
	   "The SNMP trap that is generated when a unit has been added to the stacking system."
  --#TYPE "Foundry Trap: Unit is added"
  --#SUMMARY "%s."
  --#ARGUMENTS { 1 }
  --#SEVERITY MINOR
  --#STATE OPERATIONAL
   ::= { snTraps 164 }

 snTrapStackingUnitDeleted NOTIFICATION-TYPE
   OBJECTS { snChasUnitIndex,  snAgGblTrapMessage }
   STATUS current
   DESCRIPTION
	   "The SNMP trap that is generated when a unit has been deleted from the stacking system."
  --#TYPE "Foundry Trap: Unit is deleted"
  --#SUMMARY "%s."
  --#ARGUMENTS { 1 }
  --#SEVERITY MINOR
  --#STATE OPERATIONAL
   ::= { snTraps 165 }

snTrapStackingChasPwrSupplyOK NOTIFICATION-TYPE
   OBJECTS { snChasUnitIndex, snChasPwrSupplyIndex, snAgGblTrapMessage }
   STATUS current
   DESCRIPTION
	   "The SNMP trap that is generated when a power supply operational
		status changed from failure to normal for a stacking system."
  --#TYPE "Foundry Trap: Stacking Power Supply OK"
  --#SUMMARY "%s."
  --#ARGUMENTS { 2 }
  --#SEVERITY MINOR
  --#STATE OPERATIONAL
   ::= { snTraps 166 }
   
snTrapStackingChasPwrSupplyFailed NOTIFICATION-TYPE
   OBJECTS { snChasUnitIndex, snChasPwrSupplyIndex, snAgGblTrapMessage }
   STATUS current
   DESCRIPTION
	   "The SNMP trap that is generated when a power supply operational
		status changed from normal to failure for a stacking system."
		--#TYPE "Foundry Trap: Stacking Power Supply Failure"
		--#SUMMARY "%s."
		--#ARGUMENTS { 2 }
		--#SEVERITY MINOR
		--#STATE OPERATIONAL
   ::= { snTraps 167 }

snTrapStackingChasFanNormal NOTIFICATION-TYPE
   OBJECTS { snChasUnitIndex, snChasFanIndex, snChasFanDescription }
   STATUS current
   DESCRIPTION
	   "The SNMP trap that is generated when a fan operational status
		changed from failure to normal for a stacking system"
		--#TYPE "Foundry Trap: Stacking Fan OK"
		--#SUMMARY "Stack-unit %d Fan  %d (%s)  OK."
		--#ARGUMENTS { 0, 1, 2}
		--#SEVERITY MINOR
		--#STATE OPERATIONAL
   ::= { snTraps 168 }
   
snTrapStackingChasFanFailed NOTIFICATION-TYPE
   OBJECTS { snChasUnitIndex, snChasFanIndex, snChasFanDescription }
   STATUS current
   DESCRIPTION
	   "The SNMP trap that is generated when a fan fails
		to operate normally for a stacking system."
		--#TYPE "Foundry Trap: Stacking Fan Failure"
		--#SUMMARY "Stack-unit %d Fan  %d (%s)  failed."
		--#ARGUMENTS { 0, 1, 2 }
		--#SEVERITY MINOR
		--#STATE OPERATIONAL
   ::= { snTraps 169 }

 snTrapStackingManagementMACChanged NOTIFICATION-TYPE
   OBJECTS { snAgGblTrapMessage }
   STATUS current
   DESCRIPTION
	   "The SNMP trap that is generated when the managemnet MAC
		address of a stacking system has been changed."
	--#TYPE "Foundry Trap: The management MAC address changed "
	--#SUMMARY "%s."
	--#ARGUMENTS { 0 }
	--#SEVERITY NOTIFICATIONS
	--#STATE OPERATIONAL
   ::= { snTraps 170 }  

  snTrapStackingTemperatureWarning NOTIFICATION-TYPE
   OBJECTS { snChasUnitIndex, snAgGblTrapMessage }
   STATUS current
   DESCRIPTION
	   "The SNMP trap that is generated when the actual temperature
	   reading is above the warning temperature threshold for a stack
	   sytem."
	   --#TYPE "Foundry Trap: Stacking Temperature Warning"
	   --#SUMMARY "%s."
	   --#ARGUMENTS { 1 }
	   --#SEVERITY CRITICAL
	   --#STATE OPERATIONAL
   ::= { snTraps 171 }

snTrapIfIndexAssignmentChanged NOTIFICATION-TYPE
   OBJECTS { snAgGblTrapMessage }
   STATUS current
   DESCRIPTION
	   "The SNMP trap that is generated when the Interface Index (IfIndex)
		assignment for the physical interfaces was changed."
	--#TYPE "Foundry Trap: IfIndex Assignment Changed"
	--#SUMMARY "%s."
	--#ARGUMENTS { 0 }
	--#SEVERITY INFORMATIONAL
	--#STATE OPERATIONAL
   ::= { snTraps 172 }

snTrapPBRConfigChanged NOTIFICATION-TYPE
   OBJECTS { snAgGblTrapMessage }
   STATUS current
   DESCRIPTION
	  "The SNMP trap that is generated when a Policy Based Routing (PBR) routemap 
	   is bound or unbound either globally or to an interface."
	  --#TYPE "Foundry Trap: Policy Based Routing (PBR) Config Changed "
	  --#SUMMARY "%s."
	  --#ARGUMENTS { 0 }
	  --#SEVERITY ALERTS
	  --#STATE OPERATIONAL
   ::= { snTraps  173 }

snTrapChasPwrSupplyRPSAdd NOTIFICATION-TYPE
   OBJECTS { snChasPwrSupplyIndex, snChasPwrSupplyDescription }
   STATUS current
   DESCRIPTION
	   "The SNMP trap that is generated when an External Redundant 
	   Power Supply (RPS2-EIF) is added to the system."
  --#TYPE "Foundry Trap: Power Supply RPS Added"
  --#SUMMARY "External redundant power supply %d (%s) added."
  --#ARGUMENTS { 0, 1 }
  --#SEVERITY MINOR
  --#STATE OPERATIONAL
   ::= { snTraps 174}
   
snTrapChasPwrSupplyRPSRemove NOTIFICATION-TYPE
   OBJECTS { snChasPwrSupplyIndex, snChasPwrSupplyDescription }
   STATUS current
   DESCRIPTION
	   "The SNMP trap that is generated when an External Redundant 
	   Power Supply (RPS2-EIF) is removed from the system."
  --#TYPE "Foundry Trap: Power Supply RPS Removed"
  --#SUMMARY "External redundant power supply %d (%s) removed."
  --#ARGUMENTS { 0, 1 }
  --#SEVERITY MINOR
  --#STATE OPERATIONAL
   ::= { snTraps 175}

snTrapModuleStatusChange NOTIFICATION-TYPE
   OBJECTS { snChasUnitIndex, snAgentBrdIndex, snAgentBrdModuleStatus, snAgGblTrapMessage }
   STATUS current
   DESCRIPTION
	   "The SNMP notification that is generated when a module's operational state changes.
	   The management entity receiving the notification can identify the
	   module and the event by referencing snChasUnitIndex, snAgentBrdIndex, snAgentBrdModuleStatus.
	   In case of a module-down event, the varbind snAgGblTrapMessage is a text string 
	   that describes the cause. In case of module-up event, snAgGblTrapMessage is a null
	   string. "
	--#TYPE "Foundry Trap: Module status changed"
	--#SUMMARY " Module %d (of unit %d) changed state to %d due to reason: %s."
	--#ARGUMENTS { 1,0,2,3 }
	--#SEVERITY NOTIFICATION
	--#STATE OPERATIONAL
   ::= { snTraps 176 }

snTrapChasHighSpeedFansNeeded NOTIFICATION-TYPE
   OBJECTS { snAgGblTrapMessage }
   STATUS current
   DESCRIPTION
	   "The SNMP trap that is generated when chassis doesn't have high speed fans for specific modules"
	--#TYPE "Foundry Trap: High Speed fans needed"
	--#SUMMARY "%s"
	--#ARGUMENTS { 0 }
	--#SEVERITY WARNING
	--#STATE OPERATIONAL
   ::= { snTraps 177 }

snTrapSysmaxReverted NOTIFICATION-TYPE
   OBJECTS { snAgGblTrapMessage }
   STATUS current
   DESCRIPTION
	   "The SNMP trap that is generated when the revertible
		sysmax elements are reverted during the card bringup
		if they can not be accomodated in the available memory."
	--#TYPE "Foundry Trap: Sysmax Reverted"
	--#SUMMARY "%s."
	--#ARGUMENTS { 0 }
	--#SEVERITY WARNING
	--#STATE OPERATIONAL
   ::= { snTraps 178 }


snTrapSysmaxLeftLowMem NOTIFICATION-TYPE
   OBJECTS { snAgGblTrapMessage }
   STATUS current
   DESCRIPTION
	   "The SNMP trap that is generated when its found during bootup that
		the configured sysmax set shall leave less than 10% available memory free."
	--#TYPE "Foundry Trap: Sysmax Left Low Memory"
	--#SUMMARY "%s."
	--#ARGUMENTS { 0 }
	--#SEVERITY WARNING
	--#STATE OPERATIONAL
   ::= { snTraps 179 }


snTrapSysMemoryLowThreshold NOTIFICATION-TYPE
   OBJECTS { snAgGblTrapMessage }
   STATUS current
   DESCRIPTION
	   "The SNMP trap that is generated when the available dynamic memory
		in a card is below 5% of the installed physical memory."
	--#TYPE "Foundry Trap: Low Available Memory"
	--#SUMMARY "%s."
	--#ARGUMENTS { 0 }
	--#SEVERITY WARNING
	--#STATE OPERATIONAL
   ::= { snTraps 180 }


snTrapSysMemoryOutThreshold NOTIFICATION-TYPE
   OBJECTS { snAgGblTrapMessage }
   STATUS current
   DESCRIPTION
	   "The SNMP trap that is generated when the dynamic memory
		fails to be allocated in a system."
	--#TYPE "Foundry Trap: Failed Memory Allocation"
	--#SUMMARY "%s."
	--#ARGUMENTS { 0 }
	--#SEVERITY WARNING
	--#STATE OPERATIONAL
   ::= { snTraps 181 }

snTrapLinkOAMLinkDown NOTIFICATION-TYPE
   OBJECTS {ifIndex, snAgGblTrapMessage }
   STATUS current
   DESCRIPTION
	   "The SNMP trap that is generated when Link-OAM port link status
	   has changed to down."
	  --#TYPE "Foundry Trap: Link-OAM Port Link Change"
	  --#SUMMARY "%s"
	  --#ARGUMENTS { 1 }
	  --#SEVERITY NOTIFICATIONS
	  --#STATE OPERATIONAL
   ::= { snTraps 182 }

snTrapLinkOAMLinkUp NOTIFICATION-TYPE
   OBJECTS {ifIndex, snAgGblTrapMessage }
   STATUS current
   DESCRIPTION
	   "The SNMP trap that is generated when Link-OAM port link status
	   has changed to up."
	  --#TYPE "Foundry Trap: Link-OAM Port Link Change"
	  --#SUMMARY "%s"
	  --#ARGUMENTS { 1 }
	  --#SEVERITY NOTIFICATIONS
	  --#STATE OPERATIONAL
   ::= { snTraps 183 }

snTrapI2CAccessLog NOTIFICATION-TYPE
   OBJECTS { snAgGblTrapMessage }
   STATUS current
   DESCRIPTION
	   "The SNMP trap that is generated to provide information about state of the management module's  I2C accesses."
	--#TYPE "Foundry Trap: MP I2C access data"
	--#SUMMARY "%s."
	--#ARGUMENTS { 0 }
	--#SEVERITY WARNING
	--#STATE OPERATIONAL
   ::= { snTraps 184 }
   
snTrapLinkOAMLoopbackEntered NOTIFICATION-TYPE
   OBJECTS {ifIndex, dot3OamLoopbackStatus, snAgGblTrapMessage }
   STATUS current
   DESCRIPTION
	   "The SNMP trap that is generated when Link-OAM port has entered
	   loopback mode. The link is not useful for data transfer any more."
	  --#TYPE "Foundry Trap: Link-OAM Port Loopback Mode"
	  --#SUMMARY "%s"
	  --#ARGUMENTS { 2 }
	  --#SEVERITY NOTIFICATIONS
	  --#STATE OPERATIONAL
   ::= { snTraps 185 }
   
snTrapLinkOAMLoopbackCleared NOTIFICATION-TYPE
   OBJECTS {ifIndex, dot3OamLoopbackStatus, snAgGblTrapMessage }
   STATUS current
   DESCRIPTION
	   "The SNMP trap that is generated when Link-OAM port has entered
	   loopback mode. The link is not useful for data transfer any more."
	  --#TYPE "Foundry Trap: Link-OAM Port Loopback Mode"
	  --#SUMMARY "%s"
	  --#ARGUMENTS { 2 }
	  --#SEVERITY NOTIFICATIONS
	  --#STATE OPERATIONAL
   ::= { snTraps 186 }
   
snTrapLicenseAdded NOTIFICATION-TYPE
   OBJECTS { snAgGblTrapMessage }
   STATUS current
   DESCRIPTION
	   "The SNMP trap that is generated when a new license is added to the system."
				--#TYPE "Foundry Trap: New license added"
				--#SUMMARY "%s."
				--#ARGUMENTS { 0 }
				--#SEVERITY NOTIFICATIONS
				--#STATE OPERATIONAL
   ::= { snTraps 187 }

snTrapLicenseRemoved NOTIFICATION-TYPE
   OBJECTS { snAgGblTrapMessage }
   STATUS current
   DESCRIPTION
	   "The SNMP trap that is generated when an existing license is removed from the system."
				--#TYPE "Foundry Trap: License removed"
				--#SUMMARY "%s."
				--#ARGUMENTS { 0 }
				--#SEVERITY NOTIFICATIONS
				--#STATE OPERATIONAL
   ::= { snTraps 188 }

snTrapLicenseExpires NOTIFICATION-TYPE
   OBJECTS { snAgGblTrapMessage }
   STATUS current
   DESCRIPTION
	   "The SNMP trap that is generated when a trial license is about to expire. This trap is generated
		daily for last 3 days and every 2 hours on the last day of expire."
				--#TYPE "Foundry Trap: License is about to expire"
				--#SUMMARY "%s."
				--#ARGUMENTS { 0 }
				--#SEVERITY WARNING
				--#STATE OPERATIONAL
   ::= { snTraps 189 }

snTrapLicenseExpired NOTIFICATION-TYPE
   OBJECTS { snAgGblTrapMessage }
   STATUS current
   DESCRIPTION
	   "The SNMP trap that is generated when a trial license has expired."
				--#TYPE "Foundry Trap: License expired"
				--#SUMMARY "%s."
				--#ARGUMENTS { 0 }
				--#SEVERITY WARNING
				--#STATE OPERATIONAL
   ::= { snTraps 190 }

snTrapUDLDCrcFailureDetected    NOTIFICATION-TYPE
   OBJECTS {ifIndex, snAgGblTrapMessage}
   STATUS current
   DESCRIPTION
                  "The SNMP trap that is generated when UDLD detects CRC failures on  PDUs received on a port"
                 --#TYPE "Foundry Trap:  UDLD detected CRC failures "
                 --#SUMMARY "%s."
                 --#ARGUMENTS { 1 }
                 --#SEVERITY WARNING
                 --#STATE OPERATIONAL
   ::= { snTraps 191 }

snTrapStackingStandbyElected NOTIFICATION-TYPE
   OBJECTS { snChasUnitIndex,  snAgGblTrapMessage }
   STATUS current
   DESCRIPTION
                   "The SNMP trap that is generated when a unit is elected as Standby unit for the stacking system."
  --#TYPE "Brocade Trap: Unit is elected as Standby"
  --#SUMMARY "%s."
  --#ARGUMENTS { 1 }
  --#SEVERITY MINOR
  --#STATE OPERATIONAL
   ::= { snTraps 196 }

snTrapMacMoveThresholdRate NOTIFICATION-TYPE
   OBJECTS { snAgGblTrapMessage }
   STATUS current
   DESCRIPTION
	   "The SNMP notification is generated when MAC movement exceeding the certain threshold for a sampling interval is detected.
	   Format: Mac-Move threshold-rate: MAC address <mac> moved from interface <port-id> to interface <port-id> for vlan <vlan-id>, 
	   <move-count> times exceeding the threshold rate <threshold-rate> for a sampling interval <interval> seconds"
			--#TYPE "Brocade Trap: MAC movement threshold-rate Detection"
			--#SUMMARY "%s."
			--#ARGUMENTS { 0 }
			--#SEVERITY NOTIFICATIONS
			--#STATE OPERATIONAL
   ::= { snTraps 197 }

snTrapMacMoveIntervalHistory NOTIFICATION-TYPE
   OBJECTS { snAgGblTrapMessage }
   STATUS current
   DESCRIPTION
	   "The SNMP notification is generated every user configured interval, summarizing the moves in the interval .
	   Format: Mac-Move Interval-History: <#macs> macs moved in last <interval> seconds. Total number of mac moves in the interval is <#moves>"
			--#TYPE "Brocade Trap: MAC movement interval-history Detection"
			--#SUMMARY "%s."
			--#ARGUMENTS { 0 }
			--#SEVERITY NOTIFICATIONS
			--#STATE OPERATIONAL
   ::= { snTraps 198 }

snTrapStackingMixedModeChanged NOTIFICATION-TYPE
   OBJECTS { snStackingGlobalMixedMode, snAgGblTrapMessage }
   STATUS current
   DESCRIPTION
	   "The SNMP trap that is generated when a stacking system mode is changed.
	   Format: The stacking system is changed to Mixed Stacking mode "
  --#TYPE "Brocade Trap: The system mixed stacking mode is changed"
  --#SUMMARY "%s."
  --#ARGUMENTS { 0, 1 }
  --#SEVERITY NOTIFICATIONS
  --#STATE OPERATIONAL
   ::= { snTraps 199 }

snTrapSysMonErrorDetect NOTIFICATION-TYPE
   OBJECTS { snAgGblTrapMessage }
   STATUS current
   DESCRIPTION
	   "The SNMP notification is generated when SYSMON detects internal error."
			--#TYPE "Brocade Trap: SYSMON error Detection"
			--#SUMMARY "%s."
			--#ARGUMENTS { 0 }
			--#SEVERITY WARNING
			--#STATE OPERATIONAL
   ::= { snTraps 200 }

snTrapMacNotification NOTIFICATION-TYPE
   OBJECTS { snAgGblTrapMessage }
   STATUS current
   DESCRIPTION
	   "The SNMP notification is generated when MAC event(s) is(are) detected.
	   Format: MAC-Event:MAC:<mac>-VLAN:<vlan-id>-PORT:<port-id>-ACT:<action>::MAC:<mac>-VLAN:<vlan-id>-PORT:<port-id>-ACT:<action>:: ...
	   		...MAC:<mac>-VLAN:<vlan-id>-PORT:<port-id>-ACT:<action>::
 			where action: 1-MAC addition; 2-MAC deletion; 3-remove all MACs; 4-remove MAC from a port; 
 			5-remove MAC from a VLAN; 6-remove MAC from a VLAN on a port"
			--#TYPE "Brocade Trap: MAC event notification"
			--#SUMMARY "%s."
			--#ARGUMENTS { 0 }
			--#SEVERITY NOTIFICATIONS
			--#STATE OPERATIONAL
   ::= { snTraps 201 }

snTrapMacEventBufferFull NOTIFICATION-TYPE
   OBJECTS { snAgGblTrapMessage }
   STATUS current
   DESCRIPTION
	   "The SNMP notification is generated when MAC event buffer full is detected.
	   Format: MAC-Event: The Buffer is full, FDB table walk is required"
			--#TYPE "Brocade Trap: MAC event buffer full detection"
			--#SUMMARY "%s."
			--#ARGUMENTS { 0 }
			--#SEVERITY WARNING
			--#STATE OPERATIONAL
   ::= { snTraps 202 }

snTrapStpDesignatedGuardDetect NOTIFICATION-TYPE
    OBJECTS {ifIndex, snVLanByPortCfgVLanId, snAgGblTrapMessage}
    STATUS current
    DESCRIPTION
       "The SNMP trap that is generated when VLAN's ports's Designated-Guard detect."
    --#TYPE "Foundry Trap:  Stp designated guard detect"
    --#SUMMARY "%s."
    --#ARGUMENTS {  2  }
    --#SEVERITY NOTIFICATIONS
    --#STATE OPERATIONAL
   ::= { snTraps 203 }

snTrapStpDesignatedGuardDisable NOTIFICATION-TYPE
   OBJECTS {ifIndex, snVLanByPortCfgVLanId, snAgGblTrapMessage}
   STATUS current
   DESCRIPTION
           "The SNMP trap that is generated when VLAN's ports's Designated-Guard disable."
     --#TYPE "Foundry Trap:  Stp designated guard disable"
     --#SUMMARY "%s."
     --#ARGUMENTS { 2 }
     --#SEVERITY NOTIFICATIONS
     --#STATE OPERATIONAL
   ::= { snTraps 204 }

snTrapLicenseNNLLTrialNotify NOTIFICATION-TYPE
   OBJECTS { snAgGblTrapMessage }
   STATUS current
   DESCRIPTION
	   "The SNMP trap that is generated when a non-node locked licensed feature is enabled with 
	   no a non-node locked license installed.
	   Format: Stack <stack_id>: Use of the <feature_name> feature requires a license to be purchased 
	   and installed within <day> days. "
	--#TYPE "Foundry Trap: add a NNLL license"
	--#SUMMARY "%s."
	--#ARGUMENTS { 0 }
	--#SEVERITY NOTIFICATIONS
	--#STATE OPERATIONAL
   ::= { snTraps 205 }

snTrapLicenseNNLLTrialExpiry NOTIFICATION-TYPE
   OBJECTS { snAgGblTrapMessage }
   STATUS current
   DESCRIPTION
	   "The SNMP trap that is generated when a non-node locked licensed feature is enabled after 
	   30-44 days with no a non-node locked license installed. This message will be displayed 3 times 
	   day 30, day 37, day 44. 
	   Format: Stack <stack_id>: The <feature_name> feature has been activated for <day> days. 
	   To ensure compliance, please purchase and install a license as soon as possible "
	--#TYPE "Foundry Trap: Need to add a NNLL license"
	--#SUMMARY "%s."
	--#ARGUMENTS { 0 }
	--#SEVERITY NOTIFICATIONS
	--#STATE OPERATIONAL
   ::= { snTraps 206 }

snTrapLicenseNNLLNonCompliant NOTIFICATION-TYPE
   OBJECTS { snAgGblTrapMessage }
   STATUS current
   DESCRIPTION
	   "The SNMP trap that is generated when a non-node locked licensed feature is enabled after 45+ days 
	   whit no a non-node locked license installed. Or deletion of an installed license if any of the 
	   associsted features are still enabled. This message will be displayed daily.
	   Format: Stack <shack_id>: THIS UNIT IS NOT COMPLIANT. A license for <feature_name> feature must 
	   be purchased and installed or the feature <feature_name> must be deactivated to become compliant 
	   with the terms and conditions of use "
	--#TYPE "Foundry Trap: have to add a NNLL license"
	--#SUMMARY "%s."
	--#ARGUMENTS { 0 }
	--#SEVERITY WARNING
	--#STATE OPERATIONAL
   ::= { snTraps 207 }

   snTrapLicenseNNLLDelete NOTIFICATION-TYPE
   OBJECTS { snAgGblTrapMessage }
   STATUS current
   DESCRIPTION
	   "The SNMP trap that is generated when a non-node locked licensed feature is enabled after a 
	   non-node locked license is deleted.
	   Format: Stack <shack_id>: The <license_name> license has been deleted on this unit and is available 
	   for redeployment on another unit in accordance with the terms and conditions of use. All features 
	   associated to this license must be disabled"
	--#TYPE "Foundry Trap: delete a NNLL license"
	--#SUMMARY "%s."
	--#ARGUMENTS { 0 }
	--#SEVERITY WARNING
	--#STATE OPERATIONAL
   ::= { snTraps 208 }

   snTrapStackingShowStackConnect NOTIFICATION-TYPE
   OBJECTS { snAgGblTrapMessage }
   STATUS current
   DESCRIPTION
	   "The SNMP trap that is generated when the background diagnosis detects the connection errors 
	   to notify the user to check the connections in a stacking system 
	   Format: Background diagnosis detects connection errors. Please use show stack conn to 
	   view detailed connections"
	--#TYPE "Foundry Trap: check stack connections"
	--#SUMMARY "%s."
	--#ARGUMENTS { 0 }
	--#SEVERITY NOTIFICATIONS
	--#STATE OPERATIONAL
   ::= { snTraps 209 }

snTrapStackingStandByChangedStandalone NOTIFICATION-TYPE
   OBJECTS { snChasUnitIndex, snAgGblTrapMessage }
   STATUS current
   DESCRIPTION
	   "The SNMP trap that is generated when a unit is changed from Standby to Stand alone when the active unit is down."
			--#TYPE "Brocade Trap: Unit is changed from standby to standalone"
			--#SUMMARY "%s."
			--#ARGUMENTS { 1 }
			--#SEVERITY NOTIFICATIONS
			--#STATE OPERATIONAL
   ::= { snTraps 210 }

snTrapBroadcastlimit  NOTIFICATION-TYPE
   OBJECTS { snAgGblTrapMessage }
   STATUS current
   DESCRIPTION
                   "The SNMP trap that is generated after reached the Broadcast limit."
   --#TYPE "Foundry Trap: reached the Broadcast limit"
   --#SUMMARY "%s."
   --#ARGUMENTS { 0 }
   --#SEVERITY INFORMATIONAL
   --#STATE OPERATIONAL
   ::= { snTraps 211  }

snTrapMulticastlimit   NOTIFICATION-TYPE
   OBJECTS { snAgGblTrapMessage }
   STATUS current
   DESCRIPTION
                   "The SNMP trap that is generated after reached the Multicast limit."
   --#TYPE "Foundry Trap: reached the Multicast limit"
   --#SUMMARY "%s."
   --#ARGUMENTS { 0 }
   --#SEVERITY INFORMATIONAL
   --#STATE OPERATIONAL
   ::= { snTraps 212  }

snTrapUnicastlimit  NOTIFICATION-TYPE
   OBJECTS { snAgGblTrapMessage }
   STATUS current
   DESCRIPTION
                   "The SNMP trap that is generated after reached the Unknown Unicast limit."
   --#TYPE "Foundry Trap: reached the Unknown unicast limit"
   --#SUMMARY "%s."
   --#ARGUMENTS { 0 }
   --#SEVERITY INFORMATIONAL
   --#STATE OPERATIONAL
   ::= { snTraps 213  }

-- Trapids from 1000 are reserved for XMR/IMR/MLX devices

snTrapChasFanOK NOTIFICATION-TYPE
   OBJECTS { snChasFanIndex, snChasFanDescription }
   STATUS current
   DESCRIPTION
	   "The SNMP trap that is generated when a fan operational status
		changed from failure to normal or change in the fan speed due to
		temperature variations downwards."
	--#TYPE "Foundry Trap: Fan OK"
	--#SUMMARY "Fan  %d (%s)  OK."
	--#ARGUMENTS { 0, 1 }
	--#SEVERITY MINOR
	--#STATE OPERATIONAL
   ::= { snTraps 1000 }

snTrapTemperatureOK NOTIFICATION-TYPE
   OBJECTS { snAgGblTrapMessage }
   STATUS current
   DESCRIPTION
	   "The SNMP trap that is generated when the actual temperature
	   reading is below the warning temperature threshold."
	--#TYPE "Foundry Trap: Temperature Warning"
	--#SUMMARY "%s."
	--#ARGUMENTS { 0 }
	--#SEVERITY CRITICAL
	--#STATE OPERATIONAL
   ::= { snTraps 1001 }

snTrapCAMOverflow NOTIFICATION-TYPE
   OBJECTS { snAgGblTrapMessage }
   STATUS current
   DESCRIPTION
	   "The SNMP trap that is generated when any CAM partition
	   becomes full."
	--#TYPE "Foundry Trap: CAM partition full"
	--#SUMMARY "%s."
	--#ARGUMENTS { 0 }
	--#SEVERITY ALERTS
	--#STATE OPERATIONAL
   ::= { snTraps 1002 }

snTrapOpticalMonitoringWarning NOTIFICATION-TYPE
   OBJECTS { snAgGblTrapMessage }
   STATUS current
   DESCRIPTION
       "The SNMP trap that is generated if there is a warning during optical
        monitoring.
        The first varbind, snAgGblTrapMessage, will have a detailed message on
        the cause of event. The second optional varbind, ifIndex, points to the affected interface
        originating this event. If an event does not have associated port, or has multiple
        associated ports, then ifIndex will have maximum value 0x7ffffff."
        --#TYPE "Foundry Trap: Optical Monitoring Warning"
        --#SUMMARY "%s."
        --#ARGUMENTS { 0 }
        --#SEVERITY WARNING
        --#STATE OPERATIONAL
   ::= { snTraps 1003 }

snTrapOpticalMonitoringAlarm NOTIFICATION-TYPE
   OBJECTS { snAgGblTrapMessage }
   STATUS current
   DESCRIPTION
       "The SNMP trap that is generated if there is an alarm during optical
        monitoring.
        The first varbind, snAgGblTrapMessage, will have a detailed message on
        the cause of event. The second optional varbind, ifIndex, points to the affected interface
        originating this event. If an event does not have associated port, or has multiple
        associated ports, then ifIndex will have maximum value 0x7ffffff."
        --#TYPE "Foundry Trap: Optical Monitoring Alarm"
        --#SUMMARY "%s."
        --#ARGUMENTS { 0 }
        --#SEVERITY ALERTS
        --#STATE OPERATIONAL
   ::= { snTraps 1004 }

snTrapOpticalMonitoringError NOTIFICATION-TYPE
   OBJECTS { snAgGblTrapMessage }
   STATUS current
   DESCRIPTION
       "The SNMP trap that is generated if there is an error during optical
        monitoring.
        The first varbind, snAgGblTrapMessage, will have a detailed message on
        the cause of event. The second optional varbind, ifIndex, points to the affected interface
        originating this event. If an event does not have associated port, or has multiple
        associated ports, then ifIndex will have maximum value 0x7ffffff."
        --#TYPE "Foundry Trap: Optical Monitoring Error"
        --#SUMMARY "%s."
        --#ARGUMENTS { 0 }
        --#SEVERITY INFORMATIONAL
        --#STATE OPERATIONAL
   ::= { snTraps 1005 }

snTrapPosMonitoringWarning NOTIFICATION-TYPE
   OBJECTS { snAgGblTrapMessage }
   STATUS current
   DESCRIPTION
       "The SNMP trap that is generated if there is a warning during POS 
       alarm monitoring.
        The first varbind, snAgGblTrapMessage, will have a detailed message on
        the cause of event. The second optional varbind, ifIndex, points to the affected interface
        originating this event. If an event does not have associated port, or has multiple
        associated ports, then ifIndex will have maximum value 0x7ffffff."
        --#TYPE "Foundry Trap: POS Monitoring Warning"
        --#SUMMARY "%s."
        --#ARGUMENTS { 0 }
        --#SEVERITY INFORMATIONAL
        --#STATE OPERATIONAL
   ::= { snTraps 1006 }

   snTrapPosMonitoringAlarm NOTIFICATION-TYPE
   OBJECTS { snAgGblTrapMessage }
   STATUS current
   DESCRIPTION
       "The SNMP trap that is generated if there is an alarm up/down 
       during POS alarm monitoring.
        The first varbind, snAgGblTrapMessage, will have a detailed message on
        the cause of event. The second optional varbind, ifIndex, points to the affected interface
        originating this event. If an event does not have associated port, or has multiple
        associated ports, then ifIndex will have maximum value 0x7ffffff."
        --#TYPE "Foundry Trap: POS Monitoring Alarm"
        --#SUMMARY "%s."
        --#ARGUMENTS { 0 }
        --#SEVERITY ALERTS
        --#STATE OPERATIONAL
   ::= { snTraps 1007 }

   snTrapPosMonitoringError NOTIFICATION-TYPE
   OBJECTS { snAgGblTrapMessage }
   STATUS current
   DESCRIPTION
       "The SNMP trap that is generated if there is an error during POS
        alarm monitoring.
        The first varbind, snAgGblTrapMessage, will have a detailed message on
        the cause of event. The second optional varbind, ifIndex, points to the affected interface
        originating this event. If an event does not have associated port, or has multiple
        associated ports, then ifIndex will have maximum value 0x7ffffff."
        --#TYPE "Foundry Trap: POS Monitoring Error"
        --#SUMMARY "%s."
        --#ARGUMENTS { 0 }
        --#SEVERITY INFORMATIONAL
        --#STATE OPERATIONAL
   ::= { snTraps 1008 }

snTrapXfpSfpIncompatibleOptics NOTIFICATION-TYPE
   OBJECTS { snAgGblTrapMessage }
   STATUS current
   DESCRIPTION
	   "The SNMP trap that is generated if optics is incompatible with port configuration."
	--#TYPE "Foundry Trap: Optical Incompatibility Error"
	--#SUMMARY "%s."
	--#ARGUMENTS { 0 }
	--#SEVERITY ALERTS
	--#STATE OPERATIONAL
   ::= { snTraps 1009 }

-- TRAP snMplsLspUp (1010), snMplsLspDown (1011), snMplsLspChange (1012)
-- are defined in snmpls.mib. DO NOT USE THESE IDS

snTrapTMLoggingStart NOTIFICATION-TYPE
   OBJECTS { snAgGblTrapMessage }
   STATUS current
   DESCRIPTION
	   "The SNMP trap that is generated if TM logging is started by an event trigger."
	--#TYPE "Foundry Trap: TM Logging Start"
	--#SUMMARY "%s."
	--#ARGUMENTS { 0 }
	--#SEVERITY INFORMATIONAL
	--#STATE OPERATIONAL
   ::= { snTraps 1015 }

snTrapTMLoggingStop NOTIFICATION-TYPE
   OBJECTS { snAgGblTrapMessage }
   STATUS current
   DESCRIPTION
	   "The SNMP trap that is generated if TM logging stopped due to storage full."
	--#TYPE "Foundry Trap: TM Logging Stop"
	--#SUMMARY "%s."
	--#ARGUMENTS { 0 }
	--#SEVERITY INFORMATIONAL
	--#STATE OPERATIONAL
   ::= { snTraps 1016 }

snTrapTMLoggingRestart NOTIFICATION-TYPE
   OBJECTS { snAgGblTrapMessage }
   STATUS current
   DESCRIPTION
	   "The SNMP trap that is generated if TM logging restarted after user clearing the log."
	--#TYPE "Foundry Trap: TM Logging Restart"
	--#SUMMARY "%s."
	--#ARGUMENTS { 0 }
	--#SEVERITY INFORMATIONAL
	--#STATE OPERATIONAL
   ::= { snTraps 1017    }

snTrapXfpSfpNotFoundryOptics NOTIFICATION-TYPE
   OBJECTS { snAgGblTrapMessage }
   STATUS current
   DESCRIPTION
	   "The SNMP trap that is generated if optics vendor is not Foundry Networks."
	--#TYPE "Foundry Trap: Not Foundry Networks Optics"
	--#SUMMARY "%s."
	--#ARGUMENTS { 0 }
	--#SEVERITY WARNING
	--#STATE OPERATIONAL
   ::= { snTraps 1018    }

snTrapTMRecoverySlotReset NOTIFICATION-TYPE
   OBJECTS { snAgGblTrapMessage }
   STATUS current
   DESCRIPTION
	   "The SNMP trap that is generated when TM recovery slot reset is triggered."
	--#TYPE "Foundry Trap: TM recovery level II"
	--#SUMMARY "%s."
	--#ARGUMENTS { 0 }
	--#SEVERITY INFORMATIONAL
	--#STATE OPERATIONAL
   ::= { snTraps 1019    }

--TM Egress Error TRAP
snTrapTMEgressDataError NOTIFICATION-TYPE
   OBJECTS { snAgGblTrapMessage }
   STATUS current
   DESCRIPTION
	   "The SNMP trap that is generated when system detects egress data errors on Traffic Manager.
	   For e.g.  Fabric Monitoring : TM Egress data errors detected on LP <num>/TM <num>"
	--#TYPE "Foundry Trap: TM Egress Data Error"
	--#SUMMARY "%s."
	--#ARGUMENTS { 0 }
	--#SEVERITY MAJOR
	--#STATE OPERATIONAL
::= { snTraps 1020 } 


snTrapSFMLinkDown NOTIFICATION-TYPE
   OBJECTS { snAgGblTrapMessage }
   STATUS current
   DESCRIPTION
	   "The SNMP trap that is generated when a link from LP Traffic Manager to 
	   SFM Fabric Element is down.
	   For eg.  Fabric Monitoring Link Down : SFM <num>/FE <num>/Link <num>, LP <num>/TM <num>"
	--#TYPE "Foundry Trap: SFM Link Down"
	--#SUMMARY "%s."
	--#ARGUMENTS { 0 }
	--#SEVERITY WARNING
	--#STATE OPERATIONAL
::= { snTraps 1100 }

snTrapSFMLinkUp NOTIFICATION-TYPE
   OBJECTS { snAgGblTrapMessage }
   STATUS current
   DESCRIPTION
	   "The SNMP trap that is generated when a link from LP Traffic Manager to 
	   SFM Fabric Element is up.
	   For eg.  Fabric Monitoring Link Up : SFM <num>/FE <num>/Link <num>, LP <num>/TM <num>"
	--#TYPE "Foundry Trap: SFM Link Up"
	--#SUMMARY "%s."
	--#ARGUMENTS { 0 }
	--#SEVERITY INFORMATIONAL
	--#STATE OPERATIONAL
::= { snTraps 1101 }

--FE Read/write TRAP
snTrapSFMAccessError NOTIFICATION-TYPE
   OBJECTS { snAgGblTrapMessage }
   STATUS current
   DESCRIPTION
	   "The SNMP trap that is generated when system fails to access a  SFM Fabric Element.
	   For e.g.  Fabric Monitoring : Device access failure in SFM <num>/FE <num>"
	--#TYPE "Foundry Trap: FE Access Error"
	--#SUMMARY "%s."
	--#ARGUMENTS { 0 }
	--#SEVERITY MAJOR
	--#STATE OPERATIONAL
::= { snTraps 1102 }  

snTrapChassisFanSpeedLow NOTIFICATION-TYPE
   OBJECTS { snAgGblTrapMessage }
   STATUS current
   DESCRIPTION
	   "The SNMP trap that is generated when all chassis fans change to low speed."
	--#TYPE "Foundry Trap: Chassis Fans Speed Low"
	--#SUMMARY "%s."
	--#ARGUMENTS { 0 }
	--#SEVERITY INFORMATIONAL
	--#STATE OPERATIONAL
::= { snTraps 1200 }

snTrapChassisFanSpeedMedium NOTIFICATION-TYPE
   OBJECTS { snAgGblTrapMessage }
   STATUS current
   DESCRIPTION
	   "The SNMP trap that is generated when all chassis fans change to medium speed."
	--#TYPE "Foundry Trap: Chassis Fans Speed Medium"
	--#SUMMARY "%s."
	--#ARGUMENTS { 0 }
	--#SEVERITY INFORMATIONAL
	--#STATE OPERATIONAL
::= { snTraps 1201 }

snTrapChassisFanSpeedMedHigh NOTIFICATION-TYPE
   OBJECTS { snAgGblTrapMessage }
   STATUS current
   DESCRIPTION
	   "The SNMP trap that is generated when all chassis fans change to medium high speed."
	--#TYPE "Foundry Trap: Chassis Fans Speed Medium High"
	--#SUMMARY "%s."
	--#ARGUMENTS { 0 }
	--#SEVERITY INFORMATIONAL
	--#STATE OPERATIONAL
::= { snTraps 1202 }

snTrapChassisFanSpeedHigh NOTIFICATION-TYPE
   OBJECTS { snAgGblTrapMessage }
   STATUS current
   DESCRIPTION
	   "The SNMP trap that is generated when all chassis fans change to high speed."
	--#TYPE "Foundry Trap: Chassis Fans Speed High"
	--#SUMMARY "%s."
	--#ARGUMENTS { 0 }
	--#SEVERITY INFORMATIONAL
	--#STATE OPERATIONAL
::= { snTraps 1203 }

snTrapFIPSModeEnable NOTIFICATION-TYPE
   OBJECTS { snAgGblTrapMessage }   
   STATUS current
   DESCRIPTION
                   "The SNMP trap that is generated when FIPS mode is enabled."
   --#TYPE "Foundry Trap: FIPS mode enabled by <username> from console" 
   --#SUMMARY "%s."
   --#ARGUMENTS { 0 }
   --#SEVERITY INFORMATIONAL
   --#STATE OPERATIONAL
   ::= { snTraps 1207 }

snTrapFIPSModeDisable NOTIFICATION-TYPE
   OBJECTS { snAgGblTrapMessage }
   STATUS current
   DESCRIPTION
                   "The SNMP trap that is generated when FIPS mode is disabled.The zeroization of host keys and shared secret keys is done after this trap is sent."
   --#TYPE "Foundry Trap: FIPS mode disabled by <username> from console"
   --#SUMMARY "%s."
   --#ARGUMENTS { 0 }
   --#SEVERITY INFORMATIONAL
   --#STATE OPERATIONAL
   ::= { snTraps 1208  }


snTrapFIPSHostZeroized NOTIFICATION-TYPE
   OBJECTS { snAgGblTrapMessage }
   STATUS current
   DESCRIPTION
                   "The SNMP trap that is generated when host keys are zeroized in FIPS mode"
   --#TYPE "Foundry Trap: Host keys have been zeroized by <username> from console."
   --#SUMMARY "%s."
   --#ARGUMENTS { 0 }
   --#SEVERITY INFORMATIONAL
   --#STATE OPERATIONAL
   ::= { snTraps 1209  }

snTrapFIPSSharedSecretZeroized NOTIFICATION-TYPE
   OBJECTS { snAgGblTrapMessage }
   STATUS current
   DESCRIPTION
                   "The SNMP trap that is generated when shared secret are zeroized in FIPS mode"
   --#TYPE "Foundry Trap: Shared Secrets have been zeroized by <username> from console."
   --#SUMMARY "%s."
   --#ARGUMENTS { 0 }
   --#SEVERITY INFORMATIONAL
   --#STATE OPERATIONAL
   ::= { snTraps 1210  }


snTrapFIPSPOSTStatus NOTIFICATION-TYPE
   OBJECTS { snAgGblTrapMessage }
   STATUS current
   DESCRIPTION
                   "The SNMP trap that is generated after POST."
   --#TYPE "Foundry Trap: FIPS POST status =< SUCCESS | FAIL>"
   --#SUMMARY "%s."
   --#ARGUMENTS { 0 }
   --#SEVERITY INFORMATIONAL
   --#STATE OPERATIONAL
   ::= { snTraps 1211  }

snTrapFIPSCryptoModuleFailure NOTIFICATION-TYPE
   OBJECTS { snAgGblTrapMessage }
   STATUS current
   DESCRIPTION
                   "The SNMP trap that is generated on cryptographic  module failure."
   --#TYPE "Foundry Trap: FIPS Cryptographic Module Failure"
   --#SUMMARY "%s."
   --#ARGUMENTS { 0 }
   --#SEVERITY CRITICAL 
   --#STATE OPERATIONAL
   ::= { snTraps 1212  }

END
BRCD-DOT1X-MIB DEFINITIONS ::= BEGIN

IMPORTS
	MODULE-IDENTITY, OBJECT-TYPE, Integer32, Counter32, Unsigned32
	   	FROM SNMPv2-SMI				-- [RFC2578]
	ifIndex
	   	FROM IF-MIB					-- [RFC2863]
	MacAddress 
	   	FROM SNMPv2-TC				-- [RFC2579]
       InetAddressType, InetAddress		
       	FROM INET-ADDRESS-MIB		-- [RFC4001]
	EnabledStatus
		FROM P-BRIDGE-MIB
       SnmpAdminString
        	FROM SNMP-FRAMEWORK-MIB; 	-- [RFC3411]
    
brcdDot1xAuth MODULE-IDENTITY
	LAST-UPDATED "201009300000Z" -- September 30, 2010
	ORGANIZATION "Brocade Communications Systems, Inc."
	CONTACT-INFO
		"Technical Support Center
              130 Holger Way,
              San Jose, CA  95134
              Email:  ipsupport@brocade.com
              Phone: 1-800-752-8061
              URL:  www.brocade.com"
	DESCRIPTION
		"Management Information for configuration /querying of 802.1x authentication
			It is grouped into five MIBs - 
			1. Global level configurable admin /status 802.1x information
			2. Port level EAPOL statistics information
			3. Port level configuration information
			4. Different Port state information and 
			5. 802.1x mac session information
		Copyright 1996-2010 Brocade Communications Systems, Inc.  
  		All rights reserved.
  		This Brocade Communications Systems SNMP Management Information Base Specification
 		embodies Brocade Communications Systems' confidential and proprietary
 		intellectual property. Brocade Communications Systems retains all
  		title and ownership in the Specification, including any revisions.
                                                
 		This Specification is supplied AS IS, and Brocade Communications Systems makes
 		no warranty, either express or implied, as to the use,
 		operation, condition, or performance of the specification, and any unintended 
 		consequence it may on the user environment."
	REVISION     "201009300000Z" -- September 30, 2010
	DESCRIPTION
		""
 ::= { iso(1) org(3) dod(6) internet(1) private(4) enterprises(1) foundry(1991) products(1) switch(1) snSwitch(3) 38 }
-- -------------------------------------------------------------
-- Textual Conventions
-- -------------------------------------------------------------
VlanId ::= TEXTUAL-CONVENTION
    STATUS      current
    DESCRIPTION
        "A 12-bit VLAN ID used in the VLAN Tag header."
    SYNTAX      INTEGER (1..4094)
    
-- ---------------------------------------------------------- --
-- groups in the Dot1x MIB
-- ---------------------------------------------------------- --
brcdDot1xAuthGlobalConfigGroup	OBJECT IDENTIFIER  ::=  { brcdDot1xAuth 1 }
brcdDot1xAuthPortStatistics	OBJECT IDENTIFIER  ::=  { brcdDot1xAuth 2 }
brcdDot1xAuthPortConfig		OBJECT IDENTIFIER  ::=  { brcdDot1xAuth 3 }
brcdDot1xAuthPortState		OBJECT IDENTIFIER  ::=  { brcdDot1xAuth 4 }
brcdDot1xAuthMacSession		OBJECT IDENTIFIER  ::=  { brcdDot1xAuth 5 }
brcdDot1xAuthGlobalAdminGroup	OBJECT IDENTIFIER  ::=  { brcdDot1xAuth 6 }

brcdDot1xAuthGlobalConfigQuietperiod	OBJECT-TYPE
	SYNTAX			Unsigned32 (0..4294967295)
	UNITS       		"seconds"
	MAX-ACCESS		read-write
	STATUS			current
	DESCRIPTION		"When the Brocade device is unable to authenticate a Client,
					the	amount of time the Brocade device waits before trying 
					again.. The allowed range is from 0 to 4294967295"
	DEFVAL			{ 60 }
	::= { brcdDot1xAuthGlobalConfigGroup 1 }

brcdDot1xAuthGlobalConfigTxPeriod	OBJECT-TYPE
	SYNTAX			Unsigned32 (1..4294967295)
	UNITS       		"seconds"
	MAX-ACCESS		read-write
	STATUS			current
	DESCRIPTION		"When a Client does not send back an EAP(Extensible
					Authentication Protocol)-response/identity
					frame, the amount of time the Brocade device waits before 
					retransmitting the EAP-request/identity frame to a Client
					The allowed range is from 1 to 4294967295"
	DEFVAL			{ 30 }
	::= { brcdDot1xAuthGlobalConfigGroup 2 }

brcdDot1xAuthGlobalConfigSuppTimeOut	OBJECT-TYPE
	SYNTAX			Unsigned32 (1..4294967295)
	UNITS       		"seconds"	
	MAX-ACCESS		read-write
	STATUS			current
	DESCRIPTION		"When a supplicant (Client) does not respond to an
					EAP-request frame, the amount of time before the Brocade
					device retransmits the frame
					The allowed range is from 1 to 4294967295"
	DEFVAL			{ 30 }
	::= { brcdDot1xAuthGlobalConfigGroup 3 }

brcdDot1xAuthGlobalConfigAuthServerTimeOut	OBJECT-TYPE
	SYNTAX			Unsigned32 (1..4294967295)
	UNITS       		"seconds"
	MAX-ACCESS		read-write
	STATUS			current
	DESCRIPTION		"When the Authentication Server (RADIUS) does not respond 
					to a message sent from the Client, the amount of time before
					the Brocade device retransmits the message.
					The allowed range is from 1 to 4294967295"
	DEFVAL			{ 30 }
	::= { brcdDot1xAuthGlobalConfigGroup 4 }

brcdDot1xAuthGlobalConfigMaxReq		OBJECT-TYPE
	SYNTAX			Unsigned32
	MAX-ACCESS		read-write
	STATUS			current
	DESCRIPTION		"The number of times the Brocade device retransmits an
					EAP-request/identity request frame if it does not receive 
					an EAP-response/identity response frame from a Client"
	DEFVAL			{ 2 }
	::= { brcdDot1xAuthGlobalConfigGroup 5 }

brcdDot1xAuthGlobalConfigReAuthMax		OBJECT-TYPE
	SYNTAX			Unsigned32
	MAX-ACCESS		read-write
	STATUS			current
	DESCRIPTION		"The number of re-authentication attempts that are 
					permitted before the port becomes Unauthorized"	
	DEFVAL			{ 2 }
	::= { brcdDot1xAuthGlobalConfigGroup 6 }

brcdDot1xAuthGlobalConfigReAuthPeriod	OBJECT-TYPE
	SYNTAX			Unsigned32 (1..4294967295)
	UNITS       		"seconds"
	MAX-ACCESS		read-write
	STATUS			current
	DESCRIPTION		"How often the device automatically re-authenticates 
					clients when periodic re-authentication is enabled
				 The allowed range is from 1 to 4294967295"
	DEFVAL			{ 3600 }
	::= { brcdDot1xAuthGlobalConfigGroup 7 }

brcdDot1xAuthGlobalConfigProtocolVersion	OBJECT-TYPE
	SYNTAX			Unsigned32
	MAX-ACCESS		read-only
	STATUS			current
	DESCRIPTION		"The EAP protocol version"
	 ::= { brcdDot1xAuthGlobalConfigGroup 8 }

brcdDot1xAuthGlobalConfigTotalPortsEnabled	OBJECT-TYPE
	SYNTAX			Unsigned32
	MAX-ACCESS		read-only
	STATUS			current
	DESCRIPTION		"The total number of ports that have 802.1x enabled"
	::= { brcdDot1xAuthGlobalConfigGroup 9 }

brcdDot1xAuthGlobalConfigReauthStatus	OBJECT-TYPE
	SYNTAX			EnabledStatus
	MAX-ACCESS		read-write
	STATUS			current
	DESCRIPTION		"Used to enable / disable Reauthentication globally"
	DEFVAL			{ disabled }
	::= {brcdDot1xAuthGlobalConfigGroup 10 }

brcdDot1xAuthGlobalConfigMacSessionMaxAge		OBJECT-TYPE
	SYNTAX			Unsigned32
	MAX-ACCESS		read-write
	STATUS			current
	DESCRIPTION		"The Max-Age of the 802.1x mac session- 
					A value between 1 and 65535"
	::= {brcdDot1xAuthGlobalConfigGroup 11 }

brcdDot1xAuthGlobalConfigNoAgingDeniedSessions	OBJECT-TYPE
	SYNTAX				EnabledStatus
	MAX-ACCESS			read-write
	STATUS				current
	DESCRIPTION			"Enable / Disable Mac-Session-No Aging
						for Denied  sessions"
	DEFVAL			{ disabled }
	::= {brcdDot1xAuthGlobalConfigGroup 12 }
	
brcdDot1xAuthGlobalConfigNoAgingPermittedSessions	OBJECT-TYPE
	SYNTAX				EnabledStatus
	MAX-ACCESS			read-write
	STATUS				current
	DESCRIPTION			"Enable / Disable Mac-Session-No Aging
						for Permitted sessions"
	DEFVAL			{ disabled }
	::= {brcdDot1xAuthGlobalConfigGroup 13 }

brcdDot1xAuthGlobalConfigAuthFailAction	OBJECT-TYPE	
	SYNTAX							INTEGER { blockTraffic(1),
                  									restrictedVlan(2) }
	MAX-ACCESS						read-write
	STATUS							current
	DESCRIPTION						"To Configure the action to take when the authentication fails"

::= {brcdDot1xAuthGlobalConfigGroup 14 }

---802.1x Per Port Statistics Table

brcdDot1xAuthPortStatTable		OBJECT-TYPE
	SYNTAX			SEQUENCE OF BrcdDot1xAuthPortStatEntry
	MAX-ACCESS		not-accessible	
	STATUS			current
	DESCRIPTION		"A table that contains port EAP(Extensible Authentication 
					Protocol) frames statistics for 802.1x authentication"
	::= { brcdDot1xAuthPortStatistics 1 }

brcdDot1xAuthPortStatEntry		OBJECT-TYPE
	 SYNTAX			BrcdDot1xAuthPortStatEntry
	 MAX-ACCESS		not-accessible
	 STATUS			current
	 DESCRIPTION	"An entry of EAP frames statistics indexed by ifIndex"
	 INDEX			{ifIndex  }
	 ::= { brcdDot1xAuthPortStatTable 1 }


BrcdDot1xAuthPortStatEntry  ::= SEQUENCE {
	brcdDot1xAuthPortStatRxEAPFrames				Counter32,
	brcdDot1xAuthPortStatTxEAPFrames				Counter32,
	brcdDot1xAuthPortStatRxEAPStartFrames			Counter32,
	brcdDot1xAuthPortStatRxEAPLogOffFrames			Counter32,
	brcdDot1xAuthPortStatRxEAPRespIdFrames			Counter32,
	brcdDot1xAuthPortStatTxEAPReqIdFrames			Counter32,
	brcdDot1xAuthPortStatRxEAPInvalidFrames			Counter32,
	brcdDot1xAuthPortStatEAPLastFrameVersionRx	 	Unsigned32,
	brcdDot1xAuthPortStatRxEAPRespOrIdFrames		Counter32,
	brcdDot1xAuthPortStatRxLengthErrorFrame			Integer32,
	brcdDot1xAuthPortStatTxRequestFrames			Counter32,
	brcdDot1xAuthPortStatLastEAPFrameSource		MacAddress
 }

brcdDot1xAuthPortStatRxEAPFrames	OBJECT-TYPE
	SYNTAX			Counter32	
	MAX-ACCESS		read-only
	STATUS			current
	DESCRIPTION		"The total number of EAPOL frames received on the port
				  	It includes EAP frames - "
	::= { brcdDot1xAuthPortStatEntry 1 }

brcdDot1xAuthPortStatTxEAPFrames	OBJECT-TYPE
	SYNTAX			Counter32	
	MAX-ACCESS		read-only
	STATUS			current
	DESCRIPTION		"The no of EAPOL frames transmitted on the port"
	::= { brcdDot1xAuthPortStatEntry 2 }

brcdDot1xAuthPortStatRxEAPStartFrames	OBJECT-TYPE
	SYNTAX			Counter32	
	MAX-ACCESS		read-only
	STATUS			current
	DESCRIPTION		"The number of EAPOL-Start frames received on the port"
	::= { brcdDot1xAuthPortStatEntry 3 }

brcdDot1xAuthPortStatRxEAPLogOffFrames	OBJECT-TYPE
	SYNTAX			Counter32
	MAX-ACCESS		read-only
	STATUS			current
	DESCRIPTION		"The number of EAPOL-Logoff frames received on the port"
	::= { brcdDot1xAuthPortStatEntry 4 }

brcdDot1xAuthPortStatRxEAPRespIdFrames	OBJECT-TYPE
	SYNTAX			Counter32	
	MAX-ACCESS		read-only
	STATUS			current
	DESCRIPTION		"The number of  EAP frames other than Response/Identity 
					frames received on the port"
	::= { brcdDot1xAuthPortStatEntry 5 } 

brcdDot1xAuthPortStatTxEAPReqIdFrames	OBJECT-TYPE
	SYNTAX			Counter32	
	MAX-ACCESS		read-only
	STATUS			current
	DESCRIPTION		"The number of EAP-Request/Identity frames transmitted on 
					the port"
	::= { brcdDot1xAuthPortStatEntry 6 }

brcdDot1xAuthPortStatRxEAPInvalidFrames	OBJECT-TYPE
	SYNTAX			Counter32	
	MAX-ACCESS		read-only
	STATUS			current
	DESCRIPTION		"The number of invalid EAPOL frames received on the port"
	::= { brcdDot1xAuthPortStatEntry 7 }

brcdDot1xAuthPortStatEAPLastFrameVersionRx		OBJECT-TYPE
	SYNTAX			Unsigned32
	MAX-ACCESS		read-only
	STATUS			current
	DESCRIPTION		"The version of last EAP frame received"
	::= { brcdDot1xAuthPortStatEntry 8 }

brcdDot1xAuthPortStatRxEAPRespOrIdFrames		OBJECT-TYPE
	SYNTAX			Counter32
	MAX-ACCESS		read-only
	STATUS			current
	DESCRIPTION		"The number of  received EAP response or Id frames on the 
					port"
	::= { brcdDot1xAuthPortStatEntry 9 }

brcdDot1xAuthPortStatRxLengthErrorFrame		OBJECT-TYPE	
	SYNTAX			Integer32
	MAX-ACCESS		read-only
	STATUS			current
	DESCRIPTION		"The received EAP Length Error frame" 
	::= { brcdDot1xAuthPortStatEntry 10 }

brcdDot1xAuthPortStatTxRequestFrames		OBJECT-TYPE
	SYNTAX			Counter32
	MAX-ACCESS		read-only
	STATUS			current
	DESCRIPTION		"The number of  transmitted EAP request frames on the port"
	::= { brcdDot1xAuthPortStatEntry 11 }

brcdDot1xAuthPortStatLastEAPFrameSource OBJECT-TYPE
	SYNTAX			MacAddress
	MAX-ACCESS		read-only
	STATUS			current
	DESCRIPTION		"The MAC address of the source from which the last EAP frame came"
        ::= {brcdDot1xAuthPortStatEntry 12}

---A table of 802.1x dynamic states that the port is currently in..

brcdDot1xAuthPortStateTable		OBJECT-TYPE
	SYNTAX			SEQUENCE OF BrcdDot1xAuthPortStateEntry 
	MAX-ACCESS		not-accessible
	STATUS			current
	DESCRIPTION		"A table that contains entries of port dot1x values"
	::= { brcdDot1xAuthPortState 1 }

brcdDot1xAuthPortStateEntry 			OBJECT-TYPE
	SYNTAX			BrcdDot1xAuthPortStateEntry
	MAX-ACCESS		not-accessible
	STATUS			current
	DESCRIPTION		"An entry of 802.1x config values indexed by ifIndex to
					be able to have port values"
		INDEX		{ ifIndex }
	::= { brcdDot1xAuthPortStateTable 1 }

BrcdDot1xAuthPortStateEntry ::= SEQUENCE {
	brcdDot1xAuthPortStateMacSessions			Unsigned32,
	brcdDot1xAuthPortStateAuthMacSessions		Unsigned32,
	brcdDot1xAuthPortStateOriginalPVID			Unsigned32,
	brcdDot1xAuthPortStatePVIDMacTotal			Unsigned32,
	brcdDot1xAuthPortStatePVIDMacAuthorized		Unsigned32,
	brcdDot1xAuthPortStatePortVlanState			INTEGER,
	brcdDot1xAuthPortStatePVID					Unsigned32,
	brcdDot1xAuthPortStateRestrictPVID			Unsigned32,
	brcdDot1xAuthPortStateRadiusAssignPVID		Unsigned32		
	}		

brcdDot1xAuthPortStateMacSessions	OBJECT-TYPE
	SYNTAX			Unsigned32
	MAX-ACCESS		read-only
	STATUS			current
	DESCRIPTION		"Number of 802.1x MAC sessions per port"
	::= { brcdDot1xAuthPortStateEntry 1 }

brcdDot1xAuthPortStateAuthMacSessions	OBJECT-TYPE
	SYNTAX			Unsigned32
	MAX-ACCESS		read-only
	STATUS			current
	DESCRIPTION		"Number of Authorized MAC sessions per port"
	::= { brcdDot1xAuthPortStateEntry 2 }

brcdDot1xAuthPortStateOriginalPVID	OBJECT-TYPE
	SYNTAX			Unsigned32
	MAX-ACCESS		read-only	
	STATUS			current
	DESCRIPTION		"Originally configured(not dynamically assigned)
					PVID(port's default VLAN ID) for the port"
	::= { brcdDot1xAuthPortStateEntry 3}

brcdDot1xAuthPortStatePVIDMacTotal	OBJECT-TYPE
	SYNTAX			Unsigned32
	MAX-ACCESS		read-only
	STATUS			current
	DESCRIPTION		"The number of devices transmitting untagged traffic
					 on the port's PVID"
	::= { brcdDot1xAuthPortStateEntry 4 }

brcdDot1xAuthPortStatePVIDMacAuthorized 	OBJECT-TYPE
	SYNTAX			Unsigned32
	MAX-ACCESS		read-only
	STATUS			current
	DESCRIPTION		"The number of devices transmitting untagged traffic
					on the port's PVID as a result of dynamic VLAN assignment"
	::= { brcdDot1xAuthPortStateEntry 5 }

brcdDot1xAuthPortStatePortVlanState	 OBJECT-TYPE
	SYNTAX			INTEGER { radius(1), restricted(2), normal(3) }
	MAX-ACCESS		read-only
	STATUS			current
	DESCRIPTION		"The Current Vlan state the port is in, which can be 
					RADIUS -The port's PVID was dynamically assigned by a RADIUS server 
					Restricted - The port's PVID is the restricted VLAN Normal - The port's PVID is not set by a RADIUS server,
					nor is it the restricted VLAN"
	::= { brcdDot1xAuthPortStateEntry 6 }

brcdDot1xAuthPortStatePVID		OBJECT-TYPE
	SYNTAX			Unsigned32
	MAX-ACCESS		read-only
	STATUS			current
	DESCRIPTION		"The Dot1x Authentication default Port VLAN Id"
	::= { brcdDot1xAuthPortStateEntry 7 }

brcdDot1xAuthPortStateRestrictPVID	OBJECT-TYPE
	SYNTAX			Unsigned32
	MAX-ACCESS		read-only
	STATUS			current
	DESCRIPTION		"The number of MAC sessions on the port that failed authentication and are now in the restricted VLAN 
                    (which should be the port's current PVID)"
	::= { brcdDot1xAuthPortStateEntry 8 }

brcdDot1xAuthPortStateRadiusAssignPVID		OBJECT-TYPE
	SYNTAX			Unsigned32
	MAX-ACCESS		read-only
	STATUS			current
	DESCRIPTION		"The number of times the port has changed PVIDs due to Radius VLAN assignment"
	::= { brcdDot1xAuthPortStateEntry 9 }
	
--- A table of port configuration parameters for 802.1x authentication

brcdDot1xAuthPortConfigTable		OBJECT-TYPE
	SYNTAX			SEQUENCE OF BrcdDot1xAuthPortConfigEntry 
	MAX-ACCESS		not-accessible
	STATUS			current
	DESCRIPTION		"A table that allows configuration of dot1x values for a given port"
	::= { brcdDot1xAuthPortConfig  1 }

brcdDot1xAuthPortConfigEntry 			OBJECT-TYPE
	SYNTAX			BrcdDot1xAuthPortConfigEntry
	MAX-ACCESS		not-accessible
	STATUS			current
	DESCRIPTION		"An entry of 802.1x config values"
	INDEX		{ ifIndex }
	::= { brcdDot1xAuthPortConfigTable 1 }

BrcdDot1xAuthPortConfigEntry ::= SEQUENCE {
	brcdDot1xAuthPortConfigPortControl			INTEGER,	
	brcdDot1xAuthPortConfigFilterStrictSec		EnabledStatus,
	brcdDot1xAuthPortConfigDot1xOnPort			EnabledStatus
	}		

brcdDot1xAuthPortConfigPortControl		OBJECT-TYPE
	SYNTAX			INTEGER	{ forceUnauthorized(1), controlauto(2), forceAuthorized(3)}
	MAX-ACCESS		read-write
	STATUS			current
	DESCRIPTION		"The configured port control type 
					for the interface which can be
					1. force-unauthorized - port's controlled port is placed 
					unconditionally in the unauthorized state
					2. control-auto - the controlled port is unauthorized 
					until authentication takes place between client and RADIUS
					3. force-authorized - the port's controlled port is placed
					unconditionally in the authorized state"

			::= { brcdDot1xAuthPortConfigEntry 1 }

brcdDot1xAuthPortConfigFilterStrictSec	OBJECT-TYPE
	SYNTAX			EnabledStatus
	MAX-ACCESS 	read-write
	STATUS			current
	DESCRIPTION		"To configure  filter strict security  
					on the interface - enable(1) or disable(2)"
	::= { brcdDot1xAuthPortConfigEntry 2 }

brcdDot1xAuthPortConfigDot1xOnPort			OBJECT-TYPE
	SYNTAX			EnabledStatus
	MAX-ACCESS 	read-write
	STATUS			current
	DESCRIPTION		"To Configure (enable / disable) 802.1x  on an interface level"
	::= { brcdDot1xAuthPortConfigEntry 3 }

---A table that contains 802.1x mac-sessions
 
brcdDot1xAuthMacSessionTable	OBJECT-TYPE
	SYNTAX			SEQUENCE OF BrcdDot1xAuthMacSessionEntry
	MAX-ACCESS		not-accessible
	STATUS			current
	DESCRIPTION		"A table that contains 802.1x MAC sessions"
	::= { brcdDot1xAuthMacSession 1}

brcdDot1xAuthMacSessionEntry  	OBJECT-TYPE
	SYNTAX			BrcdDot1xAuthMacSessionEntry
	MAX-ACCESS		not-accessible
	STATUS			current
	DESCRIPTION		"An entry containing information applicable to 
					a particular interface and client MAC ie., dot1x-mac-session "
	INDEX			 { ifIndex, brcdDot1xAuthMacSessionAuthMac }
	::= { brcdDot1xAuthMacSessionTable 1 }

BrcdDot1xAuthMacSessionEntry ::=
	SEQUENCE {
	brcdDot1xAuthMacSessionAuthMac		MacAddress,
	brcdDot1xAuthMacSessionUserName		SnmpAdminString,
	brcdDot1xAuthMacSessionIncomingVlanId	VlanId,
	brcdDot1xAuthMacSessionCurrentVlanId	VlanId,
	brcdDot1xAuthMacSessionAccessStatus	INTEGER,
	brcdDot1xAuthMacSessionMaxAge		Unsigned32,
	brcdDot1xAuthMacSessionAddrType		InetAddressType,
	brcdDot1xAuthMacSessionIpAddr			InetAddress,
	brcdDot1xAuthMacSessionAging			INTEGER
	}

brcdDot1xAuthMacSessionAuthMac	OBJECT-TYPE
	SYNTAX			MacAddress
	MAX-ACCESS		not-accessible
	STATUS			current
	DESCRIPTION		"Mac address of the client - which 
					basically represents the username used for RADIUS authentication"
	::= { brcdDot1xAuthMacSessionEntry 1 }

brcdDot1xAuthMacSessionUserName		OBJECT-TYPE
	SYNTAX			SnmpAdminString
	MAX-ACCESS		read-only
	STATUS			current
	DESCRIPTION		"User name of the 802.1x mac session"
	::= { brcdDot1xAuthMacSessionEntry 2 }

brcdDot1xAuthMacSessionIncomingVlanId                  OBJECT-TYPE
	SYNTAX				VlanId
	MAX-ACCESS			read-only
	STATUS				current
	DESCRIPTION			"Incoming VLAN ID"
	::= { brcdDot1xAuthMacSessionEntry 3 }

brcdDot1xAuthMacSessionCurrentVlanId 	OBJECT-TYPE
	SYNTAX			VlanId
	MAX-ACCESS		read-only
	STATUS			current
	DESCRIPTION		"The VLAN to which the port is currently assigned"
	::= { brcdDot1xAuthMacSessionEntry 4 }

brcdDot1xAuthMacSessionAccessStatus 	OBJECT-TYPE
	SYNTAX			INTEGER { permit(1), blocked(2), restrict(3), init(4) }
	MAX-ACCESS		read-only
	STATUS			current
	DESCRIPTION		"The authentication state of the dot1x-mac-session - which
					can be permitted, denied, restricted or in the Init state"
	::= { brcdDot1xAuthMacSessionEntry 5 }

brcdDot1xAuthMacSessionMaxAge	OBJECT-TYPE
	SYNTAX			Unsigned32
	MAX-ACCESS		read-only
	STATUS			current
	DESCRIPTION		"MAX Age of the mac session in which 
					  the MAC address is authenticated."
	::= { brcdDot1xAuthMacSessionEntry 6 }

brcdDot1xAuthMacSessionAddrType	 OBJECT-TYPE
	SYNTAX			InetAddressType
	MAX-ACCESS		read-only
	STATUS			current
	DESCRIPTION		"Client(supplicant) IP address Type. Supported address types 
					are ipv4(1) and ipv6(2)"
	DEFVAL	{ ipv4 }
	::= { brcdDot1xAuthMacSessionEntry 7 }

brcdDot1xAuthMacSessionIpAddr			OBJECT-TYPE
	SYNTAX			InetAddress
	MAX-ACCESS		read-only
	STATUS			current
	DESCRIPTION		"The IP Address of the client"
	::= { brcdDot1xAuthMacSessionEntry 8 }

brcdDot1xAuthMacSessionAging		OBJECT-TYPE
	SYNTAX			INTEGER { software(1), hardware(2), ena(3), notapplicable(4) }
	MAX-ACCESS		read-only
	STATUS			current
	DESCRIPTION		"The age's type - Hardware
					 or Software aging, Ena in which case
					 the aging hasn't started, or notapplicable when
					 there is a fake 802.1x mac session"
	::= { brcdDot1xAuthMacSessionEntry 9 }					 
	
---A scalar belonging to brcdDot1xAuthGlobalAdminGroup

brcdDot1xAuthGlobalAdminConfigStatus OBJECT-TYPE
	SYNTAX			EnabledStatus
	MAX-ACCESS		read-write
	STATUS			current
	DESCRIPTION		"Used to enable /disable 802.1x authentication globally"
	DEFVAL			{ disabled }
	::= { brcdDot1xAuthGlobalAdminGroup 1}

END
BROCADE-SPX-MIB DEFINITIONS ::= BEGIN

IMPORTS
	MODULE-IDENTITY, OBJECT-TYPE, Integer32
	  FROM SNMPv2-SMI
	snSwitch
		FROM FOUNDRY-SN-SWITCH-GROUP-MIB
	MacAddress
	  FROM SNMPv2-TC
	DisplayString
	  FROM FOUNDRY-SN-AGENT-MIB
	InterfaceIndexOrZero
	  FROM IF-MIB;
	  
brcdSPXMIB MODULE-IDENTITY
	LAST-UPDATED "201505120000Z" -- May 12, 2015
	ORGANIZATION "Brocade Communications Systems, Inc"
	CONTACT-INFO
			"Technical Support Center
              130 Holger Way,
              San Jose, CA  95134
              Email:  support@brocade.com
              Phone: 1-800-752-8061
              URL:  www.brocade.com"
	DESCRIPTION
			"
			Management Information for 802.1BR SPX system
			configuration and operational status.

			Supported Platforms:
                   - supported on FastIron ICX7750/ICX7450 platforms.
			
			Copyright 1996-2015 Brocade Communications Systems, Inc.
			All rights reserved.
            This Brocade Communications Systems SNMP Management Information
            Base Specification embodies Brocade Communications Systems
            confidential and proprietary intellectual property.
            Brocade Communications Systems retains all title and ownership
            in the Specification, including any revisions.
			
			This Specification is supplied AS IS, and Brocade Communications
            Systems makes no warranty, either express or implied, as to the
            use, operation, condition, or performance of the specification,
            and any unintended consequence it may on the user environment."
	REVISION     "201505120000Z" -- May 12, 2015
	DESCRIPTION
			"Initial version"
   ::= { snSwitch 40}


--
-- 802.1BR system (SPX MIB)
--

brcdSPXGlobalObjects OBJECT IDENTIFIER ::= { brcdSPXMIB 1 }
brcdSPXTableObjects  OBJECT IDENTIFIER ::= { brcdSPXMIB 2 }

--
-- SPX system Global Scalar Object Section
--

brcdSPXGlobalConfigCBState OBJECT-TYPE
	SYNTAX     INTEGER { 
			  none(0), 
			  enabled(1),
			  disabled(2)
			}
	MAX-ACCESS read-write
	STATUS     current
	DESCRIPTION
		"Configure CB (Control Bridge) state for 802.1BR feature on the global level.
		The set operation is allowed only on CB device.
		 none: reserve state. 
		 enable: 802.1BR is enable on CB.
		 disable: 802.1BR is disable on CB.
		The none state will be displayed if it is not a CB device"
	::= { brcdSPXGlobalObjects 1}


brcdSPXGlobalConfigPEState OBJECT-TYPE
	SYNTAX     INTEGER { 
			  none(0), 
			  enabled(1),
			  disabled(2)
			}
	MAX-ACCESS read-write
	STATUS     current
	DESCRIPTION
		"Configure PE (Port Extender) state for 802.1BR feature on the global level.
		The set operation is allowed only on PE standalone device.
		 none: reserve state
		 enable: 802.1BR is enabled on PE.
		 disable: 802.1BR is disabled on PE.
		 Note that enabling/disabling PE takes effect only after system is saved 
		 configure and reloaded. The none state will be displayed if it is not a PE device"
	::= { brcdSPXGlobalObjects 2}

--
-- SPX system Table Object Section
--

--
-- SPX configuration unit Table
-- Use this table to display CB and PE units in a SPX system 
-- and configure SPX related information for each PE unit on CB device
--

brcdSPXConfigUnitTable OBJECT-TYPE
	SYNTAX     SEQUENCE OF BrcdSPXConfigUnitEntry
	MAX-ACCESS not-accessible
	STATUS     current
	DESCRIPTION
		"802.1BR SPX configuration unit table."
	::= { brcdSPXTableObjects 1 }

brcdSPXConfigUnitEntry OBJECT-TYPE
	SYNTAX     BrcdSPXConfigUnitEntry
	MAX-ACCESS not-accessible
	STATUS     current
	DESCRIPTION
		"An entry in SPX configuration table."
	INDEX { brcdSPXConfigUnitIndex }
	::= { brcdSPXConfigUnitTable 1 }

BrcdSPXConfigUnitEntry ::= SEQUENCE {
	brcdSPXConfigUnitIndex                 Integer32,
	brcdSPXConfigUnitPEName                DisplayString,
	brcdSPXConfigUnitPESPXPort1            InterfaceIndexOrZero,
	brcdSPXConfigUnitPESPXPort2            InterfaceIndexOrZero,
	brcdSPXConfigUnitPESPXLag1             OCTET STRING,
	brcdSPXConfigUnitPESPXLag2             OCTET STRING,
	brcdSPXConfigUnitRowStatus             INTEGER,
	brcdSPXConfigUnitType                  DisplayString,
	brcdSPXConfigUnitState                 INTEGER
}

brcdSPXConfigUnitIndex OBJECT-TYPE
	SYNTAX Integer32
	MAX-ACCESS not-accessible
	STATUS     current
	DESCRIPTION
		"The SPX unit Id. CB unit ID is from 1 to 16.
		 PE unit ID is from 17 to 56"
	::= { brcdSPXConfigUnitEntry 1 }

brcdSPXConfigUnitPEName OBJECT-TYPE
	SYNTAX	DisplayString (SIZE (0..64))
	MAX-ACCESS read-write
	   STATUS     current
	DESCRIPTION
		"A name description of PE unit."
	::= { brcdSPXConfigUnitEntry 2 }

 brcdSPXConfigUnitPESPXPort1 OBJECT-TYPE
	SYNTAX		InterfaceIndexOrZero
	MAX-ACCESS read-write
	STATUS     current
	DESCRIPTION
		"A PE SPX port on PE unit. It returns 0 if SPX port does not exist.
		Note that the maximum PE SPX port on a PE unit is 2."
	::= { brcdSPXConfigUnitEntry 3 }

 brcdSPXConfigUnitPESPXPort2 OBJECT-TYPE
	SYNTAX		InterfaceIndexOrZero
	MAX-ACCESS read-write
	STATUS     current
	DESCRIPTION
		"A PE SPX port on PE unit. It returns 0 if SPX port does not exist.
		Note that the maximum PE SPX port on a PE unit is 2."
	::= { brcdSPXConfigUnitEntry 4 }

 brcdSPXConfigUnitPESPXLag1 OBJECT-TYPE
	SYNTAX		OCTET STRING
	MAX-ACCESS read-write
	STATUS     current
	DESCRIPTION
		"A list of interface indices which are the port membership
         of a SPX LAG group on PE. Each interface index is a 32-bit integer
         in big endian order. It returns NULL if PE SPX LAG does not exist.
         Note that the maximum PE SPX LAG on a PE unit is 2. Each SPX LAG group 
         contains up to 16 ports."
	::= { brcdSPXConfigUnitEntry 5 }

 brcdSPXConfigUnitPESPXLag2 OBJECT-TYPE
	SYNTAX		OCTET STRING
	MAX-ACCESS read-write
	STATUS     current
	DESCRIPTION
		"A list of interface indices which are the port membership
         of a SPX LAG group on PE. Each interface index is a 32-bit integer
         in big endian order. It returns NULL if PE SPX LAG does not exist.
         Note that the maximum PE SPX LAG on a PE unit is 2. Each SPX LAG group 
         contains up to 16 ports."
	::= { brcdSPXConfigUnitEntry 6 }
	
brcdSPXConfigUnitRowStatus OBJECT-TYPE
	SYNTAX     INTEGER {
				 other(1),
				 valid(2),
				 delete(3)
		  --       create(4)
			   }
	MAX-ACCESS read-write
	STATUS     current
	DESCRIPTION
			"This object is used to delete row in the
			table and control if they are used. The values that
			can be written are:
			delete(3)...deletes the row

			If the row exists, then a SET with value of create(4)
			returns error 'wrongValue'. Deleted rows go away immediately.
			The following values can be returned on reads:
			noSuchName...no such row
			other(1).....some other cases
			valid(2)....the row exists and is valid"
	::= { brcdSPXConfigUnitEntry 7 }

brcdSPXConfigUnitType OBJECT-TYPE
	SYNTAX	DisplayString
	MAX-ACCESS read-only
	   STATUS     current
	DESCRIPTION
		"A description of the configured/active system type for each unit."
	::= { brcdSPXConfigUnitEntry 8 }

brcdSPXConfigUnitState OBJECT-TYPE
	SYNTAX     INTEGER {
				 local(1),
				 remote(2),
				 reserved(3),
				 empty(4)
			   }
	MAX-ACCESS read-only
	STATUS     current
	DESCRIPTION
		"A state for each unit."
	::= { brcdSPXConfigUnitEntry 9 }

--
-- SPX operation unit Table
-- Use this table to display SPX related information for each operational CB and PE units
--

brcdSPXOperUnitTable OBJECT-TYPE
	SYNTAX     SEQUENCE OF BrcdSPXOperUnitEntry
	MAX-ACCESS not-accessible
	STATUS     current
	DESCRIPTION
		"802.1BR SPX operation unit table."
	::= { brcdSPXTableObjects 2 }


brcdSPXOperUnitEntry OBJECT-TYPE
	SYNTAX     BrcdSPXOperUnitEntry
	MAX-ACCESS not-accessible
	STATUS     current
	DESCRIPTION
		"An entry in SPX operation table."
	INDEX { brcdSPXOperUnitIndex }
	::= { brcdSPXOperUnitTable 1 }

BrcdSPXOperUnitEntry ::= SEQUENCE {
	brcdSPXOperUnitIndex                  Integer32,
	brcdSPXOperUnitType                   DisplayString,
	brcdSPXOperUnitRole                   INTEGER,
	brcdSPXOperUnitMac                    MacAddress,
	brcdSPXOperUnitPriority               Integer32,
	brcdSPXOperUnitState                  INTEGER,
	brcdSPXOperUnitDescription            DisplayString,
	brcdSPXOperUnitImgVer                 DisplayString,
	brcdSPXOperUnitBuildlVer              DisplayString
  
}
	
brcdSPXOperUnitIndex OBJECT-TYPE
	SYNTAX     Integer32 
	MAX-ACCESS not-accessible
	STATUS     current
	DESCRIPTION
		"The SPX unit Id. CB unit ID is from 1 to 16.
		 PE unit ID is from 17 to 56"
	::= { brcdSPXOperUnitEntry 1 }

brcdSPXOperUnitType OBJECT-TYPE
	SYNTAX	DisplayString
	MAX-ACCESS read-only
	STATUS     current
	DESCRIPTION
		"A description of the configured/active system type for each unit."
	::= { brcdSPXOperUnitEntry 2 }

brcdSPXOperUnitRole OBJECT-TYPE
	SYNTAX     INTEGER {
			  other(1),
				 active(2),
				 standby(3),
				 member(4),
				 standalone(5),
				 spx-pe (6)
			   }
	MAX-ACCESS read-only
	STATUS     current
	DESCRIPTION
		"A role for each unit."
	::= { brcdSPXOperUnitEntry 3 }

brcdSPXOperUnitMac OBJECT-TYPE
	SYNTAX     MacAddress
	MAX-ACCESS read-only
	STATUS     current
	DESCRIPTION
		"A MAC address for each unit"
	::= { brcdSPXOperUnitEntry 4 }

brcdSPXOperUnitPriority OBJECT-TYPE
	SYNTAX     Integer32 (0..255)
	MAX-ACCESS read-only
	STATUS     current
	DESCRIPTION
		"The priority in Active/backup election on CB units. 
		PE unit doesn't have priority, and 0 as default value." 
	::= { brcdSPXOperUnitEntry 5 }

brcdSPXOperUnitState OBJECT-TYPE
	SYNTAX     INTEGER {
				 local(1),
				 remote(2),
				 reserved(3),
				 empty(4)
			   }
	MAX-ACCESS read-only
	STATUS     current
	DESCRIPTION
		"A state for each unit "
	::= { brcdSPXOperUnitEntry 6}

brcdSPXOperUnitDescription OBJECT-TYPE
	SYNTAX		DisplayString (SIZE (0..128))
	MAX-ACCESS read-only
	STATUS     current
	DESCRIPTION
		"Describes the CB stacking or PE joining state for each unit."
	::= { brcdSPXOperUnitEntry 7 }

brcdSPXOperUnitImgVer OBJECT-TYPE
	SYNTAX		DisplayString (SIZE (0..32))
	MAX-ACCESS read-only
	STATUS     current
	DESCRIPTION
		"The version of the running software image for each unit"
	::= { brcdSPXOperUnitEntry 8 }

brcdSPXOperUnitBuildlVer OBJECT-TYPE
	SYNTAX		DisplayString (SIZE (0..32))
	MAX-ACCESS read-only
	STATUS     current
	DESCRIPTION
		"The version of the running software build for each unit"
	::= { brcdSPXOperUnitEntry 9 }

--
-- SPX configuration CB SPX port Table
-- Use this table to display and configure CB SPX ports for CB units
--

brcdSPXCBSPXPortTable OBJECT-TYPE
	SYNTAX     SEQUENCE OF BrcdSPXCBSPXPortEntry
	MAX-ACCESS not-accessible
	STATUS     current
	DESCRIPTION
		"SPX configuration CB SPX port table."
	::= { brcdSPXTableObjects 3 }

brcdSPXCBSPXPortEntry OBJECT-TYPE
	SYNTAX     BrcdSPXCBSPXPortEntry
	MAX-ACCESS not-accessible
	STATUS     current
	DESCRIPTION
		"An entry in the SPX configuration CB SPX port table."
	INDEX { brcdSPXCBSPXPortPort }
	::= { brcdSPXCBSPXPortTable 1 }

BrcdSPXCBSPXPortEntry ::= SEQUENCE {
	brcdSPXCBSPXPortPort                     InterfaceIndexOrZero,
	brcdSPXCBSPXPortPEGroup                  DisplayString,
	brcdSPXCBSPXPortRowStatus                INTEGER
}

brcdSPXCBSPXPortPort OBJECT-TYPE
	SYNTAX InterfaceIndexOrZero
	MAX-ACCESS not-accessible
	STATUS     current
	DESCRIPTION
		"The IfIndex for the configured CB SPX port. 
		CB unit can have multiple SPX ports per unit. "
	::= { brcdSPXCBSPXPortEntry 1 }

brcdSPXCBSPXPortPEGroup OBJECT-TYPE
	SYNTAX		DisplayString (SIZE (0..32))
	MAX-ACCESS  read-write
	STATUS     current
	DESCRIPTION
		"The name of IfIndex for the configured CB SPX port. 
		It is an optional field"
	::= { brcdSPXCBSPXPortEntry 2 }
	
brcdSPXCBSPXPortRowStatus OBJECT-TYPE
	SYNTAX     INTEGER {
				 other(1),
				 valid(2),
				 delete(3),
		         create(4)
			   }
	MAX-ACCESS read-write
	STATUS     current
	DESCRIPTION
			"This object is used to delete row in the
			table and control if they are used. The values that
			can be written are:
			delete(3)...deletes the row
			create(4)...creates a new row

			If the row exists, then a SET with value of create(4)
			returns error 'wrongValue'. Deleted rows go away immediately.
			The following values can be returned on reads:
			noSuchName...no such row
			other(1).....some other cases
			valid(2)....the row exists and is valid"
	::= { brcdSPXCBSPXPortEntry 3 }

--
-- SPX configuration CB SPX LAG Table
-- Use this table to display and configure CB SPX LAGs for CB units
--

brcdSPXCBSPXLagTable OBJECT-TYPE
	SYNTAX     SEQUENCE OF BrcdSPXCBSPXLagEntry
	MAX-ACCESS not-accessible
	STATUS     current
	DESCRIPTION
		"SPX configuration CB SPX LAG table."
	::= { brcdSPXTableObjects 4 }

brcdSPXCBSPXLagEntry OBJECT-TYPE
	SYNTAX     BrcdSPXCBSPXLagEntry
	MAX-ACCESS not-accessible
	STATUS     current
	DESCRIPTION
		"An entry in the SPX configuration CB SPX LAG table."
	INDEX { brcdSPXCBSPXLagPrimaryPort }
	::= { brcdSPXCBSPXLagTable 1 }

BrcdSPXCBSPXLagEntry ::= SEQUENCE {
	brcdSPXCBSPXLagPrimaryPort               InterfaceIndexOrZero,
	brcdSPXCBSPXLagLagIflist                 OCTET STRING,
	brcdSPXCBSPXLagPEGroup                   DisplayString,
	brcdSPXCBSPXLagRowStatus                 INTEGER
}

brcdSPXCBSPXLagPrimaryPort OBJECT-TYPE
	SYNTAX InterfaceIndexOrZero
	MAX-ACCESS not-accessible
	STATUS     current
	DESCRIPTION
		"The LAG primary port for the configured CB SPX LAG. This primary 
		port is the smallest port in the CB SPX LAG group. CB unit can have 
		multiple SPX LAGs per unit."
	::= { brcdSPXCBSPXLagEntry 1 }
	
brcdSPXCBSPXLagLagIflist OBJECT-TYPE
	SYNTAX OCTET STRING
	MAX-ACCESS read-write
	STATUS     current
	DESCRIPTION
		"A list of interface indices which are the port membership
         of a SPX Lag group on CB. Each interface index is a 32-bit integer
         in big endian order. It returns NULL if CB SPX Lag does not exist.
         Note that each CB SPX LAG group contains up to 16 ports."
	::= { brcdSPXCBSPXLagEntry 2 }
	
brcdSPXCBSPXLagPEGroup OBJECT-TYPE
	SYNTAX		DisplayString (SIZE (0..32))
	MAX-ACCESS  read-write
	STATUS     current
	DESCRIPTION
		"The name of SPX LAG for the configured CB SPX LAG. 
		It is an optional field"
	::= { brcdSPXCBSPXLagEntry 3 }
	
brcdSPXCBSPXLagRowStatus OBJECT-TYPE
	SYNTAX     INTEGER {
				 other(1),
				 valid(2),
				 delete(3),
		         create(4)
			   }
	MAX-ACCESS read-write
	STATUS     current
	DESCRIPTION
			"This object is used to delete row in the
			table and control if they are used. The values that
			can be written are:
			delete(3)...deletes the row
			create(4)...creates a new row

			If the row exists, then a SET with value of create(4)
			returns error 'wrongValue'. Deleted rows go away immediately.
			The following values can be returned on reads:
			noSuchName...no such row
			other(1).....some other cases
			valid(2)....the row exists and is valid"
	::= { brcdSPXCBSPXLagEntry 4 }

--
-- SPX PE group Table
-- Use this table to display CB SPX port and all PE units attached to this SPX port
-- And SPX port on other end if it is a ring topology 
--

brcdSPXPEGroupTable OBJECT-TYPE
	SYNTAX     SEQUENCE OF BrcdSPXPEGroupEntry
	MAX-ACCESS not-accessible
	STATUS     current
	DESCRIPTION
		"SPX CB SPX port and PE group table."
	::= { brcdSPXTableObjects 5 }

brcdSPXPEGroupEntry OBJECT-TYPE
	SYNTAX     BrcdSPXPEGroupEntry
	MAX-ACCESS not-accessible
	STATUS     current
	DESCRIPTION
		"An entry in the SPX PE group table."
	INDEX { brcdSPXPEGroupCBSPXPort }
	::= { brcdSPXPEGroupTable 1 }

BrcdSPXPEGroupEntry ::= SEQUENCE {
	brcdSPXPEGroupCBSPXPort                InterfaceIndexOrZero,
	brcdSPXPEGroupPEGroup                  DisplayString,
	brcdSPXPEGroupPEIdList                 DisplayString,
	brcdSPXPEGroupCBSPXEndPort             InterfaceIndexOrZero
}

brcdSPXPEGroupCBSPXPort OBJECT-TYPE
	SYNTAX InterfaceIndexOrZero
	MAX-ACCESS not-accessible
	STATUS     current
	DESCRIPTION
		"The IfIndex for the CB SPX port which is connected 
		to a group of PE units"
	::= { brcdSPXPEGroupEntry 1 }

brcdSPXPEGroupPEGroup OBJECT-TYPE
	SYNTAX		DisplayString
	MAX-ACCESS  read-only
	STATUS     current
	DESCRIPTION
		"The name of IfIndex for the configured CB SPX port. 
		It is an optional field"
	::= { brcdSPXPEGroupEntry 2 }
	
brcdSPXPEGroupPEIdList OBJECT-TYPE
	SYNTAX     DisplayString
	MAX-ACCESS read-only
	STATUS     current
	DESCRIPTION
		"A list of PE unit ID indices which are attached to a CB SPX port."
	::= { brcdSPXPEGroupEntry 3 }

brcdSPXPEGroupCBSPXEndPort OBJECT-TYPE
	SYNTAX InterfaceIndexOrZero
	MAX-ACCESS read-only
	STATUS     current
	DESCRIPTION
		"The IfIndex for the CB SPX port which is connected 
		to a group of PE units. This CB SPX port is at other end 
		if it is a ring topology. It returns 0 if it is a chain topology
		and there is no the end port."
	::= { brcdSPXPEGroupEntry 4 }
		
	
END


 
BROCADE-SYSLOG-MIB DEFINITIONS ::= BEGIN

IMPORTS
    MODULE-IDENTITY, OBJECT-TYPE, Counter32, Unsigned32
      FROM SNMPv2-SMI                  -- [RFC2578]
    RowStatus
      FROM SNMPv2-TC                   -- [RFC2579]
    InetAddress, InetAddressType
      FROM INET-ADDRESS-MIB            -- [RFC4001]
    brcdSysLog
      FROM FOUNDRY-SN-ROOT-MIB;        -- [snroo101]

brocadeSysLogMIB MODULE-IDENTITY
    LAST-UPDATED "201111040000Z"  -- Novemeber 4, 2011
    ORGANIZATION "Brocade Communications Systems, Inc."
    CONTACT-INFO
             "Technical Support Center
              130 Holger Way,
              San Jose, CA  95134
              Email:  ipsupport@brocade.com
              Phone: 1-800-752-8061
              URL:  www.brocade.com"
    DESCRIPTION
             "This MIB module contains the managed object definitions for
              syslog

              Copyright 1996-2011 Brocade Communications Systems, Inc.
              All rights reserved.
              This Brocade Communications Systems SNMP Management Information
              Base Specification embodies Brocade Communications Systems'
              confidential and proprietary intellectual property.
              Brocade Communications Systems retains all title and ownership
              in the Specification, including any revisions.

              This Specification is supplied AS IS, and Brocade Communications
              Systems makes no warranty, either express or implied, as to the
              use, operation, condition, or performance of the specification,
              and any unintended consequence it may on the user environment."

    REVISION     "201111040000Z"          -- November 04, 2011
    DESCRIPTION
            "Initial revision"
    ::= { brcdSysLog 1 }


    --
    -- Top level components of this MIB.
    --
    brcdSysLogGroup OBJECT IDENTIFIER ::= { brocadeSysLogMIB 1 }

    --
    -- IPv4/IPv6 SysLog Server table
    --
    -- snAgSysLogServerTable will be deprecated and will be replaced by
    -- brcdSysLogServerTable.

    brcdSysLogServerTable OBJECT-TYPE
        SYNTAX        SEQUENCE OF BrcdSysLogServerEntry
        MAX-ACCESS    not-accessible
        STATUS        current
        DESCRIPTION
                "System Log Server table."
        ::= { brcdSysLogGroup 1 }

    brcdSysLogServerEntry OBJECT-TYPE
        SYNTAX        BrcdSysLogServerEntry
        MAX-ACCESS    not-accessible
        STATUS        current
        DESCRIPTION
                "A row in the System Log Server table."
        INDEX        {
                brcdSysLogServerAddrType,
                brcdSysLogServerAddr,
                brcdSysLogServerUDPPort
        }
        ::= { brcdSysLogServerTable 1 }

    BrcdSysLogServerEntry ::= SEQUENCE {
        brcdSysLogServerAddrType
                InetAddressType,
        brcdSysLogServerAddr
                InetAddress,
        brcdSysLogServerUDPPort
                Unsigned32,
        brcdSysLogServerOutPkts
                Counter32,
        brcdSysLogServerRowStatus
                RowStatus
        }

    brcdSysLogServerAddrType OBJECT-TYPE
        SYNTAX      InetAddressType
        MAX-ACCESS  not-accessible
        STATUS      current
        DESCRIPTION
                "The syslog server address type. The supported address types
                 are ipv4(1) and ipv6(2)."
        ::= { brcdSysLogServerEntry 1 }

    brcdSysLogServerAddr OBJECT-TYPE
        SYNTAX      InetAddress
        MAX-ACCESS  not-accessible
        STATUS      current
        DESCRIPTION
                "IP address of syslog server."
        ::= { brcdSysLogServerEntry 2 }

    brcdSysLogServerUDPPort OBJECT-TYPE
        SYNTAX      Unsigned32  (1..65535)
        MAX-ACCESS  not-accessible
        STATUS      current
        DESCRIPTION
                "UDP port number of syslog server."
        ::= { brcdSysLogServerEntry 3 }

    brcdSysLogServerOutPkts OBJECT-TYPE
        SYNTAX      Counter32
        MAX-ACCESS  read-only
        STATUS      current
        DESCRIPTION
                "Number of sylog packets sent to this syslog server."
        ::= { brcdSysLogServerEntry 4 }

    brcdSysLogServerRowStatus OBJECT-TYPE
        SYNTAX      RowStatus
        MAX-ACCESS  read-create
        STATUS      current
        DESCRIPTION
                "Setting this object to createAndGo(4) results in addition
                 of new row. Setting this object to destroy( 6)results in
                 removal of a row. The value active(1) is returned for
                 get and get-next requests.
                 Other values in the enumeration are not used."
        ::= { brcdSysLogServerEntry 5 }

END

BROCADE-MCT-CLUSTER-MIB DEFINITIONS ::= BEGIN

IMPORTS
   MODULE-IDENTITY, OBJECT-TYPE, NOTIFICATION-TYPE,
   Unsigned32
      FROM SNMPv2-SMI                                    -- [RFC2578]
   MODULE-COMPLIANCE, OBJECT-GROUP, NOTIFICATION-GROUP
      FROM SNMPv2-CONF                                   -- [RFC2580]
   TruthValue, RowStatus, DisplayString, TimeInterval,
   TEXTUAL-CONVENTION
      FROM SNMPv2-TC                                     -- [RFC2579]
   InterfaceIndex
      FROM IF-MIB                                        -- [RFC2863]
   InetAddressType, InetAddress
      FROM INET-ADDRESS-MIB                              -- [RFC 4001]
   BrcdVlanIdOrNoneTC, BrcdVlanIdTC
      FROM FOUNDRY-SN-SWITCH-GROUP-MIB                   -- [snaclu]
   brcdMct
      FROM FOUNDRY-SN-ROOT-MIB                           -- [snrootu]
   EnabledStatus
      FROM P-BRIDGE-MIB;                                 -- [RFC4363]

brcdMctMIB MODULE-IDENTITY
   LAST-UPDATED "201201120000Z"  -- January 12, 2012
   ORGANIZATION "Brocade Communications Systems, Inc."
   CONTACT-INFO
             "Technical Support Center
              130 Holger Way,
              San Jose, CA  95134
              Email:  ipsupport@brocade.com
              Phone: 1-800-752-8061
              URL:  www.brocade.com"
   DESCRIPTION
             "The MIB module contains the managed object definition for
              Brocade Multi Chassis Trunking.

              Supported Platforms:
                   - supported on NetIron XMR/MLX CES/CER platforms.

              Copyright 1996-2012 Brocade Communications Systems, Inc.
              All rights reserved.
              This Brocade Communications Systems SNMP Management Information
              Base Specification embodies Brocade Communications Systems
              confidential and proprietary intellectual property.
              Brocade Communications Systems retains all title and ownership
              in the Specification, including any revisions.

              This Specification is supplied AS IS, and Brocade Communications
              Systems makes no warranty, either express or implied, as to the
              use, operation, condition, or performance of the specification,
              and any unintended consequence it may on the user environment."

   REVISION      "201112200000Z"  -- January 12, 2012
   DESCRIPTION
            "Initial version"

   ::= { brcdMct 1 }

---
--- Textual Conventions
---
BrcdDeployStatus ::= TEXTUAL-CONVENTION
   STATUS        current
   DESCRIPTION
      "The deploy status."
   SYNTAX        INTEGER { deploy(1), undeploy(2) }

-- Top level components of this MIB module.

-- Notifications
brcdMctNotifications OBJECT IDENTIFIER ::= { brcdMctMIB 0 }
-- Tables, Scalars
brcdMctObjects       OBJECT IDENTIFIER ::= { brcdMctMIB 1 }

---
--- MCT global configuration
---
brcdMctL2Forward OBJECT-TYPE
   SYNTAX        EnabledStatus
   MAX-ACCESS    read-write
   STATUS        current
   DESCRIPTION
       "The global cluster L2 forward state for this system. When this object
        is set to disable, the STP protocol packets coming on the MCT VLANs
        are dropped."
   ::= { brcdMctObjects 1 }

---
--- MCT Cluster Table
---
brcdMctClusterTable OBJECT-TYPE
   SYNTAX        SEQUENCE OF BrcdMctClusterEntry
   MAX-ACCESS    not-accessible
   STATUS        current
   DESCRIPTION
       "This table provides Multi Chassis Trunking Cluster information."
  ::= { brcdMctObjects 2 }

brcdMctClusterEntry OBJECT-TYPE
   SYNTAX        BrcdMctClusterEntry
   MAX-ACCESS    not-accessible
   STATUS        current
   DESCRIPTION
       "An entry in this table represents the MCT Cluster."
   INDEX   { brcdMctClusterId }
   ::= { brcdMctClusterTable 1 }

BrcdMctClusterEntry ::= SEQUENCE {
   brcdMctClusterId                    Unsigned32,
   brcdMctClusterName                  DisplayString,
   brcdMctClusterRbridgeId             Unsigned32,
   brcdMctClusterSessionVlan           BrcdVlanIdTC,
   brcdMctClusterKeepAliveVlan         BrcdVlanIdOrNoneTC,
   brcdMctClusterClientIsolationMode   INTEGER,
   brcdMctClusterClientShutdown        TruthValue,
   brcdMctClusterMemberVlans           DisplayString,
   brcdMctClusterActiveMemberVlans     DisplayString,
   brcdMctClusterDeploy                BrcdDeployStatus,
   brcdMctClusterDeployFailureReason   INTEGER,
   brcdMctClusterRowStatus             RowStatus
}

brcdMctClusterId OBJECT-TYPE
   SYNTAX        Unsigned32 (1..65535)
   MAX-ACCESS    not-accessible
   STATUS        current
   DESCRIPTION
       "The id for this MCT Cluster."
   ::= { brcdMctClusterEntry 1 }

brcdMctClusterName OBJECT-TYPE
   SYNTAX        DisplayString (SIZE(1..64))
   MAX-ACCESS    read-create
   STATUS        current
   DESCRIPTION
       "The name of this MCT Cluster. This object cannot be modified after
        creation."
   ::= { brcdMctClusterEntry 2 }

brcdMctClusterRbridgeId OBJECT-TYPE
   SYNTAX        Unsigned32 (1..35535)
   MAX-ACCESS    read-create
   STATUS        current
   DESCRIPTION
       "The remote bridge id of this MCT Cluster. This remote bridge
        id is used by the peer to communicate with this cluster node."
   ::= { brcdMctClusterEntry 3 }

brcdMctClusterSessionVlan OBJECT-TYPE
   SYNTAX        BrcdVlanIdTC
   MAX-ACCESS    read-create
   STATUS        current
   DESCRIPTION
       "The session VLAN of this MCT Cluster. The cluster session
        VLAN can be in the range of 1 to 4090, but cannot be default VLAN.
        The brcdMctClusterSessionVlan and brcdMctClusterKeepAliveVlan
        cannot be same."
   ::= { brcdMctClusterEntry 4 }

brcdMctClusterKeepAliveVlan OBJECT-TYPE
   SYNTAX        BrcdVlanIdOrNoneTC
   MAX-ACCESS    read-create
   STATUS        current
   DESCRIPTION
       "The keep-alive VLAN of this MCT Cluster. The keep-alive VLAN
        can be in the range of 0 to 4090, but cannot be default VLAN.
        The brcdMctClusterSessionVlan and brcdMctClusterKeepAliveVlan
        cannot be same.

        The value 0 indicates that keep-alive VLAN is not set for this cluster.

        If brcdMctClusterClientIsolationMode object is set to strict(2),
        then brcdMctClusterKeepAliveVlan cannot be set to except with value 0."
   DEFVAL { 0 }
   ::= { brcdMctClusterEntry 5 }

brcdMctClusterClientIsolationMode OBJECT-TYPE
   SYNTAX        INTEGER { loose(1), strict(2) }
   MAX-ACCESS    read-create
   STATUS        current
   DESCRIPTION
       "The client isolation mode of this MCT Cluster.

        When this object is set to loose(1), then whenever the
        CCP goes down the client performs the Master/Slave
        negotiation. After negotiation, the Slave shuts down
        its client ports whereas the Master client ports continue
        to forward the traffic.

        When this object is set to strict(2), then whenever the CCP
        goes down, the client interfaces on both the cluster nodes
        are administratively shutdown. In this mode, the client is
        completely isolated from the network if CCP is not
        operational.

        If brcdMctClusterKeepAliveVlan is set to a VLAN id except 0, then
        brcdMctClusterClientIsolationMode cannot be set to strict(2)."
   DEFVAL { loose }
   ::= { brcdMctClusterEntry 6 }

brcdMctClusterClientShutdown OBJECT-TYPE
   SYNTAX        TruthValue
   MAX-ACCESS    read-create
   STATUS        current
   DESCRIPTION
       "The client shutdown state of this MCT Cluster.
        When set to true, shutdown all the local client interfaces
        in the cluster. This would result in failover of traffic
        to the cluster peer."
   DEFVAL { false }
   ::= { brcdMctClusterEntry 7 }

brcdMctClusterMemberVlans OBJECT-TYPE
   SYNTAX        DisplayString
   MAX-ACCESS    read-create
   STATUS        current
   DESCRIPTION
       "The list of the member VLAN ids on which this MCT cluster is
        operating. This would be the range of VLANs for which
        there would be MAC synchronization.
        The VLANs which are not continuous are represented with a space
        separated and continuous VLANs represented with the range.
        For example: 2 5 10 to 40 100"
   ::= { brcdMctClusterEntry 8 }

brcdMctClusterActiveMemberVlans OBJECT-TYPE
   SYNTAX        DisplayString
   MAX-ACCESS    read-only
   STATUS        current
   DESCRIPTION
       "The list of the active member VLANs of this MCT Cluster.
        The VLANs which are not continuous are represented with a space
        separated and continuous VLANs represented with the range.
        For example: 2 5 10 to 40 100"
   ::= { brcdMctClusterEntry 9 }

brcdMctClusterDeploy OBJECT-TYPE
   SYNTAX        BrcdDeployStatus
   MAX-ACCESS    read-create
   STATUS        current
   DESCRIPTION
       "The admin status of this MCT Cluster. When this object
        is set to deploy, consistency check of the entire cluster
        configuration is done.

        Once the cluster is deployed, the configuration cannot be
        modified except for the brcdMctClusterMemberVlans,
        brcdMctClusterClientIsolationMode and brcdMctClusterDeploy objects."
   DEFVAL { undeploy }
   ::= { brcdMctClusterEntry 10 }

brcdMctClusterDeployFailureReason OBJECT-TYPE
   SYNTAX        INTEGER  {
                   none(1),
                   unknown(2),
                   rBridgeIdNotConfigured(3),
                   sessionVlanNotConfigured(4),
                   iclNotConfigured(5),
                   peerNotConfigured(6),
                   iclIsMrpSecondaryInterface(7),
                   iclIsErpRplInterface(8),
                   iclIsErpMsInterface(9),
                   iclIsErpFsInterface(10),
                   iclNotInSessionVlan(11),
                   iclNotInMemberVlans(12),
                   nonIclInterfacesInSessionVlan(13),
                   mgmtVeNotConfiguredInSessionVlan(14),
                   mgmtIpNotConfiguredInSessionVlan(15),
                   mgmtIpIsUsedInPeerOrClientConfig(16),
                   mgmtIpNotInSubnetOfPeerIp(17),
                   rBridgeIdIsUsedInPeerOrClientConfig(18),
                   clientInterfaceIsNotInMemberVlan(19),
                   defaultVlanConfigForSessionOrMemberVlan(20)
                }
   MAX-ACCESS    read-only
   STATUS        current
   DESCRIPTION
       "The last failure reason for cluster deploy operation through SNMP.
        The following failure reason codes are supported:
           none(1)                              - The last deploy is successful.
           unknown(2)                           - The last deploy has failed
                                                  for unknown reason.
           rBridgeIdNotConfigured(3)            - Remote bridge id is not
                                                  configured.
           sessionVlanNotConfigured(4)          - Session VLAN is not
                                                  configured.
           iclNotConfigured(5)                  - ICL is not configured.
           peerNotConfigured(6)                 - Peer is not configured.
           iclIsMrpSecondaryInterface(7)        - In NI CES/CER devices, ICL
                                                  should not be MRP
                                                  secondary interface.
           iclIsErpRplInterface(8)              - In NI CES/CER devices, ICL
                                                  should not be ERP RPL
                                                  interface.
           iclIsErpMsInterface(9)               - In NI CES/CER devices, ICL
                                                  should not be ERP MS
                                                  interface.
           iclIsErpFsInterface(10)              - In NI CES/CER devices, ICL
                                                  should not be ERP FS
                                                  interface.
           iclNotInSessionVlan(11)              - ICL is not in session VLAN.
           iclNotInMemberVlans(12)              - ICL is not in member VLANs.
           nonIclInterfacesInSessionVlan(13)    - Non ICL interfaces are
                                                  present under session VLAN.
           mgmtVeNotConfiguredInSessionVlan(14) - Management VE is not
                                                  configured in session VLAN.
           mgmtIpNotConfiguredInSessionVlan(15) - Management IP is not
                                                  configured in session VLAN.
           mgmtIpIsUsedInPeerOrClientConfig(16) - Management IP is used in peer
                                                  or client configuration.
           mgmtIpNotInSubnetOfPeerIp(17)        - Management IP is not in subnet
                                                  of peer IP.
           rBridgeIdUsedInPeerOrClientConfig(18) - Remote bridge id is used
                                                   in peer or client
                                                   configuration.
           clientInterfaceIsNotInMemberVlan(19)  - Client interface is not in
                                                   member VLAN.
           defaultVlanConfigAsSessOrMemberVlan(20) - Default VLAN is configured
                                                     as session or member VLAN."
   ::= { brcdMctClusterEntry 11 }

brcdMctClusterRowStatus OBJECT-TYPE
   SYNTAX        RowStatus
   MAX-ACCESS    read-create
   STATUS        current
   DESCRIPTION
       "The row status of this MCT Cluster. All the values of RowStatus
        are supported. The notInService(2) indicates that cluster is not
        yet activated.

        The following objects should be present in the same SNMP set request
        to create a row with brcdMctClusterRowStatus set to createAndGo(4)
        value:
           brcdMctClusterName, brcdMctClusterRbridgeId,
           brcdMctClusterSessionVlan, brcdMctClusterMemberVlans,
           objects.

        The brcdMctClusterName object should be present in the same SNMP set
        request to create a row in brcdMctClusterTable with
        brcdMctClusterRowStatus set to createAndWait(5) value.

        If the cluster is deployed, then brcdMctClusterRowStatus cannot be
        set destroy(6)"
   ::= { brcdMctClusterEntry 12 }

-- End of brcdMctClusterTable

--
-- MCT Cluster ICL table
--
brcdMctClusterIclTable OBJECT-TYPE
   SYNTAX        SEQUENCE OF BrcdMctClusterIclEntry
   MAX-ACCESS    not-accessible
   STATUS        current
   DESCRIPTION
       "This table provides Multi Chassis Trunking Cluster information."
  ::= { brcdMctObjects 3 }

brcdMctClusterIclEntry OBJECT-TYPE
   SYNTAX        BrcdMctClusterIclEntry
   MAX-ACCESS    not-accessible
   STATUS        current
   DESCRIPTION
       "An entry in this table represents the MCT Cluster ICL."
   INDEX   { brcdMctClusterId,
             IMPLIED brcdMctClusterIclName
   }
   ::= { brcdMctClusterIclTable 1 }

BrcdMctClusterIclEntry ::= SEQUENCE {
   brcdMctClusterIclName               DisplayString,
   brcdMctClusterIclIfIndex            InterfaceIndex,
   brcdMctClusterIclRowStatus          RowStatus
}

brcdMctClusterIclName OBJECT-TYPE
   SYNTAX        DisplayString (SIZE(1..64))
   MAX-ACCESS    not-accessible
   STATUS        current
   DESCRIPTION
       "The name of ICL."
   ::= { brcdMctClusterIclEntry 1 }

brcdMctClusterIclIfIndex OBJECT-TYPE
   SYNTAX        InterfaceIndex
   MAX-ACCESS    read-create
   STATUS        current
   DESCRIPTION
       "The interface index of the ICL. The ICL interface can be a single
        ethernet interface or trunk interface index."
   ::= { brcdMctClusterIclEntry 2 }

brcdMctClusterIclRowStatus OBJECT-TYPE
   SYNTAX        RowStatus
   MAX-ACCESS    read-create
   STATUS        current
   DESCRIPTION
       "The row status of this MCT Cluster ICL entry. Only the active(1),
        createAndGo(4) and destroy (6) values of RowStatus are supported.

        If the cluster is deployed, then brcdMctClusterIclRowStatus cannot be
        set destroy(6).

        If the brcdMctClusterIclName is used in the peer configuration for
        object brcdMctClusterPeerIclName, then the peer configuration should
        be removed before setting the brcdMctClusterIclRowStatus to
        destroy(6)"
   ::= { brcdMctClusterIclEntry 3 }

-- End of brcdMctClusterIclTable

--
-- MCT Cluster Peer table
--
brcdMctClusterPeerTable OBJECT-TYPE
   SYNTAX        SEQUENCE OF BrcdMctClusterPeerEntry
   MAX-ACCESS    not-accessible
   STATUS        current
   DESCRIPTION
       "This table provides Multi Chassis Trunking Cluster Peers
        information.
        The objects in this table cannot be modified after the
        cluster is deployed"
  ::= { brcdMctObjects 4 }

brcdMctClusterPeerEntry OBJECT-TYPE
   SYNTAX        BrcdMctClusterPeerEntry
   MAX-ACCESS    not-accessible
   STATUS        current
   DESCRIPTION
       "An entry in this table represents the MCT Cluster Peer."
   INDEX   {
             brcdMctClusterId,
             brcdMctClusterPeerAddrType,
             brcdMctClusterPeerAddr
   }
   ::= { brcdMctClusterPeerTable 1 }

BrcdMctClusterPeerEntry ::= SEQUENCE {
   brcdMctClusterPeerAddrType        InetAddressType,
   brcdMctClusterPeerAddr            InetAddress,
   brcdMctClusterPeerRbridgeId       Unsigned32,
   brcdMctClusterPeerIclName         DisplayString,
   brcdMctClusterPeerFastFailover    EnabledStatus,
   brcdMctClusterPeerKeepAliveTime   Unsigned32,
   brcdMctClusterPeerHoldTime        Unsigned32,
   brcdMctClusterPeerActiveVlans     DisplayString,
   brcdMctClusterPeerOperStatus      INTEGER,
   brcdMctClusterPeerDownReason      INTEGER,
   brcdMctClusterPeerUpTime          TimeInterval,
   brcdMctClusterPeerRowStatus       RowStatus
}

brcdMctClusterPeerAddrType OBJECT-TYPE
   SYNTAX        InetAddressType
   MAX-ACCESS    not-accessible
   STATUS        current
   DESCRIPTION
       "The address type of this MCT Cluster Peer. The supported address
        types are ipv4(1) and ipv6(2)."
   ::= { brcdMctClusterPeerEntry 1 }

brcdMctClusterPeerAddr OBJECT-TYPE
   SYNTAX        InetAddress
   MAX-ACCESS    not-accessible
   STATUS        current
   DESCRIPTION
       "The IPv4/IPv6 address of this MCT Cluster Peer."
   ::= { brcdMctClusterPeerEntry 2 }

brcdMctClusterPeerRbridgeId OBJECT-TYPE
   SYNTAX        Unsigned32 (1..35535)
   MAX-ACCESS    read-create
   STATUS        current
   DESCRIPTION
       "The remote bridge Id of this MCT Cluster Peer."
   ::= { brcdMctClusterPeerEntry 3 }

brcdMctClusterPeerIclName OBJECT-TYPE
   SYNTAX        DisplayString (SIZE(1..64))
   MAX-ACCESS    read-create
   STATUS        current
   DESCRIPTION
       "The ICL name of this MCT Cluster Peer. This should be same as
        brcdMctClusterIclName object for this MCT Cluster"
   ::= { brcdMctClusterPeerEntry 4 }

brcdMctClusterPeerFastFailover OBJECT-TYPE
   SYNTAX        EnabledStatus
   MAX-ACCESS    read-create
   STATUS        current
   DESCRIPTION
       "The fast failover status of this MCT Cluster Peer.

        When this object is set to enable, as soon as the ICL interface
        goes down the CCP goes down. All the remote MACs are flushed.

        When set to disable, even if the ICL interface goes down the
        CCP waits for the hold-time before making the CCP down.
        Remote MACs are flushed only when the CCP is down."
   DEFVAL { enabled }
   ::= { brcdMctClusterPeerEntry 5 }

brcdMctClusterPeerKeepAliveTime OBJECT-TYPE
   SYNTAX        Unsigned32
   MAX-ACCESS    read-create
   STATUS        current
   DESCRIPTION
       "The keep-alive time in seconds of this MCT Cluster Peer. The range of
        keep-alive time is 0 to 21845. The default is 30 seconds."
   ::= { brcdMctClusterPeerEntry 6 }

brcdMctClusterPeerHoldTime OBJECT-TYPE
   SYNTAX        Unsigned32 (3..65535)
   MAX-ACCESS    read-create
   STATUS        current
   DESCRIPTION
       "The hold time in seconds of this MCT Cluster Peer. The hold time must
        be at least 3 times the keep alive time. The range of hold time is 3
        to 65535. The default is 90 seconds."
   DEFVAL { 90 }
   ::= { brcdMctClusterPeerEntry 7 }

brcdMctClusterPeerActiveVlans OBJECT-TYPE
   SYNTAX        DisplayString
   MAX-ACCESS    read-only
   STATUS        current
   DESCRIPTION
       "The list of the active member VLANs of this MCT Cluster Peer.
        The VLANs which are not continuous are represented with a space
        separated and continuous VLANs represented with the range.
        For example: 2 5 10 to 40 100"
   ::= { brcdMctClusterPeerEntry 8 }

brcdMctClusterPeerOperStatus OBJECT-TYPE
   SYNTAX        INTEGER {
                   unknown(1),
                   noState(2),
                   init(3),
                   ccpUp(4),
                   ccpDown(5),
                   reachable(6)
                }
   MAX-ACCESS    read-only
   STATUS        current
   DESCRIPTION
       "The operational status of this MCT Cluster Peer. The follwoing
        values are supported for operational status
        unknown(1)   - Unknown state
        noState(2)   - The peer state machine is not started
        init(3)      - The peer state machine is initializing
        ccpUp(4)     - CCP is up
        ccpDown(5)   - CCP is down
        reachable(6) - CCP is down, but peer is reachable through keep
                       alive VLAN"
   ::= { brcdMctClusterPeerEntry 9 }

brcdMctClusterPeerDownReason OBJECT-TYPE
   SYNTAX        INTEGER {
                   none(1),
                   loopbackInterfaceDown(2),
                   iclInterfaceDown(3),
                   upgradeInProgress(4),
                   routeNotAvailable(5),
                   iclVeDown(6),
                   rBridgeIdMismatch(7),
                   clusterIdMismatch(8),
                   keepAliveTimeMismatch(9),
                   holdTimeMismatch(10),
                   fastFailoverMismatch(11),
                   shutdownMesgFromPeer(12),
                   tcpKeepAliveTimeout(13),
                   tcpConnCloseMesg(14),
                   holdTimeoutExpired(15),
                   sendStateTimeoutExpired(16),
                   recvStateTimeoutExpired(17),
                   initMesgSendFail(18),
                   keepAliveMesgSendFail(19),
                   invalidAppMesgRecv(20),
                   badProtocolVersionPktRecv(21),
                   badPduLengthPktRecv(22),
                   unknownCcpPktRecv(23),
                   invalidCcpPktRecv(24),
                   internalCcpErrorRecv(25),
                   ccpTcpCommFail(26)
                }
   MAX-ACCESS    read-only
   STATUS        current
   DESCRIPTION
       "The reason for the brcdMctClusterPeerOperStatus is in ccpDown(3) state.
        The following values are supported as down reason:
        none(1)                      - Peer is not in down state
        loopbackInterfaceDown(2)     - Loopback interface down
        iclInterfaceDown(3)          - ICL interface down
        upgradeInProgress(4)         - Graceful upgrade in progress
        routeNotAvailable(5)         - Route to cluster Peer is not available
        iclVeDown(6)                 - ICL VE interface down
        rBridgeIdMismatch(7)         - RBridge ID does not match with Peer
        clusterIdMismatch(8)         - Cluster ID does not match with Peer
        keepAliveTimeMismatch(9)     - KeepAlive Time does not match with Peer
        holdTimeMismatch(10)          - Hold Time does not match with Peer
        fastFailoverMismatch(11)     - Fast Failover parameter does not match
                                      with Peer
        shutdownMesgFromPeer(12)     - ShutDown message came from Peer
        tcpKeepAliveTimeout(13)      - TCP keepalive timeout message came
        tcpConnCloseMesg(14)         - TCP connection close message came
        holdTimeoutExpired(15)       - Hold timeout expired
        sendStateTimeoutExpired(16)  - Send State timeout expired
        recvStateTimeoutExpired(17)  - Recieve State timeout expired
        initMesgSendFail(18)         - Unable to send the Init message
        keepAliveMesgSendFail(19)    - Unable to send the Keepalive message
        invalidAppMesgRecv(20)       - Invalid Application packet received
                                       message came from peer
        badProtocolVersionPktRecv(21) - Bad Protocol version packet received
                                       message came from peer
        badPduLengthPktRecv(22)      - Bad PDU length packet received message
                                       came from peer
        unknownCcpPktRecv(23)        - Unknown CCP message type packet received
                                       message came from peer
        invalidCcpPktRecv(24)        - Invalid CCP message length packet
                                       received message came from peer
        internalCcpErrorRecv(25)     - Internal CCP error message came from peer
        ccpTcpCommFail(26)           - Cluster CCP TCP communication failed"
   ::= { brcdMctClusterPeerEntry 10 }

brcdMctClusterPeerUpTime OBJECT-TYPE
   SYNTAX        TimeInterval
   MAX-ACCESS    read-only
   STATUS        current
   DESCRIPTION
       "The time since this MCT Cluster Peer is up. If the
        brcdMctClusterPeerOperStatus is not in ccpUp(2) state, then zero
        will be returned."
   ::= { brcdMctClusterPeerEntry 11 }

brcdMctClusterPeerRowStatus OBJECT-TYPE
   SYNTAX        RowStatus
   MAX-ACCESS    read-create
   STATUS        current
   DESCRIPTION
       "The row status of this MCT Cluster Peer.  Only the active(1),
        notInService(2), createAndGo(4) and destroy(6) values of RowStatus
        are supported. The notInService(2) indicates that cluster is not
        yet activated.

        The SNMP set request to create a row with brcdMctClusterPeerRowStatus
        set to createAndGo(4) value should contain the
        brcdMctClusterPeerRbridgeId and brcdMctClusterPeerIclName objects in
        the same SNMP set request.

        If the cluster is deployed, then brcdMctClusterPeerRowStatus cannot be
        set destroy(6)"
   ::= { brcdMctClusterPeerEntry 12 }

-- End of brcdMctClusterPeerTable

--
-- MCT Cluster client table
--
brcdMctClusterClientTable OBJECT-TYPE
   SYNTAX        SEQUENCE OF BrcdMctClusterClientEntry
   MAX-ACCESS    not-accessible
   STATUS        current
   DESCRIPTION
       "This table provides Multi Chassis Trunking Cluster Clients information."
  ::= { brcdMctObjects 5 }

brcdMctClusterClientEntry OBJECT-TYPE
   SYNTAX        BrcdMctClusterClientEntry
   MAX-ACCESS    not-accessible
   STATUS        current
   DESCRIPTION
       "An entry in this table represents the MCT Cluster Client."
   INDEX   {
             brcdMctClusterId,
             IMPLIED brcdMctClusterClientName
   }
   ::= { brcdMctClusterClientTable 1 }

BrcdMctClusterClientEntry ::= SEQUENCE {
   brcdMctClusterClientName                 DisplayString,
   brcdMctClusterClientRbridgeId            Unsigned32,
   brcdMctClusterClientIfIndex              InterfaceIndex,
   brcdMctClusterClientOperStatus           INTEGER,
   brcdMctClusterClientDeploy               BrcdDeployStatus,
   brcdMctClusterClientDeployFailureReason  INTEGER,
   brcdMctClusterClientRowStatus            RowStatus
}

brcdMctClusterClientName OBJECT-TYPE
   SYNTAX        DisplayString (SIZE(1..64))
   MAX-ACCESS    not-accessible
   STATUS        current
   DESCRIPTION
       "The name of this MCT Cluster client."
   ::= { brcdMctClusterClientEntry 1 }

brcdMctClusterClientRbridgeId     OBJECT-TYPE
   SYNTAX        Unsigned32 (1..35535)
   MAX-ACCESS    read-create
   STATUS        current
   DESCRIPTION
       "The remote bridge id of this MCT Cluster client. This remote
        bridge ID is used by the client to communicate with this
        cluster node."
   ::= { brcdMctClusterClientEntry 2 }

brcdMctClusterClientIfIndex  OBJECT-TYPE
   SYNTAX        InterfaceIndex
   MAX-ACCESS    read-create
   STATUS        current
   DESCRIPTION
       "The interface index which is connected to this MCT Cluster
        client. The interface should be an ethernet interface or
        trunk interface."
   ::= { brcdMctClusterClientEntry 3 }

brcdMctClusterClientOperStatus   OBJECT-TYPE
   SYNTAX        INTEGER {
                   unknown(1),
                   noState(2),
                   init(3),
                   localDeploy(4),
                   adminUp(5),
                   remoteUp(6),
                   localUp(7),
                   up(8),
                   slave(9),
                   master(10),
                   masterPeerUp(11)
                }
   MAX-ACCESS    read-only
   STATUS        current
   DESCRIPTION
       "The operational status of this MCT Cluster client. The following
        values are taken by the operational status:
        unknown(1)       - Unknown state
        noState(2)       - The peer state machine is not started
        init(3)          - The peer state machine is initializing
        localDeploy(4)   - The client is up, but not configured at remote side
        adminUp(5)       - The client is up, but both the client interfaces
                           are operationally down
        remoteUp(6)      - The client's remote side is up and locally down
        localUp(7)       - The client is locallly up and remote side is down
        up(8)            - The client is up locally and at remote side
        slave(9)         - The client is down and it has taken the slave role
        master(10)       - The client is down and it has taken the master role
        masterPeerUp(11) - The client is down, it has taken the master role
                           and master peer is up."
   ::= { brcdMctClusterClientEntry 4 }

brcdMctClusterClientDeploy OBJECT-TYPE
   SYNTAX        BrcdDeployStatus
   MAX-ACCESS    read-create
   STATUS        current
   DESCRIPTION
       "The admin status of this MCT Cluster client. When this object
        is set to deploy and if cluster is not deployed, the
        configuration will be taken but the client state machine will
        not be started.

        The objects in this table are not allowed to modify after client
        is deployed except brcdMctClusterClientDeploy object."
   ::= { brcdMctClusterClientEntry 5 }

brcdMctClusterClientDeployFailureReason OBJECT-TYPE
   SYNTAX        INTEGER {
                   none(1),
                   unknown(2),
                   rBridgeIdNotConfigured(3),
                   clientInterfaceNotConfigured(4),
                   rBridgeIdUsedInClusterOrPeer(5),
                   clientInterfacePhysicallyNotUp(6),
                   clientInterfaceIsMrpRingInterface(7),
                   clientInterfaceIsErpInterface(8),
                   iclIsNotInMemberVlan(9)
                }
   MAX-ACCESS    read-only
   STATUS        current
   DESCRIPTION
       "The failure reason for the last cluster client deploy operation
        through SNMP. The following failure reasons are supported:
            none(1)                             - The last deploy is successful.
            unknown(2)                          - The last deploy is failed for
                                                  unknown reason.
            rBridgeIdNotConfigured(3)           - Remote bridge is not
                                                  configured.
            clientInterfaceNotConfigured(4)     - Client interface is not
                                                  configured.
            rBridgeIdUsedInClusterOrPeer(5)     - Remote bridge id is used in
                                                  cluster or peer configuration.
            clientInterfaceNotPresent(6)        - Client interface is physically
                                                  not present
            clientInterfaceIsMrpRingInterface(7) - Client interface is
                                                   configured as MRP ring
                                                   interface.
            clientInterfaceIsErpInterface(8)    - Client interface is configured
                                                  as ERP interface.
            iclIsNotInMemberVlan(9)             - ICL is not in member VLAN."
   ::= { brcdMctClusterClientEntry 6 }

brcdMctClusterClientRowStatus   OBJECT-TYPE
   SYNTAX        RowStatus
   MAX-ACCESS    read-create
   STATUS        current
   DESCRIPTION
       "The row status of this MCT Cluster client. All the values of RowStatus
        are supported. The notInService(2) indicates that cluster client is
        not deployed.

        The brcdMctClusterClientRbridgeId and brcdMctClusterClientIfIndex
        objects should be present in the same SNMP set request to create a row
        with brcdMctClusterClientRowStatus set to createAndGo(4) value."
   ::= { brcdMctClusterClientEntry 7 }

-- End of brcdMctClusterTable

---
--- MCT Notifications
---

brcdMctClusterPeerStatus NOTIFICATION-TYPE
   OBJECTS     { brcdMctClusterPeerOperStatus,
                 brcdMctClusterPeerDownReason
   }
   STATUS      current
   DESCRIPTION
       "This notification is generated when the
        brcdMctClusterPeerOperStatus object for peer entry in
        brcdMctClusterPeerTable changes the state to ccpUp(3),
        ccpDown(4) or reachable(5) from any other state."
   ::= { brcdMctNotifications 1 }

brcdMctClusterClientStatus NOTIFICATION-TYPE
   OBJECTS     { brcdMctClusterClientOperStatus }
   STATUS      current
   DESCRIPTION
       "This notification is generated when the
        brcdMctClusterClientOperStatus object for peer entry in
        brcdMctClusterClientTable changes the state to remoteUp(5),
        localUp(6), up(7), slave(8), master(9) or masterPeerUp(10)
        from any other state.

        This notification is not generated when the client state change happens
        when brcdMctClusterPeerOperState changes from ccpUp(2) to ccpDown(3)
        or vice versa"
   ::= { brcdMctNotifications 2 }

--- End of MCT Notifications
END
