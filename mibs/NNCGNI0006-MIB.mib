-- @(#)GNI0006.mib     1.13 09/16/94
--------------------------------------------------------------------------------
-- file: GNI0006.mib
--
-- contents:
--      This file contains the Newbridge MIB extensions for a standalone
--      network element. When this file is changed, document GNI0006 must 
--      be updated to reflect the new clearcase version number for GNI0006.mib.
--
-- history:
--      0.1 / 92.08.25 / J. Watt / Creation
--      0.2 / 93.04.04 / J. Watt / Removed P from Minus12Status name, changed
--                                 type of ProbeMPL to OCTET STRING, fixed
--                                 MAX-ACCESS for various Table's and Entry's, 
--                                 removed INDEX for ProbeMPL
-- M321-B1.01 / 93.05.20 / S. Buchko / nncExtCodeSpaceStatus should be read-only
-- M321-C1.01 / 93.06.03 / S. Buchko / Added nncExtCodeSpaceLoadSize
-- M321-C3.01 / 93.06.25 / S. Buchko / changed download requestor and server to
--                                     be display strings
-- M321-C3.02 / 93.06.28 / S. Buchko / added nncExtRestartCause, modified 
--                                     the definition of some of the restart
--                                     counters to reflect reality
-- M321-F1.01 / 93.09.30 / B. McEachern / added RestartCause definitions
--    31A0359 / 94.08.25 / C. Rajsic / added nncExtSysProductPartNumber,
--                                     nncExtSysDeviceID
--    31A0359 / 94.09.10 / J. Watt / removed 2nd copy at bottom of file,
--                                   remove underbars in definitions as they
--                                   are not legal ASN.1.
--    31A0359 / 94.09.12 / C. Rajsic / changed SYNTAX of nncExtRestartCause from
--                                     INTEGER to RestartCause.
--    31A0359 / 94.09.12 / J. Watt / Restored DESCRIPTION clauses and converted
--                                   to SNMPv2 SMI.
--    31A0359 / 94.09.13 / C. Rajsic / added DeviceID TEXTUAL-CONVENTION.
--    31A0359 / 94.09.21 / C. Rajsic / added Nci2DeviceID enums, mods from 
--                                     GNI0006 review (see minutes,94.09.15)
--    31A0359 / 94.10.20 / A. Paterson / Changed module ID to legacy module ID
--                                       number space.
--    31A0359 / 94.11.21 / M. Dubois / added newly defined
--                                      nncExtRestartSystem and
--                                      nncExtStartupDiagnosticsResults
--    31A0359 / 94.11.28 / C. Rajsic / added INDEX clause to nncExtProbeMPLEntry
--    P103679 / 1996.09.04 / M. Paquette / Change to real module names
--    48A0003 / 96.12.11 / M. Dubois / added nncExtSysCurrentDateAndTime and
--                                       nncExtSysCardTable...
--    31A1225 / 99.05.20 / jayanthi  / added NncSwBank and NncSwStatus textual 
--                                     conventions.
--
--  history-start
--  94.08.25 crajsic 31A0359 - copied from /gum/gum-daily/sun4/exec 
--  94.09.09 crajsic 31A0359 - Removed Tabs 
--  94.09.11 james 31A0359 - make valid MIB module 
--  94.09.12 crajsic 31A0359 changed SYNTAX of nncRestartCause from INTEGER 
--    to RestartCause. 
--  94.09.13 crajsic 31A0359 added DeviceID TEXTUAL-CONVENTION. 
--  94.09.21 crajsic 31A0359 added Nci2DeviceID enums. Mods maade from 
--    GNI0006 review (see minutes,94.09.15). 
--  94.10.21 andrewp 31A0359 Changed module ID to be in the number space for 
--    the "legacy" modules. 
--  94.11.28 crajsic 31A0359 Added INDEX clause to nncExtProbeMPLEntry, to 
--    satisfy mosy. 
--  96.02.19 dcauchy 31A0644: Add to oc3, tds3 and te3 for ILMI. 
--  96.03.11 bgemin 34A0130: not required in yridge-nerf 
--  96.10.24 aislam 34A0050: Added NCI-2 device Ids 
--  97.06.02 qiangwu 34A0421: This file is not needed for traffic shaper 
--  97.09.30 sthiruna P.200661: Added Fan Status, PwrSupply Status in 
--    nncExtEnvironmental (5 and 6). Also added nncExtTrafMgmt for SvcEpd/Ppd 
--    Options. 
--  98.02.28 sthiruna P.89519: Changed the size of 
--    nncExtCodeSpaceDownloadDate from 9 to 11. Also merged Basics.mib and 
--    GNI0006.mib as they are basically the same files. 
--  98.03.05 stakkar 34A0184: Added type DateAndTime from SNMPv2-TC. 
--  history-end
--
--  %%history-start%%
--  1999.06.15 jayanthi P.285550: varianting for epectl, epecompact, 
--    epecompactlite platforms. 
--  %%history-end%%
-- Copyright 1992-1999 Newbridge Networks Corporation.  All Rights Reserved.
--------------------------------------------------------------------------------
NNCGNI0006-MIB DEFINITIONS ::= BEGIN

        IMPORTS        
                MODULE-IDENTITY, OBJECT-TYPE, Counter32
                                        FROM SNMPv2-SMI

                DisplayString, TEXTUAL-CONVENTION, DateAndTime
                                        FROM SNMPv2-TC

                nncLegacyModules,
		nncExtSystem, nncExtEnvironmental, nncExtRestart, 
                nncExtCodeSpace, nncExtNVM, nncExtProbe, nncExtDiag
                                        FROM NNCGNI0001-SMI;

         nncExtBasics MODULE-IDENTITY
                LAST-UPDATED "9904301330Z"
                ORGANIZATION "Newbridge Networks Corporation"
                CONTACT-INFO
                "        Newbridge Networks Corporation
                 Postal: 600 March Road
                         Kanata, Ontario
                         Canada K2K 2E6

                 Phone:  +1 613 591 3600
                 Fax:    +1 613 591 3680"
                DESCRIPTION
                        "The MIB module containing management information
                         for basic network element functions: restart info,
                         environmental info, box identity, etc."
                ::= { nncLegacyModules 1 }


        RestartCause ::= TEXTUAL-CONVENTION
                STATUS current
                DESCRIPTION
                        "Why the box restarted."
                SYNTAX INTEGER {
                          trblnoProblem(0),
                          trblUnknown(1),
                          trblBusError(2),
                          trblAddressError(3),
                          trblIllegalInst(4),
                          trblZeroDivide(5),
                          trblChkFailure(6),
                          trblTrapVInst(7),
                          trblPrivilege(8),
                          trblTraceTrap(9),
                          trblLine1010(10),
                          trblLine1111(11),
                          trblUninitialized(15),
                          trblSpurious(24),
                          trblIntLevel1(25),        
                          trblIntLevel2(26),
                          trblIntLevel3(27),
                          trblIntLevel4(28),
                          trblIntLevel5(29),
                          trblIntLevel6(30),
                          trblIntLevel7(31),
                          trblTrap00(32),
                          trblTrap01(33),
                          trblTrap02(34),
                          trblTrap03(35),
                          trblTrap04(36),
                          trblTrap05(37),
                          trblTrap06(38),
                          trblTrap07(39),
                          trblTrap08(40),
                          trblTrap09(41),
                          trblTrap10(42),
                          trblTrap11(43),
                          trblTrap12(44),
                          trblTrap13(45),
                          trblTrap14(46),
                          trblTrap15(47),
                          trblWatchDog(48),
                          trblNCIReset(49),
                          trblNCIRunMinusOne(50),
                          trblPanic(51),
                          trblRunBootProm(52),
                          trblCopyRamToFlash(53),
                          trblDnldAborted(54),
                          trblBadFlashConfig(55),
                          trblNVMReset(56),
                          trblDspReset(57),
                          trblDspDnldFailed(58),
                          trblDspPollFailed(59),
                          trblDspDiedOnTx(60),
                          trblDspDead(61),
                          trblDCMPDeath(62),
                          trblRunningLowComms(63),
                          trblRunningLowFrame(64),
                          trblRunningLowSys(65),
                          trblRunningLowSonic(66),
                          trblRunningLowMgmt(67),
                          trblRunningLowPoolUnknown(68),
                          trblNCIReload(69),
                          trblPushButton(70),
                          trblCPUReset(71),
                          trblRDSReset(72)
                  }

        Nci2DeviceIDType ::= TEXTUAL-CONVENTION
                STATUS current
                DESCRIPTION
                        "An entities device identifier. These numbers are
                         assigned by the device ID administrator.  He/she
                         must be contacted if new device IDs need to be 
                         added."
                SYNTAX INTEGER {
                                unknown(0),
                                nc3600(1),
                                dcp3600(2),
                                dtu2601(4),
                                dtu2602(5),
                                dtu2603(6),
                                dclcRs232(7),
                                dclcX21(8),
                                dclcV35(9),
                                ldm1124(10),
                                ldm1121(11),
                                ldm1135(12),
                                nmu4601(13),
                                nmu4602(14),
                                nc3624(15),
                                nc3612(16),
                                nc3630(17),
                                dtu2601Anm(18),
                                dtu2602Anm(19),
                                dtu2603Anm(20),
                                dtu2608(21),
                                dsp3600(22),
                                dpm3600(23),
                                detT1(24),
                                detE1(25),
                                nmu4601A(26),
                                nmu4605(27),
                                nmu5602(28),
                                nmu5610(29),
                                nc3645SE(30),
                                nc3645PE(31),
                                dtu2610Pad(32),
                                dtu2606(33),
                                nmu5610ci(34),
                                ncDS3(35),
                                ta1601S(36),
                                ta1601U(37),
                                ta1602S(38),
                                ta1602U(39),
                                ta1603S(40),
                                ta1603U(41),
                                elb8230(42),
                                nvpSysMgr(43),
                                nvpVoiceSrvr(44),
                                nvpEdsp(45),
                                nc1615C(46),
                                nc3606Voice(47),
                                nc3606Data(48),
                                nvp1000(49),
                                dtu2701(50),
                                dtu2702(51),
                                dtu2703(52),
                                bert2601(53),
                                bert2602(54),
                                bert2603(55),
                                dtu2701Anm(56),
                                dtu2702Anm(57),
                                dtu2703Anm(58),
                                tap(59),
                                nmu8001(60),
                                bertMgr(61),
                                dclcRs422(62),
                                eapApi(63),
                                ncdE3(64),
                                er8231(65),
                                tr8251(66),
                                pte(67),
                                nc3664(68),
                                nc36150(69),
                                esn3700(70),
                                esnEsc(71),
                                esnOne(72),
                                dtu2704(73),
                                nmu4602Dn(74),
                                nmu4602Cn(75),
                                nmu4602Rn(76),
                                nc3620(77),
                                ncWgs(78),
                                nc36170(79),
                                bri3600St(80),
                                ncFRATM(81),
                                ncRouteServer(82),
                                ncSystemManager(83),
                                ncATMNIC(84),
                                ncYellowRidge(85),
                                ncELSU(93),
                                ncBlueRidge(97),
                                ncOrangeRidge(101),
                                ncRedRidge(102),
                                ncCampusSwitch(112)
                              }

        CurrentGenericType ::= TEXTUAL-CONVENTION
                STATUS current
                DESCRIPTION
                        "The revision of the current executing firmware in 
                         the standard Newbridge fashion.  The identifier is a 
                         string of up to 12 ASCII characters of the form
                         ZAABCD-TM-LL where:
                               ZAABC identifies the product,
                               D     identifies the major release
                               T     identifies the load type
                               M     identifies the minor release and
                               LL    identifies the load number"
                SYNTAX DisplayString (SIZE (1..16)) 

        ProductPartNumberType ::= TEXTUAL-CONVENTION
                STATUS current
                DESCRIPTION
                        "This type defines the standard Newbridge assembly
                         part number.  The assembly number identifier is a
                         string of 17 ASCII characters of the form
                         90-xxxx-VV-CC-MMM where:
                               90   - Marketing part number
                               xxxx - sequence number
                               VV   - Variant
                               CC   - Customer Code
                               MMM  - Manufacturing Code"
                SYNTAX DisplayString (SIZE (1..20)) 

  CardIDType ::= TEXTUAL-CONVENTION
                STATUS current
                DESCRIPTION
                        "An module identifier (from GNI0001 found in Tech Lib)."
                SYNTAX INTEGER {
                                unknown(0),
                                yellowRidgeMainCard(4),
                                yellowRidgeLEDBoard(5),
                                yellowRidgeOc3MmfPdmModule(6),
                                yellowRidgeBufferModule(7),
                                yellowRidgeOc3SmfPdmModule(51),
                                cpElsuMainCard(57),
                                coElsuAtmCard(58),
                                coElsuMainCard(59),
                                elsuDisplayModule(60),
                                elsuAuiBackplane(61),
                                coElsu10BaseTBackplane(62)
                               }
 
        CardSerialNumberType ::= TEXTUAL-CONVENTION
                DISPLAY-HINT "2d-2d,1d,8d"
                STATUS current
                DESCRIPTION
                        "An module serial number specification. 2d-2d,1d,8d

                  field  bytes   contents                  range
                  -----  -----   --------                  -----
                    1     1-2    week                      1..52
                    2     3-4    year                      0..99
                    3      5     assembly line             0..9
                    4     6-10   assembly number           0..99999"

                SYNTAX OCTET STRING (SIZE (10))
 

    NncSwStatus ::=   TEXTUAL-CONVENTION
    STATUS            current
    DESCRIPTION       "The NncSwStatus represents the status of any software bank."
    SYNTAX            INTEGER {
                        notApplicable(1),
                        ok(2),
                        error(3),
                        empty(4) }

 
    NncSwBank ::=   TEXTUAL-CONVENTION
    STATUS            current
    DESCRIPTION       "The NncSwBank represents a software bank."
    SYNTAX            INTEGER {
                        notapplicable(0), -- indicates an entity with no software banks.
                        bootbank(1), 
                        bank1(2),
                        bank2(3),
                        bank3(4),
                        bank4(5),
                        bank5(6),
                        bank6(7),
                        bank7(8),
                        bank8(9),
                        bank9(10),
                        bank10(11),
                        bank11(12),
                        bank12(13),
                        bank13(14),
                        bank14(15),
                        bank15(16),
                        bank16(17),
                        bank17(18),
                        bank18(19),
                        bank19(20),
                        bank20(21),
                        bank21(22),
                        bank22(23),
                        bank23(24),
                        bank24(25),
                        bank25(26),
                        bank26(27),
                        bank27(28),
                        bank28(29),
                        bank29(30),
                        bank30(31), 
                        bank31(32),
                        bank32(33),
                        unknown(257)  -- indicates that the information is not available
                                      -- for some reason.
                       }

-- -----------------------------------------------------------------------------
--
--         System Table Extensions
--
-- -----------------------------------------------------------------------------

        nncExtSysProductName        OBJECT-TYPE
                SYNTAX        DisplayString (SIZE (1..16))
                MAX-ACCESS    read-only
                STATUS        current
                DESCRIPTION
                        "The marketing name for the product, e.g. 
                         8231 MainStreet"
                ::= {nncExtSystem 1}
                
                
        nncExtSysCurrentGeneric        OBJECT-TYPE
                SYNTAX        CurrentGenericType 
                MAX-ACCESS    read-only
                STATUS        current
                DESCRIPTION
                        "The revision of the current executing firmware 
                         in the controlling component of the system."
                ::= {nncExtSystem 2}


        nncExtSysProductPartNumber OBJECT-TYPE
                SYNTAX      ProductPartNumberType
                MAX-ACCESS  read-only
                STATUS  current
                DESCRIPTION
                        "The Newbridge assembly part number for the given
                         system." 
                ::= {nncExtSystem 3}


        nncExtSysNci2DeviceID       OBJECT-TYPE
                SYNTAX      Nci2DeviceIDType
                MAX-ACCESS  read-only
                STATUS      current
                DESCRIPTION
                        "The NCI2 device ID assigned to the device."
                ::= {nncExtSystem 4}


        nncExtSysCurrentDateAndTime       OBJECT-TYPE
                SYNTAX      DateAndTime
                MAX-ACCESS  read-write
                STATUS      current
                DESCRIPTION
                        "If set on the device, this returns the date and time.
                         Otherwise, returns all 0s."
                ::= {nncExtSystem 5}

-- -----------------------------------------------------------------------------
--
--         System Card Table
--
-- -----------------------------------------------------------------------------

        nncExtSysCardTable         OBJECT-TYPE
                SYNTAX        SEQUENCE OF NncExtSysCardEntry
                MAX-ACCESS    not-accessible
                STATUS        current
                DESCRIPTION
                        "Table containing information about the card in this
                         system."
                ::= {nncExtSystem 6}
 
        nncExtSysCardEntry        OBJECT-TYPE
                SYNTAX        NncExtSysCardEntry
                MAX-ACCESS    not-accessible
                STATUS        current
                DESCRIPTION
                        "An entry in the system card table."
                INDEX {nncExtSysCardIndex}
                ::= {nncExtSysCardTable 1}
 
        NncExtSysCardEntry
                ::= SEQUENCE {
                        nncExtSysCardIndex        INTEGER,
                        nncExtSysCardIDType       CardIDType,
                        nncExtSysCardName         OCTET STRING,
                        nncExtSysCardSerialNumber CardSerialNumberType
                }

        nncExtSysCardIndex        OBJECT-TYPE
                SYNTAX       INTEGER
                MAX-ACCESS   read-only
                STATUS       current
                DESCRIPTION
                    "Card number."
                ::= {nncExtSysCardEntry 1}

        nncExtSysCardIDType       OBJECT-TYPE
                SYNTAX        CardIDType
                MAX-ACCESS    read-only
                STATUS        current
                DESCRIPTION
                        "Type of module/card."
                ::= {nncExtSysCardEntry 2}

        nncExtSysCardName        OBJECT-TYPE
                SYNTAX        OCTET STRING (SIZE (0..255))
                MAX-ACCESS    read-only
                STATUS        current
                DESCRIPTION
                        "The name of the card as saved on the SEEP."
                ::= {nncExtSysCardEntry 3}

        nncExtSysCardSerialNumber OBJECT-TYPE
                SYNTAX        CardSerialNumberType
                MAX-ACCESS    read-only
                STATUS        current
                DESCRIPTION
                        "Serial number of the current card."
                ::= {nncExtSysCardEntry 4}


-- -----------------------------------------------------------------------------
--
--         Environmental Extensions
--
-- -----------------------------------------------------------------------------

        nncExtEnvFanStatus        OBJECT-TYPE
                SYNTAX        INTEGER { fanOk(1), fanFailed(2) }
                MAX-ACCESS    read-only
                STATUS        current
                DESCRIPTION
                        "The current status of the fan. This is product
                         dependent."
                ::= {nncExtEnvironmental 1}
                
                
        nncExtEnvTemperatureSensor        OBJECT-TYPE
                SYNTAX        INTEGER { ok(1), tooHot(2) }
                MAX-ACCESS    read-only
                STATUS        current
                DESCRIPTION
                        "The suitability of the current temperature. 
                         This is product dependent."
                ::= {nncExtEnvironmental 2}
                
                
        nncExtEnvPlus12Status        OBJECT-TYPE
                SYNTAX        INTEGER { ok(1), outOfSpec(2) }
                MAX-ACCESS    read-only
                STATUS        current
                DESCRIPTION
                        "Whether or not the +12V rail is in spec.
                         This is product dependent."
                ::= {nncExtEnvironmental 3}
                
                
        nncExtEnvMinus12Status        OBJECT-TYPE
                SYNTAX        INTEGER { ok(1), outOfSpec(2) }
                MAX-ACCESS    read-only
                STATUS        current
                DESCRIPTION
                        "Whether or not the -12V rail is in spec.  
                         This is product dependent."
                ::= {nncExtEnvironmental 4}


    FanStatusType ::= TEXTUAL-CONVENTION
                STATUS          current
                DESCRIPTION
                      "A value of this type identifies if the fan status is ok or bad" 
                SYNTAX          INTEGER {ok(0), bad(1)}


        nncExtEnvFanTable   OBJECT-TYPE
                SYNTAX          SEQUENCE OF NncExtEnvFanTableEntry
                MAX-ACCESS      not-accessible
                STATUS          current
                DESCRIPTION     
                          "This table holds the fan status information"
                 ::= {nncExtEnvironmental 5}


        nncExtEnvFanTableEntry  OBJECT-TYPE
                SYNTAX         NncExtEnvFanTableEntry
                MAX-ACCESS     not-accessible
                STATUS         current
                DESCRIPTION
                        " A conceptual row for nncExtEnvFanTable. "
                INDEX   {nncExtEnvFanIndex}
                ::=  {nncExtEnvFanTable 1}    

        NncExtEnvFanTableEntry ::= SEQUENCE
        {
               nncExtEnvFanIndex                INTEGER,
               nncExtEnvFanStatusByFanIndex     FanStatusType
        }

        nncExtEnvFanIndex     OBJECT-TYPE
               SYNTAX           INTEGER (1..255) 
               MAX-ACCESS     read-only
               STATUS         current
               DESCRIPTION   
                      "The index into the fan table"
               ::= {nncExtEnvFanTableEntry 1}


        nncExtEnvFanStatusByFanIndex     OBJECT-TYPE
                SYNTAX             FanStatusType
                MAX-ACCESS         read-only
                STATUS             current
                DESCRIPTION
                        "The state of the fan - ok or bad"
                ::= {nncExtEnvFanTableEntry 2}


        PwrSupplyStatusType ::= TEXTUAL-CONVENTION
                STATUS          current
                DESCRIPTION
                      "A value of this type identifies the power supply status" 
                SYNTAX          INTEGER {ok(0), noAc(1), noDc(2), notPresent(3)}


        nncExtEnvPwrSupplyTable    OBJECT-TYPE
                SYNTAX          SEQUENCE OF NncExtEnvPwrSupplyTableEntry
                MAX-ACCESS      not-accessible
                STATUS          current
                DESCRIPTION     
                          "This table holds the fan status information"
                 ::= {nncExtEnvironmental 6}


        nncExtEnvPwrSupplyTableEntry  OBJECT-TYPE
                SYNTAX             NncExtEnvPwrSupplyTableEntry
                MAX-ACCESS         not-accessible
                STATUS             current
                DESCRIPTION
                        " A conceptual row for nncExtEnvPwrSupplyTable. "
                INDEX   {nncExtEnvPwrSupplySlotIndex}
                ::=  {nncExtEnvPwrSupplyTable 1}    

        NncExtEnvPwrSupplyTableEntry ::= SEQUENCE
        {
               nncExtEnvPwrSupplySlotIndex     INTEGER,
               nncExtEnvPwrSupplyStatus        PwrSupplyStatusType
        }

        nncExtEnvPwrSupplySlotIndex   OBJECT-TYPE
               SYNTAX               INTEGER (1..255)
               MAX-ACCESS           read-only
               STATUS               current
               DESCRIPTION   
                      "Power Supply Slot Number  - Ranges from 1 to 255"
               ::= {nncExtEnvPwrSupplyTableEntry 1}


        nncExtEnvPwrSupplyStatus     OBJECT-TYPE
                SYNTAX                PwrSupplyStatusType
                MAX-ACCESS            read-only
                STATUS                current
                DESCRIPTION
                        "The state of the power supply - ok , off, bad or not present"
                ::= {nncExtEnvPwrSupplyTableEntry 2}

-- -----------------------------------------------------------------------------
--
--         Restart Info Extensions
--
-- -----------------------------------------------------------------------------

        nncExtRestarts        OBJECT-TYPE
                SYNTAX        Counter32 
                MAX-ACCESS    read-only
                STATUS        current
                DESCRIPTION
                        "The number of times the active code bank has restarted."
                ::= {nncExtRestart 1}


        nncExtFaultInducedRestarts        OBJECT-TYPE
                SYNTAX        Counter32 
                MAX-ACCESS    read-only
                STATUS        current
                DESCRIPTION
                        "The number of restarts of the active code bank that 
                         have been caused by a fault, e.g. processor trap."
                ::= {nncExtRestart 2}


        nncExtLastFault        OBJECT-TYPE
                SYNTAX        RestartCause
                MAX-ACCESS    read-only
                STATUS        current
                DESCRIPTION
                        "The cause of the last restart of the active code bank
                         that was caused by a fault, e.g. processor trap."
                ::= {nncExtRestart 3}


        nncExtFaultRepetitions        OBJECT-TYPE
                SYNTAX        INTEGER (1..'ffffffff'h)
                MAX-ACCESS    read-only
                STATUS        current
                DESCRIPTION
                        "The number of consecutive times the fault reported in
                         nncExtLastFault has been repeated."
                ::= {nncExtRestart 4}


        nncExtRestartTracebackTable        OBJECT-TYPE
                SYNTAX        SEQUENCE OF NncExtRestartTracebackEntry
                MAX-ACCESS    not-accessible
                STATUS        current
                DESCRIPTION
                        "The sequence of program counter values that lead to the
                         last recorded fault."
                ::= {nncExtRestart 5}
                
                
        nncExtRestartTracebackEntry        OBJECT-TYPE
                SYNTAX        NncExtRestartTracebackEntry
                MAX-ACCESS    not-accessible
                STATUS        current
                DESCRIPTION
                        "An entry in the sequence of program counter values."
                INDEX { nncExtRestartTracebackIndex }
                ::= {nncExtRestartTracebackTable 1}
                
                
        NncExtRestartTracebackEntry
                ::= SEQUENCE {
                        nncExtRestartTracebackIndex   INTEGER,
                        nncExtRestartTracebackPCValue INTEGER
                }


        nncExtRestartTracebackIndex        OBJECT-TYPE
                SYNTAX        INTEGER (1..255)
                MAX-ACCESS    read-only
                STATUS        current
                DESCRIPTION
                        "The index into the traceback table"
                ::= {nncExtRestartTracebackEntry 1}
                
                
        nncExtRestartTracebackPCValue        OBJECT-TYPE
                SYNTAX        INTEGER (0..'ffffffff'h)
                MAX-ACCESS    read-only
                STATUS        current
                DESCRIPTION
                        "The program counter value for this entry in the
                         traceback table."
                ::= {nncExtRestartTracebackEntry 2}
                
                
        nncExtRestartRegisterTable        OBJECT-TYPE
                SYNTAX        SEQUENCE OF NncExtRestartRegisterEntry
                MAX-ACCESS    not-accessible
                STATUS        current
                DESCRIPTION
                        "The sequence of register values at the last recorded
                         fault."
                ::= {nncExtRestart 6}
                
                
        nncExtRestartRegisterEntry        OBJECT-TYPE
                SYNTAX        NncExtRestartRegisterEntry
                MAX-ACCESS    not-accessible
                STATUS        current
                DESCRIPTION
                        "An entry in the set of register values."
                INDEX { nncExtRestartRegisterIndex }
                ::= {nncExtRestartRegisterTable 1}
                
-- for a Motorola processor, the register mapping is TBD...

        NncExtRestartRegisterEntry
                ::= SEQUENCE {
                        nncExtRestartRegisterIndex INTEGER,
                        nncExtRestartRegisterValue INTEGER
                }


        nncExtRestartRegisterIndex        OBJECT-TYPE
                SYNTAX        INTEGER (1..255)
                MAX-ACCESS    read-only
                STATUS        current
                DESCRIPTION
                        "The index into the Register table.  The Index
                         to register mapping for a Motorola processor
                         is as follows:
                            1  - D0
                            2  - D1
                            :
                            8  - D8
                            9  - A0
                            :
                            15 - A6
                            16 - Status Reg
                            17 - Program Counter"
                ::= {nncExtRestartRegisterEntry 1}
                
                
        nncExtRestartRegisterValue        OBJECT-TYPE
                SYNTAX        INTEGER (0..'ffffffff'h)
                MAX-ACCESS    read-only
                STATUS        current
                DESCRIPTION
                        "The register value for this entry in the
                         Register table."
                ::= {nncExtRestartRegisterEntry 2}
                
                
                
        nncExtRestartForceToBoot        OBJECT-TYPE
                SYNTAX        INTEGER (0..36000)
                UNITS         "seconds"
                MAX-ACCESS    read-write
                STATUS        current
                DESCRIPTION
                        "A set will cause the box to start executing from the
                         boot PROM after the delay specified by the value
                         written.  A second set before the delay has expired
                         will be rejected with badValue.  A read will return
                         zero."
                ::= { nncExtRestart 7}


        nncExtRestartCause        OBJECT-TYPE
                SYNTAX        RestartCause
                MAX-ACCESS    read-only
                STATUS        current
                DESCRIPTION
                        "The cause of the last restart of the system."
                ::= {nncExtRestart 8}


        nncExtRestartSystem  OBJECT-TYPE
                SYNTAX        INTEGER (0..36000)
                UNITS         "Seconds"
                MAX-ACCESS    read-write
                STATUS        current
                DESCRIPTION   
                        "A set will cause the Node to restart after a specified
                         delay and then execute the System code that resides in
                         the Next Active Code Bank. The delay is specified by
                         the value written. A second set before the delay has
                         expired will be rejected with badValue. A read will
                         return zero. "
                ::= { nncExtRestart 9 }


        
-- -----------------------------------------------------------------------------
--
--         Code Space Extensions
--
-- -----------------------------------------------------------------------------

--
-- Code space 1 is always the Boot PROM
--
        CodeSpaceIndex ::= TEXTUAL-CONVENTION
                STATUS current
                DESCRIPTION
                        "The index into the codespace."
                SYNTAX INTEGER (1..3)
        
        nncExtCodeSpaceCurrentlyActive        OBJECT-TYPE
                SYNTAX        CodeSpaceIndex 
                MAX-ACCESS    read-only
                STATUS        current
                DESCRIPTION
                        "The index into the code space table of the code space
                         from which the box is currently executing"
                ::= {nncExtCodeSpace 1}
                

        nncExtCodeSpaceNextActive        OBJECT-TYPE
                SYNTAX        CodeSpaceIndex 
                MAX-ACCESS    read-write
                STATUS        current
                DESCRIPTION
                        "The index into the code space table of the code space
                         from which the box will execute after the next restart."
                ::= {nncExtCodeSpace 2}


        nncExtCodeSpaceNumber        OBJECT-TYPE
                SYNTAX        CodeSpaceIndex 
                MAX-ACCESS    read-only
                STATUS        current
                DESCRIPTION
                        "The number of code spaces supported by this box."
                ::= {nncExtCodeSpace 3}

        nncExtCodeSpaceTable        OBJECT-TYPE
                SYNTAX        SEQUENCE OF NncExtCodeSpaceEntry  
                MAX-ACCESS    not-accessible
                STATUS        current
                DESCRIPTION
                        "Information about all of the code spaces present in 
                         this box."
                ::= {nncExtCodeSpace 4}
                
                
        nncExtCodeSpaceEntry        OBJECT-TYPE
                SYNTAX        NncExtCodeSpaceEntry  
                MAX-ACCESS    not-accessible
                STATUS        current
                DESCRIPTION
                        "Information about one of the code spaces present in 
                         this box."
                INDEX { nncExtCodeSpaceIndex }
                ::= {nncExtCodeSpaceTable 1}
                
                
        NncExtCodeSpaceEntry 
                ::= SEQUENCE {
                        nncExtCodeSpaceIndex             CodeSpaceIndex,
                        nncExtCodeSpaceSize              INTEGER,
                        nncExtCodeSpaceStatus            INTEGER,
                        nncExtCodeSpaceGeneric           DisplayString,
                        nncExtCodeSpaceDownloadDate      DisplayString,
                        nncExtCodeSpaceDownloadTime      DisplayString,
                        nncExtCodeSpaceDownloadServer    DisplayString,
                        nncExtCodeSpaceDownloadRequestor DisplayString,
                        nncExtCodeSpaceCompressionType   INTEGER,
                        nncExtCodeSpaceLoadSize          INTEGER,
                        nncExtCodeSpaceCompressLoadSize  INTEGER
                }
                                

        nncExtCodeSpaceIndex        OBJECT-TYPE
                SYNTAX        CodeSpaceIndex 
                MAX-ACCESS    read-only
                STATUS        current
                DESCRIPTION
                        "The code space of interest"
                ::= {nncExtCodeSpaceEntry 1}
                
                
        nncExtCodeSpaceSize        OBJECT-TYPE
                SYNTAX        INTEGER (0..'ffffffff'h) 
                UNITS         "bytes"
                MAX-ACCESS    read-only
                STATUS        current
                DESCRIPTION
                        "The size (in bytes) of the maximum code space
                         available in flash memory."
                ::= {nncExtCodeSpaceEntry 2}
                
                
        nncExtCodeSpaceStatus        OBJECT-TYPE
                SYNTAX        INTEGER  { valid(1), invalid(2) }
                MAX-ACCESS    read-only
                STATUS        current
                DESCRIPTION
                        "Whether or not the specified code space is considered
                         to be sane e.g.,checksum is valid."
                ::= {nncExtCodeSpaceEntry 3}
                
                
        nncExtCodeSpaceGeneric        OBJECT-TYPE
                SYNTAX        CurrentGenericType 
                MAX-ACCESS    read-only
                STATUS        current
                DESCRIPTION
                        "Which generic is contained in the code space."
                ::= {nncExtCodeSpaceEntry 4}
                
                
        nncExtCodeSpaceDownloadDate        OBJECT-TYPE
                SYNTAX        DisplayString (SIZE (11))
                MAX-ACCESS    read-only
                STATUS        current
                DESCRIPTION
                        "The date on which this generic was downloaded.
                         This OBJECT is known by the target."
                ::= {nncExtCodeSpaceEntry 5}
                
                
        nncExtCodeSpaceDownloadTime        OBJECT-TYPE
                SYNTAX        DisplayString (SIZE (8))
                MAX-ACCESS    read-only
                STATUS        current
                DESCRIPTION
                        "The time at which this generic was downloaded.
                         This OBJECT is known by the target."
                ::= {nncExtCodeSpaceEntry 6}
                
                
        nncExtCodeSpaceDownloadServer        OBJECT-TYPE
                SYNTAX        DisplayString
                MAX-ACCESS    read-only
                STATUS        current
                DESCRIPTION
                        "The address of the source of the generic
                         that is present in the code space."
                ::= {nncExtCodeSpaceEntry 7}
                
                
        nncExtCodeSpaceDownloadRequestor        OBJECT-TYPE
                SYNTAX        DisplayString
                MAX-ACCESS    read-only
                STATUS        current
                DESCRIPTION
                        "The address of the entity that caused this
                         code space to be downloaded with the current 
                         generic."
                ::= {nncExtCodeSpaceEntry 8}
                
                
        nncExtCodeSpaceCompressionType        OBJECT-TYPE
                SYNTAX        INTEGER { none(1), c1(2), c2(3), c3(4) }
                MAX-ACCESS    read-only
                STATUS        current
                DESCRIPTION
                        "The kind of compression used on the load before it
                         was placed into flash."
                ::= {nncExtCodeSpaceEntry 9}


        nncExtCodeSpaceLoadSize        OBJECT-TYPE
                SYNTAX        INTEGER (0..'ffffffff'h) 
                UNITS         "bytes"
                MAX-ACCESS    read-only
                STATUS        current
                DESCRIPTION
                        "The size (in bytes) of the load stored in this
                         code space when decompressed."
                ::= {nncExtCodeSpaceEntry 10}

        nncExtCodeSpaceCompressLoadSize  OBJECT-TYPE
                SYNTAX        INTEGER (0..'ffffffff'h)
                UNITS         "bytes"
                MAX-ACCESS    read-only
                STATUS        current
                DESCRIPTION
                        "The size (in bytes) of the load stored in this
                         code space when compressed."
                ::= {nncExtCodeSpaceEntry 11}
                
-- -----------------------------------------------------------------------------
--
--         NVM Extensions
--
-- -----------------------------------------------------------------------------

        NVMPoolIndex ::= TEXTUAL-CONVENTION
                STATUS current
                DESCRIPTION
                        "Index into the NVM pool."
                SYNTAX INTEGER (1..3)
        

        nncExtNVMUsageTable        OBJECT-TYPE
                SYNTAX        SEQUENCE OF NncExtNVMUsageEntry  
                MAX-ACCESS    not-accessible
                STATUS        current
                DESCRIPTION
                        "How much NVM is used in the box in bytes."
                ::= {nncExtNVM 1}
                
                
        nncExtNVMUsageEntry        OBJECT-TYPE
                SYNTAX        NncExtNVMUsageEntry  
                MAX-ACCESS    not-accessible
                STATUS        current
                DESCRIPTION
                        "How much NVM is used in a pool of it"
                INDEX { nncExtNVMPoolIndex }
                ::= {nncExtNVMUsageTable 1}
                
                
        NncExtNVMUsageEntry 
                ::= SEQUENCE {
                        nncExtNVMPoolIndex      NVMPoolIndex,
                        nncExtNVMPoolSize       INTEGER,
                        nncExtNVMPoolBytesUsed  INTEGER
                }


        nncExtNVMPoolIndex        OBJECT-TYPE
                SYNTAX        NVMPoolIndex
                MAX-ACCESS    read-only
                STATUS        current
                DESCRIPTION
                        "Which NVM pool"
                ::= {nncExtNVMUsageEntry 1}


        nncExtNVMPoolSize        OBJECT-TYPE
                SYNTAX        INTEGER (0..'ffffffff'h)
                UNITS         "bytes"
                MAX-ACCESS    read-only
                STATUS        current
                DESCRIPTION
                        "The total number of bytes in the pool"
                ::= {nncExtNVMUsageEntry 2}


        nncExtNVMPoolBytesUsed        OBJECT-TYPE
                SYNTAX        INTEGER (0..'ffffffff'h)
                UNITS         "bytes"
                MAX-ACCESS    read-only
                STATUS        current
                DESCRIPTION
                        "The number of bytes used in the pool"
                ::= {nncExtNVMUsageEntry 3}


        nncExtNVMLastRepair        OBJECT-TYPE
                SYNTAX        OCTET STRING (SIZE (31))
                MAX-ACCESS    read-only
                STATUS        current
                DESCRIPTION
                        "Details of the last repair made to the database
                         returned in a string format -- a readable form of 
                         the following:
                Offset   Length        Meaning
                0        1        Number Of Bytes in the String (=31)
                1        1        Length of repaired item (in bytes)
                2        4        Address of Block containing repaired item
                6        2         block number of the repaired block
                8        2        item number of repaired entry
                10        2        first parameter of repaired item
                12        2        second parameter of repaired item
                14        1        length of date string
                15        9        date of repair (DD-MMM-YY)
                24        1        length of time string (=6)
                25        6        time of repair (HH:MMX)"
                ::= {nncExtNVM 2}

-- -----------------------------------------------------------------------------
--
--         Probe Extensions
--
-- -----------------------------------------------------------------------------

        nncExtProbeMPLTable        OBJECT-TYPE
                SYNTAX        SEQUENCE OF NncExtProbeMPLEntry
                MAX-ACCESS    not-accessible
                STATUS        current
                DESCRIPTION
                        "A window into the Master Parameter List."
                ::= {nncExtProbe 1}
        
        nncExtProbeMPLEntry        OBJECT-TYPE
                SYNTAX        NncExtProbeMPLEntry
                MAX-ACCESS    not-accessible
                STATUS        current
                DESCRIPTION
                        "An entry in the master parameter list.  The instance
                         identifer is of the form:
                                 nncExtProbeMPL.<c>.<i>.<m1>.<m2>.<m3>.<m4>"
                INDEX {nncExtProbeMPL}
                ::= {nncExtProbeMPLTable 1}
                
        NncExtProbeMPLEntry
                ::= SEQUENCE {
                        nncExtProbeMPL    OCTET STRING
                }
                
        nncExtProbeMPL        OBJECT-TYPE
                SYNTAX        OCTET STRING (SIZE (0..255))
                MAX-ACCESS    read-write
                STATUS        current
                DESCRIPTION
                        "A window into in the Master Parameter List.  The
                         instance identifer is of the form:
                                 <c>.<i>.<m1>.<m2>.<m3>.<m4>"
                ::= {nncExtProbeMPLEntry 1}


-- -----------------------------------------------------------------------------
--
--         Traffic Management Extensions
--
-- -----------------------------------------------------------------------------

       SvcEpdOptionType ::= TEXTUAL-CONVENTION
                STATUS          current
                DESCRIPTION
                      "A value of this type identifies the early packet discard option - off or on" 
                SYNTAX          INTEGER {off(0), on(1)}


       SvcPpdOptionType ::= TEXTUAL-CONVENTION
                STATUS          current
                DESCRIPTION
                      "A value of this type identifies the partial packet discard option - off or on" 
                SYNTAX          INTEGER {off(0), on(1)}


--        nncExtEpdOption       OBJECT-TYPE
--                SYNTAX        SvcEpdOptionType 
--                MAX-ACCESS    read-write
--                STATUS        current
--                DESCRIPTION
--                        "Epd option chosen - on or off"
--              ::= {nncExtTrafMgmnt 1}


--        nncExtPpdOption       OBJECT-TYPE
--                SYNTAX        SvcPpdOptionType
--                MAX-ACCESS    read-write
--                STATUS        current
--                DESCRIPTION
--                        "Ppd option - on or off"
--                ::= {nncExtTrafMgmnt 2}

-- -----------------------------------------------------------------------------
--
--         Diagnostic Extensions
--
-- -----------------------------------------------------------------------------

        nncDiagUndoAll        OBJECT-TYPE
                SYNTAX        INTEGER { undo(1) }
                MAX-ACCESS    read-write
                STATUS        current
                DESCRIPTION
                        "A write of 'undo' to this parameter will cause all
                         maintenance operations to be removed, e.g. loopbacks
                         busy-outs, etc"
                ::= {nncExtDiag 1}

        nncExtStartupDiagnosticResults  OBJECT-TYPE
               	SYNTAX          INTEGER { passed(1), unspecifiedFailure(2) }
                MAX-ACCESS      read-only
                STATUS          current
                DESCRIPTION   
                        "If ALL of the systems startup diagnostic tests passed
                         successfully, then this object is set to passed
                         otherwise it is set to failed "
                ::= { nncExtDiag 2 }


-------------------------------------------------------------------------------
--      Review Minutes
-------------------------------------------------------------------------------
--      MINUTES-BEGIN
--              REVIEW-DATE  "1996.12.11"
--              BODY  "
--
--
--      TO:     Wayne Burwell*, Rob de Vlugt, Arun Chandrasekaran,
--              Azaduer Kurkjian*, Tom C. Wilson*
--      CC:     Numbers Admin, Tom Walton, Sandra Stark
--      FROM:   Martin Dubois*
--
--      A meeting was held on 96.12.11 to review GNI0006.mib, the area
--      interface definition for the Basics area in the system region.
--      Attendees are marked with * in the TO and CC lists above.
--
--      Outcome
--
--      It was the consensus of the review team that this file is
--      acceptable with the indicated modifications.
--
--      Actions:
--      A1 -    M. Dubois to update the file as indicated in D1 below.
--              To be completed by 96.12.13
--              Response:
--                                              Status: CLOSED
--
--      A2 -    M. Dubois to check on the name of this module:
--                - on regional, it is called Basics.mib
--                - in ClearCase, it is called GNI0006.mib
--              To be completed by 96.12.13
--              Response: BASICS
--                                              Status: CLOSED
--
--
--      A3 -    M. Dubois to find out if DateAndTime can be used.
--              To be completed by 96.12.13
--              Response: yes, SNMPv2 object types are already used in
--                        GNI0006.mib
--                                              Status: CLOSED
--
--
--
--      Decisions:
--      D1 -    GNI0006.mib shall be updated as follows:
--              a) nncExtSysCurrentDateAndTime will be of type DisplayString
--                 if DateAndTime cannot be used (see A3) and made read-only
--              b) LAST-UPDATED to be updated
--
--
--      "
--
--      END-MINUTES
--
-------------------------------------------------------------------------------
--      Review Minutes
-------------------------------------------------------------------------------
--      MINUTES-BEGIN
--              REVIEW-DATE  "1999.04.15"
--              BODY  "
--
--
--      TO:     AtmSw
--      FROM:   Jayanthi Venkatasubba
--
--      A EDR was announced on 99.04.15 to review GNI0006.mib, the area
--      interface definition for the Basics area in the system region.
--
--      Outcome
--
--      No action items were generated from the EDR and hence the 
--      document is acceptable.
--
--      END-MINUTES

END -- NNCGNI0006-MIB DEFINITIONS
