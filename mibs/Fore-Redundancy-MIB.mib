-- 
-- Copyright 1999 by Fore Systems, Inc. 
-- Converted to SMIv2 rfc 2578,2579,2580 - STD 58
--
-- Copyright 1999 by Fore Systems, Inc.

Fore-Redundancy-MIB DEFINITIONS ::= BEGIN

IMPORTS
        Integer32,
	OBJECT-TYPE,
	MODULE-IDENTITY,
	NOTIFICATION-TYPE			FROM SNMPv2-SMI
	hardware,
	atmSwitch				FROM Fore-Common-MIB
	trapLogIndex                            FROM Fore-TrapLog-MIB;

------------------------------------------------------------------------
-- MIB Groups

asx4000RedundancyModule  MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "The Fore ASX-4000 redundancy mib."
    ::= { hardware 9 }

asx4000RedFabricGroup   OBJECT IDENTIFIER ::= { asx4000RedundancyModule 1 }
asx4000RedPortCardGroup OBJECT IDENTIFIER ::= { asx4000RedundancyModule 2 }
asx4000RedundancyGroup  OBJECT IDENTIFIER ::= { asx4000RedundancyModule 3 }
asx4000RedNetmodGroup   OBJECT IDENTIFIER ::= { asx4000RedundancyModule 4 }

------------------------------------------------------------------------
Asx4000RedundancyState ::= INTEGER {
                           initializing(1),
                           cloning(2),
                           testing(3),
                           unprotected(4),
                           passive(5),
                           errored-detected(6),
                           armed(7),
                           requalifying(8)
                           }
------------------------------------------------------------------------

-- The 4000RedFabric Group

asx4000RedFabricTable  OBJECT-TYPE
	SYNTAX	SEQUENCE OF Asx4000RedFabricEntry
	MAX-ACCESS	not-accessible
	STATUS	current
	DESCRIPTION
		"A table of  fabric entries."
	::= { asx4000RedFabricGroup 1 }

asx4000RedFabricEntry OBJECT-TYPE
	SYNTAX	Asx4000RedFabricEntry
	MAX-ACCESS	not-accessible
	STATUS	current
	DESCRIPTION
		"A table entry containing fabric information."
	INDEX	{ asx4000RedFabricIndex}
	::= { asx4000RedFabricTable 1 }

Asx4000RedFabricEntry ::=
	SEQUENCE {
                asx4000RedFabricIndex                   Integer32,
                asx4000RedFabricAdminMode               INTEGER,
                asx4000RedFabricOperState               INTEGER, 
                asx4000RedFabricPendingAdminMode        INTEGER, 
                asx4000RedFabricCommittedState          INTEGER,
                asx4000RedFabricCloningState            INTEGER,
                asx4000RedFabricSwitchCommand           INTEGER,
                asx4000RedFabricRedundancyState         Asx4000RedundancyState
        }

asx4000RedFabricIndex  OBJECT-TYPE
	SYNTAX	Integer32
	MAX-ACCESS	read-only
	STATUS	current
	DESCRIPTION
		"The index of this fabric"
	::= { asx4000RedFabricEntry 1 }

asx4000RedFabricAdminMode  OBJECT-TYPE
	SYNTAX	INTEGER {
			working(1),
			protection(2),
			unprotected(3)
		}
	MAX-ACCESS	read-only
	STATUS	current
	DESCRIPTION
		"The admin mode for this fabric"
	::= { asx4000RedFabricEntry 2 }

asx4000RedFabricOperState  OBJECT-TYPE
	SYNTAX	INTEGER {
			active(1),
			standby(2),
			unprotected(3)
		}
	MAX-ACCESS	read-only
	STATUS	current
	DESCRIPTION
		"The oper state for this fabric"
	::= { asx4000RedFabricEntry 3 }

asx4000RedFabricPendingAdminMode  OBJECT-TYPE
 	SYNTAX	INTEGER {
			working(1),
			protection(2),
			unprotected(3),
                        none(4)
		}
	MAX-ACCESS	read-write	
      STATUS	current
	DESCRIPTION
		"This variable is used to set the value for admin mode for 
                 this fabric.The asx4000RedFabricAdminMode variable is set 
                 to this value on setting the asx4000RedFabricCommit variable"
	::= { asx4000RedFabricEntry 4 }

asx4000RedFabricCommittedState  OBJECT-TYPE
 	SYNTAX	INTEGER {
			no(1),
			yes(2)
                }
	MAX-ACCESS	read-only	
      STATUS	current
	DESCRIPTION
		"This variable indicates if a command has been committed 
                for this particular fabric."
	::= { asx4000RedFabricEntry 5 }

asx4000RedFabricCloningState  OBJECT-TYPE
	SYNTAX	INTEGER {
			done(1),
			inprogress(2),
			notApplicable(3)
		}
	MAX-ACCESS	read-only
	STATUS	deprecated
	DESCRIPTION
		"The cloning state of this fabric"
	::= { asx4000RedFabricEntry 6 }


asx4000RedFabricSwitchCommand  OBJECT-TYPE
	SYNTAX	INTEGER {
			active(1), 
			standby(2)
		}
	MAX-ACCESS	read-write
	STATUS	current
	DESCRIPTION
		"User initiated command at fabric level switchovers. Setting
             this variable with the following values causes the switchover to 
             happen as explained.
             
             active   - causes a switchover to active for this
                        fabric
             standy   - causes a switchover to standby for this 
                        fabric

                        Note this object is write-only and reading it will
                        result in implementation-specific results."
	::= { asx4000RedFabricEntry 7}

asx4000RedFabricRedundancyState OBJECT-TYPE
        SYNTAX Asx4000RedundancyState
        MAX-ACCESS read-only
        STATUS current
        DESCRIPTION
               "This is the current redundancy state of th efabric.  The
                possible values for this variable are dependent upon whether
                the fabric is protected or not, and whether it supports
                passive or active redundancy."
        ::= { asx4000RedFabricEntry 8}

asx4000RedFabricGroupCommit OBJECT-TYPE
      SYNTAX 	INTEGER {
 			commit(1) 
		}
      MAX-ACCESS      read-write
      STATUS      current
      DESCRIPTION
           " A command to commit a fabric group configuration

           Note this object is write-only and reading it will
           result in implementation-specific results."
      ::= { asx4000RedFabricGroup 3}

------------------------------------------------------------------------
-- The  4000RedPortcard Group

asx4000RedPortCardTable  OBJECT-TYPE
	SYNTAX	SEQUENCE OF Asx4000RedPortCardEntry
	MAX-ACCESS	not-accessible
	STATUS	current
	DESCRIPTION
		"A table of 4000Red  Portcard information."
	::= { asx4000RedPortCardGroup 1 }

asx4000RedPortCardEntry OBJECT-TYPE
	SYNTAX	Asx4000RedPortCardEntry
	MAX-ACCESS	not-accessible
	STATUS	current
	DESCRIPTION
		"A table entry containing portcard  information."
	INDEX	{ asx4000RedPortCardFabIndex, asx4000RedPortCardIndex}
	::= { asx4000RedPortCardTable 1 }

Asx4000RedPortCardEntry ::=
	SEQUENCE {
                asx4000RedPortCardFabIndex                Integer32, 
                asx4000RedPortCardIndex                   INTEGER, 
                asx4000RedPortCardCloningState            INTEGER
        }

asx4000RedPortCardFabIndex  OBJECT-TYPE
	SYNTAX	Integer32
	MAX-ACCESS	read-only
	STATUS	current
	DESCRIPTION
		"The fabric index this portcard is connected to"
	::= { asx4000RedPortCardEntry 1 }

asx4000RedPortCardIndex OBJECT-TYPE
	SYNTAX	INTEGER {
                  ab(1), 
                  cd(2) 
                }
	MAX-ACCESS	read-only
	STATUS	current
	DESCRIPTION
		"The netmod pair index of this portcard"
	::= { asx4000RedPortCardEntry 2 }

asx4000RedPortCardCloningState  OBJECT-TYPE
	SYNTAX	INTEGER {
                  done(1), 
                  inprogress(2) ,
                  notApplicable(3)
                }
	MAX-ACCESS read-only
	STATUS	   current
	DESCRIPTION
		"The netmod pair index of this portcard"
	::= { asx4000RedPortCardEntry 3 }

------------------------------------------------------------------------

-- The ASX-4000 Redundancy Group

asx4000RedundancyGroupTable  OBJECT-TYPE
        SYNTAX  SEQUENCE OF Asx4000RedundancyGroupEntry
        MAX-ACCESS  not-accessible
        STATUS  current
        DESCRIPTION
                "This is the Redundancy Group table."
        ::= { asx4000RedundancyGroup 1 }

asx4000RedundancyGroupEntry  OBJECT-TYPE
        SYNTAX  Asx4000RedundancyGroupEntry
        MAX-ACCESS  not-accessible
        STATUS  current
        DESCRIPTION
                "This is a Redundancy Group entry, which represents the
                 configuration of a working and protection fabric and
                 their associated portcards."
        INDEX  { asx4000RedGroupName }
        ::= { asx4000RedundancyGroupTable 1 }

Asx4000RedundancyGroupEntry ::=
        SEQUENCE {
                asx4000RedGroupName                      INTEGER,
                asx4000RedGroupRevertMode                INTEGER,
                asx4000RedGroupQualifyTimer              Integer32,
                asx4000RedGroupErrorThreshold            Integer32,
                asx4000RedGroupErrorBlockSize            Integer32
        }

asx4000RedGroupName  OBJECT-TYPE
        SYNTAX  INTEGER {
                  r12(1),
                  r34(2)
                }
        MAX-ACCESS  read-only
        STATUS  current
        DESCRIPTION
                "This is the redundancy group name.  A redundancy group
                 name identifies a working and protection fabric and their
                 associated portcards are a single unit."
        ::= { asx4000RedundancyGroupEntry 1 }

asx4000RedGroupRevertMode  OBJECT-TYPE
        SYNTAX  INTEGER {
                  on(1),
                  off(2)
                }
        MAX-ACCESS  read-write
        STATUS  current
        DESCRIPTION
                "This is the revert mode for this redundancy group.  If
                 the revert mode is on(1), automatic switchover from the
                 protection fabric to the working fabric will occur if
                 the working fabric becomes available.  Setting the revert
                 mode to off(2) disables this behavior."
        DEFVAL  { off }
        ::= { asx4000RedundancyGroupEntry 2 }

asx4000RedGroupQualifyTimer  OBJECT-TYPE
        SYNTAX  Integer32
        MAX-ACCESS  read-write
        STATUS  current
        DESCRIPTION
                "This is the qualification timer in minutes for this
                 redundancy group.  For fabric and portcards that support
                 active redundancy, asx4000RedGroupQualifyTimer is the
                 number of minutes that an errored fabric or portcard
                 must undergo error-free loopback testing before
                 being declared as an available fabric or portcard.
                 This timer has no effect for fabrics and portcards
                 that do not support active redundancy."
        DEFVAL { 5 }
        ::= { asx4000RedundancyGroupEntry 3 }

asx4000RedGroupErrorThreshold  OBJECT-TYPE
        SYNTAX  Integer32
        MAX-ACCESS  read-write
        STATUS  current
        DESCRIPTION
                "This is the loopback error threshold in cells for this
                 redundancy group.  For fabrics and portcards that support
                 active redundancy, if the number of loopback cell errors
                 equals or exceeds asx4000RedGroupErrorThreshold during
                 the past asx4000RedGroupErrorBlockSize loopback cells,
                 then an error condition is declared for the
                 loopback components.  Setting this error threshold to
                 zero (0) disables error checking.  The maximum value is
                 the error block size asx4000RedGroupErrorBlockSize."
        DEFVAL  { 2 }
        ::= { asx4000RedundancyGroupEntry 4 }

asx4000RedGroupErrorBlockSize  OBJECT-TYPE
        SYNTAX  Integer32
        MAX-ACCESS  read-only
        STATUS  current
        DESCRIPTION
                "This is the loopback error block size in cells for this
                 redundancy group.  For fabrics and portcards that support
                 active redundancy, this is the number of consecutive
                 loopback cells over which the error threshold
                 asx4000RedGroupErrorThreshold will be applied."
        ::= { asx4000RedundancyGroupEntry 5 }

------------------------------------------------------------------------
-- The  4000RedNetmod Group

asx4000RedNetmodTable  OBJECT-TYPE
	SYNTAX	SEQUENCE OF Asx4000RedNetmodEntry
	MAX-ACCESS	not-accessible
	STATUS		current
	DESCRIPTION
		"A table of 4000Red  Netmod information."
	::= { asx4000RedNetmodGroup 1 }

asx4000RedNetmodEntry OBJECT-TYPE
	SYNTAX	Asx4000RedNetmodEntry
	MAX-ACCESS	not-accessible
	STATUS		current
	DESCRIPTION
		"A table entry containing netmod information."
	INDEX	{ asx4000RedNetmodFabIndex, asx4000RedNetmodIndex}
	::= { asx4000RedNetmodTable 1 }

Asx4000RedNetmodEntry ::=
	SEQUENCE {
                asx4000RedNetmodFabIndex                Integer32, 
                asx4000RedNetmodIndex                   Integer32, 
                asx4000RedNetmodRedundancyState         Asx4000RedundancyState
        }

asx4000RedNetmodFabIndex  OBJECT-TYPE
	SYNTAX	Integer32
	MAX-ACCESS	read-only
	STATUS		current
	DESCRIPTION
		"The fabric index this netmod is connected to"
	::= { asx4000RedNetmodEntry 1 }

asx4000RedNetmodIndex OBJECT-TYPE
	SYNTAX	Integer32
	MAX-ACCESS	read-only
	STATUS		current
	DESCRIPTION
		"The netmod index of this netmod"
	::= { asx4000RedNetmodEntry 2 }

asx4000RedNetmodRedundancyState OBJECT-TYPE
        SYNTAX  Asx4000RedundancyState
        MAX-ACCESS  read-only
        STATUS      current
        DESCRIPTION
                "This is the current redundancy state of the netmod.  The
                 possible values for this variable are dependent upon whether
                 the fabric to which this netmod is connection to is protected 
                 or not, and whether it supports passive or active redundancy."
        ::= { asx4000RedNetmodEntry 3 }



------------------------------------------------------------------------
-- Redundancy Traps

redundancyFabricSwitchover NOTIFICATION-TYPE
	OBJECTS {  asx4000RedFabricIndex, trapLogIndex }
	STATUS      current
	DESCRIPTION
		"This trap reports the change of active fabric due to an 
		automatic or revertive switchover. The fabric identified
		by the trap variable asx4000RedFabricIndex is the newly
		active fabric."
	::= { atmSwitch 0 2018 }

redundancyFabricErrorCleared  NOTIFICATION-TYPE
	OBJECTS {  asx4000RedFabricIndex, trapLogIndex }
	STATUS      current
        DESCRIPTION
                "This trap reports the clearing of the active redundancy
                 fabric error for the fabric identified by the trap
                 variable asx4000RedFabricIndex."
	::= { asx4000RedundancyModule 0 2 }

redundancyFabricErrorDetected  NOTIFICATION-TYPE
	OBJECTS {  asx4000RedFabricIndex, trapLogIndex }
	STATUS      current
        DESCRIPTION
                "This trap reports the declaration of the active
                 redundancy fabric error for the fabric identified
                 by the trap variable asx4000RedFabricIndex."
	::= { asx4000RedundancyModule 0 3 }

redundancyNetmodErrorCleared NOTIFICATION-TYPE
        OBJECTS { asx4000RedNetmodFabIndex, asx4000RedNetmodIndex,
                    trapLogIndex }
	STATUS      current
        DESCRIPTION
                "This trap reports the clearing of the active redundancy
                 netmod error for the netmod identified by the trap
                 variables asx4000RedNetmodFabIndex and 
                 asx4000RedNetmodIndex."
	::= { asx4000RedundancyModule 0 4 }

redundancyNetmodErrorDetected NOTIFICATION-TYPE
        OBJECTS { asx4000RedNetmodFabIndex, asx4000RedNetmodIndex,
                    trapLogIndex }
	STATUS      current
        DESCRIPTION
                "This trap reports the declaration of the active redundancy 
                 netmod error for the netmod identified by the trap
                 variables asx4000RedNetmodFabIndex and 
                 asx4000RedNetmodIndex."
	::= { asx4000RedundancyModule 0 5 }

END
