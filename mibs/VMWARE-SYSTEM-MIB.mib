VMWARE-SYSTEM-MIB DEFINITIONS ::= BEGIN

IMPORTS
    OBJECT-TYPE 
      FROM RFC1155-SMI

   DisplayString 
      FROM RFC1213-MIB

-- MIB items for vmwSystem subtree (general VMware system information).

   vmwSystem  -- OBJECT IDENTIFIER ::= { vmware 1 }
      FROM VMWARE-ROOT-MIB;

vmwProdName    OBJECT-TYPE 
   SYNTAX      DisplayString
   ACCESS      read-only
   STATUS      mandatory
   DESCRIPTION
      "The product name."
   ::= { vmwSystem 1 }

vmwProdVersion OBJECT-TYPE 
   SYNTAX      DisplayString
   ACCESS      read-only
   STATUS      mandatory
   DESCRIPTION
      "Product version."
   ::= { vmwSystem 2 }

vmwProdOID     OBJECT-TYPE 
   SYNTAX      OBJECT IDENTIFIER 
   ACCESS      read-only
   STATUS      mandatory
   DESCRIPTION
      "Version-specific unique OID for product in the VMware MIB."
   ::= { vmwSystem 3 } 

vmwProdBuild   OBJECT-TYPE 
   SYNTAX      DisplayString 
   ACCESS      read-only
   STATUS      mandatory
   DESCRIPTION
      "Build number of the product."
   ::= { vmwSystem 4 } 
END
