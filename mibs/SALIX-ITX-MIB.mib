SALIX-ITX-MIB DEFINITIONS ::= BEGIN

-- Note: Compile with SMICNG using options below to product intermediate
--       file output.
--
--        SMICNG /Y /Z /F <filename.imf> itx.inc

IMPORTS
   MODULE-IDENTITY, OBJECT-TYPE, IpAddress,
   Integer32                                  FROM SNMPv2-SMI

   MODULE-COMPLIANCE, OBJECT-GROUP            FROM SNMPv2-CONF
   
   ifIndex                                    FROM IF-MIB
   
   PhysicalIndex                              FROM ENTITY-MIB
   
   DisplayString                              FROM RFC1213-MIB  
   
   voip                                       FROM SALIX-MIB;     

itxMIB MODULE-IDENTITY
      LAST-UPDATED "9810130000Z"
      ORGANIZATION "SALIX Technologies"
      CONTACT-INFO "904 Wind River Lane
                   Suite 101
                   Gaithersburg, MD  20878
                   (301)-417-0017"
      DESCRIPTION  "The ITX enterprise specific MIB"
      ::= { voip 1 }

-- Groups under ItxMIB     
   itxMIBObjects      OBJECT IDENTIFIER ::= { itxMIB 1 }
   itxMIBTraps        OBJECT IDENTIFIER ::= { itxMIB 2 }
   itxMIBCompliance   OBJECT IDENTIFIER ::= { itxMIB 3 }  
   itxMIBTrapPrefix   OBJECT IDENTIFIER ::= { itxMIBTraps 0 }
  
-- Groups in the ITX MIB module  
  
   itxSystem          OBJECT IDENTIFIER ::=  { itxMIBObjects 1 }
   itxDsp             OBJECT IDENTIFIER ::=  { itxMIBObjects 2 }
   itxMediaController OBJECT IDENTIFIER ::=  { itxMIBObjects 3 }       
      
   -- DSP
   
      -- DSP Status Table
      
      itxDspStatusTable OBJECT-TYPE
         SYNTAX      SEQUENCE OF ItxDspStatusEntry
         MAX-ACCESS  not-accessible
         STATUS      current
         DESCRIPTION
            "The itxDspStatusTable provides a means to find the
             status of a specific DSP.  There are 64 (8x8)
             entries for each Transcoder plug-in"
         ::= { itxDsp 1 }
         
      itxDspStatusEntry OBJECT-TYPE
         SYNTAX      ItxDspStatusEntry
         MAX-ACCESS  not-accessible
         STATUS      current
         DESCRIPTION
            "This sequence contains information to identify
             the specific DSP on a specific Transcoder plug-in.
             In addition, it also contains the Operational
             Status for the specified DSP"
         INDEX { itxDspStatusPhysIndex,
                 itxDspStatusRow,
                 itxDspStatusColumn }
         ::= { itxDspStatusTable 1 }
         
      ItxDspStatusEntry ::= SEQUENCE {
         itxDspStatusPhysIndex   PhysicalIndex,
         itxDspStatusRow         INTEGER,
         itxDspStatusColumn      INTEGER,
         itxDspStatusOperStatus  INTEGER
      }
      
      itxDspStatusPhysIndex OBJECT-TYPE
         SYNTAX      PhysicalIndex
         MAX-ACCESS  not-accessible
         STATUS      current
         DESCRIPTION
            "The entPhysicalIndex that uniqely identifies the
             DSP complex on the Transcoder plug-in."
      ::= { itxDspStatusEntry 1 }
      
      itxDspStatusRow OBJECT-TYPE
         SYNTAX INTEGER(1..8)
         MAX-ACCESS  not-accessible
         STATUS      current
         DESCRIPTION
            "The row in the DSP complex for the DSP entry.
             When used together with itxDspStatusColumn, the
             exact DSP in the DSP complex can be found"
      ::= { itxDspStatusEntry 2 }
                  
      itxDspStatusColumn OBJECT-TYPE
         SYNTAX INTEGER(1..8)
         MAX-ACCESS  not-accessible
         STATUS      current
         DESCRIPTION
            "The column in the DSP complex for the DSP entry.
             When used together with itxDspStatusRow, the
             exact DSP in the DSP complex can be found"
      ::= { itxDspStatusEntry 3 }  
                
      itxDspStatusOperStatus OBJECT-TYPE
         SYNTAX      INTEGER { up(1),
                               down(2),
                               unknown(3) }
         MAX-ACCESS  read-only
         STATUS      current
         DESCRIPTION
            "The Operational status of the specified DSP.
            
               up(1)       - The DSP is operational
               down(2)     - The DSP is not operational
               unknown(3)  - The Operational Status of the DSP
                             is not known"
      ::= { itxDspStatusEntry 4 }
        
         -- Media Controller Objects
         
         itxMediaControllerPrimaryIpAddress OBJECT-TYPE
            SYNTAX      IpAddress
            MAX-ACCESS  read-write
            STATUS      current
            DESCRIPTION
               "The IP Address for the Primary Media Controller"
            ::= { itxMediaController 1 } 
            
         itxMediaControllerPrimaryPort OBJECT-TYPE
            SYNTAX      INTEGER(0..65535)
            MAX-ACCESS  read-write
            STATUS      current
            DESCRIPTION
               "The port for the Primary Media Controller"
            ::= { itxMediaController 2 }            
            
         itxMediaControllerSecondaryIpAddress OBJECT-TYPE
            SYNTAX      IpAddress
            MAX-ACCESS  read-write
            STATUS      current
            DESCRIPTION
               "The IP Address for the Secondary Media Controller"
            ::= { itxMediaController 3 }   
            
         itxMediaControllerSecondaryPort OBJECT-TYPE
            SYNTAX      INTEGER(0..65535)
            MAX-ACCESS  read-write
            STATUS      current
            DESCRIPTION
               "The port for the Secondary Media Controller"
            ::= { itxMediaController 4 }   
            
            
        itxMediaControllerActiveController OBJECT-TYPE
             SYNTAX     INTEGER { primary(1), secondary(2) }
             MAX-ACCESS read-write
             STATUS     current
             DESCRIPTION
                  "The configured active Media Controller the Call Control is using 
                   to handle call management.  Writing a value that is different 
                   from its current value will force Call Control to switch to 
                   using the specified Media Controller.
      
                   primary(1)    -  The Primary Media Contrller is the active
                                    controller
                   secondary (2) -  The Secondary Media Contrller is the active
                                    controller"
             ::= { itxMediaController 5 }
            
         itxIsdnBackHaulMediaControllerIpAddress OBJECT-TYPE
            SYNTAX      IpAddress
            MAX-ACCESS  read-write
            STATUS      current
            DESCRIPTION
               "The IP Address for the ISDN BackHaul Media Controller"
            ::= { itxMediaController 6 } 
            
         itxIsdnBackHaulMediaControllerPort OBJECT-TYPE
            SYNTAX      INTEGER(0..65535)
            MAX-ACCESS  read-write
            STATUS      current
            DESCRIPTION
               "The port for the ISDN BackHaul Media Controller"
            ::= { itxMediaController 7 } 
            
      -- ITX Configuration options            
            
         itxMediaSubnet OBJECT-TYPE
            SYNTAX      IpAddress
            MAX-ACCESS  read-write
            STATUS      current
            DESCRIPTION
               "The subnet from which media IP address are selected from"         
            ::= { itxMIBObjects 4 }
            
         itxMediaSubnetMask OBJECT-TYPE
            SYNTAX      IpAddress
            MAX-ACCESS  read-write
            STATUS      current
            DESCRIPTION
               "The subnet mask from which media IP address are selected from"         
            DEFVAL { 'FFFFFFFF'h }      -- 255.255.255.255               
            ::= { itxMIBObjects 5 }
         
         -- For future release:
         --   
         -- itxNetworkManagementSubnet OBJECT-TYPE                                  
         --    SYNTAX      IpAddress
         --    MAX-ACCESS  read-write
         --    STATUS      current
         --    DESCRIPTION
         --       "The subnet from which IP address are selected from
         --        for network management"         
         --    ::= { itxMIBObjects 6 } 
            
         itxNetworkManagementAddress OBJECT-TYPE                                  
            SYNTAX      IpAddress
            MAX-ACCESS  read-write
            STATUS      current
            DESCRIPTION
               "The IP Address for the NMS Agent"         
            ::= { itxMIBObjects 7 } 
            
         itxNetworkManagementSubnetMask OBJECT-TYPE                                  
            SYNTAX      IpAddress
            MAX-ACCESS  read-write
            STATUS      current
            DESCRIPTION
               "The Subnet Mask for the NMS Agent"         
            ::= { itxMIBObjects 8 }             
           
         -- For future release:
         --           
         -- itxCallControlSubnet OBJECT-TYPE
         --    SYNTAX      IpAddress
         --    MAX-ACCESS  read-write
         --    STATUS      current
         --    DESCRIPTION
         --       "The Subnet for the Secondary Media Controller"         
         --    ::= { itxMIBObjects 9 } 
            
         itxCallControlAddress OBJECT-TYPE
            SYNTAX      IpAddress
            MAX-ACCESS  read-write
            STATUS      current
            DESCRIPTION
               "The Subnet for Call Control"         
            ::= { itxMIBObjects 10 } 
            
         itxCallControlSubnetMask OBJECT-TYPE
            SYNTAX      IpAddress
            MAX-ACCESS  read-write
            STATUS      current
            DESCRIPTION
               "The SubnetMask for Call Control"
            ::= { itxMIBObjects 11 }               
            
          itxEthernetTable OBJECT-TYPE
              SYNTAX  SEQUENCE OF ItxEthernetEntry
              MAX-ACCESS  not-accessible
              STATUS  current
              DESCRIPTION
                      "The ITX default Gateway for ethernet interfaces."
              ::= { itxMIBObjects 15 }

          itxEthernetEntry OBJECT-TYPE
              SYNTAX  ItxEthernetEntry
              MAX-ACCESS  not-accessible
              STATUS  current
              DESCRIPTION
                      "The Default Gateway entry is indexed by ifIndex.  
                       The entry contains the Ip address for the default 
                       gateway for the specified Ethernet interface.  
                       There are no entries in the table for non-ethernet 
                       interfaces and exactly one for each ethernet 
                       interface"
              INDEX   { ifIndex }
              ::= { itxEthernetTable 1 }

          ItxEthernetEntry ::=
              SEQUENCE {
               itxDefaultGateway     IpAddress,
               itxIpAddress          IpAddress,
               itxSubnetMask         IpAddress
          }
          
          itxDefaultGateway OBJECT-TYPE
               SYNTAX      IpAddress
               MAX-ACCESS  read-write
               STATUS      current
               DESCRIPTION
                  "The IP Address of the default gateway"
               ::= { itxEthernetEntry 1 }
               
          itxIpAddress OBJECT-TYPE
               SYNTAX      IpAddress
               MAX-ACCESS  read-write
               STATUS      current
               DESCRIPTION
                  "The IP Address of the interface"
               ::= { itxEthernetEntry 2 }

          itxSubnetMask OBJECT-TYPE
               SYNTAX      IpAddress
               MAX-ACCESS  read-write
               STATUS      current
               DESCRIPTION
                  "The Subnetmask of the interface.  One of these
                  objects exists for each of the ethernet interface in
                  the chassis"
               ::= { itxEthernetEntry 3 }
               
          itxSnmpManagementEntityIpAddress OBJECT-TYPE
              SYNTAX  IpAddress
              MAX-ACCESS  read-write
              STATUS  current
              DESCRIPTION
                      "The Ip Address for SNMP Management Entity for the Agent (ITX)
                       to send the traps to.  Used together with the 
                       itxSnmpManagementEntityPort to fully specify the Entity"
              ::= { itxMIBObjects 13 }
              
          itxSnmpManagementEntityPort OBJECT-TYPE
              SYNTAX  INTEGER(0..65535)
              MAX-ACCESS  read-write
              STATUS  current
              DESCRIPTION
                      "The Port for SNMP Management Entity for the Agent (ITX)
                       to send the traps to.  Used together with the 
                       itxSnmpManagementEntityIpAddress to fully specify the Entity"
              ::= { itxMIBObjects 14 }
              
         itxCallControlProtocol OBJECT-TYPE
            SYNTAX      INTEGER { ipdcVersion0dot15(1),
                                  sgcpVersion0(2),
                                  mgcpVersion0dot1(3) }
            MAX-ACCESS  read-write
            STATUS      current
            DESCRIPTION
               "The IPDC protocol version number
               
                  version0dot15(1) - IPDC Version 0.15,
                  sgcpVersion0(2)  - SGCP Version 0,
                  mgcpVersion0.1(3) - MGCP Version 0.1"
            ::= { itxMIBObjects 16 }
            
            
         itxCompandingLaw OBJECT-TYPE
            SYNTAX      INTEGER { aLaw(0),
                                  muLaw(1)}
            MAX-ACCESS  read-write
            STATUS      current
            DESCRIPTION
               "The value selects either aLaw or muLaw as the companding law"
            ::= { itxMIBObjects 18 }
            
         itxDnsIpAddress OBJECT-TYPE
            SYNTAX      IpAddress
            MAX-ACCESS  read-write
            STATUS      current
            DESCRIPTION
               "The Ip Address for the Domain Name server the system should
                use to map hostnames to Ip Addresses"
            ::= { itxMIBObjects 19 }
            
         itxHostname OBJECT-TYPE
            SYNTAX      DisplayString (SIZE(1..255))
            MAX-ACCESS  read-only
            STATUS      current
            DESCRIPTION
               "The Fully Qualified Hostname for the system (includes both 
                the hostname and the domain name.  i.e.:

                     etx5000.salix.com

                would be a valid value"
            ::= { itxMIBObjects 20 }

         itxEthernetLoadSharing OBJECT-TYPE
            SYNTAX      INTEGER { disabled(1),
                                  enabled(0) }
            MAX-ACCESS  read-write
            STATUS      current
            DESCRIPTION
               "This object controls Ethernet Load Sharing across
                multiple Ethernet Interfaces.  The default value is
                enabled.  By setting the value to disabled, calls
                will no longer be load shared across ethernet interfaces"
            DEFVAL { enabled }
            ::= { itxMIBObjects 21 }

   itxNFSObjects      OBJECT IDENTIFIER ::= { itxMIBObjects 22 }

         itxNFSIpAddress OBJECT-TYPE
            SYNTAX      IpAddress
            MAX-ACCESS  read-write
            STATUS      current
            DESCRIPTION
                "This object controls the Ip Address that the ETX will
                mount its file system from.  Any changes to this
                object while there is a currently mounted file system
                will not be effective until the currently mounted file
                system is unmounted"
            ::= { itxNFSObjects 1 }

         itxNFSPath OBJECT-TYPE
            SYNTAX      DisplayString (SIZE(1..50))
            MAX-ACCESS  read-write
            STATUS      current
            DESCRIPTION
                "This object controls the Path that the ETX will
                mount its file system from.  Any changes to this
                object while there is a currently mounted file system
                will not be effective until the currently mounted file
                system is unmounted"
            ::= { itxNFSObjects 2 }

         itxNFSUserId OBJECT-TYPE
            SYNTAX      Integer32
            MAX-ACCESS  read-write
            STATUS      current
            DESCRIPTION
                "This object controls the User Id (uid) that the ETX
                will use when communicating with the NFS server.  Any
                changes to this object while there is a currently
                mounted file system will not be effective until the
                currently mounted file system is unmounted"
            ::= {itxNFSObjects 3 }

         itxNFSGroupId OBJECT-TYPE
            SYNTAX      Integer32
            MAX-ACCESS  read-write
            STATUS      current
            DESCRIPTION
                "This object controls the Group Id (gid) that the ETX
                will use when communicating with the NFS server.  Any
                changes to this object while there is a currently
                mounted file system will not be effective until the
                currently mounted file system is unmounted"
            ::= { itxNFSObjects 4 }

         itxNFSStatus OBJECT-TYPE
            SYNTAX      INTEGER { mounted(1),
                                  unmounted(2)}
            MAX-ACCESS  read-write
            STATUS      current
            DESCRIPTION
                "This object shows the current status of the nfs
                connection.  In addition, the nfs volume can be
                mounted and unmounted by writing the approriate value
                to this object"
            ::= { itxNFSObjects 5 }

-- Conformance Statements

itxGroups          OBJECT IDENTIFIER    ::= {itxMIBCompliance 1 }
itxCompliances     OBJECT IDENTIFIER    ::= {itxMIBCompliance 2 }
   
-- Compliance Statements

itxCompliance MODULE-COMPLIANCE
     STATUS       current
     DESCRIPTION
                  "The basic implementation requirements for the ITX MIB."
     MODULE       -- This module
--     MANDATORY-GROUPS { itxSystemGroup }
     ::= { itxCompliances 1 }

-- Units of conformance

--  itxSystemGroup     OBJECT-GROUP
--       OBJECTS {
--               }
--       STATUS       current
--       DESCRIPTION  "Additional itx specific objects to the mib-2 system
--                   group."
--       ::= {itxGroups 1}   
   
      itxDspGroup OBJECT-GROUP
         OBJECTS {       
            itxDspStatusOperStatus
         }
         STATUS         current
         DESCRIPTION    "Itx Dsp Group"
         ::= { itxGroups 4}
      
   itxMediaControllerGroup OBJECT-GROUP
      OBJECTS {
         itxMediaControllerPrimaryIpAddress,
         itxMediaControllerPrimaryPort,
         itxMediaControllerSecondaryIpAddress,
         itxMediaControllerSecondaryPort
      }
      STATUS         current
      DESCRIPTION    "Itx Media Controller Group"
      ::= { itxGroups 7}      
END
