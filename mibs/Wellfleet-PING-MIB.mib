Wellfleet-PING-MIB DEFINITIONS ::= BEGIN

-- Created by mdl2asn version 3.1
-- Creation date: Wed Aug 30 16:46:28 EDT 1995


    IMPORTS

      IpAddress, Gauge
        FROM RFC1155-SMI
      OBJECT-TYPE
        FROM RFC-1212
      DisplayString
        FROM RFC1213-MIB
      wfPingGroup
        FROM Wellfleet-COMMON-MIB;


    wfPingTable OBJECT-TYPE
        SYNTAX	SEQUENCE OF WfPingEntry
        ACCESS	not-accessible
        STATUS	mandatory
        DESCRIPTION
                "Ping table"
        ::= { wfPingGroup 1 }

    wfPingEntry OBJECT-TYPE
        SYNTAX	WfPingEntry
        ACCESS	not-accessible
        STATUS	mandatory
        DESCRIPTION
                "A list of control entries used to initiate and manage network layer
                echo request sequences"
        INDEX	{ wfPingType,
    		  wfPingIndex }
        ::= { wfPingTable 1 }

    WfPingEntry ::= SEQUENCE {
    	    wfPingDelete
    		INTEGER,
    	    wfPingIndex
    		INTEGER,
    	    wfPingType
    		INTEGER,
    	    wfPingAddress
    		OCTET STRING,
    	    wfPingSize
    		INTEGER,
    	    wfPingTimeOut
    		INTEGER,
    	    wfPingRetry
    		INTEGER,
    	    wfPingTraceRoute
    		INTEGER,
    	    wfPingDelay
    		INTEGER,
    	    wfPingRemaining
    		INTEGER,
    	    wfPingTimer
    		INTEGER,
    	    wfPingSourceRoute
    		INTEGER,
    	    wfPingSourceAddress
    		OCTET STRING,
    	    wfPingTypeOfService
    		INTEGER,
    	    wfPingNumHistBucketsRequested
    		INTEGER,
    	    wfPingNumHistBucketsGranted
    		INTEGER,
    	    wfPingSiteName
    		DisplayString,
    	    wfPingStatus
    		INTEGER,
    	    wfPingAction
    		INTEGER,
    	    wfPingLastMinRoundTripTime
    		INTEGER,
    	    wfPingLastMaxRoundTripTime
    		INTEGER,
    	    wfPingLastTotalRoundTripTime
    		INTEGER,
    	    wfPingIPAddress
    		IpAddress,
    	    wfPingSuccessStatus
    		INTEGER,
            wfPingMaxHopCount
                INTEGER
        }

    wfPingDelete OBJECT-TYPE
        SYNTAX	INTEGER {
    		    created(1),
    		    deleted(2)
    		}
        ACCESS	read-write
        STATUS	mandatory
        DESCRIPTION
                "When set, will cause this row in the table to be deleted"
        DEFVAL	{ created }
        ::= { wfPingEntry 1 }

    wfPingIndex OBJECT-TYPE
        SYNTAX	INTEGER
        ACCESS	read-only
        STATUS	mandatory
        DESCRIPTION
                "Index into the Ping Table"
        ::= { wfPingEntry 2 }

    wfPingType OBJECT-TYPE
        SYNTAX	INTEGER {
    		    ip(1),
    		    ipx(2),
    		    llc(3),
    		    osi(4),
    		    vines(5),
    		    appletalk(6)
    		}
        ACCESS	read-only
        STATUS	mandatory
        DESCRIPTION
                "Type of Ping Protocol"
        ::= { wfPingEntry 3 }

    wfPingAddress OBJECT-TYPE
        SYNTAX	OCTET STRING
        ACCESS	read-write
        STATUS	mandatory
        DESCRIPTION
                "Address of the object to echo"
        ::= { wfPingEntry 4 }

    wfPingSize OBJECT-TYPE
        SYNTAX	INTEGER(1..4850)
        ACCESS	read-write
        STATUS	mandatory
        DESCRIPTION
                "Size of the echo request packet in bytes"
        DEFVAL	{ 16 }
        ::= { wfPingEntry 5 }

    wfPingTimeOut OBJECT-TYPE
        SYNTAX	INTEGER(1..65535)
        ACCESS	read-write
        STATUS	mandatory
        DESCRIPTION
                "Amount of time in seconds before deciding success"
        DEFVAL	{ 5 }
        ::= { wfPingEntry 6 }

    wfPingRetry OBJECT-TYPE
        SYNTAX	INTEGER(1..65535)
        ACCESS	read-write
        STATUS	mandatory
        DESCRIPTION
                "The number of times to retry"
        DEFVAL	{ 1 }
        ::= { wfPingEntry 7 }

    wfPingTraceRoute OBJECT-TYPE
        SYNTAX	INTEGER {
    		    trace(1),
    		    notrace(2)
    		}
        ACCESS	read-write
        STATUS	mandatory
        DESCRIPTION
                "Selecting PING_TRACE (1) will cause a traceroute to be performed and
                the result placed in wfPingTraceTable"
        DEFVAL	{ notrace }
        ::= { wfPingEntry 8 }

    wfPingDelay OBJECT-TYPE
        SYNTAX	INTEGER(1..65535)
        ACCESS	read-write
        STATUS	mandatory
        DESCRIPTION
                "Number of milliseconds to wait between sending echo packets"
        DEFVAL	{ 250 }
        ::= { wfPingEntry 9 }

    wfPingRemaining OBJECT-TYPE
        SYNTAX	INTEGER
        ACCESS	read-only
        STATUS	mandatory
        DESCRIPTION
                "The number of ICMP echoes left to send in this sequence. This will be
                decremented for each time we need to retry and increment wfPingRetry.
                Whenever a sequence is started, the wfPingReceived and wfPingDropped
                will be reset to zero."
        ::= { wfPingEntry 10 }

    wfPingTimer OBJECT-TYPE
        SYNTAX	INTEGER(0..65535)
        ACCESS	read-write
        STATUS	mandatory
        DESCRIPTION
                "Time in minutes for the request to begin again, zero means do it once"
        ::= { wfPingEntry 11 }

    wfPingSourceRoute OBJECT-TYPE
        SYNTAX	INTEGER {
    		    nosourceroute(1),
    		    strictsourceroute(2),
    		    loosesourceroute(3)
    		}
        ACCESS	read-write
        STATUS	mandatory
        DESCRIPTION
                "Option that can be set to use loose or strict source routing. IF the
                value is something other than PING_NOSOURCEROUTE, the corresponding
                rows in wfPingSourceRouteTable will be used"
        DEFVAL	{ nosourceroute }
        ::= { wfPingEntry 12 }

    wfPingSourceAddress OBJECT-TYPE
        SYNTAX	OCTET STRING
        ACCESS	read-write
        STATUS	mandatory
        DESCRIPTION
                "Address that specifies the source of the Ping Request"
        ::= { wfPingEntry 13 }

    wfPingTypeOfService OBJECT-TYPE
        SYNTAX	INTEGER {
    		    tosnormal(1)
    		}
        ACCESS	read-write
        STATUS	mandatory
        DESCRIPTION
                "Tells how the ICMP packet should be handled. According to RFC 1349,
                Normal service is preferred (wfPingTypeOfService = 1)"
        DEFVAL	{ tosnormal }
        ::= { wfPingEntry 14 }

    wfPingNumHistBucketsRequested OBJECT-TYPE
        SYNTAX	INTEGER(1..60)
        ACCESS	read-write
        STATUS	mandatory
        DESCRIPTION
                "Number of history buckets that the user asked for which will only be
                granted if the timer mechanism is being used. Otherwise, only 1 bucket
                will be granted for the single ping"
        DEFVAL	{ 1 }
        ::= { wfPingEntry 15 }

    wfPingNumHistBucketsGranted OBJECT-TYPE
        SYNTAX	INTEGER
        ACCESS	read-only
        STATUS	mandatory
        DESCRIPTION
                "The number of history buckets that the user was granted. We don't
                grant more then 60 which will allow them to do a ping a minute"
        ::= { wfPingEntry 16 }

    wfPingSiteName OBJECT-TYPE
        SYNTAX	DisplayString
        ACCESS	read-write
        STATUS	mandatory
        DESCRIPTION
                "Character string to store the name of the Site. This is not used for
                domain name resolution !  It is purely for cosmetic purposes for customer
                generated reports"
        ::= { wfPingEntry 17 }

    wfPingStatus OBJECT-TYPE
        SYNTAX	INTEGER {
    		    done(1),
    		    busy(2),
    		    badaddress(3),
    		    error(4),
    		    timeout(5),
    		    invalidparams(6),
    		    resourceerror(7),
    		    targetunreach(8),
    		    ipunavail(9),
    		    icmpdestunreach(10),
    		    ttlexceeded(11),
    		    notimplemented(12),
    		    icmphostunreach(13),
    		    icmpnetunreach(14),
    		    icmpprohibnet(15),
    		    icmpprohibhost(16),
    		    icmpsrcrtefail(17),
    		    protounreach(18),
    		    portunreach(19),
    		    fragneeded(20)
    		}
        ACCESS	read-only
        STATUS	mandatory
        DESCRIPTION
                "Status of the ping request"
        ::= { wfPingEntry 18 }

    wfPingAction OBJECT-TYPE
        SYNTAX	INTEGER {
    		    go(1),
    		    waiting(2)
    		}
        ACCESS	read-write
        STATUS	mandatory
        DESCRIPTION
                "Begin processing ping when set to GO"
        DEFVAL	{ waiting }
        ::= { wfPingEntry 19 }

    wfPingLastMinRoundTripTime OBJECT-TYPE
        SYNTAX	INTEGER
        ACCESS	read-only
        STATUS	mandatory
        DESCRIPTION
                "The last minimum round trip time."
        ::= { wfPingEntry 20 }

    wfPingLastMaxRoundTripTime OBJECT-TYPE
        SYNTAX	INTEGER
        ACCESS	read-only
        STATUS	mandatory
        DESCRIPTION
                "The last maximum round trip time."
        ::= { wfPingEntry 21 }

    wfPingLastTotalRoundTripTime OBJECT-TYPE
        SYNTAX	INTEGER
        ACCESS	read-only
        STATUS	mandatory
        DESCRIPTION
                "The last total round trip time in milliseconds."
        ::= { wfPingEntry 22 }

    wfPingIPAddress OBJECT-TYPE
        SYNTAX	IpAddress
        ACCESS	read-only
        STATUS	mandatory
        DESCRIPTION
                "stations who can't interpret octet string formats."
        ::= { wfPingEntry 23 }

    wfPingSuccessStatus OBJECT-TYPE
        SYNTAX	INTEGER
        ACCESS	read-only
        STATUS	mandatory
        DESCRIPTION
                "interpreting the detailed status returned by wfPingStatus."
        ::= { wfPingEntry 24 }

    wfPingMaxHopCount OBJECT-TYPE
        SYNTAX  INTEGER(1..60)
        ACCESS  read-write
        STATUS  mandatory
        DESCRIPTION
                "Number of maximum hop count when trace route is enabled.
                 The default maximum hop count is 30."
        DEFVAL  { 30 }
        ::= { wfPingEntry 25 }

    wfPingTraceTable OBJECT-TYPE
        SYNTAX	SEQUENCE OF WfPingTraceEntry
        ACCESS	not-accessible
        STATUS	mandatory
        DESCRIPTION
                "Table that contains trace route information"
        ::= { wfPingGroup 2 }

    wfPingTraceEntry OBJECT-TYPE
        SYNTAX	WfPingTraceEntry
        ACCESS	not-accessible
        STATUS	mandatory
        DESCRIPTION
                "A conceptual row containing information about a network hop associated
                with a particular echo request."
        INDEX	{ wfPingTraceType,
    		  wfPingEntryIndex,
    		  wfPingTraceIndex }
        ::= { wfPingTraceTable 1 }

    WfPingTraceEntry ::= SEQUENCE {
    	    wfPingTraceType
    		INTEGER,
    	    wfPingEntryIndex
    		INTEGER,
    	    wfPingTraceIndex
    		INTEGER,
    	    wfPingTraceAddress
    		OCTET STRING
        }

    wfPingTraceType OBJECT-TYPE
        SYNTAX	INTEGER
        ACCESS	read-only
        STATUS	mandatory
        DESCRIPTION
                "Type of Ping protocol"
        ::= { wfPingTraceEntry 1 }

    wfPingEntryIndex OBJECT-TYPE
        SYNTAX	INTEGER
        ACCESS	read-only
        STATUS	mandatory
        DESCRIPTION
                "This is the corresponding index into the Ping Table"
        ::= { wfPingTraceEntry 2 }

    wfPingTraceIndex OBJECT-TYPE
        SYNTAX	INTEGER
        ACCESS	read-only
        STATUS	mandatory
        DESCRIPTION
                "A unique integer describing the order in which a particular hop was
                encountered."
        ::= { wfPingTraceEntry 3 }

    wfPingTraceAddress OBJECT-TYPE
        SYNTAX	OCTET STRING
        ACCESS	read-only
        STATUS	mandatory
        DESCRIPTION
                "Address of the route we passed through"
        ::= { wfPingTraceEntry 4 }

    wfPingSourceTable OBJECT-TYPE
        SYNTAX	SEQUENCE OF WfPingSourceEntry
        ACCESS	not-accessible
        STATUS	mandatory
        DESCRIPTION
                "Table that contains source route information"
        ::= { wfPingGroup 3 }

    wfPingSourceEntry OBJECT-TYPE
        SYNTAX	WfPingSourceEntry
        ACCESS	not-accessible
        STATUS	mandatory
        DESCRIPTION
                "A row in the Ping SourceTable"
        INDEX	{ wfPingSourceType,
    		  wfPingSourceEntryIndex,
    		  wfPingSourceIndex }
        ::= { wfPingSourceTable 1 }

    WfPingSourceEntry ::= SEQUENCE {
    	    wfPingSourceDelete
    		INTEGER,
    	    wfPingSourceType
    		INTEGER,
    	    wfPingSourceEntryIndex
    		INTEGER,
    	    wfPingSourceIndex
    		INTEGER,
    	    wfPingSourceRouteAddress
    		OCTET STRING
        }

    wfPingSourceDelete OBJECT-TYPE
        SYNTAX	INTEGER {
    		    sourcecreated(1),
    		    sourcedeleted(2)
    		}
        ACCESS	read-write
        STATUS	mandatory
        DESCRIPTION
                "When set, will cause this row in the table to be deleted."
        DEFVAL	{ sourcecreated }
        ::= { wfPingSourceEntry 1 }

    wfPingSourceType OBJECT-TYPE
        SYNTAX	INTEGER
        ACCESS	read-only
        STATUS	mandatory
        DESCRIPTION
                "Type of Ping Protocol"
        ::= { wfPingSourceEntry 2 }

    wfPingSourceEntryIndex OBJECT-TYPE
        SYNTAX	INTEGER
        ACCESS	read-only
        STATUS	mandatory
        DESCRIPTION
                "This is the corresponding index into the Ping Table"
        ::= { wfPingSourceEntry 3 }

    wfPingSourceIndex OBJECT-TYPE
        SYNTAX	INTEGER
        ACCESS	read-only
        STATUS	mandatory
        DESCRIPTION
                "A unique index for this source route"
        ::= { wfPingSourceEntry 4 }

    wfPingSourceRouteAddress OBJECT-TYPE
        SYNTAX	OCTET STRING
        ACCESS	read-write
        STATUS	mandatory
        DESCRIPTION
                "Address of the route we are to pass through"
        ::= { wfPingSourceEntry 5 }

    wfPingHistoryTable OBJECT-TYPE
        SYNTAX	SEQUENCE OF WfPingHistoryEntry
        ACCESS	not-accessible
        STATUS	mandatory
        DESCRIPTION
                "Table that contains ping history information"
        ::= { wfPingGroup 4 }

    wfPingHistoryEntry OBJECT-TYPE
        SYNTAX	WfPingHistoryEntry
        ACCESS	not-accessible
        STATUS	mandatory
        DESCRIPTION
                "A row in the Ping HistoryTable"
        INDEX	{ wfPingHistoryType,
    		  wfPingHistoryEntryIndex,
    		  wfPingHistoryIndex }
        ::= { wfPingHistoryTable 1 }

    WfPingHistoryEntry ::= SEQUENCE {
    	    wfPingHistoryType
    		INTEGER,
    	    wfPingHistoryEntryIndex
    		INTEGER,
    	    wfPingHistoryIndex
    		INTEGER,
    	    wfPingReceived
    		Gauge,
    	    wfPingDropped
    		Gauge,
    	    wfPingRoundTripTime
    		INTEGER,
    	    wfPingTotalRoundTripTime
    		INTEGER,
    	    wfPingMinRoundTripTime
    		INTEGER,
    	    wfPingMaxRoundTripTime
    		INTEGER,
    	    wfPingBegan
    		OCTET STRING
        }

    wfPingHistoryType OBJECT-TYPE
        SYNTAX	INTEGER
        ACCESS	read-only
        STATUS	mandatory
        DESCRIPTION
                "Type of Ping protocol"
        ::= { wfPingHistoryEntry 1 }

    wfPingHistoryEntryIndex OBJECT-TYPE
        SYNTAX	INTEGER
        ACCESS	read-only
        STATUS	mandatory
        DESCRIPTION
                "This is the corresponding index in the ping table"
        ::= { wfPingHistoryEntry 2 }

    wfPingHistoryIndex OBJECT-TYPE
        SYNTAX	INTEGER
        ACCESS	read-only
        STATUS	mandatory
        DESCRIPTION
                "This is the unique history table index"
        ::= { wfPingHistoryEntry 3 }

    wfPingReceived OBJECT-TYPE
        SYNTAX	Gauge
        ACCESS	read-only
        STATUS	mandatory
        DESCRIPTION
                "The total number of ICMP echo packets received in this sequence. A
                sequence is defined from the time the ping request began to the time
                it was either successful or an error occurred. This field will be
                reset to zero at the start of every new sequence."
        ::= { wfPingHistoryEntry 4 }

    wfPingDropped OBJECT-TYPE
        SYNTAX	Gauge
        ACCESS	read-only
        STATUS	mandatory
        DESCRIPTION
                "The number of ICMP packets dropped since this ping sequence started.
                It will be reset to zero at the start of every new ping sequence"
        ::= { wfPingHistoryEntry 5 }

    wfPingRoundTripTime OBJECT-TYPE
        SYNTAX	INTEGER
        ACCESS	read-only
        STATUS	mandatory
        DESCRIPTION
                "The round trip time of the last ICMP packet in milliseconds"
        ::= { wfPingHistoryEntry 6 }

    wfPingTotalRoundTripTime OBJECT-TYPE
        SYNTAX	INTEGER
        ACCESS	read-only
        STATUS	mandatory
        DESCRIPTION
                "The sum of the total round trip times of successful pings received in
                this sequence"
        ::= { wfPingHistoryEntry 7 }

    wfPingMinRoundTripTime OBJECT-TYPE
        SYNTAX	INTEGER
        ACCESS	read-only
        STATUS	mandatory
        DESCRIPTION
                "The minimum round trip time in this sequence"
        ::= { wfPingHistoryEntry 8 }

    wfPingMaxRoundTripTime OBJECT-TYPE
        SYNTAX	INTEGER
        ACCESS	read-only
        STATUS	mandatory
        DESCRIPTION
                "The maximum round trip time in this sequence"
        ::= { wfPingHistoryEntry 9 }

    wfPingBegan OBJECT-TYPE
        SYNTAX	OCTET STRING
        ACCESS	read-only
        STATUS	mandatory
        DESCRIPTION
                "The date and time this ping request was last executed"
        ::= { wfPingHistoryEntry 10 }

    END  -- Wellfleet-PING-MIB
