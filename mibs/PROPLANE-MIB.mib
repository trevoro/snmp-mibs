------------------------------------------------------------------------------
--
-- MIB      : Proprietary LANE                             Lucent Technologies
--
-- Version  : 2.1.0                                        8 March 2000
--
-- RCS Id   : Gidi
--
------------------------------------------------------------------------------
--
-- Copyright 2000 Lucent Technologies,  Ltd.  
-- All Rights Reserved.  
--
-- Reproduction of this document is authorized on condition 
-- that the foregoing copyright notice is included.
--
-- This Lucent Technologies SNMP Management Information Base
-- Specification embodies Lucent Technologies confidential and
-- proprietary intellectual property.  Lucent Technologies retains all
-- title and ownership in the Specification, including any revisions
--
-- It is Lucent Technologies intent to encourage the widespread use of this
-- Specification in connection with the management of Lucent Technologies
-- products.
-- Lucent Technologies grants vendors, end-users, and other interested parties
-- a non-exclusive license to use this Specification in connection
-- with the management of Lucent Technologies products.
--
-- This Specification is supplied "as is," and Lucent Technologies makes
-- no warranty, either express or implied, as to the use,
-- operation, condition, or performance of the Specification.
--
------------------------------------------------------------------------------
--
-- RCS
--
-- Version 2.1.0
-- 8 March 00
-- Add the MIBs: propLaneElanLuni2capability, propLaneElanLuni2capabilityOper,
--               propLaneLesLuni2capability and propLaneLesLecTable.
--
-- Version 1.0.2
-- 21 December 98
-- 1. Add the MIBs: propLaneSlotNextLesSelector, propLaneSlotNextBusSelector
--      propLaneSlotNextLecsSelector
-- 2. Change propLaneLecsResOrigin to have the same enum names as CLI.
--
-- Version 1.0.1
-- 21 April 98
-- 1. Remove "_" .
--
-- Version 1.0.0
-- 22 March 98
-- 1. Base on Madge mdgLane MIB
--
------------------------------------------------------------------------------
--
--
-- Overview :
--
-- The Proprietary LANE MIB defines manageable objects used by the following 
-- devices -
--
--	Meritage ATM Switch
--
--
-- The Proprietary LANE MIB contains the following groups :-
--
-- propLaneMgmtLEC	- This group contains information about the management
--			LEC. This information is additional to information in
--			MIB II and the LEC MIB.
--
-- propLaneElan		 - This group contains information that suppliments the
--			elanConf table in the ELAN MIB. It manages Prop LES 
--			auto-registry and configures Prop distributed ELANs.
--
-- propLaneLes		- This group contains information that suppliments the
--			lesConfTable in the LES MIB. It configures Prop LESs
--			and the BUS unicast filter.
--
-- propLaneLecs		- This group contains information about the LECS
--			location and about the local LECS if there is one. It
--			configures the default ELANs and sets resilient LECS 
--			parameters.
--
-- propLaneResLecs	- This group provides a table of resilient LECSs.
--
-- propLaneSlot		- This group contains information about the Next Index
--			of Servers per Slot instead of the standard ConfNextId. 
--			It does not deal with the Proprietery LANE features.

-------------------------------------------------------------------------------



PROPLANE-MIB DEFINITIONS ::= BEGIN

IMPORTS
	DisplayString		FROM RFC1213-MIB
	TimeTicks		FROM RFC1155-SMI
	OBJECT-TYPE		FROM RFC-1212
	lannet			FROM GEN-MIB;

-- useful types

	AtmAddress ::= OCTET STRING (SIZE(20))   
	MacAddress ::= OCTET STRING (SIZE(6))   

-- the Proprietary LANE MIB
-- The propLane MIB forms part of the general LANNET MIB as follows:
-- LANNET-MIB { iso org(3) dod(6) internet(1) private(4) enterprises(1) 81 }


	propLane		OBJECT IDENTIFIER ::= { lannet 34 }

-- groups in the Prop Lane MIB

	propLaneMgmtLEC		OBJECT IDENTIFIER ::= { propLane 1 }
	propLaneElan		OBJECT IDENTIFIER ::= { propLane 2 }
	propLaneLes		OBJECT IDENTIFIER ::= { propLane 3 }
	propLaneLecs		OBJECT IDENTIFIER ::= { propLane 4 }
	propLaneResLecs		OBJECT IDENTIFIER ::= { propLane 5 }
	propLaneSlot		OBJECT IDENTIFIER ::= { propLane 6 }


--------------------------------------------------------------------------------

-- the propLaneMgmtLEC group


        propLaneMgmtLECCurrentAddress OBJECT-TYPE
                SYNTAX MacAddress
                ACCESS read-only
                STATUS mandatory
                DESCRIPTION
                        "The actual address currently being used by the 
                         management LEC."
                ::= {propLaneMgmtLEC 1 }
                                          
        propLaneMgmtLECIfIndexMap OBJECT-TYPE
                SYNTAX INTEGER
                ACCESS read-only
                STATUS mandatory
                DESCRIPTION
                        "The corresponding entry in the interfaces table of
                        MIB II"
                ::= {propLaneMgmtLEC 2 }

        propLaneMgmtLECLecIndexMap OBJECT-TYPE
                SYNTAX INTEGER
                ACCESS read-only
                STATUS mandatory
                DESCRIPTION
                        "The corresponding entry in the ATM LEC MIB"
                ::= {propLaneMgmtLEC 3 }

-- the propLaneElan Group

        propLaneElanConfTable OBJECT-TYPE
                SYNTAX SEQUENCE OF PropLaneElanConfEntry
                ACCESS not-accessible
                STATUS mandatory
                DESCRIPTION
                        "A table containing information about each ELAN."
                ::= { propLaneElan 1 }
        
        propLaneElanConfEntry OBJECT-TYPE
                SYNTAX PropLaneElanConfEntry
                ACCESS not-accessible
                STATUS mandatory
                DESCRIPTION
                        "An entry containing information about a particular 
                        ELAN."
                INDEX {propLaneElanConfIndex }
                ::= { propLaneElanConfTable 1 }
        
        PropLaneElanConfEntry ::= SEQUENCE
                {
                propLaneElanConfIndex                INTEGER,
                propLaneElanSecurity                 INTEGER,
                propLaneElanLesDiscovery             INTEGER,
                propLaneElanLesRgstrType             INTEGER,
                propLaneElanLesActualRgstrType       INTEGER,
                propLaneElanMaximumActiveLes         INTEGER,
                propLaneElanLesAddrForm              INTEGER,
                propLaneElanGroupLesAddress          AtmAddress,
                propLaneElanLuni2capability          INTEGER,
                propLaneElanLuni2capabilityOper      INTEGER
                }
        
        propLaneElanConfIndex OBJECT-TYPE
                SYNTAX INTEGER
                ACCESS read-only
                STATUS mandatory
                DESCRIPTION
                        "Index into this table, matches the ELAN MIB
                        elanConfIndex."
                ::= { propLaneElanConfEntry 1 }
        
        propLaneElanSecurity OBJECT-TYPE
                SYNTAX INTEGER
                        {
                        open       (1),
                        closed     (2)
                        }
                ACCESS read-write
                STATUS mandatory
                DESCRIPTION
                        "The status of the ELAN security.
                         open - a LEC can join this ELAN without any
                         ELAN info
                         closed - a LEC can ONLY join this ELAN if it
                         has some ELAN info."
                ::= { propLaneElanConfEntry 2 }
        
        propLaneElanLesDiscovery OBJECT-TYPE
                SYNTAX INTEGER
                        {
                        auto       (1),
                        manual     (2)
                        }
                ACCESS read-write
                STATUS mandatory
                DESCRIPTION
                        "Determines how the ELAN discovers its LES.

                         auto - LES discovered automatically if
                         we have a Prop LES.

                         manual - the user must enter a LES address."
                ::= { propLaneElanConfEntry 3 }

        propLaneElanLesRgstrType OBJECT-TYPE
                SYNTAX INTEGER
                        {
                        autosense   (1),
                        single      (2),
                        resilient   (3),
                        distributed (4)
                        }
                ACCESS read-write
                STATUS mandatory
                DESCRIPTION
                        "The LES registration mode to be supported by LECS.

                         autosense - the LECS will adopt the proprietary
                         registration version from the first registering LES.

                         single - the LECS will only allow a LES using the
 		proprietary registration method.

                         resilient - the LECS will only allow a LES using the 
 		proprietary registration method which
                         supports resilient LESes. 

                         distributed - the LECS will only allow a LES using the
 		proprietary registration method which
                         supports LNNI phase 1 LESes."
                ::= { propLaneElanConfEntry 4 }

        propLaneElanLesActualRgstrType OBJECT-TYPE
                SYNTAX INTEGER
                        {
                        none        (1),
                        single      (2),
                        resilient   (3),
                        distrib     (4)
                        }
                ACCESS read-only
                STATUS mandatory
                DESCRIPTION
                        "The actual LES registration mode that the LECS has adopted.

                         single - the LES has used the proprietary
                         registration method with the LECS.

                         resilient - the LES has used the proprietary
                         registration method to register with the LECS.

                         distrib - the LES has used the proprietary
                         registration method to register with the LECS.

                         none - the registration mode is undefined as no LES
                         has registered yet."
                ::= { propLaneElanConfEntry 5 }

        propLaneElanMaximumActiveLes OBJECT-TYPE
                SYNTAX INTEGER (0..16)
                ACCESS read-write
                STATUS mandatory
                DESCRIPTION
                        "The maximum number of active LES's for the ELAN.
                         Can only be written when the propLaneElanLesType
                         is distributed. If propLaneElanLesActualType is
                         not distributed then reading will always return
                         the value 1."
                ::= { propLaneElanConfEntry 6 }

        propLaneElanLesAddrForm OBJECT-TYPE
                SYNTAX INTEGER
                        {
                        groupAddr  (1),
                        roundRobin (2),
                        longMatch  (3)
                        }
                ACCESS read-write
                STATUS mandatory
                DESCRIPTION
                        "The method by which the LES address will be formulated. 
                         Can only be written when the propLaneElanLesType is 
                         distributed.

                         groupAddr - a user-provided group 
                         address will be used

                         roundRobin   - the address will be picked
                         on a round robin basis

                         longMatch - the longest matching LES
                         address will be used."
                ::= { propLaneElanConfEntry 7 }

        propLaneElanGroupLesAddress OBJECT-TYPE
                SYNTAX AtmAddress
                ACCESS read-write
                STATUS mandatory
                DESCRIPTION
                        "The group LES address of the ELAN.
                         Can only be written when the propLaneElanLesType is 
                         distributed."
                ::= { propLaneElanConfEntry 8 }

        propLaneElanLuni2capability OBJECT-TYPE
                SYNTAX INTEGER
                        {
                        yes     (1),
                        no      (2),
                        auto    (3)
                        }
                ACCESS read-write
                STATUS mandatory
                DESCRIPTION
                        "The configured LUNI 2 capability of the ELAN. If
                         yes, then the ELAN is LUNI 2 capable, and LECs
                         using either LANE 1 or LUNI 2 can join the ELAN.
                         If no, then LUNI 2 clients will be told to use
                         LANE 1 instead of LUNI 2.
                         If auto, then the capability is determined by
                         the capability of the first LES to register for
                         the ELAN (auto-register ELANs only)."
                ::= { propLaneElanConfEntry 9 }

        propLaneElanLuni2capabilityOper OBJECT-TYPE
                SYNTAX INTEGER
                        {
                        yes     (1),
                        no      (2),
                        auto    (3)
                        }
                ACCESS read-only
                STATUS mandatory
                DESCRIPTION
	                "The detected LUNI 2 capability of the ELAN. If
	                 yes, then the ELAN is LUNI 2 capable, and LECs
	                 using either LANE 1 or LUNI 2 can join the ELAN.
	                 If no, then LUNI 2 clients will be told to use
	                 LANE 1 instead of LUNI 2. Auto is an interim state
                         which indicates that the ELAN capability will be
                         determined by the first LES to register the ELAN, and
                         it has not been autodetected yet."
                ::= { propLaneElanConfEntry 10 }


        propLaneElanLesTable OBJECT-TYPE
                SYNTAX SEQUENCE OF PropLaneElanLesTableEntry
                ACCESS not-accessible
                STATUS mandatory
                DESCRIPTION
                        "A table containing information about each LES of 
                        an ELAN."
                ::= { propLaneElan 2 }
        
        propLaneElanLesTableEntry OBJECT-TYPE
                SYNTAX PropLaneElanLesTableEntry
                ACCESS not-accessible
                STATUS mandatory
                DESCRIPTION
                        "An entry containing information about a particular 
                        LES of an ELAN."
                INDEX { propLaneElanConfIndex, propLaneElanLesIndex }
                ::= { propLaneElanLesTable 1 }
        
        PropLaneElanLesTableEntry ::= SEQUENCE
                {
                propLaneElanLesIndex		INTEGER,
                propLaneElanLesLecIdLow		INTEGER,
                propLaneElanLesLecIdHigh	INTEGER
                }
        
        propLaneElanLesIndex OBJECT-TYPE
                SYNTAX INTEGER
                ACCESS read-only
                STATUS mandatory
                DESCRIPTION
                        "Index into this table, matches the ELAN MIB
                        elanLesIndex."
                ::= { propLaneElanLesTableEntry 1 }
        
        propLaneElanLesLecIdLow OBJECT-TYPE
                SYNTAX INTEGER
                ACCESS read-only
                STATUS mandatory
                DESCRIPTION
                        "The lower end of the LES LEC ID range."
                ::= { propLaneElanLesTableEntry 2 }

        propLaneElanLesLecIdHigh OBJECT-TYPE
                SYNTAX INTEGER
                ACCESS read-only
                STATUS mandatory
                DESCRIPTION
                        "The higher end of the LES LEC ID range."
                ::= { propLaneElanLesTableEntry 3 }
                

-- the propLaneLes Group

        propLaneLesConfTable OBJECT-TYPE
                SYNTAX SEQUENCE OF PropLaneLesConfEntry
                ACCESS not-accessible
                STATUS mandatory
                DESCRIPTION
                        "A table containing information about each LES."
                ::= { propLaneLes 1 }
        
        propLaneLesConfEntry OBJECT-TYPE
                SYNTAX PropLaneLesConfEntry
                ACCESS not-accessible
                STATUS mandatory
                DESCRIPTION
                        "An entry containing information about a particular 
                        LES."
                INDEX {propLaneLesConfIndex }
                ::= { propLaneLesConfTable 1 }
        
        PropLaneLesConfEntry ::= SEQUENCE
                {
                propLaneLesConfIndex         INTEGER,
                propLaneLesMode              INTEGER,
                propLaneLesActiveStatus      INTEGER,
                propLaneLesLecIdLow          INTEGER,
                propLaneLesLecIdHigh         INTEGER,
                propLaneLesBusUnicastFilter  INTEGER,
                propLaneLesLuni2capability   INTEGER
                }
        
        propLaneLesConfIndex OBJECT-TYPE
                SYNTAX INTEGER
                ACCESS read-only
                STATUS mandatory
                DESCRIPTION
                        "Index into this table, matches the LES MIB
                        lesConfIndex."
                ::= { propLaneLesConfEntry 1 }
        
        propLaneLesMode OBJECT-TYPE
                SYNTAX INTEGER
                        {
                        manual      (1),
                        single      (2),
                        resilient   (3),
                        distrib     (4)
                        }
                ACCESS read-write
                STATUS mandatory
                DESCRIPTION
                        "The LES registration mode.
                         manual - the LES is ATM Forum compliant as per
                         LANE v1.0 and will not attempt to register with 
                         the LECS. This means that management must 
                         tell the LECS the address of the LES.

                         single - the LES will use a proprietary
                         registration method.

                         resilient - the LES will use a proprietary
                         registration method.

                         distrib - the LES will use a proprietary
                         registration method, and can register with a LNNI
                         phase 1 or better Prop LECS."

                ::= { propLaneLesConfEntry 2 }
        
        propLaneLesActiveStatus OBJECT-TYPE
                SYNTAX INTEGER
                        {
                        active         (1),
                        standby        (2),
                        not-registered (3),
                        none           (4)
                        }
                ACCESS read-only
                STATUS mandatory
                DESCRIPTION
                        "The LES active status.
                         active - the LES has resilient capability and is
                         ACTIVE.

                         standby - the LES has resilient capability and is
                         on STANDBY.

                         not-registered - the LES has resilient capability
                         but is not yet registered.

                         none - the LES doesn't have resilient capability."
                ::= { propLaneLesConfEntry 3 }

        propLaneLesLecIdLow OBJECT-TYPE
                SYNTAX INTEGER
                ACCESS read-only
                STATUS mandatory
                DESCRIPTION
                        "The lower end of the LES LEC ID range."
                ::= { propLaneLesConfEntry 4 }
        
        propLaneLesLecIdHigh OBJECT-TYPE
                SYNTAX INTEGER
                ACCESS read-only
                STATUS mandatory
                DESCRIPTION
                        "The higher end of the LES LEC ID range."
                ::= { propLaneLesConfEntry 5 }

        propLaneLesBusUnicastFilter OBJECT-TYPE
                SYNTAX INTEGER
                        {
                        disabled       (1),
                        enabled        (2)
                        }
                ACCESS read-write
                STATUS mandatory
                DESCRIPTION
                        "Whether BUS filter unicast filtering is enabled
                         or disabled."
                ::= { propLaneLesConfEntry 6 }
 
        propLaneLesLuni2capability OBJECT-TYPE
                SYNTAX INTEGER
                        {
                        no      (1),
                        yes     (2)
                        }
                ACCESS read-write
                STATUS mandatory
                DESCRIPTION
                        "The configured LUNI 2 capability of the LES. If
                         yes, then the LES is LUNI 2 capable, and LECs
                         using either LANE 1 or LUNI 2 can join the ELAN.
                         If no, then LUNI 2 clients will be told to use
                         LANE 1 instead of LUNI 2. Default value is yes (2)."
                ::= { propLaneLesConfEntry 7 }


        propLaneLesLecTable OBJECT-TYPE
                SYNTAX SEQUENCE OF PropLaneLesLecEntry
                ACCESS not-accessible
                STATUS mandatory
                DESCRIPTION
                        "A table containing information about each LEC of 
                        a LES."
                ::= { propLaneLes 2 }
        
        propLaneLesLecEntry OBJECT-TYPE
                SYNTAX PropLaneLesLecEntry
                ACCESS not-accessible
                STATUS mandatory
                DESCRIPTION
                        "An entry containing information about a particular 
                        LEC of a LES."
                INDEX { propLaneLesConfIndex, propLaneLesLecIndex }
                ::= { propLaneLesLecTable 1 }
        
        PropLaneLesLecEntry ::= SEQUENCE
                {
                propLaneLesLecIndex              INTEGER,
                propLaneLesLecLuni2granted       INTEGER,
                propLaneLesLecSelectiveMulticast INTEGER
                }
        
        propLaneLesLecIndex OBJECT-TYPE
                SYNTAX INTEGER
                ACCESS read-only
                STATUS mandatory
                DESCRIPTION
                        "Index into this table, matches the LES MIB lesLecIndex."
                ::= { propLaneLesLecEntry 1 }
        
        propLaneLesLecLuni2granted OBJECT-TYPE
                SYNTAX INTEGER
                        {
                        no      (1),
                        yes     (2)
                        }
                ACCESS read-only
                STATUS mandatory
                DESCRIPTION
                        "Whether the LEC joined the LES as a LUNI2 
                         client or a LANE v1 client."
                ::= { propLaneLesLecEntry 2 }

        propLaneLesLecSelectiveMulticast OBJECT-TYPE
                SYNTAX INTEGER
                        {
                        no      (1),
                        yes     (2)
                        }
                ACCESS read-only
                STATUS mandatory
                DESCRIPTION
                        "Whether the LEC joined the LES requesting 
                         selective multicast."
                ::= { propLaneLesLecEntry 3 }
              
-- the propLaneLecs group

propLaneLecsTable OBJECT-TYPE
	SYNTAX SEQUENCE OF PropLaneLecsEntry
	ACCESS not-accessible
	STATUS mandatory
	DESCRIPTION
		"A table containing information about a LECS in a Slot."
	::= { propLaneLecs 1 }
        
propLaneLecsEntry OBJECT-TYPE
	SYNTAX PropLaneLecsEntry
	ACCESS not-accessible
	STATUS mandatory
	DESCRIPTION
		"An entry containing information about a LECS."
	INDEX {propLaneLecsSlotIndex }
                ::= { propLaneLecsTable 1 }
        
PropLaneLecsEntry ::= SEQUENCE
                {
	propLaneLecsSlotIndex		INTEGER,
	propLaneLecsLocation		INTEGER,
	propLaneLecsRemoteAddress	AtmAddress,
	propLaneLecsLocalSelector 	INTEGER,
	propLaneLecsDefTRElan		DisplayString,
	propLaneLecsDefEthElan		DisplayString,
	propLaneLecsDefUnspecElan	DisplayString,
	propLaneLecsResilientNetStatus 	INTEGER,
	propLaneLecsResilientMode 	INTEGER,
	propLaneLecsResilientStatus 	INTEGER,
	propLaneLecsResilientPriority 	INTEGER
}
        
propLaneLecsSlotIndex OBJECT-TYPE
                SYNTAX INTEGER
                ACCESS read-only
                STATUS mandatory
                DESCRIPTION
                        "An index into this table."
                ::= { propLaneLecsEntry 1 }

propLaneLecsLocation OBJECT-TYPE
                SYNTAX INTEGER
                        {
                        local-wka        (1),
                        local-selector   (2),
                        remote-wka       (3),
                        remote-atm-addr  (4),
                        remote-res-lecs  (5)
                        }
                ACCESS read-write
                STATUS mandatory
                DESCRIPTION
                        "The LECS location.
                         local-wka       - 
                             The LECS is local at the WKA.
                         local-selector  - 
                             The LECS is local.
                         remote-wka      - 
                             The LECS is remote at the WKA.
                         remote-atm-addr - 
                             The LECS is remote at the address given in 
                             RemoteAddress below.
                         remote-res-lecs - 
                             The LECS is a remote resilient LECS, found 
                             at the address given below. By setting location
                             to remote, this implies that this device IS NOT
                             taking part in the resilient LECS scheme itself."
                ::= { propLaneLecsEntry 2 }

        propLaneLecsRemoteAddress OBJECT-TYPE
                SYNTAX AtmAddress
                ACCESS read-write
                STATUS mandatory
                DESCRIPTION
                        "The remote (non-WKA) LECS address."
                ::= {propLaneLecsEntry 3 }

        propLaneLecsLocalSelector OBJECT-TYPE
                SYNTAX INTEGER
                ACCESS read-write
                STATUS mandatory
                DESCRIPTION
                        "The local LECS address selector."
                ::= {propLaneLecsEntry 4 }

        propLaneLecsDefTRElan OBJECT-TYPE
                SYNTAX DisplayString (SIZE (0..32))
                ACCESS read-write
                STATUS mandatory
                DESCRIPTION
                        "The name of the default TR ELAN."
                ::= { propLaneLecsEntry 5 }

        propLaneLecsDefEthElan OBJECT-TYPE
                SYNTAX DisplayString (SIZE (0..32))
                ACCESS read-write
                STATUS mandatory
                DESCRIPTION
                        "The name of the default ethernet ELAN."
                ::= { propLaneLecsEntry 6 }

        propLaneLecsDefUnspecElan OBJECT-TYPE
                SYNTAX DisplayString (SIZE (0..32))
                ACCESS read-write
                STATUS mandatory
                DESCRIPTION
                        "The name of the default unspecified ELAN."
                ::= { propLaneLecsEntry 7 }

        propLaneLecsResilientNetStatus OBJECT-TYPE
                SYNTAX INTEGER
                        {
                        discovering    (1),
                        forming        (2),
                        synchronising  (3),
                        running        (4),
                        not-resilient  (5)
                        }
                ACCESS read-only
                STATUS mandatory
                DESCRIPTION
                        "Status of the resilient LECS network as a whole.
                         discovering   - The algorithm is trying to find all
                                         participating devices in the scheme.
                         forming       - The algorithm is trying to contact
                                         each device.
                         synchronising - The algorithm is checking that all
                                         parties have connectivity to all 
                                         other parties.
                         running       - The scheme is running normally.
                         not-resilient - This device is not taking part in the
                                         resilient scheme."
                ::= { propLaneLecsEntry 8 }

        propLaneLecsResilientMode OBJECT-TYPE
                SYNTAX INTEGER
                        {
                        enabled       (1),
                        disabled      (2)
                        }
                ACCESS read-write
                STATUS mandatory
                DESCRIPTION
                        "Whether this LECS is taking part in the resilient
                         LECS election scheme."
                ::= { propLaneLecsEntry 9 }

        propLaneLecsResilientStatus OBJECT-TYPE
                SYNTAX INTEGER
                        {
                        active        (1),
                        standby       (2),
                        not-resilient (3)
                        }
                ACCESS read-only
                STATUS mandatory
                DESCRIPTION
                        "Status of this LECS in the resilient scheme."
                ::= { propLaneLecsEntry 10 }

        propLaneLecsResilientPriority OBJECT-TYPE
                SYNTAX INTEGER (0..255)
                ACCESS read-write
                STATUS mandatory
                DESCRIPTION
                        "LECS priority in the resilient scheme."
                ::= { propLaneLecsEntry 11 }



-- the propLaneResLecs group

propLaneLecsResTable OBJECT-TYPE
                SYNTAX SEQUENCE OF PropLaneLecsResEntry
                ACCESS not-accessible
                STATUS mandatory
                DESCRIPTION
                        "A table containing information about each LECS
                         in the resilient LECS scheme."
                ::= { propLaneResLecs 1 }
        
propLaneLecsResEntry OBJECT-TYPE
                SYNTAX PropLaneLecsResEntry
                ACCESS not-accessible
                STATUS mandatory
                DESCRIPTION
                        "An entry containing information about a particular
                         LECS in the resilient scheme."
                INDEX { propLaneLecsSlotIndex, propLaneLecsResIndex }
                ::= { propLaneLecsResTable 1 }
        
        PropLaneLecsResEntry ::= SEQUENCE
                {
                propLaneLecsResIndex      INTEGER,
                propLaneLecsResAddress    AtmAddress,
                propLaneLecsResPriority   INTEGER,
                propLaneLecsResStatus     INTEGER,
                propLaneLecsResOrigin     INTEGER,
                propLaneLecsResRowStatus  INTEGER,
                propLaneLecsResActiveTime TimeTicks,
                propLaneLecsResAddrForm   INTEGER,
                propLaneLecsResSelector   INTEGER
                }
        
        propLaneLecsResIndex OBJECT-TYPE
                SYNTAX INTEGER
                ACCESS read-only
                STATUS mandatory
                DESCRIPTION
                        "An index into this table."
                ::= { propLaneLecsResEntry 1 }
        
        propLaneLecsResAddress OBJECT-TYPE
                SYNTAX AtmAddress
                ACCESS read-only
                STATUS mandatory
                DESCRIPTION
                        "The ATM address of this resilient LECS."
                ::= { propLaneLecsResEntry 2 }

        propLaneLecsResPriority OBJECT-TYPE
                SYNTAX INTEGER (0..255)
                ACCESS read-only
                STATUS mandatory
                DESCRIPTION
                        "The priority of this LECS in the scheme."
                ::= { propLaneLecsResEntry 3 }

        propLaneLecsResStatus OBJECT-TYPE
                SYNTAX INTEGER
                        {
                        active         (1),
                        standby        (2),
                        timing-out     (3),
                        not-found      (4)
                        }
                ACCESS read-only
                STATUS mandatory
                DESCRIPTION
                        "The resilient status and link status of this LECS
                         from the viewpoint of this agent.

                         - timing-out means this agent has temporarily failed
                           to contact the LECS.

                         - not-found means that either communication to the 
                           LECS has timed-out, or that the LECS has never 
                           been found."
                ::= { propLaneLecsResEntry 4 }

        propLaneLecsResOrigin OBJECT-TYPE
                SYNTAX INTEGER
                        {
                        manual          (1),
                        pvc-svc         (2),  -- detected through svc to pvc 0.29
                        pvc             (3),  -- discovered through pvc 0.29
                        local           (4),
                        snmp            (5)
                        }
                ACCESS read-only
                STATUS mandatory
                DESCRIPTION
                        "How this LECS was found."
                ::= { propLaneLecsResEntry 5 }

        propLaneLecsResRowStatus OBJECT-TYPE
                SYNTAX INTEGER {
                        delete(1),
                        undercreation(2),
                        valid(3)
                        }
                ACCESS read-only
                STATUS mandatory
                DESCRIPTION
                        "The status of this entry. 
                         For row creation (currently unsupported) :
                         The manager should first set this field to 
                         undercreation(2) before setting any of the other 
                         fields. When all values required have
                         been given it shoud be set to valid(3). If
                         insufficient entries have been given when it is
                         set to valid(3) then the agent will reject the
                         request with BAD_VALUE."
                ::= { propLaneLecsResEntry 6 }

        propLaneLecsResActiveTime OBJECT-TYPE
               SYNTAX      TimeTicks
               ACCESS      read-only
               STATUS      mandatory
               DESCRIPTION
                       "The time in centiseconds since this RLECS last
                        transitioned to active. Only non-zero values
                        are valid here; a zero value meaning that either
                        the RLECS was never active, or that no info is
                        available for it." 
                ::= { propLaneLecsResEntry 7 }

        propLaneLecsResAddrForm OBJECT-TYPE
                SYNTAX INTEGER {
                        wka      (1),
                        selector (2),
                        unknown  (3)
                        }
                ACCESS read-only
                STATUS mandatory
                DESCRIPTION
                        "The type of address that this LECS will use when
                         it is active. Selector means switch address
                         plus the selector given below."
                ::= { propLaneLecsResEntry 8 }

        propLaneLecsResSelector OBJECT-TYPE
               SYNTAX      INTEGER (0..255)
               ACCESS      read-only
               STATUS      mandatory
               DESCRIPTION
                       "The selector if the LECS is using its switch
                        address."
                ::= { propLaneLecsResEntry 9 }



-- the propLaneSlot  group

propLaneSlotTable OBJECT-TYPE
	SYNTAX SEQUENCE OF PropLaneSlotEntry
	ACCESS not-accessible
	STATUS mandatory
	DESCRIPTION
		" A table containing information about a LANE Server in a Slot
		of the ATM switch. "
                ::= { propLaneSlot 1 }

propLaneSlotEntry OBJECT-TYPE
	SYNTAX PropLaneSlotEntry 
	ACCESS not-accessible
	STATUS mandatory
	DESCRIPTION
		"An entry containing information about a particular 
		Slot in the switch. "
	INDEX { propLaneSlotIndex }
	::= { propLaneSlotTable 1}

PropLaneSlotEntry ::= SEQUENCE  
                {
	propLaneSlotIndex			INTEGER,
	propLaneSlotElanConfNextId		INTEGER,
	propLaneSlotLecsConfNextId 		INTEGER,
	propLaneSlotLesConfNextId		INTEGER,
	propLaneSlotBusConfNextId		INTEGER,
	propLaneSlotNextLesSelector             INTEGER, 
	propLaneSlotNextBusSelector             INTEGER,
	propLaneSlotNextLecsSelector            INTEGER
	}
 
propLaneSlotIndex OBJECT-TYPE
	SYNTAX INTEGER
	ACCESS read-only
	STATUS mandatory
	DESCRIPTION
		"Index into this table."
	::= { propLaneSlotEntry 1 }

propLaneSlotElanConfNextId  OBJECT-TYPE
	SYNTAX   INTEGER
	ACCESS    read-only
	STATUS    mandatory
	DESCRIPTION
		"The next available ELAN index in this Slot provided by
		the agent.  The value of this object can be used as the
		index to the standard elanConfTable during creation.
		Instead of the standard elanConfNextId."
	::= { propLaneSlotEntry 2 }

propLaneSlotLecsConfNextId  OBJECT-TYPE
	SYNTAX   INTEGER
	ACCESS    read-only
	STATUS    mandatory
	DESCRIPTION
		"The next available LECS index in this Slot. 
		The value of this object can be used as the index to the
		lecsTable during creation.
		Instead of the standard lecsConfNextId."
	::= { propLaneSlotEntry 3 }

propLaneSlotLesConfNextId  OBJECT-TYPE
	SYNTAX   INTEGER
	ACCESS    read-only
	STATUS    mandatory
	DESCRIPTION
		"The next available LES index in this Slot.
		 The value of this object can be used as the index by the
		network manager to create an entry in the lesConfTable.
		Instead of the standard lesConfNextId."
	::= { propLaneSlotEntry 4 }

propLaneSlotBusConfNextId  OBJECT-TYPE
	SYNTAX     INTEGER
	ACCESS read-only
	STATUS     mandatory
	DESCRIPTION
		"The next available BUS index in this Slot.
		 The value of this object can be used as the index by the
		network manager to create an entry in the busConfTable.
		Instead of the standard busConfNextId."
	::= { propLaneSlotEntry 5 }
 

propLaneSlotNextLesSelector OBJECT-TYPE
        SYNTAX INTEGER
        ACCESS read-only
        STATUS mandatory
        DESCRIPTION
                "A suitable value for the next LES selector in this Slot."
        ::= { propLaneSlotEntry 6 }

propLaneSlotNextBusSelector OBJECT-TYPE
        SYNTAX INTEGER
        ACCESS read-only
        STATUS mandatory
        DESCRIPTION
                "A suitable value for the next BUS selector in this Slot."
        ::= { propLaneSlotEntry 7 }

propLaneSlotNextLecsSelector OBJECT-TYPE
        SYNTAX INTEGER
        ACCESS read-only
        STATUS mandatory
        DESCRIPTION
                "A suitable value for the next LECS selector in this Slot."
        ::= { propLaneSlotEntry 8 }


END
