-- Copyright 1998 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description 
-- 1.00A     28-Apr-98  M. Cyr          Initial Revision

HDSLGT2030-MIB DEFINITIONS ::= BEGIN

IMPORTS
	OBJECT-TYPE			FROM RFC-1212
	DisplayString			FROM RFC1213-MIB
	hdslGT2030                      FROM GDCHDSL-MIB;

hdslGT2030System            OBJECT IDENTIFIER ::= { hdslGT2030 1 }
hdslGT2030Version           OBJECT IDENTIFIER ::= { hdslGT2030System 1 }

-- ***************************************************************************
-- The interfaces are defined as follows:
--	Unit	0
--	DTE	1
--	Loop1	2
--	Loop2   3
-- ***************************************************************************

gdcGT2030SystemMIBversion OBJECT-TYPE
    	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdslGT2030Version 1 }
 
 
 
-- ********************************************************************
-- GDC Hdsl Alarm Object Identifier Definitions
-- ********************************************************************
hdslGT2030Alarms            OBJECT IDENTIFIER ::= { hdslGT2030 2 }

hdslGT2030NoResponseAlm		OBJECT IDENTIFIER ::= { hdslGT2030Alarms 1 }
hdslGT2030DiagRxErrAlm		OBJECT IDENTIFIER ::= { hdslGT2030Alarms 2 }
hdslGT2030PowerUpAlm		OBJECT IDENTIFIER ::= { hdslGT2030Alarms 3 }
hdslGT2030UnitFailure           OBJECT IDENTIFIER ::= { hdslGT2030Alarms 4 }
hdslGT2030ChecksumCorrupt       OBJECT IDENTIFIER ::= { hdslGT2030Alarms 5 }
hdslGT2030LossofSignal		OBJECT IDENTIFIER ::= { hdslGT2030Alarms 6 }
hdslGT2030UnavailableSec	OBJECT IDENTIFIER ::= { hdslGT2030Alarms 7 }
hdslGT2030ErrorSec		OBJECT IDENTIFIER ::= { hdslGT2030Alarms 8 }
hdslGT2030LossofSyncWord	OBJECT IDENTIFIER ::= { hdslGT2030Alarms 9 }
hdslGT2030MajorBER 		OBJECT IDENTIFIER ::= { hdslGT2030Alarms 10 }
hdslGT2030MinorBER 		OBJECT IDENTIFIER ::= { hdslGT2030Alarms 11 }

 
-- ALARM			Maskable	Valid Interfaces
--===============================================================
--hdslNoResponseAlm		No		Unit
--hdslDiagRxErrAlm              No              Unit
--hdslPowerUpAlm		No		Unit
--hdslUnitFailure               No              Unit
--hdslChecksumCorrupt           No              Unit
--hdslLossofSignal              Yes             L1, L2
--hdslUnavailableSec            Yes             L1, L2
--hdslErrorSec                  Yes             L1, L2
--hdslLossofSyncWord		Yes		L1, L2
--hdslGT2030MajorBER		Yes		L1, L2
--hdslGT2030MinorBER		Yes		L1, L2


END
