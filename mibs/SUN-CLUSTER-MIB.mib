--
-- CDDL HEADER START
--
-- The contents of this file are subject to the terms of the
-- Common Development and Distribution License (the License).
-- You may not use this file except in compliance with the License.
--
-- You can obtain a copy of the license at usr/src/CDDL.txt
-- or http://www.opensolaris.org/os/licensing.
-- See the License for the specific language governing permissions
-- and limitations under the License.
--
-- When distributing Covered Code, include this CDDL HEADER in each
-- file and include the License file at usr/src/CDDL.txt.
-- If applicable, add the following below this CDDL HEADER, with the
-- fields enclosed by brackets [] replaced with your own identifying
-- information: Portions Copyright [yyyy] [name of copyright owner]
--
-- CDDL HEADER END
--
-------------------------------------------------------
-- Copyright (c) 2000, 2010, Oracle and/or its affiliates. All rights reserved.
-- 
--
-- ident	"@(#)sun-cluster-mib.mib	1.7	10/03/29 SMI" 
--
-------------------------------------------------------
-- Oracle Solaris Cluster 3.x
-------------------------------------------------------
SUN-CLUSTER-MIB DEFINITIONS ::= BEGIN

  IMPORTS
        enterprises, MODULE-IDENTITY, OBJECT-TYPE, Counter64, Integer32
                FROM SNMPv2-SMI
         OBJECT-GROUP
                FROM SNMPv2-CONF
         DisplayString, RowStatus
               FROM SNMPv2-TC;

sunclustermod MODULE-IDENTITY
    LAST-UPDATED "0005051256Z"
    ORGANIZATION "Oracle Corporation"
    CONTACT-INFO
        "       Oracle Corporation 
       Customer Support
            Postal: 500 Oracle Parkway
       Redwood Shores, CA-94065
    USA
                         Tel: +1-650-960-7000"
    DESCRIPTION
        "Oracle Solaris Cluster MIB monitors and manages Oracle Solaris Cluster 3.x configuration."

    ::= { modules 1 }

sun       	OBJECT IDENTIFIER ::= { enterprises 42 }
prod      	OBJECT IDENTIFIER ::= { sun 2 }
suncluster	OBJECT IDENTIFIER ::= { prod 80 }
sunmc		OBJECT IDENTIFIER ::= { suncluster 1 }
modules		OBJECT IDENTIFIER ::= { sunmc 1 }

--***

clusterInfo	OBJECT IDENTIFIER ::= { sunclustermod 1 }
nodes		OBJECT IDENTIFIER ::= { sunclustermod 2 }
deviceGroups	OBJECT IDENTIFIER ::= { sunclustermod 3 }
quorumDevices	OBJECT IDENTIFIER ::= { sunclustermod 4 }
transport	OBJECT IDENTIFIER ::= { sunclustermod 5 }
resourceGroups	OBJECT IDENTIFIER ::= { sunclustermod 6 }
resourceTypes	OBJECT IDENTIFIER ::= { sunclustermod 7 }

clusterStatus	OBJECT IDENTIFIER ::= { clusterInfo 1 }
clusterConfiguration	OBJECT IDENTIFIER ::= { clusterInfo 2 }

nodeStatus	OBJECT IDENTIFIER ::= { nodes 1 }
nodeConfiguration	OBJECT IDENTIFIER ::= { nodes 2 }

deviceGroupsStatus	OBJECT IDENTIFIER ::= { deviceGroups 1 }
deviceGroupsConfiguration	OBJECT IDENTIFIER ::= { deviceGroups 2 }

quorumDevicesStatus	OBJECT IDENTIFIER ::= { quorumDevices 1 }
quorumDevicesConfiguration OBJECT IDENTIFIER ::= { quorumDevices 2 }

transportStatus		OBJECT IDENTIFIER ::= { transport 1 }
transportConfiguration OBJECT IDENTIFIER ::= { transport 2 }

rgStatus		OBJECT IDENTIFIER ::= { resourceGroups 1 }
rgConfiguration		OBJECT IDENTIFIER ::= { resourceGroups 2 }	

foRgStatusBranch	OBJECT IDENTIFIER ::= { rgStatus 1 }
scRgStatusBranch	OBJECT IDENTIFIER ::= { rgStatus 2 }

foRgConfigBranch	OBJECT IDENTIFIER ::= { rgConfiguration 1 }
forgConfigInfo		OBJECT IDENTIFIER ::= { foRgConfigBranch 3 }
foRsConfigBranch	OBJECT IDENTIFIER ::= { foRgConfigBranch 4 }
foRsConfigGen		OBJECT IDENTIFIER ::= {	foRsConfigBranch 1 }
foRsConfigStandProps	OBJECT IDENTIFIER ::= {	foRsConfigBranch 2 }
foRsConfigExtProps	OBJECT IDENTIFIER ::= {	foRsConfigBranch 3 }
foRsConfigMethods	OBJECT IDENTIFIER ::= {	foRsConfigBranch 4 }


scRgConfigBranch	OBJECT IDENTIFIER ::= { rgConfiguration 2 }
scrgConfigInfo		OBJECT IDENTIFIER ::= { scRgConfigBranch 3 }
scRsConfigBranch	OBJECT IDENTIFIER ::= { scRgConfigBranch 4 }
scRsConfigGen		OBJECT IDENTIFIER ::= {	scRsConfigBranch 1 }
scRsConfigStandProps	OBJECT IDENTIFIER ::= {	scRsConfigBranch 2 }
scRsConfigExtProps	OBJECT IDENTIFIER ::= {	scRsConfigBranch 3 }
scRsConfigMethods	OBJECT IDENTIFIER ::= {	scRsConfigBranch 4 }

definitionBranch	OBJECT IDENTIFIER ::= { resourceTypes 1 }
resourceList		OBJECT IDENTIFIER ::= { resourceTypes 2 }
rtOverview		OBJECT IDENTIFIER ::= { definitionBranch 1 }
rtMethodProps		OBJECT IDENTIFIER ::= { definitionBranch 2 }
rtParams		OBJECT IDENTIFIER ::= { definitionBranch 3 }


--*** cluster info subtree

clsClusterName OBJECT-TYPE
    SYNTAX      DisplayString
    MAX-ACCESS  read-only
    STATUS      current
    DESCRIPTION
                "Cluster name"
    ::= { clusterStatus 1 }

clsMinVotesRequired OBJECT-TYPE
    SYNTAX      Integer32
    MAX-ACCESS  read-only
    STATUS      current
    DESCRIPTION
                "Minimum votes required to get cluster quorum"
    ::= { clusterStatus 2 }

clsCurrentVotes OBJECT-TYPE
    SYNTAX      Integer32
    MAX-ACCESS  read-only
    STATUS      current
    DESCRIPTION
                "Integer value"
    ::= { clusterStatus 3 }

clcClusterName OBJECT-TYPE
    SYNTAX      DisplayString
    MAX-ACCESS  read-only
    STATUS      current
    DESCRIPTION
                "Character string value"
    ::= { clusterConfiguration 1 }

clcInstallMode OBJECT-TYPE
    SYNTAX      DisplayString
    MAX-ACCESS  read-only
    STATUS      current
    DESCRIPTION
                "Character string value"
    ::= { clusterConfiguration 2 }

clcPrivateNetAddr OBJECT-TYPE
    SYNTAX      DisplayString
    MAX-ACCESS  read-only
    STATUS      current
    DESCRIPTION
                "Character string value"
    ::= { clusterConfiguration 3 }

clcPrivateNetMask OBJECT-TYPE
    SYNTAX      DisplayString
    MAX-ACCESS  read-only
    STATUS      current
    DESCRIPTION
                "Character string value"
    ::= { clusterConfiguration 4 }

clcAddNodeAuthType OBJECT-TYPE
    SYNTAX      DisplayString
    MAX-ACCESS  read-only
    STATUS      current
    DESCRIPTION
                "Character string value"
    ::= { clusterConfiguration 5 }

clcAddNodeAuthList OBJECT-TYPE
    SYNTAX      DisplayString
    MAX-ACCESS  read-only
    STATUS      current
    DESCRIPTION
                "Character string value"
    ::= { clusterConfiguration 6 }


--*** node subtree

nodeTable OBJECT-TYPE
    SYNTAX      SEQUENCE OF NodeTableEntry
    MAX-ACCESS  not-accessible
    STATUS      current
    DESCRIPTION
                "MIB tree branch"
    ::= { nodeStatus 1 }

nodeDeviceTable OBJECT-TYPE
    SYNTAX      SEQUENCE OF NodeDeviceTableEntry
    MAX-ACCESS  not-accessible
    STATUS      current
    DESCRIPTION
                "MIB tree branch"
    ::= { nodeStatus 2 }

nodeConfigTable OBJECT-TYPE
    SYNTAX      SEQUENCE OF NodeConfigTableEntry
    MAX-ACCESS  not-accessible
    STATUS      current
    DESCRIPTION
                "MIB tree branch"
    ::= { nodeConfiguration 1 }

nodeDeviceConfigTable OBJECT-TYPE
    SYNTAX      SEQUENCE OF NodeDeviceConfigTableEntry
    MAX-ACCESS  not-accessible
    STATUS      current
    DESCRIPTION
                "MIB tree branch"
    ::= { nodeConfiguration 2 }

--*** 

nodeTableEntry OBJECT-TYPE
    SYNTAX      NodeTableEntry
    MAX-ACCESS  not-accessible
    STATUS      current
    DESCRIPTION
                "MIB tree branch"
    INDEX  { ndsNodeName }
    ::= { nodeTable 1 }

NodeTableEntry ::=
    SEQUENCE {
        ndsNodeName
            DisplayString,
        ndsStatus
            DisplayString,
        ndsCurrentNodeVotes
            Integer32
    }

ndsNodeName OBJECT-TYPE
    SYNTAX      DisplayString
    MAX-ACCESS  read-only
    STATUS      current
    DESCRIPTION
                "Character string value"
    ::= { nodeTableEntry 1 }

ndsStatus OBJECT-TYPE
    SYNTAX      DisplayString
    MAX-ACCESS  read-only
    STATUS      current
    DESCRIPTION
                "Character string value"
    ::= { nodeTableEntry 2 }

ndsCurrentNodeVotes OBJECT-TYPE
    SYNTAX      Integer32
    MAX-ACCESS  read-only
    STATUS      current
    DESCRIPTION
                "Integer value"
    ::= { nodeTableEntry 3 }

--***

nodeDeviceTableEntry OBJECT-TYPE
    SYNTAX      NodeDeviceTableEntry
    MAX-ACCESS  not-accessible
    STATUS      current
    DESCRIPTION
                "MIB tree branch"
    INDEX  { ddsNodeName }
    ::= { nodeDeviceTable 1 }

NodeDeviceTableEntry ::=
    SEQUENCE {
        ddsNodeName
            DisplayString,
        ddsMasteredDeviceGroupList
            DisplayString,
        ddsMasteredRGList
            DisplayString
    }

ddsNodeName OBJECT-TYPE
    SYNTAX      DisplayString
    MAX-ACCESS  read-only
    STATUS      current
    DESCRIPTION
                "Character string value"
    ::= { nodeDeviceTableEntry 1 }

ddsMasteredDeviceGroupList OBJECT-TYPE
    SYNTAX      DisplayString
    MAX-ACCESS  read-only
    STATUS      current
    DESCRIPTION
                "Character string value"
    ::= { nodeDeviceTableEntry 2 }

ddsMasteredRGList OBJECT-TYPE
    SYNTAX      DisplayString
    MAX-ACCESS  read-only
    STATUS      current
    DESCRIPTION
                "Character string value"
    ::= { nodeDeviceTableEntry 3 }

--***

nodeConfigTableEntry OBJECT-TYPE
    SYNTAX      NodeConfigTableEntry
    MAX-ACCESS  not-accessible
    STATUS      current
    DESCRIPTION
                "MIB tree branch"
    INDEX  { ndcNodeName }
    ::= { nodeConfigTable 1 }

NodeConfigTableEntry ::=
    SEQUENCE {
        ndcNodeName
            DisplayString,
	ndcDefaultVotes
            Integer32,
        ndcPrivateNetHostname
            DisplayString,
        ndcTransportAdapterList
            DisplayString
    }

ndcNodeName OBJECT-TYPE
    SYNTAX      DisplayString
    MAX-ACCESS  read-only
    STATUS      current
    DESCRIPTION
                "Character string value"
    ::= { nodeConfigTableEntry 1 }

ndcDefaultVotes	OBJECT-TYPE
    SYNTAX      Integer32
    MAX-ACCESS  read-only
    STATUS      current
    DESCRIPTION
                "Integer value"
    ::= { nodeConfigTableEntry 2 }

ndcPrivateNetHostname OBJECT-TYPE
    SYNTAX      DisplayString
    MAX-ACCESS  read-only
    STATUS      current
    DESCRIPTION
                "Character string value"
    ::= { nodeConfigTableEntry 3 }

ndcTransportAdapterList OBJECT-TYPE
    SYNTAX      DisplayString
    MAX-ACCESS  read-only
    STATUS      current
    DESCRIPTION
                "Character string value"
    ::= { nodeConfigTableEntry 4 }

--***

nodeDeviceConfigTableEntry OBJECT-TYPE
    SYNTAX      NodeDeviceConfigTableEntry
    MAX-ACCESS  not-accessible
    STATUS      current
    DESCRIPTION
                "MIB tree branch"
    INDEX  { ddcNodeName }
    ::= { nodeDeviceConfigTable 1 }

NodeDeviceConfigTableEntry ::=
    SEQUENCE {
        ddcNodeName
            DisplayString,
	ddcQuorumDeviceList
            DisplayString,
        ddcPossibleMasteredDeviceGroupList
            DisplayString,
        ddcPossibleMasteredRGList
            DisplayString
    }

ddcNodeName OBJECT-TYPE
    SYNTAX      DisplayString
    MAX-ACCESS  read-only
    STATUS      current
    DESCRIPTION
                "Character string value"
    ::= { nodeDeviceConfigTableEntry 1 }

ddcQuorumDeviceList	OBJECT-TYPE
    SYNTAX      DisplayString
    MAX-ACCESS  read-only
    STATUS      current
    DESCRIPTION
                "Character string value"
    ::= { nodeDeviceConfigTableEntry 2 }

ddcPossibleMasteredDeviceGroupList OBJECT-TYPE
    SYNTAX      DisplayString
    MAX-ACCESS  read-only
    STATUS      current
    DESCRIPTION
                "Character string value"
    ::= { nodeDeviceConfigTableEntry 3 }

ddcPossibleMasteredRGList OBJECT-TYPE
    SYNTAX      DisplayString
    MAX-ACCESS  read-only
    STATUS      current
    DESCRIPTION
                "Character string value"
    ::= { nodeDeviceConfigTableEntry 4 }

--*** device groups subtree

deviceGroupTable OBJECT-TYPE
    SYNTAX      SEQUENCE OF DeviceGroupTableEntry
    MAX-ACCESS  not-accessible
    STATUS      current
    DESCRIPTION
                "MIB tree branch"
    ::= { deviceGroupsStatus 1 }

deviceGroupTableEntry OBJECT-TYPE
    SYNTAX      DeviceGroupTableEntry
    MAX-ACCESS  not-accessible
    STATUS      current
    DESCRIPTION
                "MIB tree branch"
    INDEX  { dgsDeviceGroupName }
    ::= { deviceGroupTable 1 }

DeviceGroupTableEntry ::=
    SEQUENCE {
        dgsDeviceGroupName
            DisplayString,
        dgsDeviceGroupStatus
            DisplayString,
        dgsDeviceGroupPrimaryList
            DisplayString
    }

dgsDeviceGroupName OBJECT-TYPE
    SYNTAX      DisplayString
    MAX-ACCESS  read-only
    STATUS      current
    DESCRIPTION
                "Character string value"
    ::= { deviceGroupTableEntry 1 }

dgsDeviceGroupStatus OBJECT-TYPE
    SYNTAX      DisplayString
    MAX-ACCESS  read-only
    STATUS      current
    DESCRIPTION
                "Character string value"
    ::= { deviceGroupTableEntry 2 }

dgsDeviceGroupPrimaryList OBJECT-TYPE
    SYNTAX      DisplayString
    MAX-ACCESS  read-only
    STATUS      current
    DESCRIPTION
                "Character string value"
    ::= { deviceGroupTableEntry 3 }

--***

replicaTable OBJECT-TYPE
    SYNTAX      SEQUENCE OF ReplicaTableEntry
    MAX-ACCESS  not-accessible
    STATUS      current
    DESCRIPTION
                "MIB tree branch"
    ::= { deviceGroupsStatus 2 }

replicaTableEntry OBJECT-TYPE
    SYNTAX      ReplicaTableEntry
    MAX-ACCESS  not-accessible
    STATUS      current
    DESCRIPTION
                "MIB tree branch"
    INDEX  { rpsDeviceGroupName,
              rpsNodeName }
    ::= { replicaTable 1 }

ReplicaTableEntry ::=
    SEQUENCE {
        rpsDeviceGroupName
            DisplayString,
        rpsNodeName
            DisplayString,
        rpsStatus
            DisplayString
    }

rpsDeviceGroupName OBJECT-TYPE
    SYNTAX      DisplayString
    MAX-ACCESS  read-only
    STATUS      current
    DESCRIPTION
                "Character string value"
    ::= { replicaTableEntry 1 }

rpsNodeName OBJECT-TYPE
    SYNTAX      DisplayString
    MAX-ACCESS  read-only
    STATUS      current
    DESCRIPTION
                "Character string value"
    ::= { replicaTableEntry 2 }

rpsStatus OBJECT-TYPE
    SYNTAX      DisplayString
    MAX-ACCESS  read-only
    STATUS      current
    DESCRIPTION
                "Character string value"
    ::= { replicaTableEntry 3 }

--***

deviceGroupConfigTable OBJECT-TYPE
    SYNTAX      SEQUENCE OF DeviceGroupTableEntry
    MAX-ACCESS  not-accessible
    STATUS      current
    DESCRIPTION
                "MIB tree branch"
    ::= { deviceGroupsConfiguration 1 }

deviceGroupConfigTableEntry OBJECT-TYPE
    SYNTAX      DeviceGroupConfigTableEntry
    MAX-ACCESS  not-accessible
    STATUS      current
    DESCRIPTION
                "MIB tree branch"
    INDEX  { dgcDeviceGroupName }
    ::= { deviceGroupConfigTable 1 }

DeviceGroupConfigTableEntry ::=
    SEQUENCE {
        dgcDeviceGroupName
            DisplayString,
        dgcServiceType
            DisplayString,
        dgcFailback
            DisplayString,
        dgcNodeList
            DisplayString,
        dgcNodeOrder
            DisplayString,
        dgcDeviceList
            DisplayString
    }

dgcDeviceGroupName OBJECT-TYPE
    SYNTAX      DisplayString
    MAX-ACCESS  read-only
    STATUS      current
    DESCRIPTION
                "Character string value"
    ::= { deviceGroupConfigTableEntry 1 }

dgcServiceType OBJECT-TYPE
    SYNTAX      DisplayString
    MAX-ACCESS  read-only
    STATUS      current
    DESCRIPTION
                "Character string value"
    ::= { deviceGroupConfigTableEntry 2 }

dgcFailback OBJECT-TYPE
    SYNTAX      DisplayString
    MAX-ACCESS  read-only
    STATUS      current
    DESCRIPTION
                "Character string value"
    ::= { deviceGroupConfigTableEntry 3 }


dgcNodeList OBJECT-TYPE
    SYNTAX      DisplayString
    MAX-ACCESS  read-only
    STATUS      current
    DESCRIPTION
                "Character string value"
    ::= { deviceGroupConfigTableEntry 4 }

dgcNodeOrder OBJECT-TYPE
    SYNTAX      DisplayString
    MAX-ACCESS  read-only
    STATUS      current
    DESCRIPTION
                "Character string value"
    ::= { deviceGroupConfigTableEntry 5 }

dgcDeviceList OBJECT-TYPE
    SYNTAX      DisplayString
    MAX-ACCESS  read-only
    STATUS      current
    DESCRIPTION
                "Character string value"
    ::= { deviceGroupConfigTableEntry 6 }


--*** quorum devices subtree

quorumDeviceTable OBJECT-TYPE
    SYNTAX      SEQUENCE OF QuorumDeviceTableEntry
    MAX-ACCESS  not-accessible
    STATUS      current
    DESCRIPTION
                "MIB tree branch"
    ::= { quorumDevicesStatus 1 }

quorumDeviceTableEntry OBJECT-TYPE
    SYNTAX      QuorumDeviceTableEntry
    MAX-ACCESS  not-accessible
    STATUS      current
    DESCRIPTION
                "MIB tree branch"
    INDEX  { qdsQuorumDeviceName }
    ::= { quorumDeviceTable 1 }

QuorumDeviceTableEntry ::=
    SEQUENCE {
        qdsQuorumDeviceName
            DisplayString,
        qdsStatus
            DisplayString,
        qdsCurrentVotes
            Integer32,
        qdsOwnerNode
            DisplayString
    }

qdsQuorumDeviceName OBJECT-TYPE
    SYNTAX      DisplayString
    MAX-ACCESS  read-only
    STATUS      current
    DESCRIPTION
                "Character string value"
    ::= { quorumDeviceTableEntry 1 }

qdsStatus OBJECT-TYPE
    SYNTAX      DisplayString
    MAX-ACCESS  read-only
    STATUS      current
    DESCRIPTION
                "Character string value"
    ::= { quorumDeviceTableEntry 2 }

qdsCurrentVotes OBJECT-TYPE
    SYNTAX      Integer32
    MAX-ACCESS  read-only
    STATUS      current
    DESCRIPTION
                "Integer value"
    ::= { quorumDeviceTableEntry 3 }

qdsOwnerNode OBJECT-TYPE
    SYNTAX      DisplayString
    MAX-ACCESS  read-only
    STATUS      current
    DESCRIPTION
                "Character string value"
    ::= { quorumDeviceTableEntry 4 }

--***

quorumDeviceConfigTable OBJECT-TYPE
    SYNTAX      SEQUENCE OF QuorumDeviceConfigTableEntry
    MAX-ACCESS  not-accessible
    STATUS      current
    DESCRIPTION
                "MIB tree branch"
    ::= { quorumDevicesConfiguration 1 }

quorumDeviceConfigTableEntry OBJECT-TYPE
    SYNTAX      QuorumDeviceConfigTableEntry
    MAX-ACCESS  not-accessible
    STATUS      current
    DESCRIPTION
                "MIB tree branch"
    INDEX  { qdcQuorumDeviceName }
    ::= { quorumDeviceConfigTable 1 }

QuorumDeviceConfigTableEntry ::=
    SEQUENCE {
        qdcQuorumDeviceName
            DisplayString,
        qdcQuorumDevicePath
            DisplayString,
        qdcEnabled
            DisplayString,
        qdcDefaultVotes
            Integer32,
        qdcPortList
            DisplayString
    }

qdcQuorumDeviceName OBJECT-TYPE
    SYNTAX      DisplayString
    MAX-ACCESS  read-only
    STATUS      current
    DESCRIPTION
                "Character string value"
    ::= { quorumDeviceConfigTableEntry 1 }

qdcQuorumDevicePath OBJECT-TYPE
    SYNTAX      DisplayString
    MAX-ACCESS  read-only
    STATUS      current
    DESCRIPTION
                "Character string value"
    ::= { quorumDeviceConfigTableEntry 2 }

qdcEnabled OBJECT-TYPE
    SYNTAX      DisplayString
    MAX-ACCESS  read-only
    STATUS      current
    DESCRIPTION
                "Character string value"
    ::= { quorumDeviceConfigTableEntry 3 }

qdcDefaultVotes OBJECT-TYPE
    SYNTAX      Integer32
    MAX-ACCESS  read-only
    STATUS      current
    DESCRIPTION
                "Integer value"
    ::= { quorumDeviceConfigTableEntry 4 }

qdcPortList OBJECT-TYPE
    SYNTAX      DisplayString
    MAX-ACCESS  read-only
    STATUS      current
    DESCRIPTION
                "Character string value"
    ::= { quorumDeviceConfigTableEntry 5 }

quorumDevicePortConfigTable OBJECT-TYPE
    SYNTAX      SEQUENCE OF QuorumDevicePortConfigTableEntry
    MAX-ACCESS  not-accessible
    STATUS      current
    DESCRIPTION
                "MIB tree branch"
    ::= { quorumDevicesConfiguration 2 }

quorumDevicePortConfigTableEntry OBJECT-TYPE
    SYNTAX      QuorumDevicePortConfigTableEntry
    MAX-ACCESS  not-accessible
    STATUS      current
    DESCRIPTION
                "MIB tree branch"
    INDEX  { qpcQuorumDeviceName,
              qpcQuorumDeviceHost }
    ::= { quorumDevicePortConfigTable 1 }

QuorumDevicePortConfigTableEntry ::=
    SEQUENCE {
        qpcQuorumDeviceName
            DisplayString,
        qpcQuorumDeviceHost
            DisplayString,
        qpcEnabled
            DisplayString
    }

qpcQuorumDeviceName OBJECT-TYPE
    SYNTAX      DisplayString
    MAX-ACCESS  read-only
    STATUS      current
    DESCRIPTION
                "Character string value"
    ::= { quorumDevicePortConfigTableEntry 1 }

qpcQuorumDeviceHost OBJECT-TYPE
    SYNTAX      DisplayString
    MAX-ACCESS  read-only
    STATUS      current
    DESCRIPTION
                "Character string value"
    ::= { quorumDevicePortConfigTableEntry 2 }

qpcEnabled OBJECT-TYPE
    SYNTAX      DisplayString
    MAX-ACCESS  read-only
    STATUS      current
    DESCRIPTION
                "Character string value"
    ::= { quorumDevicePortConfigTableEntry 3 }


--*** transport subtree

pathTable OBJECT-TYPE
    SYNTAX      SEQUENCE OF PathTableEntry
    MAX-ACCESS  not-accessible
    STATUS      current
    DESCRIPTION
                "MIB tree branch"
    ::= { transportStatus 1 }

pathTableEntry OBJECT-TYPE
    SYNTAX      PathTableEntry
    MAX-ACCESS  not-accessible
    STATUS      current
    DESCRIPTION
                "MIB tree branch"
    INDEX  { ptsAdapterName1,
              ptsAdapterName2 }
    ::= { pathTable 1 }

PathTableEntry ::=
    SEQUENCE {
        ptsAdapterName1
            DisplayString,
        ptsAdapterName2
            DisplayString,
        ptsStatus
            DisplayString
    }

ptsAdapterName1 OBJECT-TYPE
    SYNTAX      DisplayString
    MAX-ACCESS  read-only
    STATUS      current
    DESCRIPTION
                "Character string value"
    ::= { pathTableEntry 1 }

ptsAdapterName2 OBJECT-TYPE
    SYNTAX      DisplayString
    MAX-ACCESS  read-only
    STATUS      current
    DESCRIPTION
                "Character string value"
    ::= { pathTableEntry 2 }

ptsStatus OBJECT-TYPE
    SYNTAX      DisplayString
    MAX-ACCESS  read-only
    STATUS      current
    DESCRIPTION
                "Character string value"
    ::= { pathTableEntry 3 }

--***

adapterConfigTable OBJECT-TYPE
    SYNTAX      SEQUENCE OF AdapterConfigTableEntry
    MAX-ACCESS  not-accessible
    STATUS      current
    DESCRIPTION
                "MIB tree branch"
    ::= { transportConfiguration 1 }

adapterConfigTableEntry OBJECT-TYPE
    SYNTAX      AdapterConfigTableEntry
    MAX-ACCESS  not-accessible
    STATUS      current
    DESCRIPTION
                "MIB tree branch"
    INDEX  { adcNodeName,
              adcAdapterName }
    ::= { adapterConfigTable 1 }

AdapterConfigTableEntry ::=
    SEQUENCE {
        adcNodeName
            DisplayString,
        adcAdapterName
            DisplayString,
        adcType
            DisplayString,
        adcEnabled
            DisplayString
    }

adcNodeName OBJECT-TYPE
    SYNTAX      DisplayString
    MAX-ACCESS  read-only
    STATUS      current
    DESCRIPTION
                "Character string value"
    ::= { adapterConfigTableEntry 1 }

adcAdapterName OBJECT-TYPE
    SYNTAX      DisplayString
    MAX-ACCESS  read-only
    STATUS      current
    DESCRIPTION
                "Character string value"
    ::= { adapterConfigTableEntry 2 }

adcType OBJECT-TYPE
    SYNTAX      DisplayString
    MAX-ACCESS  read-only
    STATUS      current
    DESCRIPTION
                "Character string value"
    ::= { adapterConfigTableEntry 3 }

adcEnabled OBJECT-TYPE
    SYNTAX      DisplayString
    MAX-ACCESS  read-only
    STATUS      current
    DESCRIPTION
                "Character string value"
    ::= { adapterConfigTableEntry 4 }

--***

junctionConfigTable OBJECT-TYPE
    SYNTAX      SEQUENCE OF JunctionConfigTableEntry
    MAX-ACCESS  not-accessible
    STATUS      current
    DESCRIPTION
                "MIB tree branch"
    ::= { transportConfiguration 2 }

junctionConfigTableEntry OBJECT-TYPE
    SYNTAX      JunctionConfigTableEntry
    MAX-ACCESS  not-accessible
    STATUS      current
    DESCRIPTION
                "MIB tree branch"
    INDEX  { jncJunctionName }
    ::= { junctionConfigTable 1 }

JunctionConfigTableEntry ::=
    SEQUENCE {
        jncJunctionName
            DisplayString,
        jncType
            DisplayString,
        jncEnabled
            DisplayString,
        jncPortList
            DisplayString
    }

jncJunctionName OBJECT-TYPE
    SYNTAX      DisplayString
    MAX-ACCESS  read-only
    STATUS      current
    DESCRIPTION
                "Character string value"
    ::= { junctionConfigTableEntry 1 }

jncType OBJECT-TYPE
    SYNTAX      DisplayString
    MAX-ACCESS  read-only
    STATUS      current
    DESCRIPTION
                "Character string value"
    ::= { junctionConfigTableEntry 2 }

jncEnabled OBJECT-TYPE
    SYNTAX      DisplayString
    MAX-ACCESS  read-only
    STATUS      current
    DESCRIPTION
                "Character string value"
    ::= { junctionConfigTableEntry 3 }

jncPortList OBJECT-TYPE
    SYNTAX      DisplayString
    MAX-ACCESS  read-only
    STATUS      current
    DESCRIPTION
                "Character string value"
    ::= { junctionConfigTableEntry 4 }

--***

cableConfigTable OBJECT-TYPE
    SYNTAX      SEQUENCE OF CableConfigTableEntry
    MAX-ACCESS  not-accessible
    STATUS      current
    DESCRIPTION
                "MIB tree branch"
    ::= { transportConfiguration 3 }

cableConfigTableEntry OBJECT-TYPE
    SYNTAX      CableConfigTableEntry
    MAX-ACCESS  not-accessible
    STATUS      current
    DESCRIPTION
                "MIB tree branch"
    INDEX  { cbcEndType1,
              cbcEndpoint1,
              cbcEndType2,
              cbcEndpoint2 }
    ::= { cableConfigTable 1 }

CableConfigTableEntry ::=
    SEQUENCE {
        cbcEndType1
            DisplayString,
        cbcEndpoint1
            DisplayString,
        cbcEndType2
            DisplayString,
        cbcEndpoint2
            DisplayString,
        cbcEnabled
            DisplayString
    }

cbcEndType1 OBJECT-TYPE
    SYNTAX      DisplayString
    MAX-ACCESS  read-only
    STATUS      current
    DESCRIPTION
                "Character string value"
    ::= { cableConfigTableEntry 1 }

cbcEndpoint1 OBJECT-TYPE
    SYNTAX      DisplayString
    MAX-ACCESS  read-only
    STATUS      current
    DESCRIPTION
                "Character string value"
    ::= { cableConfigTableEntry 2 }

cbcEndType2 OBJECT-TYPE
    SYNTAX      DisplayString
    MAX-ACCESS  read-only
    STATUS      current
    DESCRIPTION
                "Character string value"
    ::= { cableConfigTableEntry 3 }

cbcEndpoint2 OBJECT-TYPE
    SYNTAX      DisplayString
    MAX-ACCESS  read-only
    STATUS      current
    DESCRIPTION
                "Character string value"
    ::= { cableConfigTableEntry 4 }

cbcEnabled OBJECT-TYPE
    SYNTAX      DisplayString
    MAX-ACCESS  read-only
    STATUS      current
    DESCRIPTION
                "Character string value"
    ::= { cableConfigTableEntry 5 }

--*** rg subtree

forgStatusTable OBJECT-TYPE
    SYNTAX      SEQUENCE OF ForgStatusTableEntry
    MAX-ACCESS  not-accessible
    STATUS      current
    DESCRIPTION
                "MIB tree branch"
    ::= { foRgStatusBranch 1 }

forgStatusTableEntry OBJECT-TYPE
    SYNTAX      ForgStatusTableEntry
    MAX-ACCESS  not-accessible
    STATUS      current
    DESCRIPTION
                "MIB tree branch"
    INDEX  { frgName,
              frgPrim }
    ::= { forgStatusTable 1 }

ForgStatusTableEntry ::=
    SEQUENCE {
	frgRowStatus
            DisplayString,
        frgName
            DisplayString,
        frgPrim
            DisplayString,
        frgPrimStatus
            DisplayString,
        frgState
            DisplayString
    }

frgRowStatus OBJECT-TYPE
    SYNTAX      DisplayString
    MAX-ACCESS  not-accessible
    STATUS      current
    DESCRIPTION
                "Character string value"
    ::= { forgStatusTableEntry 1 }

frgName OBJECT-TYPE
    SYNTAX      DisplayString
    MAX-ACCESS  read-only
    STATUS      current
    DESCRIPTION
                "Character string value"
    ::= { forgStatusTableEntry 2 }

frgPrim OBJECT-TYPE
    SYNTAX      DisplayString
    MAX-ACCESS  read-only
    STATUS      current
    DESCRIPTION
                "Character string value"
    ::= { forgStatusTableEntry 3 }

frgPrimStatus OBJECT-TYPE
    SYNTAX      DisplayString
    MAX-ACCESS  read-only
    STATUS      current
    DESCRIPTION
                "Character string value"
    ::= { forgStatusTableEntry 4 }

frgState OBJECT-TYPE
    SYNTAX      DisplayString
    MAX-ACCESS  read-only
    STATUS      current
    DESCRIPTION
                "Character string value"
    ::= { forgStatusTableEntry 5 }

--***

frsStatusTable OBJECT-TYPE
    SYNTAX      SEQUENCE OF FrsStatusTableEntry
    MAX-ACCESS  not-accessible
    STATUS      current
    DESCRIPTION
                "MIB tree branch"
    ::= { foRgStatusBranch 2 }

frsStatusTableEntry OBJECT-TYPE
    SYNTAX      FrsStatusTableEntry
    MAX-ACCESS  not-accessible
    STATUS      current
    DESCRIPTION
                "MIB tree branch"
    INDEX  { frsRgName,
              frsRsName,
              frsRsPrim }
    ::= { frsStatusTable 1 }

FrsStatusTableEntry ::=
    SEQUENCE {
        frsRowstatus
            RowStatus,
        frsRgName
            DisplayString,
        frsRsName
            DisplayString,
        frsRsPrim
            DisplayString,
        frsRsPrimStatus
            DisplayString,
        frsRsFMStatus
            DisplayString,
        frsRsRGMState
            DisplayString
    }

frsRowstatus OBJECT-TYPE
    SYNTAX      RowStatus
    MAX-ACCESS  not-accessible
    STATUS      current
    DESCRIPTION
                "Table row status"
    ::= { frsStatusTableEntry 1 }

frsRgName OBJECT-TYPE
    SYNTAX      DisplayString
    MAX-ACCESS  read-only
    STATUS      current
    DESCRIPTION
                "Character string value"
    ::= { frsStatusTableEntry 2 }

frsRsName OBJECT-TYPE
    SYNTAX      DisplayString
    MAX-ACCESS  read-only
    STATUS      current
    DESCRIPTION
                "Character string value"
    ::= { frsStatusTableEntry 3 }

frsRsPrim OBJECT-TYPE
    SYNTAX      DisplayString
    MAX-ACCESS  read-only
    STATUS      current
    DESCRIPTION
                "Character string value"
    ::= { frsStatusTableEntry 4 }

frsRsPrimStatus OBJECT-TYPE
    SYNTAX      DisplayString
    MAX-ACCESS  read-only
    STATUS      current
    DESCRIPTION
                "Character string value"
    ::= { frsStatusTableEntry 5 }

frsRsFMStatus OBJECT-TYPE
    SYNTAX      DisplayString
    MAX-ACCESS  read-only
    STATUS      current
    DESCRIPTION
                "Character string value"
    ::= { frsStatusTableEntry 6 }

frsRsRGMState OBJECT-TYPE
    SYNTAX      DisplayString
    MAX-ACCESS  read-only
    STATUS      current
    DESCRIPTION
                "Character string value"
    ::= { frsStatusTableEntry 7 }

--*** scalable status info

scrgStatusTable OBJECT-TYPE
    SYNTAX      SEQUENCE OF ForgStatusTableEntry
    MAX-ACCESS  not-accessible
    STATUS      current
    DESCRIPTION
                "MIB tree branch"
    ::= { scRgStatusBranch 1 }

scrgStatusTableEntry OBJECT-TYPE
    SYNTAX      ScrgStatusTableEntry
    MAX-ACCESS  not-accessible
    STATUS      current
    DESCRIPTION
                "MIB tree branch"
    INDEX  { srgName,
              srgPrim }
    ::= { scrgStatusTable 1 }

ScrgStatusTableEntry ::=
    SEQUENCE {
        srgRowstatus
            RowStatus,
        srgName
            DisplayString,
        srgPrim
            DisplayString,
        srgPrimStatus
            DisplayString,
        srgState
            DisplayString
    }

srgRowstatus OBJECT-TYPE
    SYNTAX      RowStatus
    MAX-ACCESS  not-accessible
    STATUS      current
    DESCRIPTION
                "Table row status"
    ::= { scrgStatusTableEntry 1 }

srgName OBJECT-TYPE
    SYNTAX      DisplayString
    MAX-ACCESS  read-only
    STATUS      current
    DESCRIPTION
                "Character string value"
    ::= { scrgStatusTableEntry 2 }

srgPrim OBJECT-TYPE
    SYNTAX      DisplayString
    MAX-ACCESS  read-only
    STATUS      current
    DESCRIPTION
                "Character string value"
    ::= { scrgStatusTableEntry 3 }

srgPrimStatus OBJECT-TYPE
    SYNTAX      DisplayString
    MAX-ACCESS  read-only
    STATUS      current
    DESCRIPTION
                "Character string value"
    ::= { scrgStatusTableEntry 4 }

srgState OBJECT-TYPE
    SYNTAX      DisplayString
    MAX-ACCESS  read-only
    STATUS      current
    DESCRIPTION
                "Character string value"
    ::= { scrgStatusTableEntry 5 }

--***

srsStatusTable OBJECT-TYPE
    SYNTAX      SEQUENCE OF SrsStatusTableEntry
    MAX-ACCESS  not-accessible
    STATUS      current
    DESCRIPTION
                "MIB tree branch"
    ::= { scRgStatusBranch 2 }

srsStatusTableEntry OBJECT-TYPE
    SYNTAX      SrsStatusTableEntry
    MAX-ACCESS  not-accessible
    STATUS      current
    DESCRIPTION
                "MIB tree branch"
    INDEX  { srsRgName,
              srsRsName,
              srsRsPrim }
    ::= { srsStatusTable 1 }

SrsStatusTableEntry ::=
    SEQUENCE {
        srsRowstatus
            RowStatus,
        srsRgName
            DisplayString,
        srsRsName
            DisplayString,
        srsRsPrim
            DisplayString,
        srsRsPrimStatus
            DisplayString,
        srsRsFMStatus
            DisplayString,
        srsRsRGMState
            DisplayString
    }

srsRowstatus OBJECT-TYPE
    SYNTAX      RowStatus
    MAX-ACCESS  not-accessible
    STATUS      current
    DESCRIPTION
                "Table row status"
    ::= { srsStatusTableEntry 1 }

srsRgName OBJECT-TYPE
    SYNTAX      DisplayString
    MAX-ACCESS  read-only
    STATUS      current
    DESCRIPTION
                "Character string value"
    ::= { srsStatusTableEntry 2 }

srsRsName OBJECT-TYPE
    SYNTAX      DisplayString
    MAX-ACCESS  read-only
    STATUS      current
    DESCRIPTION
                "Character string value"
    ::= { srsStatusTableEntry 3 }

srsRsPrim OBJECT-TYPE
    SYNTAX      DisplayString
    MAX-ACCESS  read-only
    STATUS      current
    DESCRIPTION
                "Character string value"
    ::= { srsStatusTableEntry 4 }

srsRsPrimStatus OBJECT-TYPE
    SYNTAX      DisplayString
    MAX-ACCESS  read-only
    STATUS      current
    DESCRIPTION
                "Character string value"
    ::= { srsStatusTableEntry 5 }

srsRsFMStatus OBJECT-TYPE
    SYNTAX      DisplayString
    MAX-ACCESS  read-only
    STATUS      current
    DESCRIPTION
                "Character string value"
    ::= { srsStatusTableEntry 6 }

srsRsRGMState OBJECT-TYPE
    SYNTAX      DisplayString
    MAX-ACCESS  read-only
    STATUS      current
    DESCRIPTION
                "Character string value"
    ::= { srsStatusTableEntry 7 }

--*** FO RG config info

forgConfigTable OBJECT-TYPE
    SYNTAX      SEQUENCE OF ForgConfigTableEntry
    MAX-ACCESS  not-accessible
    STATUS      current
    DESCRIPTION
                "MIB tree branch"
    ::= { forgConfigInfo 1 }

forgConfigTableEntry OBJECT-TYPE
    SYNTAX      ForgConfigTableEntry
    MAX-ACCESS  not-accessible
    STATUS      current
    DESCRIPTION
                "MIB tree branch"
    INDEX  { frgcRgName }
    ::= { forgConfigTable 1 }

ForgConfigTableEntry ::=
    SEQUENCE {
        frgcRowstatus
            RowStatus,
        frgcRgName
            DisplayString,
        frgcRgPrimaries
            DisplayString,
        frgcRgDesc
            DisplayString,
        frgcRsList
            DisplayString,
        frgcRgMaxPrim
            Integer32,
        frgcRgDesPrim
            Integer32,
        frgcRgFailbackFlag
            DisplayString,
        frgcNetDepend
            DisplayString,
        frgcRgDepend
            DisplayString,
        frgcRgGlobRUsed
            DisplayString,
        frgcRgPathPrefix
            DisplayString
    }

frgcRowstatus OBJECT-TYPE
    SYNTAX      RowStatus
    MAX-ACCESS  not-accessible
    STATUS      current
    DESCRIPTION
                "Table row status"
    ::= { forgConfigTableEntry 1 }

frgcRgName OBJECT-TYPE
    SYNTAX      DisplayString
    MAX-ACCESS  read-only
    STATUS      current
    DESCRIPTION
                "Character string value"
    ::= { forgConfigTableEntry 2 }

frgcRgPrimaries OBJECT-TYPE
    SYNTAX      DisplayString
    MAX-ACCESS  read-only
    STATUS      current
    DESCRIPTION
                "Character string value"
    ::= { forgConfigTableEntry 3 }

frgcRgDesc OBJECT-TYPE
    SYNTAX      DisplayString
    MAX-ACCESS  read-only
    STATUS      current
    DESCRIPTION
                "Character string value"
    ::= { forgConfigTableEntry 4 }

frgcRsList OBJECT-TYPE
    SYNTAX      DisplayString
    MAX-ACCESS  read-only
    STATUS      current
    DESCRIPTION
                "Character string value"
    ::= { forgConfigTableEntry 5 }

frgcRgMaxPrim OBJECT-TYPE
    SYNTAX      Integer32
    MAX-ACCESS  read-only
    STATUS      current
    DESCRIPTION
                "Integer value"
    ::= { forgConfigTableEntry 6 }

frgcRgDesPrim OBJECT-TYPE
    SYNTAX      Integer32
    MAX-ACCESS  read-only
    STATUS      current
    DESCRIPTION
                "Integer value"
    ::= { forgConfigTableEntry 7 }

frgcRgFailbackFlag OBJECT-TYPE
    SYNTAX      DisplayString
    MAX-ACCESS  read-only
    STATUS      current
    DESCRIPTION
                "Character string value"
    ::= { forgConfigTableEntry 8 }

frgcNetDepend OBJECT-TYPE
    SYNTAX      DisplayString
    MAX-ACCESS  read-only
    STATUS      current
    DESCRIPTION
                "Character string value"
    ::= { forgConfigTableEntry 9 }

frgcRgDepend OBJECT-TYPE
    SYNTAX      DisplayString
    MAX-ACCESS  read-only
    STATUS      current
    DESCRIPTION
                "Character string value"
    ::= { forgConfigTableEntry 10 }

frgcRgGlobRUsed OBJECT-TYPE
    SYNTAX      DisplayString
    MAX-ACCESS  read-only
    STATUS      current
    DESCRIPTION
                "Character string value"
    ::= { forgConfigTableEntry 11 }

frgcRgPathPrefix OBJECT-TYPE
    SYNTAX      DisplayString
    MAX-ACCESS  read-only
    STATUS      current
    DESCRIPTION
                "Character string value"
    ::= { forgConfigTableEntry 12 }

--*** fo rs config

forsGenConfigTable OBJECT-TYPE
    SYNTAX      SEQUENCE OF ForsGenConfigTableEntry
    MAX-ACCESS  not-accessible
    STATUS      current
    DESCRIPTION
                "MIB tree branch"
    ::= { foRsConfigGen 1 }

forsGenConfigTableEntry OBJECT-TYPE
    SYNTAX      ForsGenConfigTableEntry
    MAX-ACCESS  not-accessible
    STATUS      current
    DESCRIPTION
                "MIB tree branch"
    INDEX  { frcRgName,
             frcRsName }
    ::= { forsGenConfigTable 1 }

ForsGenConfigTableEntry ::=
    SEQUENCE {
        frcRowstatus
            RowStatus,
        frcRgName
            DisplayString,
        frcRsName
            DisplayString,
        frcRsType
            DisplayString,
        frcRsEnabled
            DisplayString,
        frcRsMonitored
            DisplayString,
        frcRsStrongDepend
            DisplayString,
        frcRsWeakDepend
            DisplayString
    }

frcRowstatus OBJECT-TYPE
    SYNTAX      RowStatus
    MAX-ACCESS  not-accessible
    STATUS      current
    DESCRIPTION
                "Table row status"
    ::= { forsGenConfigTableEntry 1 }

frcRgName OBJECT-TYPE
    SYNTAX      DisplayString
    MAX-ACCESS  read-only
    STATUS      current
    DESCRIPTION
                "Character string value"
    ::= { forsGenConfigTableEntry 2 }

frcRsName OBJECT-TYPE
    SYNTAX      DisplayString
    MAX-ACCESS  read-only
    STATUS      current
    DESCRIPTION
                "Character string value"
    ::= { forsGenConfigTableEntry 3 }

frcRsType OBJECT-TYPE
    SYNTAX      DisplayString
    MAX-ACCESS  read-only
    STATUS      current
    DESCRIPTION
                "Character string value"
    ::= { forsGenConfigTableEntry 4 }

frcRsEnabled OBJECT-TYPE
    SYNTAX      DisplayString
    MAX-ACCESS  read-only
    STATUS      current
    DESCRIPTION
                "Character string value"
    ::= { forsGenConfigTableEntry 5 }

frcRsMonitored OBJECT-TYPE
    SYNTAX      DisplayString
    MAX-ACCESS  read-only
    STATUS      current
    DESCRIPTION
                "Character string value"
    ::= { forsGenConfigTableEntry 6 }

frcRsStrongDepend OBJECT-TYPE
    SYNTAX      DisplayString
    MAX-ACCESS  read-only
    STATUS      current
    DESCRIPTION
                "Character string value"
    ::= { forsGenConfigTableEntry 7 }

frcRsWeakDepend OBJECT-TYPE
    SYNTAX      DisplayString
    MAX-ACCESS  read-only
    STATUS      current
    DESCRIPTION
                "Character string value"
    ::= { forsGenConfigTableEntry 8 }

-- *** fo rs stand prop info

forsComPropConfigTable OBJECT-TYPE
    SYNTAX      SEQUENCE OF ForsComPropConfigTableEntry
    MAX-ACCESS  not-accessible
    STATUS      current
    DESCRIPTION
                "MIB tree branch"
    ::= { foRsConfigStandProps 1 }

forsComPropConfigTableEntry OBJECT-TYPE
    SYNTAX      ForsComPropConfigTableEntry
    MAX-ACCESS  not-accessible
    STATUS      current
    DESCRIPTION
                "MIB tree branch"
    INDEX  { frstRgName,
              frstRsName,
              frstRsPropName }
    ::= { forsComPropConfigTable 1 }

ForsComPropConfigTableEntry ::=
    SEQUENCE {
        frstRowstatus
            RowStatus,
        frstRgName
            DisplayString,
        frstRsName
            DisplayString,
        frstRsPropName
            DisplayString,
        frstRsPropValue
            DisplayString,
        frstRsPropDesc
            DisplayString
    }

frstRowstatus OBJECT-TYPE
    SYNTAX      RowStatus
    MAX-ACCESS  not-accessible
    STATUS      current
    DESCRIPTION
                "Table row status"
    ::= { forsComPropConfigTableEntry 1 }

frstRgName OBJECT-TYPE
    SYNTAX      DisplayString
    MAX-ACCESS  read-only
    STATUS      current
    DESCRIPTION
                "Character string value"
    ::= { forsComPropConfigTableEntry 2 }

frstRsName OBJECT-TYPE
    SYNTAX      DisplayString
    MAX-ACCESS  read-only
    STATUS      current
    DESCRIPTION
                "Character string value"
    ::= { forsComPropConfigTableEntry 3 }

frstRsPropName OBJECT-TYPE
    SYNTAX      DisplayString
    MAX-ACCESS  read-only
    STATUS      current
    DESCRIPTION
                "Character string value"
    ::= { forsComPropConfigTableEntry 4 }

frstRsPropValue OBJECT-TYPE
    SYNTAX      DisplayString
    MAX-ACCESS  read-only
    STATUS      current
    DESCRIPTION
                "Character string value"
    ::= { forsComPropConfigTableEntry 5 }

frstRsPropDesc OBJECT-TYPE
    SYNTAX      DisplayString
    MAX-ACCESS  read-only
    STATUS      current
    DESCRIPTION
                "Character string value"
    ::= { forsComPropConfigTableEntry 6 }


-- ***

forsExtPropConfigTable OBJECT-TYPE
    SYNTAX      SEQUENCE OF ForsExtPropConfigTableEntry
    MAX-ACCESS  not-accessible
    STATUS      current
    DESCRIPTION
                "MIB tree branch"
    ::= { foRsConfigExtProps 1 }

forsExtPropConfigTableEntry OBJECT-TYPE
    SYNTAX      ForsExtPropConfigTableEntry
    MAX-ACCESS  not-accessible
    STATUS      current
    DESCRIPTION
                "MIB tree branch"
    INDEX  { frexRgName,
              frexRsName,
              frexRsPropName }
    ::= { forsExtPropConfigTable 1 }

ForsExtPropConfigTableEntry ::=
    SEQUENCE {
        frexRowstatus
            RowStatus,
        frexRgName
            DisplayString,
        frexRsName
            DisplayString,
        frexRsPropName
            DisplayString,
        frexRsPropValue
            DisplayString,
        frexRsPropDesc
            DisplayString
    }

frexRowstatus OBJECT-TYPE
    SYNTAX      RowStatus
    MAX-ACCESS  not-accessible
    STATUS      current
    DESCRIPTION
                "Table row status"
    ::= { forsExtPropConfigTableEntry 1 }

frexRgName OBJECT-TYPE
    SYNTAX      DisplayString
    MAX-ACCESS  read-only
    STATUS      current
    DESCRIPTION
                "Character string value"
    ::= { forsExtPropConfigTableEntry 2 }

frexRsName OBJECT-TYPE
    SYNTAX      DisplayString
    MAX-ACCESS  read-only
    STATUS      current
    DESCRIPTION
                "Character string value"
    ::= { forsExtPropConfigTableEntry 3 }

frexRsPropName OBJECT-TYPE
    SYNTAX      DisplayString
    MAX-ACCESS  read-only
    STATUS      current
    DESCRIPTION
                "Character string value"
    ::= { forsExtPropConfigTableEntry 4 }

frexRsPropValue OBJECT-TYPE
    SYNTAX      DisplayString
    MAX-ACCESS  read-only
    STATUS      current
    DESCRIPTION
                "Character string value"
    ::= { forsExtPropConfigTableEntry 5 }

frexRsPropDesc OBJECT-TYPE
    SYNTAX      DisplayString
    MAX-ACCESS  read-only
    STATUS      current
    DESCRIPTION
                "Character string value"
    ::= { forsExtPropConfigTableEntry 6 }

-- *** fo rs method timeout info

forsTimeoutConfigTable OBJECT-TYPE
    SYNTAX      SEQUENCE OF ForsTimeoutConfigTableEntry
    MAX-ACCESS  not-accessible
    STATUS      current
    DESCRIPTION
                "MIB tree branch"
    ::= { foRsConfigMethods 1 }

forsTimeoutConfigTableEntry OBJECT-TYPE
    SYNTAX      ForsTimeoutConfigTableEntry
    MAX-ACCESS  not-accessible
    STATUS      current
    DESCRIPTION
                "MIB tree branch"
    INDEX  { frtoRgName,
              frtoRsName,
              frtoRsPropName }
    ::= { forsTimeoutConfigTable 1 }

ForsTimeoutConfigTableEntry ::=
    SEQUENCE {
        frtoRowstatus
            RowStatus,
        frtoRgName
            DisplayString,
        frtoRsName
            DisplayString,
        frtoRsPropName
            DisplayString,
        frtoRsPropValue
            DisplayString,
        frtoRsPropDesc
            DisplayString
    }

frtoRowstatus OBJECT-TYPE
    SYNTAX      RowStatus
    MAX-ACCESS  not-accessible
    STATUS      current
    DESCRIPTION
                "Table row status"
    ::= { forsTimeoutConfigTableEntry 1 }

frtoRgName OBJECT-TYPE
    SYNTAX      DisplayString
    MAX-ACCESS  read-only
    STATUS      current
    DESCRIPTION
                "Character string value"
    ::= { forsTimeoutConfigTableEntry 2 }

frtoRsName OBJECT-TYPE
    SYNTAX      DisplayString
    MAX-ACCESS  read-only
    STATUS      current
    DESCRIPTION
                "Character string value"
    ::= { forsTimeoutConfigTableEntry 3 }

frtoRsPropName OBJECT-TYPE
    SYNTAX      DisplayString
    MAX-ACCESS  read-only
    STATUS      current
    DESCRIPTION
                "Character string value"
    ::= { forsTimeoutConfigTableEntry 4 }

frtoRsPropValue OBJECT-TYPE
    SYNTAX      DisplayString
    MAX-ACCESS  read-only
    STATUS      current
    DESCRIPTION
                "Character string value"
    ::= { forsTimeoutConfigTableEntry 5 }

frtoRsPropDesc OBJECT-TYPE
    SYNTAX      DisplayString
    MAX-ACCESS  read-only
    STATUS      current
    DESCRIPTION
                "Character string value"
    ::= { forsTimeoutConfigTableEntry 6 }

-- *** sc rg config info

scrgConfigTable OBJECT-TYPE
    SYNTAX      SEQUENCE OF ScrgConfigTableEntry
    MAX-ACCESS  not-accessible
    STATUS      current
    DESCRIPTION
                "MIB tree branch"
    ::= { scrgConfigInfo 1 }

scrgConfigTableEntry OBJECT-TYPE
    SYNTAX      ScrgConfigTableEntry
    MAX-ACCESS  not-accessible
    STATUS      current
    DESCRIPTION
                "MIB tree branch"
    INDEX  { srgcRgName }
    ::= { scrgConfigTable 1 }

ScrgConfigTableEntry ::=
    SEQUENCE {
        srgcRowstatus
            RowStatus,
        srgcRgName
            DisplayString,
        srgcRgPrimaries
            DisplayString,
        srgcRgDesc
            DisplayString,
        srgcRsList
            DisplayString,
        srgcRgMaxPrim
            Integer32,
        srgcRgDesPrim
            Integer32,
        srgcRgFailbackFlag
            DisplayString,
        srgcNetDepend
            DisplayString,
        srgcRgDepend
            DisplayString,
        srgcRgGlobRUsed
            DisplayString,
        srgcRgPathPrefix
            DisplayString
    }

srgcRowstatus OBJECT-TYPE
    SYNTAX      RowStatus
    MAX-ACCESS  not-accessible
    STATUS      current
    DESCRIPTION
                "Table row status"
    ::= { scrgConfigTableEntry 1 }

srgcRgName OBJECT-TYPE
    SYNTAX      DisplayString
    MAX-ACCESS  read-only
    STATUS      current
    DESCRIPTION
                "Character string value"
    ::= { scrgConfigTableEntry 2 }

srgcRgPrimaries OBJECT-TYPE
    SYNTAX      DisplayString
    MAX-ACCESS  read-only
    STATUS      current
    DESCRIPTION
                "Character string value"
    ::= { scrgConfigTableEntry 3 }

srgcRgDesc OBJECT-TYPE
    SYNTAX      DisplayString
    MAX-ACCESS  read-only
    STATUS      current
    DESCRIPTION
                "Character string value"
    ::= { scrgConfigTableEntry 4 }

srgcRsList OBJECT-TYPE
    SYNTAX      DisplayString
    MAX-ACCESS  read-only
    STATUS      current
    DESCRIPTION
                "Character string value"
    ::= { scrgConfigTableEntry 5 }

srgcRgMaxPrim OBJECT-TYPE
    SYNTAX      Integer32
    MAX-ACCESS  read-only
    STATUS      current
    DESCRIPTION
                "Integer value"
    ::= { scrgConfigTableEntry 6 }

srgcRgDesPrim OBJECT-TYPE
    SYNTAX      Integer32
    MAX-ACCESS  read-only
    STATUS      current
    DESCRIPTION
                "Integer value"
    ::= { scrgConfigTableEntry 7 }

srgcRgFailbackFlag OBJECT-TYPE
    SYNTAX      DisplayString
    MAX-ACCESS  read-only
    STATUS      current
    DESCRIPTION
                "Character string value"
    ::= { scrgConfigTableEntry 8 }

srgcNetDepend OBJECT-TYPE
    SYNTAX      DisplayString
    MAX-ACCESS  read-only
    STATUS      current
    DESCRIPTION
                "Character string value"
    ::= { scrgConfigTableEntry 9 }

srgcRgDepend OBJECT-TYPE
    SYNTAX      DisplayString
    MAX-ACCESS  read-only
    STATUS      current
    DESCRIPTION
                "Character string value"
    ::= { scrgConfigTableEntry 10 }

srgcRgGlobRUsed OBJECT-TYPE
    SYNTAX      DisplayString
    MAX-ACCESS  read-only
    STATUS      current
    DESCRIPTION
                "Character string value"
    ::= { scrgConfigTableEntry 11 }

srgcRgPathPrefix OBJECT-TYPE
    SYNTAX      DisplayString
    MAX-ACCESS  read-only
    STATUS      current
    DESCRIPTION
                "Character string value"
    ::= { scrgConfigTableEntry 12 }

--*** sc rs config

scrsGenConfigTable OBJECT-TYPE
    SYNTAX      SEQUENCE OF ScrsGenConfigTableEntry
    MAX-ACCESS  not-accessible
    STATUS      current
    DESCRIPTION
                "MIB tree branch"
    ::= { scRsConfigGen 1 }

scrsGenConfigTableEntry OBJECT-TYPE
    SYNTAX      ScrsGenConfigTableEntry
    MAX-ACCESS  not-accessible
    STATUS      current
    DESCRIPTION
                "MIB tree branch"
    INDEX  { srcRgName,
             srcRsName }
    ::= { scrsGenConfigTable 1 }

ScrsGenConfigTableEntry ::=
    SEQUENCE {
        srcRowstatus
            RowStatus,
        srcRgName
            DisplayString,
        srcRsName
            DisplayString,
        srcRsType
            DisplayString,
        srcRsEnabled
            DisplayString,
        srcRsMonitored
            Integer32,
        srcRsStrongDepend
            DisplayString,
        srcRsWeakDepend
            DisplayString
    }

srcRowstatus OBJECT-TYPE
    SYNTAX      RowStatus
    MAX-ACCESS  not-accessible
    STATUS      current
    DESCRIPTION
                "Table row status"
    ::= { scrsGenConfigTableEntry 1 }

srcRgName OBJECT-TYPE
    SYNTAX      DisplayString
    MAX-ACCESS  read-only
    STATUS      current
    DESCRIPTION
                "Character string value"
    ::= { scrsGenConfigTableEntry 2 }

srcRsName OBJECT-TYPE
    SYNTAX      DisplayString
    MAX-ACCESS  read-only
    STATUS      current
    DESCRIPTION
                "Character string value"
    ::= { scrsGenConfigTableEntry 3 }

srcRsType OBJECT-TYPE
    SYNTAX      DisplayString
    MAX-ACCESS  read-only
    STATUS      current
    DESCRIPTION
                "Character string value"
    ::= { scrsGenConfigTableEntry 4 }

srcRsEnabled OBJECT-TYPE
    SYNTAX      DisplayString
    MAX-ACCESS  read-only
    STATUS      current
    DESCRIPTION
                "Character string value"
    ::= { scrsGenConfigTableEntry 5 }

srcRsMonitored OBJECT-TYPE
    SYNTAX      Integer32
    MAX-ACCESS  read-only
    STATUS      current
    DESCRIPTION
                "Integer value"
    ::= { scrsGenConfigTableEntry 6 }

srcRsStrongDepend OBJECT-TYPE
    SYNTAX      DisplayString
    MAX-ACCESS  read-only
    STATUS      current
    DESCRIPTION
                "Character string value"
    ::= { scrsGenConfigTableEntry 7 }

srcRsWeakDepend OBJECT-TYPE
    SYNTAX      DisplayString
    MAX-ACCESS  read-only
    STATUS      current
    DESCRIPTION
                "Character string value"
    ::= { scrsGenConfigTableEntry 8 }

-- *** sc rs stand prop info

scrsComPropConfigTable OBJECT-TYPE
    SYNTAX      SEQUENCE OF ScrsComPropConfigTableEntry
    MAX-ACCESS  not-accessible
    STATUS      current
    DESCRIPTION
                "MIB tree branch"
    ::= { scRsConfigStandProps 1 }

scrsComPropConfigTableEntry OBJECT-TYPE
    SYNTAX      ScrsComPropConfigTableEntry
    MAX-ACCESS  not-accessible
    STATUS      current
    DESCRIPTION
                "MIB tree branch"
    INDEX  { srstRgName,
              srstRsName,
              srstRsPropName }
    ::= { scrsComPropConfigTable 1 }

ScrsComPropConfigTableEntry ::=
    SEQUENCE {
        srstRowstatus
            RowStatus,
        srstRgName
            DisplayString,
        srstRsName
            DisplayString,
        srstRsPropName
            DisplayString,
        srstRsPropValue
            DisplayString,
        srstRsPropDesc
            DisplayString
    }

srstRowstatus OBJECT-TYPE
    SYNTAX      RowStatus
    MAX-ACCESS  not-accessible
    STATUS      current
    DESCRIPTION
                "Table row status"
    ::= { scrsComPropConfigTableEntry 1 }

srstRgName OBJECT-TYPE
    SYNTAX      DisplayString
    MAX-ACCESS  read-only
    STATUS      current
    DESCRIPTION
                "Character string value"
    ::= { scrsComPropConfigTableEntry 2 }

srstRsName OBJECT-TYPE
    SYNTAX      DisplayString
    MAX-ACCESS  read-only
    STATUS      current
    DESCRIPTION
                "Character string value"
    ::= { scrsComPropConfigTableEntry 3 }

srstRsPropName OBJECT-TYPE
    SYNTAX      DisplayString
    MAX-ACCESS  read-only
    STATUS      current
    DESCRIPTION
                "Character string value"
    ::= { scrsComPropConfigTableEntry 4 }

srstRsPropValue OBJECT-TYPE
    SYNTAX      DisplayString
    MAX-ACCESS  read-only
    STATUS      current
    DESCRIPTION
                "Character string value"
    ::= { scrsComPropConfigTableEntry 5 }

srstRsPropDesc OBJECT-TYPE
    SYNTAX      DisplayString
    MAX-ACCESS  read-only
    STATUS      current
    DESCRIPTION
                "Character string value"
    ::= { scrsComPropConfigTableEntry 6 }


-- ***

scrsExtPropConfigTable OBJECT-TYPE
    SYNTAX      SEQUENCE OF ScrsExtPropConfigTableEntry
    MAX-ACCESS  not-accessible
    STATUS      current
    DESCRIPTION
                "MIB tree branch"
    ::= { scRsConfigExtProps 1 }

scrsExtPropConfigTableEntry OBJECT-TYPE
    SYNTAX      ScrsExtPropConfigTableEntry
    MAX-ACCESS  not-accessible
    STATUS      current
    DESCRIPTION
                "MIB tree branch"
    INDEX  { srexRgName,
              srexRsName,
              frexRsPropName }
    ::= { scrsExtPropConfigTable 1 }

ScrsExtPropConfigTableEntry ::=
    SEQUENCE {
        srexRowstatus
            RowStatus,
        srexRgName
            DisplayString,
        srexRsName
            DisplayString,
        srexRsPropName
            DisplayString,
        srexRsPropValue
            DisplayString,
        srexRsPropDesc
            DisplayString
    }

srexRowstatus OBJECT-TYPE
    SYNTAX      RowStatus
    MAX-ACCESS  not-accessible
    STATUS      current
    DESCRIPTION
                "Table row status"
    ::= { scrsExtPropConfigTableEntry 1 }

srexRgName OBJECT-TYPE
    SYNTAX      DisplayString
    MAX-ACCESS  read-only
    STATUS      current
    DESCRIPTION
                "Character string value"
    ::= { scrsExtPropConfigTableEntry 2 }

srexRsName OBJECT-TYPE
    SYNTAX      DisplayString
    MAX-ACCESS  read-only
    STATUS      current
    DESCRIPTION
                "Character string value"
    ::= { scrsExtPropConfigTableEntry 3 }

srexRsPropName OBJECT-TYPE
    SYNTAX      DisplayString
    MAX-ACCESS  read-only
    STATUS      current
    DESCRIPTION
                "Character string value"
    ::= { scrsExtPropConfigTableEntry 4 }

srexRsPropValue OBJECT-TYPE
    SYNTAX      DisplayString
    MAX-ACCESS  read-only
    STATUS      current
    DESCRIPTION
                "Character string value"
    ::= { scrsExtPropConfigTableEntry 5 }

srexRsPropDesc OBJECT-TYPE
    SYNTAX      DisplayString
    MAX-ACCESS  read-only
    STATUS      current
    DESCRIPTION
                "Character string value"
    ::= { scrsExtPropConfigTableEntry 6 }

-- *** sc rs method timeout info

scrsTimeoutConfigTable OBJECT-TYPE
    SYNTAX      SEQUENCE OF ScrsTimeoutConfigTableEntry
    MAX-ACCESS  not-accessible
    STATUS      current
    DESCRIPTION
                "MIB tree branch"
    ::= { scRsConfigMethods 1 }

scrsTimeoutConfigTableEntry OBJECT-TYPE
    SYNTAX      ScrsTimeoutConfigTableEntry
    MAX-ACCESS  not-accessible
    STATUS      current
    DESCRIPTION
                "MIB tree branch"
    INDEX  { srtoRgName,
              srtoRsName,
              srtoRsPropName }
    ::= { scrsTimeoutConfigTable 1 }

ScrsTimeoutConfigTableEntry ::=
    SEQUENCE {
        srtoRowstatus
            RowStatus,
        srtoRgName
            DisplayString,
        srtoRsName
            DisplayString,
        srtoRsPropName
            DisplayString,
        srtoRsPropValue
            DisplayString,
        srtoRsPropDesc
            DisplayString
    }

srtoRowstatus OBJECT-TYPE
    SYNTAX      RowStatus
    MAX-ACCESS  not-accessible
    STATUS      current
    DESCRIPTION
                "Table row status"
    ::= { scrsTimeoutConfigTableEntry 1 }

srtoRgName OBJECT-TYPE
    SYNTAX      DisplayString
    MAX-ACCESS  read-only
    STATUS      current
    DESCRIPTION
                "Character string value"
    ::= { scrsTimeoutConfigTableEntry 2 }

srtoRsName OBJECT-TYPE
    SYNTAX      DisplayString
    MAX-ACCESS  read-only
    STATUS      current
    DESCRIPTION
                "Character string value"
    ::= { scrsTimeoutConfigTableEntry 3 }

srtoRsPropName OBJECT-TYPE
    SYNTAX      DisplayString
    MAX-ACCESS  read-only
    STATUS      current
    DESCRIPTION
                "Character string value"
    ::= { scrsTimeoutConfigTableEntry 4 }

srtoRsPropValue OBJECT-TYPE
    SYNTAX      DisplayString
    MAX-ACCESS  read-only
    STATUS      current
    DESCRIPTION
                "Character string value"
    ::= { scrsTimeoutConfigTableEntry 5 }

srtoRsPropDesc OBJECT-TYPE
    SYNTAX      DisplayString
    MAX-ACCESS  read-only
    STATUS      current
    DESCRIPTION
                "Character string value"
    ::= { scrsTimeoutConfigTableEntry 6 }

--*** resourceTypes subtree


rtOverviewTable OBJECT-TYPE
    SYNTAX      SEQUENCE OF RtOverviewTableEntry
    MAX-ACCESS  not-accessible
    STATUS      current
    DESCRIPTION
                "MIB tree branch"
    ::= { rtOverview 1 }

rtOverviewTableEntry OBJECT-TYPE
    SYNTAX      RtOverviewTableEntry
    MAX-ACCESS  not-accessible
    STATUS      current
    DESCRIPTION
                "MIB tree branch"
    INDEX  { rtoName }
    ::= { rtOverviewTable 1 }

RtOverviewTableEntry ::=
    SEQUENCE {
        rtoName
            DisplayString,
        rtoNodes
            DisplayString,
        rtoDesc
            DisplayString,
        rtoBaseDir
            DisplayString,
        rtoSingleInst
            DisplayString,
        rtoInitNodes
            DisplayString,
        rtoFailover
            DisplayString,
        rtoSysDefType
            DisplayString,
        rtoDepend
            DisplayString,
        rtoApiVersion
            Integer32,
        rtoVersion
            DisplayString,
        rtoPkglist
            DisplayString
    }

rtoName OBJECT-TYPE
    SYNTAX      DisplayString
    MAX-ACCESS  read-only
    STATUS      current
    DESCRIPTION
                "Character string value"
    ::= { rtOverviewTableEntry 1 }

rtoNodes OBJECT-TYPE
    SYNTAX      DisplayString
    MAX-ACCESS  read-only
    STATUS      current
    DESCRIPTION
                "Character string value"
    ::= { rtOverviewTableEntry 2 }

rtoDesc OBJECT-TYPE
    SYNTAX      DisplayString
    MAX-ACCESS  read-only
    STATUS      current
    DESCRIPTION
                "Character string value"
    ::= { rtOverviewTableEntry 3 }

rtoBaseDir OBJECT-TYPE
    SYNTAX      DisplayString
    MAX-ACCESS  read-only
    STATUS      current
    DESCRIPTION
                "Character string value"
    ::= { rtOverviewTableEntry 4 }

rtoSingleInst OBJECT-TYPE
    SYNTAX      DisplayString
    MAX-ACCESS  read-only
    STATUS      current
    DESCRIPTION
                "Character string value"
    ::= { rtOverviewTableEntry 5 }

rtoInitNodes OBJECT-TYPE
    SYNTAX      DisplayString
    MAX-ACCESS  read-only
    STATUS      current
    DESCRIPTION
                "Character string value"
    ::= { rtOverviewTableEntry 6 }

rtoFailover OBJECT-TYPE
    SYNTAX      DisplayString
    MAX-ACCESS  read-only
    STATUS      current
    DESCRIPTION
                "Character string value"
    ::= { rtOverviewTableEntry 7 }

rtoSysDefType OBJECT-TYPE
    SYNTAX      DisplayString
    MAX-ACCESS  read-only
    STATUS      current
    DESCRIPTION
                "Character string value"
    ::= { rtOverviewTableEntry 8 }

rtoDepend OBJECT-TYPE
    SYNTAX      DisplayString
    MAX-ACCESS  read-only
    STATUS      current
    DESCRIPTION
                "Character string value"
    ::= { rtOverviewTableEntry 9 }

rtoApiVersion OBJECT-TYPE
    SYNTAX      Integer32
    MAX-ACCESS  read-only
    STATUS      current
    DESCRIPTION
                "Integer value"
    ::= { rtOverviewTableEntry 10 }

rtoVersion OBJECT-TYPE
    SYNTAX      DisplayString
    MAX-ACCESS  read-only
    STATUS      current
    DESCRIPTION
                "Character string value"
    ::= { rtOverviewTableEntry 11 }

rtoPkglist OBJECT-TYPE
    SYNTAX      DisplayString
    MAX-ACCESS  read-only
    STATUS      current
    DESCRIPTION
                "Character string value"
    ::= { rtOverviewTableEntry 12 }

--***

rtMethodTable OBJECT-TYPE
    SYNTAX      SEQUENCE OF RtMethodTableEntry
    MAX-ACCESS  not-accessible
    STATUS      current
    DESCRIPTION
                "MIB tree branch"
    ::= { rtMethodProps 1 }

rtMethodTableEntry OBJECT-TYPE
    SYNTAX      RtMethodTableEntry
    MAX-ACCESS  not-accessible
    STATUS      current
    DESCRIPTION
                "MIB tree branch"
    INDEX  { rtmName }
    ::= { rtMethodTable 1 }

RtMethodTableEntry ::=
    SEQUENCE {
        rtmName
            DisplayString,
        rtmSTART
            DisplayString,
        rtmSTOP
            DisplayString,
        rtmPRIMCHANGE
            DisplayString,
        rtmVALIDATE
            DisplayString,
        rtmUPDATE
            DisplayString,
        rtmINIT
            DisplayString,
        rtmFINI
            DisplayString,
        rtmBOOT
            DisplayString,
        rtmMONINIT
            DisplayString,
        rtmMONSTART
            DisplayString,
        rtmMONSTOP
            DisplayString,
        rtmMONCHECK
            DisplayString,
        rtmPRENETSTART
            DisplayString,
        rtmPOSTNETSTOP
            DisplayString
    }

rtmName OBJECT-TYPE
    SYNTAX      DisplayString
    MAX-ACCESS  read-only
    STATUS      current
    DESCRIPTION
                "Character string value"
    ::= { rtMethodTableEntry 1 }

rtmSTART OBJECT-TYPE
    SYNTAX      DisplayString
    MAX-ACCESS  read-only
    STATUS      current
    DESCRIPTION
                "Character string value"
    ::= { rtMethodTableEntry 2 }

rtmSTOP OBJECT-TYPE
    SYNTAX      DisplayString
    MAX-ACCESS  read-only
    STATUS      current
    DESCRIPTION
                "Character string value"
    ::= { rtMethodTableEntry 3 }

rtmPRIMCHANGE OBJECT-TYPE
    SYNTAX      DisplayString
    MAX-ACCESS  read-only
    STATUS      current
    DESCRIPTION
                "Character string value"
    ::= { rtMethodTableEntry 4 }

rtmVALIDATE OBJECT-TYPE
    SYNTAX      DisplayString
    MAX-ACCESS  read-only
    STATUS      current
    DESCRIPTION
                "Character string value"
    ::= { rtMethodTableEntry 5 }

rtmUPDATE OBJECT-TYPE
    SYNTAX      DisplayString
    MAX-ACCESS  read-only
    STATUS      current
    DESCRIPTION
                "Character string value"
    ::= { rtMethodTableEntry 6 }

rtmINIT OBJECT-TYPE
    SYNTAX      DisplayString
    MAX-ACCESS  read-only
    STATUS      current
    DESCRIPTION
                "Character string value"
    ::= { rtMethodTableEntry 7 }

rtmFINI OBJECT-TYPE
    SYNTAX      DisplayString
    MAX-ACCESS  read-only
    STATUS      current
    DESCRIPTION
                "Character string value"
    ::= { rtMethodTableEntry 8 }

rtmBOOT OBJECT-TYPE
    SYNTAX      DisplayString
    MAX-ACCESS  read-only
    STATUS      current
    DESCRIPTION
                "Character string value"
    ::= { rtMethodTableEntry 9 }

rtmMONINIT OBJECT-TYPE
    SYNTAX      DisplayString
    MAX-ACCESS  read-only
    STATUS      current
    DESCRIPTION
                "Character string value"
    ::= { rtMethodTableEntry 10 }

rtmMONSTART OBJECT-TYPE
    SYNTAX      DisplayString
    MAX-ACCESS  read-only
    STATUS      current
    DESCRIPTION
                "Character string value"
    ::= { rtMethodTableEntry 11 }

rtmMONSTOP OBJECT-TYPE
    SYNTAX      DisplayString
    MAX-ACCESS  read-only
    STATUS      current
    DESCRIPTION
                "Character string value"
    ::= { rtMethodTableEntry 12 }

rtmMONCHECK OBJECT-TYPE
    SYNTAX      DisplayString
    MAX-ACCESS  read-only
    STATUS      current
    DESCRIPTION
                "Character string value"
    ::= { rtMethodTableEntry 13 }

rtmPRENETSTART OBJECT-TYPE
    SYNTAX      DisplayString
    MAX-ACCESS  read-only
    STATUS      current
    DESCRIPTION
                "Character string value"
    ::= { rtMethodTableEntry 14 }

rtmPOSTNETSTOP OBJECT-TYPE
    SYNTAX      DisplayString
    MAX-ACCESS  read-only
    STATUS      current
    DESCRIPTION
                "Character string value"
    ::= { rtMethodTableEntry 15 }

--***

rtParamTable OBJECT-TYPE
    SYNTAX      SEQUENCE OF RtParamTableEntry
    MAX-ACCESS  not-accessible
    STATUS      current
    DESCRIPTION
                "MIB tree branch"
    ::= { rtParams 1 }

rtParamTableEntry OBJECT-TYPE
    SYNTAX      RtParamTableEntry
    MAX-ACCESS  not-accessible
    STATUS      current
    DESCRIPTION
                "MIB tree branch"
    INDEX  { rtpName,
              rtpPropName }
    ::= { rtParamTable 1 }

RtParamTableEntry ::=
    SEQUENCE {
        rtpName
            DisplayString,
        rtpPropName
            DisplayString,
        rtpPropExt
            DisplayString,
        rtpPropTunable
            DisplayString,
        rtpPropType
            DisplayString,
        rtpPropDefault
            DisplayString,
        rtpPropMin
            DisplayString,
        rtpPropMax
            DisplayString,
        rtpPropArrayMin
            DisplayString,
        rtpPropArrayMax
            DisplayString,
        rtpPropDesc
            DisplayString
    }

rtpName OBJECT-TYPE
    SYNTAX      DisplayString
    MAX-ACCESS  read-only
    STATUS      current
    DESCRIPTION
                "Character string value"
    ::= { rtParamTableEntry 1 }

rtpPropName OBJECT-TYPE
    SYNTAX      DisplayString
    MAX-ACCESS  read-only
    STATUS      current
    DESCRIPTION
                "Character string value"
    ::= { rtParamTableEntry 2 }

rtpPropExt OBJECT-TYPE
    SYNTAX      DisplayString
    MAX-ACCESS  read-only
    STATUS      current
    DESCRIPTION
                "Character string value"
    ::= { rtParamTableEntry 3 }

rtpPropTunable OBJECT-TYPE
    SYNTAX      DisplayString
    MAX-ACCESS  read-only
    STATUS      current
    DESCRIPTION
                "Character string value"
    ::= { rtParamTableEntry 4 }

rtpPropType OBJECT-TYPE
    SYNTAX      DisplayString
    MAX-ACCESS  read-only
    STATUS      current
    DESCRIPTION
                "Character string value"
    ::= { rtParamTableEntry 5 }

rtpPropDefault OBJECT-TYPE
    SYNTAX      DisplayString
    MAX-ACCESS  read-only
    STATUS      current
    DESCRIPTION
                "Character string value"
    ::= { rtParamTableEntry 6 }

rtpPropMin OBJECT-TYPE
    SYNTAX      DisplayString
    MAX-ACCESS  read-only
    STATUS      current
    DESCRIPTION
                "Character string value"
    ::= { rtParamTableEntry 7 }

rtpPropMax OBJECT-TYPE
    SYNTAX      DisplayString
    MAX-ACCESS  read-only
    STATUS      current
    DESCRIPTION
                "Character string value"
    ::= { rtParamTableEntry 8 }

rtpPropArrayMin OBJECT-TYPE
    SYNTAX      DisplayString
    MAX-ACCESS  read-only
    STATUS      current
    DESCRIPTION
                "Character string value"
    ::= { rtParamTableEntry 9 }

rtpPropArrayMax OBJECT-TYPE
    SYNTAX      DisplayString
    MAX-ACCESS  read-only
    STATUS      current
    DESCRIPTION
                "Character string value"
    ::= { rtParamTableEntry 10 }

rtpPropDesc OBJECT-TYPE
    SYNTAX      DisplayString
    MAX-ACCESS  read-only
    STATUS      current
    DESCRIPTION
                "Character string value"
    ::= { rtParamTableEntry 11 }

--***

rtrsTable OBJECT-TYPE
    SYNTAX      SEQUENCE OF RtrsTableEntry
    MAX-ACCESS  not-accessible
    STATUS      current
    DESCRIPTION
                "MIB tree branch"
    ::= { resourceList 1 }

rtrsTableEntry OBJECT-TYPE
    SYNTAX      RtrsTableEntry
    MAX-ACCESS  not-accessible
    STATUS      current
    DESCRIPTION
                "MIB tree branch"
    INDEX  { rtrsRtName,
             rtrsRgName,
              rtrsRsName }
    ::= { rtrsTable 1 }

RtrsTableEntry ::=
    SEQUENCE {
        rtrsRtName
            DisplayString,
        rtrsRgName
            DisplayString,
        rtrsRsName
            DisplayString
    }

rtrsRtName OBJECT-TYPE
    SYNTAX      DisplayString
    MAX-ACCESS  read-only
    STATUS      current
    DESCRIPTION
                "Character string value"
    ::= { rtrsTableEntry 1 }

rtrsRgName OBJECT-TYPE
    SYNTAX      DisplayString
    MAX-ACCESS  read-only
    STATUS      current
    DESCRIPTION
                "Character string value"
    ::= { rtrsTableEntry 2 }

rtrsRsName OBJECT-TYPE
    SYNTAX      DisplayString
    MAX-ACCESS  read-only
    STATUS      current
    DESCRIPTION
                "Character string value"
    ::= { rtrsTableEntry 3 }


--***


END
