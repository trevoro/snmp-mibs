-- *****************************************************************************
-- Unisphere-Data-V35-CONF
--
-- SNMP Agent Capabilities definitions for the X.21/V.35 MIB.
--
-- Copyright (c) 2002 Unisphere Networks, Inc.  All rights reserved.
-- *****************************************************************************

Unisphere-Data-V35-CONF DEFINITIONS ::= BEGIN

IMPORTS
    MODULE-IDENTITY
        FROM SNMPv2-SMI
    AGENT-CAPABILITIES
        FROM SNMPv2-CONF
    usDataAgents
        FROM Unisphere-Data-Agents
    usdV35Group
        FROM Unisphere-Data-V35-MIB;

usdV35Agent MODULE-IDENTITY
    LAST-UPDATED "200201252143Z"  -- 25-Jan-02 04:43 PM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the X.21/V.35 server component
        of the SNMP agent in the Unisphere Routing Switch family of products."
    -- Revision History
    REVISION    "200201252143Z"  -- 25-Jan-02 04:43 PM EST  - RX 4.0
    DESCRIPTION
        "The initial release of this management information module."
    ::= { usDataAgents 54 }

usdV35AgentV1 AGENT-CAPABILITIES
    PRODUCT-RELEASE
        "Version 1 of the X.21/V.35 component of the Unisphere Routing Switch
        SNMP agent.  This version of the X.21/V.35 component is supported in the
        Unisphere RX 4.0 and subsequent system releases."
    STATUS      current
    DESCRIPTION
        "The MIB supported by the SNMP agent for the X.21/V.35 application in
        the Unisphere Routing Switch."
    SUPPORTS    Unisphere-Data-V35-MIB
        INCLUDES  {
            usdV35Group }
    ::= { usdV35Agent 1 }

END
