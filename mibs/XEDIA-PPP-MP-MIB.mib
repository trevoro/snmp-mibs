XEDIA-PPP-MP-MIB DEFINITIONS ::= BEGIN

IMPORTS 
    MODULE-IDENTITY, OBJECT-TYPE, Counter32, Gauge32
        FROM SNMPv2-SMI
    MODULE-COMPLIANCE, OBJECT-GROUP
        FROM SNMPv2-CONF
    ifIndex
        FROM IF-MIB
    xediaMibs
        FROM XEDIA-REG
    ;


xediaPppMpMIB MODULE-IDENTITY
    LAST-UPDATED "9809171500Z" -- September 1, 1998   
    ORGANIZATION "Xedia Corp."
    CONTACT-INFO
        "support@xedia.com"
    DESCRIPTION
        "This module defines objects for management of Xedia's 
        PPP Multilink Protocol component."
    ::= { xediaMibs 21 }


-- ****************************************************************
-- Top-level organization of the MIB
-- ****************************************************************

xediaPppMpObjects          OBJECT IDENTIFIER ::= { xediaPppMpMIB 1 }
xediaPppMpConformance      OBJECT IDENTIFIER ::= { xediaPppMpMIB 2 }

mpBundle                   OBJECT IDENTIFIER ::= { xediaPppMpObjects 1 }

-- ****************************************************************
-- Textual Conventions (datatypes)
-- ****************************************************************

-- Hack for pre-1902 compiler:
Unsigned32 ::= Gauge32


-- ****************************************************************
-- Object Definitions
-- ****************************************************************

-- The following tables are used in conjunction with static and
-- dynamic Multilink PPP interfaces.  Static MP interfaces are those
-- configured statically for site-to-site MP sessions whose PPP links
-- are running over real physical links.  Dynamic MP interfaces exist
-- over virtual PPP links created via L2TP.


-- ==============================================
-- The Multilink PPP (MP) Bundle Status Table
-- ==============================================
--

mpBundleStatusTable   OBJECT-TYPE
     SYNTAX     SEQUENCE OF MpBundleStatusEntry
     MAX-ACCESS not-accessible
     STATUS     current
     DESCRIPTION
               "A table containing Multilink PPP bundle specific
               variables for this Multilink PPP implementation.

               The following objects reflect the values of the
               option parameters negotiated during the PPP Link
               Control Protocol negotiation for links that
               reside in this MP Bundle:
                   mpBundleStatusLocalMRRU
                   mpBundleStatusRemoteMRRU
                   mpBundleStatusLocalEndpointDiscr
                   mpBundleStatusRemoteEndpointDiscr
                   mpBundleStatusRcvShortSeq
                   mpBundleStatusXmtShortSeq
                   mpBundleStatusSmallPktMaxSize
                   mpBundleStatusMediumPktMaxSize


               These values are not meaningful until after the
               PPP Option negotiation has completed, which is
               indicated by the link reaching the open state
               (i.e., ifOperStatus is set to up).
 
               Therefore, when ifOperStatus is not up, the values
               of these variables will reflect unnegotiated values, 
               i.e. MRRU and Endpoint Discriminator values will be 0
               while the Rcv and Xmt Short Sequence Numbers will be 
               disabled."               
     ::= { mpBundle 1 }

mpBundleStatusEntry   OBJECT-TYPE
     SYNTAX     MpBundleStatusEntry
     MAX-ACCESS not-accessible
     STATUS     current
     DESCRIPTION
               "Management information about a particular
               PPP Multilink Protocol Bundle."
     INDEX     { ifIndex }
     ::= { mpBundleStatusTable 1 }

MpBundleStatusEntry ::= SEQUENCE {
     mpBundleStatusPacketTooLongs
          Counter32,
     mpBundleStatusLocalMRRU
          Unsigned32,
     mpBundleStatusRemoteMRRU
          Unsigned32,
     mpBundleStatusLocalEndptDiscr
          OCTET STRING,
     mpBundleStatusRemoteEndptDiscr
          OCTET STRING,
     mpBundleStatusRcvShortSeq
          INTEGER,
     mpBundleStatusXmtShortSeq
          INTEGER,
     mpBundleStatusSmallPktMaxSize
          Unsigned32,          
     mpBundleStatusMediumPktMaxSize
          Unsigned32,          
     mpBundleStatusSingleFragsRcvd
          Counter32,
     mpBundleStatusReasmReqds
          Counter32,
     mpBundleStatusReasmFails
          Counter32,
     mpBundleStatusReasmOks
          Counter32,
     mpBundleStatusRcvdFragsDiscarded
          Counter32,
     mpBundleStatusDropTooManyFrags
          Counter32,          
     mpBundleStatusSingleFragsSent
          Counter32,
     mpBundleStatusFragCreates
          Counter32,
     mpBundleStatusFragFails
          Counter32,
     mpBundleStatusFragOks
          Counter32,          
     mpBundleStatusRcvdFragsBuffered
          Counter32     
     }

mpBundleStatusPacketTooLongs   OBJECT-TYPE
     SYNTAX    Counter32
     MAX-ACCESS    read-only
     STATUS    current
     DESCRIPTION
               "The number of received packets that have been
               discarded because their length exceeded the MRRU."
     ::= { mpBundleStatusEntry 1 }

mpBundleStatusLocalMRRU   OBJECT-TYPE
     SYNTAX     Unsigned32 (0..65535)
     MAX-ACCESS read-only
     STATUS     current
     DESCRIPTION
                "The current value of the Maximum Receive
                Reconstructed Unit (MRRU) for the local MP
                entity. This value is the MRRU that the remote MP
                entity is using when sending packets to the local MP
                entity. The value of this object is meaningful only
                when the bundle has reached the open state
                (ifOperStatus is up)."
      ::= { mpBundleStatusEntry 2 }

mpBundleStatusRemoteMRRU   OBJECT-TYPE
     SYNTAX     Unsigned32 (0..65535)
     MAX-ACCESS read-only
     STATUS     current
     DESCRIPTION
               "The current value of the Maximum Receive
               Reconstructed Unit (MRRU) for the remote Multilink PPP
               Entity. This value is the MRRU that the local entity is
               using when sending packets to the remote Multilink PPP
               entity. The value of this object is meaningful only
               when the bundle has reached the open state
               (ifOperStatus is up)."
      ::= { mpBundleStatusEntry 3 }
 
mpBundleStatusLocalEndptDiscr   OBJECT-TYPE
     SYNTAX     OCTET STRING (SIZE (21))
     MAX-ACCESS read-only
     STATUS     current
     DESCRIPTION
               "The current value of the Endpoint Discriminator
               which identifies this Multilink PPP bundle on the
               local peer.  When the remote peer desires to add
               a new link to this Multilink PPP bundle, it will
               include this value during link establishment of
               the new link.  This value will indicate to the
               local peer that the new link is intended to join
               this existing Multilink PPP bundle.
   
               The first byte in the string identifies the Class
               of the Endpoint Discriminator.  The remaining
               bytes in the string contain the actual Endpoint
               Discriminator value."
      REFERENCE
               "Section 5.1.3, Endpoint Discriminator Option, 
               of RFC1990."
      ::= { mpBundleStatusEntry 4 }

mpBundleStatusRemoteEndptDiscr   OBJECT-TYPE
     SYNTAX     OCTET STRING (SIZE (4))
     MAX-ACCESS read-only
     STATUS     current
     DESCRIPTION
                "The current value of the Endpoint Discriminator which
                identifies this Multilink PPP bundle on the remote
                peer.  When the local peer desires to add a new link
                to this Multilink PPP bundle, it will include this
                value during link establishment of the new link.  This
                value will indicate to the remote peer that the new
                link is intended to join this existing Multilink PPP
                bundle.

                The first byte in the string identifies the Class of
                the Endpoint Discriminator.  The remaining bytes in
                the string contain the actual Endpoint Discriminator
                value."
      REFERENCE
               "Section 5.1.3, Endpoint Discriminator Option, 
               of RFC1990."
      ::= { mpBundleStatusEntry 5 }

mpBundleStatusRcvShortSeq   OBJECT-TYPE
     SYNTAX    INTEGER {
               enabled(1),
               disabled(2)
          }
     MAX-ACCESS    read-only
     STATUS        current
     DESCRIPTION
               "Indicates whether the remote Multilink PPP
               entity will use the Short Sequence Number Header
               Format when transmitting packets to the local
               Multilink PPP entity.  The value of this object
               is meaningful only when the bundle has reached the
               open state (ifOperStatus is up)."
      REFERENCE
               "Section 5.1.2, Short Sequence Number Header
               Format Option, of RFC1990."
      ::= { mpBundleStatusEntry 6 }

mpBundleStatusXmtShortSeq   OBJECT-TYPE
     SYNTAX    INTEGER {
               enabled(1),
               disabled(2)
          }
     MAX-ACCESS    read-only
     STATUS        current
     DESCRIPTION
               "Indicates whether the local Multilink PPP
               entity will use the Short Sequence Number Header
               Format when transmitting packets to the remote
               Multilink PPP entity.  The value of this object
               is meaningful only when the bundle has reached the
               open state (ifOperStatus is up)."
      REFERENCE
               "Section 5.1.2, Short Sequence Number Header
               Format Option, of RFC1990."
      ::= { mpBundleStatusEntry 7 } 

mpBundleStatusSmallPktMaxSize   OBJECT-TYPE
     SYNTAX     Unsigned32 (0..65535)
     MAX-ACCESS read-only
     STATUS     current
     DESCRIPTION
               "The maximum size in bytes of a Small PPP packet.
               Use of this parameter is no longer recommended.
               The MP fragmentation threshold is controlled 
               by mpBundleStatusMediumPktMaxSize.

               Small PPP packets are defined to be those which will be
               encapsulated in a single Multilink Protocol Fragment
               and always sent on the first link in the Bundle.

               Note that this parameter only applies to outgoing PPP
               packets sent by this system.  Reassembly of incoming
               packets is unaffected by this value.

               Note that the default value of 12 bytes effectively
               means that no packets are subject to this rule."
     REFERENCE
               "(Not explicitly defined by RFC1990)"
     DEFVAL    { 12 }
     ::= { mpBundleStatusEntry 8 }


mpBundleStatusMediumPktMaxSize   OBJECT-TYPE
     SYNTAX     Unsigned32 (0..65535)
     MAX-ACCESS read-only
     STATUS     current
     DESCRIPTION
               "The maximum size in bytes of a Medium PPP packet.
               This value specifies the threshold at which Multilink
               fragmentation is applied to transmitted packets, i.e.
               packets smaller than this size will be encapsulated in 
               a single Multilink Protocol fragment and sent on a single
               link, packets larger than this size will be fragmented 
               over all links in the bundle.

               This value starts at mpBundleConfigMediumPktMaxSize
               and is adjusted downwards according to the peer's MRRU
               and each of the peer's link's MRUs.

               Medium PPP packets are defined to be those which will be
               encapsulated in a single Multilink Protocol Fragment
               and sent on each link in the Bundle in a round-robin
               fashion.

               Packets larger than this threshold are considered Large
               PPP packets.  Large PPP packets will be fragmented into
               multiple Multilink Protocol Fragments and sent across
               all links in the bundle.
        
               Setting this value to its maximum (65535) will prevent
               fragmentation at the MP layer of outgoing PPP packets,
               i.e. it will cause all outgoing PPP packets to be
               considered either Small or Medium sized PPP packets.

               Note that this parameter only applies to outgoing PPP
               packets sent by this system.  Reassembly of incoming
               packets is unaffected by this value."
     REFERENCE
               "(Not explicitly defined by RFC1990)"
     DEFVAL    { 64 }
     ::= { mpBundleStatusEntry 9 }


mpBundleStatusSingleFragsRcvd   OBJECT-TYPE
     SYNTAX    Counter32
     MAX-ACCESS    read-only
     STATUS    current
     DESCRIPTION
               "The number of MP fragments received that contain
                an entire PPP packet."
     ::= { mpBundleStatusEntry 10 }

mpBundleStatusReasmReqds   OBJECT-TYPE
     SYNTAX    Counter32
     MAX-ACCESS    read-only
     STATUS    current
     DESCRIPTION
               "The number of MP fragments received that require
                reassembly into PPP packets."
     ::= { mpBundleStatusEntry 11 }

mpBundleStatusReasmFails   OBJECT-TYPE
     SYNTAX    Counter32
     MAX-ACCESS    read-only
     STATUS    current
     DESCRIPTION
               "The number of fragmented PPP packets which failed
                to be reassembled."
     ::= { mpBundleStatusEntry 12 }

mpBundleStatusReasmOks   OBJECT-TYPE
     SYNTAX    Counter32
     MAX-ACCESS    read-only
     STATUS    current
     DESCRIPTION
               "The number of fragmented PPP packets received and
                successfully reassembled."
     ::= { mpBundleStatusEntry 13 }

mpBundleStatusRcvdFragsDiscarded   OBJECT-TYPE
     SYNTAX    Counter32
     MAX-ACCESS    read-only
     STATUS    current
     DESCRIPTION
               "The number of MP fragments discarded
                for some reason by the MP layer."
     ::= { mpBundleStatusEntry 14 }


mpBundleStatusDropTooManyFrags   OBJECT-TYPE
     SYNTAX    Counter32
     MAX-ACCESS    read-only
     STATUS    current
     DESCRIPTION
               "The number of MP fragments discarded because the
               MP layer has no more space to buffer fragments."
     ::= { mpBundleStatusEntry 15 }

mpBundleStatusSingleFragsSent   OBJECT-TYPE
     SYNTAX    Counter32
     MAX-ACCESS    read-only
     STATUS    current
     DESCRIPTION
               "The number of MP fragments sent that contain
                an entire PPP packet."
     ::= { mpBundleStatusEntry 16 }

mpBundleStatusFragCreates   OBJECT-TYPE
     SYNTAX    Counter32
     MAX-ACCESS    read-only
     STATUS    current
     DESCRIPTION
               "The number of MP fragments created to contain
                a fragment of a PPP packet."
     ::= { mpBundleStatusEntry 17 }

mpBundleStatusFragFails   OBJECT-TYPE
     SYNTAX    Counter32
     MAX-ACCESS    read-only
     STATUS    current
     DESCRIPTION
               "The number of attempts to create an MP fragment
                which failed and resulted in discarding of the
                PPP packet to be transmitted."
     ::= { mpBundleStatusEntry 18 }

mpBundleStatusFragOks   OBJECT-TYPE
     SYNTAX    Counter32
     MAX-ACCESS    read-only
     STATUS    current
     DESCRIPTION
               "The number of MP fragments successfully sent
                which contain a fragment of a PPP packet."
     ::= { mpBundleStatusEntry 19 }

mpBundleStatusRcvdFragsBuffered   OBJECT-TYPE
     SYNTAX    Counter32
     MAX-ACCESS    read-only
     STATUS    current
     DESCRIPTION
               "The number of received MP fragments currently
                buffered awaiting reassembly and delivery"
     ::= { mpBundleStatusEntry 20 }


-- ==============================================
-- The Multilink PPP (MP) Bundle Config Table
-- ==============================================
--

mpBundleConfigTable   OBJECT-TYPE
     SYNTAX     SEQUENCE OF MpBundleConfigEntry
     MAX-ACCESS not-accessible
     STATUS     current
     DESCRIPTION
               "A table containing the LCP configuration
               parameters for this PPP MP Bundle. These variables
               represent the initial configuration of the PPP MP
               Bundle. The actual values of the negotiable
               parameters (MRRU and Short Sequence Numbers) may
               be changed during LCP negotiation as the link is
               brought up.

               The following objects reflect the initial values
               that will be proposed when LCP negotiation begins:
                    mpBundleConfigLocalMRRU
                    mpBundleConfigLocalEndptDiscr
                    mpBundleConfigRcvShortSeq

               Note: the Endpoint Discriminator is non-negotiable,
               the value configured above (or the default if this
               is not configured) will be the Endpoint Discriminator used.

               The following objects are not negotiated during LCP:
                    mpBundleConfigSmallPktMaxSize
                    mpBundleConfigMediumPktMaxSize."
     ::= { mpBundle 2 }

mpBundleConfigEntry   OBJECT-TYPE
     SYNTAX     MpBundleConfigEntry
     MAX-ACCESS not-accessible
     STATUS     current
     DESCRIPTION
                "Configuration information for a particular
                Multilink PPP Bundle."
     INDEX     { ifIndex }
     ::= { mpBundleConfigTable 1 }

MpBundleConfigEntry ::= SEQUENCE {
     mpBundleConfigLocalMRRU
          Unsigned32,
     mpBundleConfigLocalEndptDiscr
          OCTET STRING,
     mpBundleConfigRcvShortSeq
          INTEGER,
     mpBundleConfigSmallPktMaxSize
          Unsigned32,
     mpBundleConfigMediumPktMaxSize
          Unsigned32                
     }

mpBundleConfigLocalMRRU   OBJECT-TYPE
     SYNTAX     Unsigned32 (0..65535)
     MAX-ACCESS read-write
     STATUS     current
     DESCRIPTION
                "The initial Maximum Receive Reconstructed Unit
               (MRRU) that the local MP entity will advertise to
               the remote entity at the onset of LCP
               negotiation. If the value of this variable is 0
               then the local MP entity will advertise the
               default MRRU value of 1600 bytes. Changing this
               object will have effect when the link is next
               restarted.

               After the link comes up, the status variable
               mpBundleStatusLocalMRRU will reflect the actual
               MRRU negotiated with the peer during LCP
               negotiation."
     REFERENCE
               "Section 5.1.1, Multilink MRRU LCP option of RFC 1990."
     DEFVAL    { 1600 }
     ::= { mpBundleConfigEntry 1 }

mpBundleConfigLocalEndptDiscr   OBJECT-TYPE
     SYNTAX      OCTET STRING (SIZE (0..21))
     MAX-ACCESS  read-write
     STATUS      current
     DESCRIPTION
               "The value to be advertised to the remote peer
               as the Endpoint Discriminator to be used to
               identify this Multilink PPP bundle.

               After the remote peer has received this value,
               it should include this value during LCP
               negotiation of any new links intended to join
               this Multilink PPP bundle.
   
               The first byte in the string identifies the Class
               of the Endpoint Discriminator.  The remaining
               bytes in the string contain the actual Endpoint
               Discriminator value.

               If the value of this variable is 0 then the
               local peer will use the MAC address of the local
               box as the value to advertise as the local
               Endpoint Discriminator.

               After the link comes up, the status variable
               mpBundleStatusLocalEndptDiscr will reflect this
               Endpoint Discriminator value which has been
               sent to the peer (i.e. this value is not
               negotiated with the peer, the peer must accept
               whatever Endpoint Discriminator we send to them)."
     REFERENCE
               "Section 5.1.3, Endpoint Discriminator Option, 
               of RFC 1990."
     DEFVAL    { '0'h }
     ::= { mpBundleConfigEntry 2 }

mpBundleConfigRcvShortSeq   OBJECT-TYPE
     SYNTAX     INTEGER {
        enabled (1), 
        disabled (2)
        }
     MAX-ACCESS read-write
     STATUS     current
     DESCRIPTION
               "If enabled(1) then the local peer will attempt
               to negotiate Short Sequence Number Header
               Format for the MP encapsulated PPP traffic sent
               from the remote peer to the local peer.

               If disabled(2) then no attempt to negotiate
               Short Sequence Numbers will be performed,
               indicating that instead the default Long
               Sequence Number Fragment Format should be used
               for all traffic sent by the remote peer to
               the local peer.

               This setting has no effect on the negotation of
               Short Sequence Number Header Format for the
               traffic flowing in the opposite direction (from
               the local peer to the remote peer).  The use of
               Short Sequence Number Fragment Format on that
               traffic will be determined by whatever the
               remote peer proposes. 

               Changing this object will have effect when the
               link is next restarted (either by toggling
               ifAdminStatus for this interface down and then
               up again, or by rebooting the entire system).

               After the link comes up, the status variable
               mpBundleStatusLocalMRRU will reflect the actual
               MRRU negotiated with the peer during LCP
               negotiation."
     REFERENCE
                "Section 5.1.2, Short Sequence Number Header Format Option,
                of RFC1990."
     DEFVAL    { enabled }
     ::= { mpBundleConfigEntry 3 }


mpBundleConfigSmallPktMaxSize   OBJECT-TYPE
     SYNTAX     Unsigned32 (0..65535)
     MAX-ACCESS read-write
     STATUS     current
     DESCRIPTION
               "The maximum size in bytes of a Small PPP packet.
               Use of this parameter is no longer recommended.
               To control the MP fragmentation threshold see
               mpBundleConfigMediumPktMaxSize. 

               Small PPP packets are defined to be those which will be
               encapsulated in a single Multilink Protocol Fragment
               and always sent on the first link in the Bundle.

               Note that this parameter only applies to outgoing PPP
               packets sent by this system.  Reassembly of incoming
               packets is unaffected by this value.

               Note that the default value of 12 bytes effectively
               means that no packets are subject to this rule."
     REFERENCE
               "(Not explicitly defined by RFC1990)"
     DEFVAL    { 12 }
     ::= { mpBundleConfigEntry 4 }


mpBundleConfigMediumPktMaxSize   OBJECT-TYPE
     SYNTAX     Unsigned32 (0..65535)
     MAX-ACCESS read-write
     STATUS     current
     DESCRIPTION
               "The maximum size in bytes of a Medium PPP packet.
               This value specifies the threshold at which Multilink
               fragmentation is applied to transmitted packets, i.e.
               packets smaller than this size will be encapsulated in 
               a single Multilink Protocol fragment and sent on a single
               link, packets larger than this size will be fragmented 
               over all links in the bundle.

               Medium PPP packets are defined to be those which will be
               encapsulated in a single Multilink Protocol Fragment
               and sent on each link in the Bundle in a round-robin
               fashion.

               Packets larger than this threshold are considered Large
               PPP packets.  Large PPP packets will be fragmented into
               multiple Multilink Protocol Fragments and sent across
               all links in the bundle.
        
               Setting this value to its maximum (65535) will prevent
               fragmentation at the MP layer of outgoing PPP packets,
               i.e. it will cause all outgoing PPP packets to be
               considered either Small or Medium sized PPP packets.

               Note that this parameter only applies to outgoing PPP
               packets sent by this system.  Reassembly of incoming
               packets is unaffected by this value."
     REFERENCE
               "(Not explicitly defined by RFC1990)"
     DEFVAL    { 64 }
     ::= { mpBundleConfigEntry 5 }



-- ****************************************************************
-- Conformance Statements
-- ****************************************************************

mpCompliances OBJECT IDENTIFIER ::= { xediaPppMpConformance 1 }
mpGroups      OBJECT IDENTIFIER ::= { xediaPppMpConformance 2 }

--
-- Compliance Statements
--

mpCompliance MODULE-COMPLIANCE
    STATUS      current
    DESCRIPTION
        "The compliance statement for all agents that support this
        MIB. A compliant agent implements all objects defined in this
        MIB."
    MODULE  -- this module
    MANDATORY-GROUPS {
        mpAllGroup
    }
    ::= { mpCompliances 1 }

--
-- Object Groups
--

mpAllGroup OBJECT-GROUP
    OBJECTS {
        mpBundleStatusPacketTooLongs,
        mpBundleStatusLocalMRRU,
        mpBundleStatusRemoteMRRU,
        mpBundleStatusLocalEndptDiscr,
        mpBundleStatusRemoteEndptDiscr,
        mpBundleStatusRcvShortSeq,
        mpBundleStatusXmtShortSeq,
        mpBundleStatusSmallPktMaxSize,
        mpBundleStatusMediumPktMaxSize,
        mpBundleStatusSingleFragsRcvd,
        mpBundleStatusReasmReqds,
        mpBundleStatusReasmFails,
        mpBundleStatusReasmOks,
        mpBundleStatusRcvdFragsDiscarded,
        mpBundleStatusDropTooManyFrags,
        mpBundleStatusSingleFragsSent,
        mpBundleStatusFragCreates,
        mpBundleStatusFragFails,
        mpBundleStatusFragOks,
        mpBundleStatusRcvdFragsBuffered,
        mpBundleConfigLocalMRRU,
        mpBundleConfigLocalEndptDiscr,
        mpBundleConfigRcvShortSeq,
        mpBundleConfigSmallPktMaxSize,
        mpBundleConfigMediumPktMaxSize
     }
    STATUS      current
    DESCRIPTION
        "The set of all accessible objects in this MIB."
    ::= { mpGroups 1 }

END
