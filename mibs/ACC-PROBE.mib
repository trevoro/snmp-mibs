ACC-PROBE DEFINITIONS ::= BEGIN

    IMPORTS
	 OBJECT-TYPE, IpAddress, TimeTicks, Gauge, Counter FROM RFC1155-SMI
        accTrapLogSeqNum FROM ACC-SYSTEM
accBRG, DisplayString, RowStatus, IfIndex, SmdsAddress
             FROM ACC-MIB;
-- Probe Group
     accProbe           OBJECT IDENTIFIER  ::= { accBRG 13 }
	accProbeAddr	OBJECT-TYPE   
			SYNTAX	OCTET STRING
			ACCESS	read-write
			STATUS	mandatory
			DESCRIPTION
               		 " Hexadecimal representation of the memory 
			   address of the long-word whose content we seek."
			::= { accProbe 1 }
	accProbeData	OBJECT-TYPE   
			SYNTAX	INTEGER
			ACCESS	read-only
			STATUS	mandatory
			DESCRIPTION
              		 " Contents (long word) of memory location 
			   of accProbeAddr."
			::= { accProbe 2 }

END
