Nortel-Magellan-Passport-FrameRelayUniMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      PassportCounter64,
      InterfaceIndex,
      Gauge32,
      Integer32,
      Unsigned32
   FROM Nortel-Magellan-Passport-StandardTextualConventionsMIB

      AsciiString,
      Hex,
      NonReplicated,
      FixedPoint3,
      HexString,
      EnterpriseDateAndTime,
      Link,
      DigitString,
      Unsigned64
   FROM Nortel-Magellan-Passport-TextualConventionsMIB;




-- LAST-UPDATED   "9905250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrameRelayUni Enterprise MIB."

frameRelayUniMIB OBJECT IDENTIFIER ::= { passportMIBs 24 }










-- FrameRelayUni/n
-- This component defines an instance of the Frame Relay UNI 
-- service. The component instance value n is a unique positive integer 
-- within a module. Framer is created whenever the FrUni is added. 
-- Users who need VirtualFramer should delete the Framer first, then 
-- add the VirtualFramer.

frUni OBJECT IDENTIFIER ::= { components 71 }



frUniRowStatusTable OBJECT-TYPE
   SYNTAX     SEQUENCE OF FrUniRowStatusEntry
   ACCESS     not-accessible
   STATUS     mandatory
   DESCRIPTION
     "This entry controls the addition and deletion of 
      frUni components."
::= { frUni 1 }

frUniRowStatusEntry OBJECT-TYPE
   SYNTAX     FrUniRowStatusEntry
   ACCESS     not-accessible
   STATUS     mandatory
   DESCRIPTION
     "A single entry in the table represents a single 
      frUni component."
   INDEX {
      frUniIndex }
::= { frUniRowStatusTable 1 }

FrUniRowStatusEntry ::= SEQUENCE {
   frUniRowStatus
      RowStatus,
   frUniComponentName
      DisplayString,
   frUniStorageType
      StorageType,
   frUniIndex
      Integer32 }

frUniRowStatus OBJECT-TYPE
   SYNTAX     RowStatus 
   ACCESS     read-write
   STATUS     mandatory
   DESCRIPTION
     "This variable is used as the basis for SNMP naming of
      frUni components.
      These components can be added and deleted."
::= { frUniRowStatusEntry 1 }

frUniComponentName OBJECT-TYPE
   SYNTAX     DisplayString 
   ACCESS     read-only
   STATUS     mandatory
   DESCRIPTION
     "This variable provides the component's string name for
      use with the ASCII Console Interface"
::= { frUniRowStatusEntry 2 }

frUniStorageType OBJECT-TYPE
   SYNTAX     StorageType 
   ACCESS     read-only
   STATUS     mandatory
   DESCRIPTION
     "This variable represents the storage type value for the
      frUni tables."
::= { frUniRowStatusEntry 4 }

frUniIndex OBJECT-TYPE
   SYNTAX     Integer32 (1..65535)
   ACCESS     not-accessible
   STATUS     mandatory
   DESCRIPTION
     "This variable represents the index for the frUni tables."
::= { frUniRowStatusEntry 10 }

frUniCidDataTable OBJECT-TYPE
   SYNTAX     SEQUENCE OF FrUniCidDataEntry
   ACCESS     not-accessible
   STATUS     mandatory
   DESCRIPTION
     "This group contains the attribute for a component's Customer 
      Identifier (CID). Refer to the attribute description for a detailed 
      explanation of CIDs."
::= { frUni 10 }

frUniCidDataEntry OBJECT-TYPE
   SYNTAX     FrUniCidDataEntry
   ACCESS     not-accessible
   STATUS     mandatory
   DESCRIPTION
     "An entry in the frUniCidDataTable."
   INDEX {
      frUniIndex }
::= { frUniCidDataTable 1 }

FrUniCidDataEntry ::= SEQUENCE {
   frUniCustomerIdentifier
      Unsigned32 }

frUniCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { frUniCidDataEntry 1 }

frUniStateTable OBJECT-TYPE
   SYNTAX     SEQUENCE OF FrUniStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { frUni 11 }

frUniStateEntry OBJECT-TYPE
   SYNTAX     FrUniStateEntry
   ACCESS     not-accessible
   STATUS     mandatory
   DESCRIPTION
     "An entry in the frUniStateTable."
   INDEX {
      frUniIndex }
::= { frUniStateTable 1 }

FrUniStateEntry ::= SEQUENCE {
   frUniAdminState
      INTEGER,
   frUniOperationalState
      INTEGER,
   frUniUsageState
      INTEGER,
   frUniAvailabilityStatus
      OCTET STRING,
   frUniProceduralStatus
      OCTET STRING,
   frUniControlStatus
      OCTET STRING,
   frUniAlarmStatus
      OCTET STRING,
   frUniStandbyStatus
      INTEGER,
   frUniUnknownStatus
      INTEGER }

frUniAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { frUniStateEntry 1 }

frUniOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { frUniStateEntry 2 }

frUniUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { frUniStateEntry 3 }

frUniAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { frUniStateEntry 4 }

frUniProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { frUniStateEntry 5 }

frUniControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { frUniStateEntry 6 }

frUniAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { frUniStateEntry 7 }

frUniStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { frUniStateEntry 8 }

frUniUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { frUniStateEntry 9 }

frUniStatsTable OBJECT-TYPE
   SYNTAX     SEQUENCE OF FrUniStatsEntry
   ACCESS     not-accessible
   STATUS     mandatory
   DESCRIPTION
     "FrUni/n Statistics
      This group contains the statistics about the operational behavior of 
      the service at the interface level."
::= { frUni 12 }

frUniStatsEntry OBJECT-TYPE
   SYNTAX     FrUniStatsEntry
   ACCESS     not-accessible
   STATUS     mandatory
   DESCRIPTION
     "An entry in the frUniStatsTable."
   INDEX {
      frUniIndex }
::= { frUniStatsTable 1 }

FrUniStatsEntry ::= SEQUENCE {
   frUniLastUnknownDlci
      Unsigned32,
   frUniUnknownDlciFramesFromIf
      Counter32,
   frUniInvalidHeaderFramesFromIf
      Counter32 }

frUniLastUnknownDlci OBJECT-TYPE
   SYNTAX     Unsigned32 (0..1023)
   ACCESS     read-only
   STATUS     mandatory
   DESCRIPTION
     "This attribute identifies the most recent DLCI which user frames 
      were received on for which a DLCI has not been provisioned on the 
      port."
   DEFVAL     { 0 }
::= { frUniStatsEntry 1 }

frUniUnknownDlciFramesFromIf OBJECT-TYPE
   SYNTAX     Counter32 
   ACCESS     read-only
   STATUS     mandatory
   DESCRIPTION
     "This attribute contains a count of the number of frames received 
      from the interface with an unknown DLCI (DLCI which is not 
      provisioned). When the maximum is reached the count wraps to 
      zero."
::= { frUniStatsEntry 2 }

frUniInvalidHeaderFramesFromIf OBJECT-TYPE
   SYNTAX     Counter32 
   ACCESS     read-only
   STATUS     mandatory
   DESCRIPTION
     "This attribute counts the number of frames received from the 
      interface with an invalid header format. When the maximum is 
      reached the count wraps to zero."
::= { frUniStatsEntry 3 }

frUniIfEntryTable OBJECT-TYPE
   SYNTAX     SEQUENCE OF FrUniIfEntryEntry
   ACCESS     not-accessible
   STATUS     mandatory
   DESCRIPTION
     "This group contains the provisionable attributes for the ifEntry."
::= { frUni 13 }

frUniIfEntryEntry OBJECT-TYPE
   SYNTAX     FrUniIfEntryEntry
   ACCESS     not-accessible
   STATUS     mandatory
   DESCRIPTION
     "An entry in the frUniIfEntryTable."
   INDEX {
      frUniIndex }
::= { frUniIfEntryTable 1 }

FrUniIfEntryEntry ::= SEQUENCE {
   frUniIfAdminStatus
      INTEGER,
   frUniIfIndex
      InterfaceIndex }

frUniIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { frUniIfEntryEntry 1 }

frUniIfIndex OBJECT-TYPE
   SYNTAX     InterfaceIndex (1..65535)
   ACCESS     read-only
   STATUS     mandatory
   DESCRIPTION
     "This is the index for the IfEntry. Its value is automatically initialized 
      during the provisioning process."
::= { frUniIfEntryEntry 2 }

frUniOperStatusTable OBJECT-TYPE
   SYNTAX     SEQUENCE OF FrUniOperStatusEntry
   ACCESS     not-accessible
   STATUS     mandatory
   DESCRIPTION
     "This group includes the Operational Status attribute. This attribute 
      defines the current operational state of this component."
::= { frUni 14 }

frUniOperStatusEntry OBJECT-TYPE
   SYNTAX     FrUniOperStatusEntry
   ACCESS     not-accessible
   STATUS     mandatory
   DESCRIPTION
     "An entry in the frUniOperStatusTable."
   INDEX {
      frUniIndex }
::= { frUniOperStatusTable 1 }

FrUniOperStatusEntry ::= SEQUENCE {
   frUniSnmpOperStatus
      INTEGER }

frUniSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { frUniOperStatusEntry 1 }

frUniEmissionPriorityQsTable OBJECT-TYPE
   SYNTAX     SEQUENCE OF FrUniEmissionPriorityQsEntry
   ACCESS     not-accessible
   STATUS     mandatory
   DESCRIPTION
     "This group contains the provisionable attribute to specifie the 
      number of Frame Relay egress emission priority queues to be used 
      on that Frame Relay Interface"
::= { frUni 15 }

frUniEmissionPriorityQsEntry OBJECT-TYPE
   SYNTAX     FrUniEmissionPriorityQsEntry
   ACCESS     not-accessible
   STATUS     mandatory
   DESCRIPTION
     "An entry in the frUniEmissionPriorityQsTable."
   INDEX {
      frUniIndex }
::= { frUniEmissionPriorityQsTable 1 }

FrUniEmissionPriorityQsEntry ::= SEQUENCE {
   frUniNumberOfEmissionQs
      Unsigned32 }

frUniNumberOfEmissionQs OBJECT-TYPE
   SYNTAX     Unsigned32 (2 | 4)
   ACCESS     read-write
   STATUS     mandatory
   DESCRIPTION
     "This attribute specifies the number of egress emission priority 
      queues that will be used for that Frame Relay interface. The 
      possible values of this attribute are 2 or 4:
      For V.35, V.11, HSSI, E1, DS1, E3, DS3 or 8pDS1 the possible 
      values are: 2 (in which case they are hardware queues), or 4 (in 
      which case they are software queues).
      For DS1C, E1C or DS3C the possible values are 2, 4 (in all cases 
      they are software queues)."
   DEFVAL     { 2 }
::= { frUniEmissionPriorityQsEntry 1 }

frUniFrmToIfByQueueTable OBJECT-TYPE
   SYNTAX     SEQUENCE OF FrUniFrmToIfByQueueEntry
   ACCESS     not-accessible
   STATUS     mandatory
   DESCRIPTION
     "This attribute counts the total number of frames transmitted to the 
      interface per egress emission priority queue since the component 
      has been activated. There is potientially a maximum of 4 emission 
      priority queues. The number of available egress queues varies 
      according to the value of the provisionable attribute 
      numberOfEmissionQs. Egress queue 0 has the lowest priority, while 
      egress queue 3 has the highest priority. The queue values
      are only indicated when the numberOfEmissionQs is set to 4 
      queues."
::= { frUni 341 }

frUniFrmToIfByQueueEntry OBJECT-TYPE
   SYNTAX     FrUniFrmToIfByQueueEntry
   ACCESS     not-accessible
   STATUS     mandatory
   DESCRIPTION
     "An entry in the frUniFrmToIfByQueueTable."
   INDEX {
      frUniIndex,
      frUniFrmToIfByQueueIndex }
::= { frUniFrmToIfByQueueTable 1 }

FrUniFrmToIfByQueueEntry ::= SEQUENCE {
   frUniFrmToIfByQueueIndex
      Integer32,
   frUniFrmToIfByQueueValue
      Unsigned32 }

frUniFrmToIfByQueueIndex OBJECT-TYPE
   SYNTAX     Integer32 (0..3)
   ACCESS     not-accessible
   STATUS     mandatory
   DESCRIPTION
     "This variable represents the index for the frUniFrmToIfByQueueTable."
::= { frUniFrmToIfByQueueEntry 1 }

frUniFrmToIfByQueueValue OBJECT-TYPE
   SYNTAX     Unsigned32 (0..4294967295)
   ACCESS     read-only
   STATUS     mandatory
   DESCRIPTION
     "This variable represents an individual value for the
      frUniFrmToIfByQueueTable."
::= { frUniFrmToIfByQueueEntry 2 }

frUniOctetToIfByQueueTable OBJECT-TYPE
   SYNTAX     SEQUENCE OF FrUniOctetToIfByQueueEntry
   ACCESS     not-accessible
   STATUS     mandatory
   DESCRIPTION
     "This attribute counts the total number of octets transmitted from the 
      service to the interface per emission priority queue since the 
      component has been activated. There is potientially a maximum of 
      4 emission priority queues. The number of available egress queues 
      varies according to the value of the provisionable attribute 
      numberOfEmissionQs. Egress queue 0 has the lowest priority, while 
      egress queue 3 has the highest priority."
::= { frUni 342 }

frUniOctetToIfByQueueEntry OBJECT-TYPE
   SYNTAX     FrUniOctetToIfByQueueEntry
   ACCESS     not-accessible
   STATUS     mandatory
   DESCRIPTION
     "An entry in the frUniOctetToIfByQueueTable."
   INDEX {
      frUniIndex,
      frUniOctetToIfByQueueIndex }
::= { frUniOctetToIfByQueueTable 1 }

FrUniOctetToIfByQueueEntry ::= SEQUENCE {
   frUniOctetToIfByQueueIndex
      Integer32,
   frUniOctetToIfByQueueValue
      Unsigned32 }

frUniOctetToIfByQueueIndex OBJECT-TYPE
   SYNTAX     Integer32 (0..3)
   ACCESS     not-accessible
   STATUS     mandatory
   DESCRIPTION
     "This variable represents the index for the frUniOctetToIfByQueueTable."
::= { frUniOctetToIfByQueueEntry 1 }

frUniOctetToIfByQueueValue OBJECT-TYPE
   SYNTAX     Unsigned32 (0..4294967295)
   ACCESS     read-only
   STATUS     mandatory
   DESCRIPTION
     "This variable represents an individual value for the
      frUniOctetToIfByQueueTable."
::= { frUniOctetToIfByQueueEntry 2 }


-- This group contains a superset of all attributes which may apply to a 
-- VC. Particular applications will typically offer only a subset of 
-- these attributes by providing a definition of their own DNA 
-- subcomponent. 

frUniDna OBJECT IDENTIFIER ::= { frUni 2 }



frUniDnaRowStatusTable OBJECT-TYPE
   SYNTAX     SEQUENCE OF FrUniDnaRowStatusEntry
   ACCESS     not-accessible
   STATUS     mandatory
   DESCRIPTION
     "This entry controls the addition and deletion of 
      frUniDna components."
::= { frUniDna 1 }

frUniDnaRowStatusEntry OBJECT-TYPE
   SYNTAX     FrUniDnaRowStatusEntry
   ACCESS     not-accessible
   STATUS     mandatory
   DESCRIPTION
     "A single entry in the table represents a single 
      frUniDna component."
   INDEX {
      frUniIndex,
      frUniDnaIndex }
::= { frUniDnaRowStatusTable 1 }

FrUniDnaRowStatusEntry ::= SEQUENCE {
   frUniDnaRowStatus
      RowStatus,
   frUniDnaComponentName
      DisplayString,
   frUniDnaStorageType
      StorageType,
   frUniDnaIndex
      NonReplicated }

frUniDnaRowStatus OBJECT-TYPE
   SYNTAX     RowStatus 
   ACCESS     read-only
   STATUS     mandatory
   DESCRIPTION
     "This variable is used as the basis for SNMP naming of
      frUniDna components.
      These components cannot be added nor deleted."
::= { frUniDnaRowStatusEntry 1 }

frUniDnaComponentName OBJECT-TYPE
   SYNTAX     DisplayString 
   ACCESS     read-only
   STATUS     mandatory
   DESCRIPTION
     "This variable provides the component's string name for
      use with the ASCII Console Interface"
::= { frUniDnaRowStatusEntry 2 }

frUniDnaStorageType OBJECT-TYPE
   SYNTAX     StorageType 
   ACCESS     read-only
   STATUS     mandatory
   DESCRIPTION
     "This variable represents the storage type value for the
      frUniDna tables."
::= { frUniDnaRowStatusEntry 4 }

frUniDnaIndex OBJECT-TYPE
   SYNTAX     NonReplicated 
   ACCESS     not-accessible
   STATUS     mandatory
   DESCRIPTION
     "This variable represents the index for the frUniDna tables."
::= { frUniDnaRowStatusEntry 10 }

frUniDnaAddressTable OBJECT-TYPE
   SYNTAX     SEQUENCE OF FrUniDnaAddressEntry
   ACCESS     not-accessible
   STATUS     mandatory
   DESCRIPTION
     "This group contains attributes common to all DNAs. Every DNA 
      used in the network is defined with this group of 2 attributes."
::= { frUniDna 10 }

frUniDnaAddressEntry OBJECT-TYPE
   SYNTAX     FrUniDnaAddressEntry
   ACCESS     not-accessible
   STATUS     mandatory
   DESCRIPTION
     "An entry in the frUniDnaAddressTable."
   INDEX {
      frUniIndex,
      frUniDnaIndex }
::= { frUniDnaAddressTable 1 }

FrUniDnaAddressEntry ::= SEQUENCE {
   frUniDnaNumberingPlanIndicator
      INTEGER,
   frUniDnaDataNetworkAddress
      DigitString }

frUniDnaNumberingPlanIndicator OBJECT-TYPE
   SYNTAX     INTEGER  {
                 x121(0),
                 e164(1) }
   ACCESS     read-write
   STATUS     mandatory
   DESCRIPTION
     "This attribute indicates the Numbering Plan Indicator (NPI) of the 
      DNA that is entered. Address may belong to X.121 or E.164 plans. 
      X.121 is used in packet switched data networks."
   DEFVAL     { x121 }
::= { frUniDnaAddressEntry 1 }

frUniDnaDataNetworkAddress OBJECT-TYPE
   SYNTAX     DigitString (SIZE (1..15))
   ACCESS     read-write
   STATUS     mandatory
   DESCRIPTION
     "This attribute indicates the customer's unique identifier. It is the 
      equivalent of the telephone number in the telephone network."
::= { frUniDnaAddressEntry 2 }

frUniDnaOutgoingOptionsTable OBJECT-TYPE
   SYNTAX     SEQUENCE OF FrUniDnaOutgoingOptionsEntry
   ACCESS     not-accessible
   STATUS     mandatory
   DESCRIPTION
     "This group defines DNA call options for calls made from the 
      interface. These options are not used for calls arriving to the 
      interface represented by this DNA."
::= { frUniDna 11 }

frUniDnaOutgoingOptionsEntry OBJECT-TYPE
   SYNTAX     FrUniDnaOutgoingOptionsEntry
   ACCESS     not-accessible
   STATUS     mandatory
   DESCRIPTION
     "An entry in the frUniDnaOutgoingOptionsTable."
   INDEX {
      frUniIndex,
      frUniDnaIndex }
::= { frUniDnaOutgoingOptionsTable 1 }

FrUniDnaOutgoingOptionsEntry ::= SEQUENCE {
   frUniDnaOutDefaultPriority
      INTEGER,
   frUniDnaOutDefaultPathSensitivity
      INTEGER,
   frUniDnaOutPathSensitivityOverRide
      INTEGER,
   frUniDnaOutDefaultPathReliability
      INTEGER,
   frUniDnaOutAccess
      INTEGER,
   frUniDnaDefaultTransferPriority
      INTEGER,
   frUniDnaTransferPriorityOverRide
      INTEGER }

frUniDnaOutDefaultPriority OBJECT-TYPE
   SYNTAX     INTEGER  {
                 normal(0),
                 high(1) }
   ACCESS     read-write
   STATUS     mandatory
   DESCRIPTION
     "This attribute indicates the default priority of outgoing calls from 
      the DTE to the network.
      
      It can be overridden by the discardPriority under DLCI Direct Call 
      subcomponent.
      
      This option can be also included in X.25 signalling, in such case it 
      will be overruled."
   DEFVAL     { normal }
::= { frUniDnaOutgoingOptionsEntry 7 }

frUniDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls that use this DNA. The chosen default 
      class of path sensitivity applies to all outgoing calls established 
      using this DNA. 
      
      This attribute, if set to throughput, indicates that the default class is 
      throughput sensitive. If set to delay, then the default class is delay 
      sensitive. The default of outDefaultPathSensitivity is throughput."
   DEFVAL     { throughput }
::= { frUniDnaOutgoingOptionsEntry 11 }

frUniDnaOutPathSensitivityOverRide OBJECT-TYPE
   SYNTAX     INTEGER  {
                 no(0),
                 yes(1) }
   ACCESS     read-write
   STATUS     obsolete
   DESCRIPTION
     "If this attribute is set to yes in the call request, the called end will 
      use the calling end provisioning data on path sensitivity to override 
      its own provisioning data.
      
      The default of outPathSensitivityOverRide is yes."
   DEFVAL     { yes }
::= { frUniDnaOutgoingOptionsEntry 12 }

frUniDnaOutDefaultPathReliability OBJECT-TYPE
   SYNTAX     INTEGER  {
                 high(0),
                 normal(1) }
   ACCESS     read-write
   STATUS     mandatory
   DESCRIPTION
     "This attribute specifies the default class of routing for reliability 
      routing for all outgoing calls (from the DTE to the network) using 
      this particular DNA. The chosen default class of routing applies to 
      all outgoing calls established using this DNA, and applies to the 
      packets travelling in both directions on all outgoing calls (local to 
      remote, and remote to local). For incoming calls, the default class of 
      routing is chosen by the calling party (as opposed to DPN, where 
      either end of the call can choose the default routing class).
      This attribute, if set to a value of normal, indicates that the default 
      class of routing is normal reliability routing. If set to a value of 
      high, then the default class of routing is high reliability routing.
      High reliability is the standard choice for most DPN and Passport 
      services. It usually indicates that packets are overflowed or 
      retransmitted at various routing levels. Typically high reliability 
      results in duplication and disordering of packets in the network 
      when errors are detected or during link congestion. However, the 
      VC handles the duplication and disordering to ensure that packets 
      are delivered to the DTE properly.
      For the Frame Relay service, duplication of packets is not desired, 
      in which case, normal reliability may be chosen as the preferred 
      class of routing."
   DEFVAL     { normal }
::= { frUniDnaOutgoingOptionsEntry 14 }

frUniDnaOutAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that outgoing 
      calls (from the DTE to the network) to the open (non-CUG) part of 
      the network are permitted. It also permits outgoing calls to DTEs 
      that have Incoming Access capabilities. If set to a value of 
      disallowed, then such calls cannot be made using this DNA. Such 
      calls will be cleared by the local DCE.
      This attribute corresponds to the CCITT 'Closed User Group with 
      Outgoing Access' feature for DNAs in that outgoing access is 
      granted if this attribute is set to a value of allowed."
   DEFVAL     { disallowed }
::= { frUniDnaOutgoingOptionsEntry 17 }

frUniDnaDefaultTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-write
   STATUS     mandatory
   DESCRIPTION
     "This attribute specifies the default transfer priority for all outgoing 
      calls using this particular DNA. It can be overridden by the 
      transferPriority provisioned in the Dlci DirectCall sub-component.
      
      The transfer priority is a preference configured for an application 
      according to its delay-sensitivity requirement. Frames with higher 
      transfer priority are served by the network before the frames with 
      lower priority. The transfer priority standard is defined to have 16 
      levels from 0 to 15.
      
      Each transfer priority n, where n indicates the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required.
      
      The default defaultTransferPriority is 0."
   DEFVAL     { n0 }
::= { frUniDnaOutgoingOptionsEntry 18 }

frUniDnaTransferPriorityOverRide OBJECT-TYPE
   SYNTAX     INTEGER  {
                 no(0),
                 yes(1) }
   ACCESS     read-write
   STATUS     mandatory
   DESCRIPTION
     "When this attribute is set to yes in the call request, the called end 
      will use the calling end provisioning data on transfer priority to 
      override its own provisioning data. If it is set no, the called end 
      will use its own provisioning data on transfer priority.
      
      This attribute is not applicable for Frame Relay SVCs.
      
      For more information about transfer priority, please refer to the 
      previous attribute defaultTransferPriority.
      
      The default of transferPriorityOverRide is yes."
   DEFVAL     { yes }
::= { frUniDnaOutgoingOptionsEntry 19 }

frUniDnaIncomingOptionsTable OBJECT-TYPE
   SYNTAX     SEQUENCE OF FrUniDnaIncomingOptionsEntry
   ACCESS     not-accessible
   STATUS     mandatory
   DESCRIPTION
     "This group defines options for incoming calls. These options are 
      used for calls arriving to the interface represented by this DNA. For 
      calls originated from the interface, IncomingOptions attributes are 
      not used."
::= { frUniDna 12 }

frUniDnaIncomingOptionsEntry OBJECT-TYPE
   SYNTAX     FrUniDnaIncomingOptionsEntry
   ACCESS     not-accessible
   STATUS     mandatory
   DESCRIPTION
     "An entry in the frUniDnaIncomingOptionsTable."
   INDEX {
      frUniIndex,
      frUniDnaIndex }
::= { frUniDnaIncomingOptionsTable 1 }

FrUniDnaIncomingOptionsEntry ::= SEQUENCE {
   frUniDnaIncAccess
      INTEGER }

frUniDnaIncAccess OBJECT-TYPE
   SYNTAX     INTEGER  {
                 disallowed(0),
                 allowed(1) }
   ACCESS     read-write
   STATUS     mandatory
   DESCRIPTION
     "This attribute, if set to a value of allowed specifies that incoming 
      calls (from the network to the DTE) from the open (non-CUG) part 
      of the network are permitted. It also permits incoming calls from 
      DTEs that have outgoing access capabilities. If set to a value of 
      disallowed, such calls cannot be made to this DNA. They will be 
      cleared by the local DCE.
      This attribute corresponds to the CCITT 'Closed User Group with 
      Incoming Access' feature for DNAs in that incoming access is 
      granted if this attribute is set to a value of allowed."
   DEFVAL     { disallowed }
::= { frUniDnaIncomingOptionsEntry 9 }

frUniDnaCallOptionsTable OBJECT-TYPE
   SYNTAX     SEQUENCE OF FrUniDnaCallOptionsEntry
   ACCESS     not-accessible
   STATUS     mandatory
   DESCRIPTION
     "This group defines additional all options for not related to direction 
      of the call."
::= { frUniDna 13 }

frUniDnaCallOptionsEntry OBJECT-TYPE
   SYNTAX     FrUniDnaCallOptionsEntry
   ACCESS     not-accessible
   STATUS     mandatory
   DESCRIPTION
     "An entry in the frUniDnaCallOptionsTable."
   INDEX {
      frUniIndex,
      frUniDnaIndex }
::= { frUniDnaCallOptionsTable 1 }

FrUniDnaCallOptionsEntry ::= SEQUENCE {
   frUniDnaAccountClass
      Unsigned32,
   frUniDnaAccountCollection
      OCTET STRING,
   frUniDnaServiceExchange
      Unsigned32,
   frUniDnaEgressAccounting
      INTEGER,
   frUniDnaDataPath
      INTEGER }

frUniDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator.
      This attribute is returned by the local VC in the accounting record 
      for all calls that are set up using this particular DNA."
   DEFVAL     { 0 }
::= { frUniDnaCallOptionsEntry 10 }

frUniDnaAccountCollection OBJECT-TYPE
   SYNTAX     OCTET STRING (SIZE (1))
   ACCESS     read-write
   STATUS     mandatory
   DESCRIPTION
     "This attribute indicates that accounting records are to be collected 
      by the network for the various reasons: billing, test, study, auditing. 
      The last of the parameters, force, indicates that accounting records 
      are to be collected irrespective of other collection reasons. The 
      force option is available for X.75 Gateways only. If none of these 
      reasons are set, then accounting will be suppressed.
      To set a specific accounting collection reason, the reason is entered 
      and the corresponding bit in the structure is set to a value of 1. To 
      turn off a specific accounting collection reason, the reason is 
      entered preceded with the '~' character, and the corresponding bit in 
      the structure is set to a value of 0.
      The bit placement for the accounting collection reasons is as 
      follows:
      Bit 0  - Bill
      Bit 1  - Test
      Bit 2  - Study
      Bit 3  - Audit
      Bit 4  - Force

      Description of bits:
      bill(0)
      test(1)
      study(2)
      audit(3)
      force(4)"
   DEFVAL     { '80'H }
::= { frUniDnaCallOptionsEntry 11 }

frUniDnaServiceExchange OBJECT-TYPE
   SYNTAX     Unsigned32 (0..255)
   ACCESS     read-write
   STATUS     mandatory
   DESCRIPTION
     "This attribute is an arbitrary number, Data Service Exchange, as 
      entered by the network operator and reported in accounting record. 
      It is converted into an internal 8-bit integer value for use in the 
      accounting record as well as in various X.25 and X.75 Tariff 
      utilities."
   DEFVAL     { 0 }
::= { frUniDnaCallOptionsEntry 12 }

frUniDnaEgressAccounting OBJECT-TYPE
   SYNTAX     INTEGER  {
                 no(0),
                 yes(1) }
   ACCESS     read-write
   STATUS     mandatory
   DESCRIPTION
     "This attribute specifies if egress accounting is enabled by the frame 
      relay service. If egress accounting is disabled, only segment counts 
      are collected by the VC. No frame relay counts appear in the 
      accounting records for the frame relay service. If egress accounting 
      is enabled, the accounting records for the frame relay service will 
      contain frame relay specific counts."
   DEFVAL     { no }
::= { frUniDnaCallOptionsEntry 13 }

frUniDnaDataPath OBJECT-TYPE
   SYNTAX     INTEGER  {
                 dprsOnly(0),
                 dprsMcsOnly(1),
                 dprsMcsFirst(2) }
   ACCESS     read-write
   STATUS     mandatory
   DESCRIPTION
     "This attribute specifies the data path to be used by Virtual Circuits 
      on this interface. If the connection has a DirectCall component then 
      the value can be overridden by the dataPath attribute of the 
      DirectCall component.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used."
   DEFVAL     { dprsOnly }
::= { frUniDnaCallOptionsEntry 21 }


-- 
-- FrUni/n Dna ClosedUserGroup
-- FrNni/n Dna ClosedUserGroup
-- This group defines options associated with national or international 
-- CUG Identifier. Other DNAs in the network can have CUGs defined 
-- which groups these DNAs by CUG interlockCode. If DNAs are 
-- defined with CUGs, calls from DNAs which do not have the same 
-- interlockCode defined are refused. Attributes incAccess and 
-- outAccess can override this rule.
-- 
-- A CUG is provisioned by default as a SELECTABLE CUG. If a 
-- SELECTABLE CUG is provisioned, the DTE can include a CUG 
-- facility in the call request. If it does, the DTE selects a specific 
-- CUG by signaling the CUG's index. A DTE can subscribe to as 
-- many as 256 SELECTABLE CUGs.
-- 
-- A SIMPLE CUG is provisioned by setting a SELECTABLE CUG's 
-- preferential attribute to the value yes. There are two prerequisites: a 
-- single SELECTABLE CUG must exist; its attributes incCalls and 
-- outCalls must both be set to allowed. If a SIMPLE CUG is 
-- provisioned, it is the default CUG used to establish a call when the 
-- call request sent by the DTE does not include any CUG facility. If 
-- the DTE includes any CUG facility in the call request, the call is 
-- cleared. A DTE subscribing to a SIMPLE CUG cannot subscribe to 
-- any other CUG.

frUniDnaCug OBJECT IDENTIFIER ::= { frUniDna 2 }



frUniDnaCugRowStatusTable OBJECT-TYPE
   SYNTAX     SEQUENCE OF FrUniDnaCugRowStatusEntry
   ACCESS     not-accessible
   STATUS     mandatory
   DESCRIPTION
     "This entry controls the addition and deletion of 
      frUniDnaCug components."
::= { frUniDnaCug 1 }

frUniDnaCugRowStatusEntry OBJECT-TYPE
   SYNTAX     FrUniDnaCugRowStatusEntry
   ACCESS     not-accessible
   STATUS     mandatory
   DESCRIPTION
     "A single entry in the table represents a single 
      frUniDnaCug component."
   INDEX {
      frUniIndex,
      frUniDnaIndex,
      frUniDnaCugIndex }
::= { frUniDnaCugRowStatusTable 1 }

FrUniDnaCugRowStatusEntry ::= SEQUENCE {
   frUniDnaCugRowStatus
      RowStatus,
   frUniDnaCugComponentName
      DisplayString,
   frUniDnaCugStorageType
      StorageType,
   frUniDnaCugIndex
      Integer32 }

frUniDnaCugRowStatus OBJECT-TYPE
   SYNTAX     RowStatus 
   ACCESS     read-write
   STATUS     mandatory
   DESCRIPTION
     "This variable is used as the basis for SNMP naming of
      frUniDnaCug components.
      These components can be added and deleted."
::= { frUniDnaCugRowStatusEntry 1 }

frUniDnaCugComponentName OBJECT-TYPE
   SYNTAX     DisplayString 
   ACCESS     read-only
   STATUS     mandatory
   DESCRIPTION
     "This variable provides the component's string name for
      use with the ASCII Console Interface"
::= { frUniDnaCugRowStatusEntry 2 }

frUniDnaCugStorageType OBJECT-TYPE
   SYNTAX     StorageType 
   ACCESS     read-only
   STATUS     mandatory
   DESCRIPTION
     "This variable represents the storage type value for the
      frUniDnaCug tables."
::= { frUniDnaCugRowStatusEntry 4 }

frUniDnaCugIndex OBJECT-TYPE
   SYNTAX     Integer32 (0..255)
   ACCESS     not-accessible
   STATUS     mandatory
   DESCRIPTION
     "This variable represents the index for the frUniDnaCug tables."
::= { frUniDnaCugRowStatusEntry 10 }

frUniDnaCugCugOptionsTable OBJECT-TYPE
   SYNTAX     SEQUENCE OF FrUniDnaCugCugOptionsEntry
   ACCESS     not-accessible
   STATUS     mandatory
   DESCRIPTION
     "Attributes in this group define ClosedUserGroup options associated 
      with interlockCode. DNA's with the same CUG (interlockCode) can 
      make calls within this group. Various combinations which permit or 
      prevent calls in the same CUG group are defined here."
::= { frUniDnaCug 10 }

frUniDnaCugCugOptionsEntry OBJECT-TYPE
   SYNTAX     FrUniDnaCugCugOptionsEntry
   ACCESS     not-accessible
   STATUS     mandatory
   DESCRIPTION
     "An entry in the frUniDnaCugCugOptionsTable."
   INDEX {
      frUniIndex,
      frUniDnaIndex,
      frUniDnaCugIndex }
::= { frUniDnaCugCugOptionsTable 1 }

FrUniDnaCugCugOptionsEntry ::= SEQUENCE {
   frUniDnaCugType
      INTEGER,
   frUniDnaCugDnic
      DigitString,
   frUniDnaCugInterlockCode
      Unsigned32,
   frUniDnaCugPreferential
      INTEGER,
   frUniDnaCugOutCalls
      INTEGER,
   frUniDnaCugIncCalls
      INTEGER }

frUniDnaCugType OBJECT-TYPE
   SYNTAX     INTEGER  {
                 national(0),
                 international(1) }
   ACCESS     read-write
   STATUS     mandatory
   DESCRIPTION
     "This attribute specifies the CUG type - the CUG is either a national 
      CUG, or an international CUG. International closed user groups are 
      usually established between DTEs for which there is an X.75 
      Gateway between; whereas national closed user groups are usually 
      established between DTEs for which there is no X.75 Gateway 
      between. (National CUGs cannot normally traverse an X.75 
      Gateway).
      If this attribute is set to national, then the CUG is a national CUG, 
      in which case, the dnic should be left at its default value since it is 
      not part of a national CUG. If this attribute is set to international, 
      then the CUG is an international CUG, in which case, the dnic 
      should be set appropriately as part of the CUG interlockCode."
   DEFVAL     { national }
::= { frUniDnaCugCugOptionsEntry 1 }

frUniDnaCugDnic OBJECT-TYPE
   SYNTAX     DigitString (SIZE (4))
   ACCESS     read-write
   STATUS     mandatory
   DESCRIPTION
     "This attribute specifies the dnic (Data Network ID Code) of the 
      CUG by which packet networks are identified. This attribute is not 
      applicable if the CUG is a national CUG, as specified by the CUG 
      type attribute. There are usually 1 or 2 dnics assigned per country, 
      for public networks. The U.S. is an exception where each BOC has 
      a dnic. Also, a group of private networks can have its own dnic.
      
      dnic value is not an arbitrary number. It is assigned by international 
      agreement and controlled by CCITT."
   DEFVAL     { '30303030'H }  -- "0000"
::= { frUniDnaCugCugOptionsEntry 2 }

frUniDnaCugInterlockCode OBJECT-TYPE
   SYNTAX     Unsigned32 (0..65535)
   ACCESS     read-write
   STATUS     mandatory
   DESCRIPTION
     "This attribute specifies the CUG identifier of a national or 
      international CUG call. It is an arbitrary number and it also can be 
      called CUG in some descriptions. Interfaces (DNA's) defined with 
      this number can make calls to DNA's with the same interlockCode."
   DEFVAL     { 65535 }
::= { frUniDnaCugCugOptionsEntry 3 }

frUniDnaCugPreferential OBJECT-TYPE
   SYNTAX     INTEGER  {
                 no(0),
                 yes(1) }
   ACCESS     read-write
   STATUS     mandatory
   DESCRIPTION
     "The attribute 'preferential', if set to yes indicates that this CUG is 
      the SIMPLE CUG (as defined in ITU X.36 [10/96]), in which case 
      it will be used during the call establishment phase if the DTE has 
      not explicitly specified a CUG index in the call request packet. If set 
      to no, then this CUG is not the SIMPLE CUG, but an instance of 
      the SELECTABLE CUG.
      
      The attribute 'preferential' is set to no by CAS when a CUG 
      instance is created. If only one CUG instance exists under a DNA, 
      and if this CUG's attributes 'incCalls' and 'outCall' are both set to 
      allowed, then this CUG instance can be changed to a SIMPLE CUG 
      by setting the attribute 'preferential' to yes. If more than one CUG 
      instances exist under a DNA, none of the CUGs can be set by the 
      user as 'preferential'. Essentially, the attribute 'preferential' 
      distinguishes a SIMPLE CUG from a SELECTABLE CUG.
      
      In the case of a FRUNI DNA with a single CUG instance, the CUG 
      can be a SIMPLE CUG (preferential = yes) or the only instance of a 
      SELECTABLE CUG (preferential = no)."
   DEFVAL     { no }
::= { frUniDnaCugCugOptionsEntry 4 }

frUniDnaCugOutCalls OBJECT-TYPE
   SYNTAX     INTEGER  {
                 disallowed(0),
                 allowed(1) }
   ACCESS     read-write
   STATUS     mandatory
   DESCRIPTION
     "This attribute, if set to allowed indicates that outgoing calls (from 
      the DTE into the network) can be made using this particular CUG. 
      If set to a value of disallowed, then outgoing calls cannot be made 
      using this CUG - such calls will be cleared by the local DCE.
      This attribute corresponds to the CCITT 'Outgoing Calls Barred' 
      feature for CUGs in that outgoing calls are barred if this attribute is 
      set to a value of disallowed."
   DEFVAL     { allowed }
::= { frUniDnaCugCugOptionsEntry 5 }

frUniDnaCugIncCalls OBJECT-TYPE
   SYNTAX     INTEGER  {
                 disallowed(0),
                 allowed(1) }
   ACCESS     read-write
   STATUS     mandatory
   DESCRIPTION
     "This attribute, if set to allowed indicates that incoming calls (from 
      the network to the DTE) can be made using this particular CUG. If 
      set to disallowed, then incoming calls cannot be made using this 
      CUG - such calls will be cleared by the local DCE.
      This attribute corresponds to the CCITT 'Incoming Calls Barred' 
      feature for CUGs in that incoming calls are barred if this attribute is 
      set to a value of disallowed."
   DEFVAL     { allowed }
::= { frUniDnaCugCugOptionsEntry 6 }


-- FrUni/n Dna HuntGroupMember
-- This component specifies the interaction of this DNA with one or 
-- more hunt groups to which it is expected to belong.
-- Note that is not possible to automatically verify the consistency of 
-- the hunt group membership specified under this component with the 
-- hunt group provisioning on the DPN Hunt Group Server(s).

frUniDnaHgM OBJECT IDENTIFIER ::= { frUniDna 3 }



frUniDnaHgMRowStatusTable OBJECT-TYPE
   SYNTAX     SEQUENCE OF FrUniDnaHgMRowStatusEntry
   ACCESS     not-accessible
   STATUS     mandatory
   DESCRIPTION
     "This entry controls the addition and deletion of 
      frUniDnaHgM components."
::= { frUniDnaHgM 1 }

frUniDnaHgMRowStatusEntry OBJECT-TYPE
   SYNTAX     FrUniDnaHgMRowStatusEntry
   ACCESS     not-accessible
   STATUS     mandatory
   DESCRIPTION
     "A single entry in the table represents a single 
      frUniDnaHgM component."
   INDEX {
      frUniIndex,
      frUniDnaIndex,
      frUniDnaHgMIndex }
::= { frUniDnaHgMRowStatusTable 1 }

FrUniDnaHgMRowStatusEntry ::= SEQUENCE {
   frUniDnaHgMRowStatus
      RowStatus,
   frUniDnaHgMComponentName
      DisplayString,
   frUniDnaHgMStorageType
      StorageType,
   frUniDnaHgMIndex
      NonReplicated }

frUniDnaHgMRowStatus OBJECT-TYPE
   SYNTAX     RowStatus 
   ACCESS     read-write
   STATUS     mandatory
   DESCRIPTION
     "This variable is used as the basis for SNMP naming of
      frUniDnaHgM components.
      These components can be added and deleted."
::= { frUniDnaHgMRowStatusEntry 1 }

frUniDnaHgMComponentName OBJECT-TYPE
   SYNTAX     DisplayString 
   ACCESS     read-only
   STATUS     mandatory
   DESCRIPTION
     "This variable provides the component's string name for
      use with the ASCII Console Interface"
::= { frUniDnaHgMRowStatusEntry 2 }

frUniDnaHgMStorageType OBJECT-TYPE
   SYNTAX     StorageType 
   ACCESS     read-only
   STATUS     mandatory
   DESCRIPTION
     "This variable represents the storage type value for the
      frUniDnaHgM tables."
::= { frUniDnaHgMRowStatusEntry 4 }

frUniDnaHgMIndex OBJECT-TYPE
   SYNTAX     NonReplicated 
   ACCESS     not-accessible
   STATUS     mandatory
   DESCRIPTION
     "This variable represents the index for the frUniDnaHgM tables."
::= { frUniDnaHgMRowStatusEntry 10 }

frUniDnaHgMIfTable OBJECT-TYPE
   SYNTAX     SEQUENCE OF FrUniDnaHgMIfEntry
   ACCESS     not-accessible
   STATUS     mandatory
   DESCRIPTION
     "This group contains the interface parameters between the 
      HuntGroupMember and the hunt group server."
::= { frUniDnaHgM 10 }

frUniDnaHgMIfEntry OBJECT-TYPE
   SYNTAX     FrUniDnaHgMIfEntry
   ACCESS     not-accessible
   STATUS     mandatory
   DESCRIPTION
     "An entry in the frUniDnaHgMIfTable."
   INDEX {
      frUniIndex,
      frUniDnaIndex,
      frUniDnaHgMIndex }
::= { frUniDnaHgMIfTable 1 }

FrUniDnaHgMIfEntry ::= SEQUENCE {
   frUniDnaHgMAvailabilityUpdateThreshold
      Unsigned32 }

frUniDnaHgMAvailabilityUpdateThreshold OBJECT-TYPE
   SYNTAX     Unsigned32 (2048..16777216)
   ACCESS     read-write
   STATUS     mandatory
   DESCRIPTION
     "This attribute specifies how much availableAggregateCIR can 
      change before an Availability Message Packet (AMP) is sent to the 
      hunt group server informing it of the change.
      If the value specified is not a multiple of 2048, the value actually 
      used as the threshold will be the next higher multiple of 2048."
   DEFVAL     { 8192 }
::= { frUniDnaHgMIfEntry 1 }

frUniDnaHgMOpTable OBJECT-TYPE
   SYNTAX     SEQUENCE OF FrUniDnaHgMOpEntry
   ACCESS     not-accessible
   STATUS     mandatory
   DESCRIPTION
     "This group contains the operational attributes of the 
      HuntGroupMember component."
::= { frUniDnaHgM 11 }

frUniDnaHgMOpEntry OBJECT-TYPE
   SYNTAX     FrUniDnaHgMOpEntry
   ACCESS     not-accessible
   STATUS     mandatory
   DESCRIPTION
     "An entry in the frUniDnaHgMOpTable."
   INDEX {
      frUniIndex,
      frUniDnaIndex,
      frUniDnaHgMIndex }
::= { frUniDnaHgMOpTable 1 }

FrUniDnaHgMOpEntry ::= SEQUENCE {
   frUniDnaHgMMaximumAvailableAggregateCir
      Unsigned32,
   frUniDnaHgMAvailableAggregateCir
      Unsigned32,
   frUniDnaHgMAvailabilityDelta
      INTEGER,
   frUniDnaHgMAvailableDlcis
      Unsigned32 }

frUniDnaHgMMaximumAvailableAggregateCir OBJECT-TYPE
   SYNTAX     Unsigned32 (0..4294967295)
   ACCESS     read-only
   STATUS     mandatory
   DESCRIPTION
     "This attribute indicates the maximum aggregate CIR availability for 
      this hunt group member. It is the sum of the maximum CIRs 
      provisioned for SVCs in the FrUni Signaling component."
::= { frUniDnaHgMOpEntry 1 }

frUniDnaHgMAvailableAggregateCir OBJECT-TYPE
   SYNTAX     Unsigned32 (0..4294967295)
   ACCESS     read-only
   STATUS     mandatory
   DESCRIPTION
     "This attribute indicates the current available aggregate CIR reported 
      to the hunt group in the Availability Message Packet (AMP). It is 
      incremented by the application when a DLCI is freed. It is 
      decremented when a DLCI is allocated. The value is the sum of the 
      currently available aggregate CIRs for SVCs.
      Both this attribute and the availableDlcis attribute must be non zero 
      for this DNA to receive calls on the hunt group."
::= { frUniDnaHgMOpEntry 2 }

frUniDnaHgMAvailabilityDelta OBJECT-TYPE
   SYNTAX     INTEGER (-16777216..16777215)
   ACCESS     read-only
   STATUS     mandatory
   DESCRIPTION
     "This attribute indicates the net change in the available aggregate 
      CIR since the last Availability Message Packet (AMP) was sent to 
      the Hunt Group. Once the absolute value of this attribute reaches 
      the availabilityUpdateThreshold an AMP is sent to the hunt group 
      server(s) and the availabilityDelta is re-computed."
::= { frUniDnaHgMOpEntry 3 }

frUniDnaHgMAvailableDlcis OBJECT-TYPE
   SYNTAX     Unsigned32 (0..4096)
   ACCESS     read-only
   STATUS     mandatory
   DESCRIPTION
     "This attribute indicates the number of DLCIs available for SVCs on 
      the interface associated with this DNA. If this value reaches 0, an 
      AMP with zero availability is sent to the hunt group server(s).
      Both this attribute and the availableAggregateCir attribute must be 
      non zero for this DNA to receive calls on the hunt group."
::= { frUniDnaHgMOpEntry 5 }


-- FrUni/n Dna HgM HuntGroupAddress/n
-- This component specifies a hunt group address to which this 
-- member belongs. A hunt group member belongs to at least one hunt 
-- group.

frUniDnaHgMHgAddr OBJECT IDENTIFIER ::= { frUniDnaHgM 2 }



frUniDnaHgMHgAddrRowStatusTable OBJECT-TYPE
   SYNTAX     SEQUENCE OF FrUniDnaHgMHgAddrRowStatusEntry
   ACCESS     not-accessible
   STATUS     mandatory
   DESCRIPTION
     "This entry controls the addition and deletion of 
      frUniDnaHgMHgAddr components."
::= { frUniDnaHgMHgAddr 1 }

frUniDnaHgMHgAddrRowStatusEntry OBJECT-TYPE
   SYNTAX     FrUniDnaHgMHgAddrRowStatusEntry
   ACCESS     not-accessible
   STATUS     mandatory
   DESCRIPTION
     "A single entry in the table represents a single 
      frUniDnaHgMHgAddr component."
   INDEX {
      frUniIndex,
      frUniDnaIndex,
      frUniDnaHgMIndex,
      frUniDnaHgMHgAddrIndex }
::= { frUniDnaHgMHgAddrRowStatusTable 1 }

FrUniDnaHgMHgAddrRowStatusEntry ::= SEQUENCE {
   frUniDnaHgMHgAddrRowStatus
      RowStatus,
   frUniDnaHgMHgAddrComponentName
      DisplayString,
   frUniDnaHgMHgAddrStorageType
      StorageType,
   frUniDnaHgMHgAddrIndex
      Integer32 }

frUniDnaHgMHgAddrRowStatus OBJECT-TYPE
   SYNTAX     RowStatus 
   ACCESS     read-write
   STATUS     mandatory
   DESCRIPTION
     "This variable is used as the basis for SNMP naming of
      frUniDnaHgMHgAddr components.
      These components can be added and deleted."
::= { frUniDnaHgMHgAddrRowStatusEntry 1 }

frUniDnaHgMHgAddrComponentName OBJECT-TYPE
   SYNTAX     DisplayString 
   ACCESS     read-only
   STATUS     mandatory
   DESCRIPTION
     "This variable provides the component's string name for
      use with the ASCII Console Interface"
::= { frUniDnaHgMHgAddrRowStatusEntry 2 }

frUniDnaHgMHgAddrStorageType OBJECT-TYPE
   SYNTAX     StorageType 
   ACCESS     read-only
   STATUS     mandatory
   DESCRIPTION
     "This variable represents the storage type value for the
      frUniDnaHgMHgAddr tables."
::= { frUniDnaHgMHgAddrRowStatusEntry 4 }

frUniDnaHgMHgAddrIndex OBJECT-TYPE
   SYNTAX     Integer32 (0..1)
   ACCESS     not-accessible
   STATUS     mandatory
   DESCRIPTION
     "This variable represents the index for the frUniDnaHgMHgAddr tables."
::= { frUniDnaHgMHgAddrRowStatusEntry 10 }

frUniDnaHgMHgAddrAddrTable OBJECT-TYPE
   SYNTAX     SEQUENCE OF FrUniDnaHgMHgAddrAddrEntry
   ACCESS     not-accessible
   STATUS     mandatory
   DESCRIPTION
     "This group contains attributes common to all DNAs. Every DNA 
      used in the network is defined with this group of 2 attributes."
::= { frUniDnaHgMHgAddr 10 }

frUniDnaHgMHgAddrAddrEntry OBJECT-TYPE
   SYNTAX     FrUniDnaHgMHgAddrAddrEntry
   ACCESS     not-accessible
   STATUS     mandatory
   DESCRIPTION
     "An entry in the frUniDnaHgMHgAddrAddrTable."
   INDEX {
      frUniIndex,
      frUniDnaIndex,
      frUniDnaHgMIndex,
      frUniDnaHgMHgAddrIndex }
::= { frUniDnaHgMHgAddrAddrTable 1 }

FrUniDnaHgMHgAddrAddrEntry ::= SEQUENCE {
   frUniDnaHgMHgAddrNumberingPlanIndicator
      INTEGER,
   frUniDnaHgMHgAddrDataNetworkAddress
      DigitString }

frUniDnaHgMHgAddrNumberingPlanIndicator OBJECT-TYPE
   SYNTAX     INTEGER  {
                 x121(0),
                 e164(1) }
   ACCESS     read-write
   STATUS     mandatory
   DESCRIPTION
     "This attribute indicates the Numbering Plan Indicator (NPI) of the 
      DNA. The address may belong to X.121 or E.164 plans."
   DEFVAL     { x121 }
::= { frUniDnaHgMHgAddrAddrEntry 1 }

frUniDnaHgMHgAddrDataNetworkAddress OBJECT-TYPE
   SYNTAX     DigitString (SIZE (1..15))
   ACCESS     read-write
   STATUS     mandatory
   DESCRIPTION
     "This attribute contains digits which form the unique identifier of the 
      customer interface. It can be compared (approximation only) to a 
      telephone number where the phone number identifies a unique 
      telephone set. DNA digits are selected and assigned by network 
      operators."
::= { frUniDnaHgMHgAddrAddrEntry 2 }


-- FrUni/n Framer
-- FrNni/n Framer
-- FrAtm/n Framer
-- This component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

frUniFramer OBJECT IDENTIFIER ::= { frUni 3 }



frUniFramerRowStatusTable OBJECT-TYPE
   SYNTAX     SEQUENCE OF FrUniFramerRowStatusEntry
   ACCESS     not-accessible
   STATUS     mandatory
   DESCRIPTION
     "This entry controls the addition and deletion of 
      frUniFramer components."
::= { frUniFramer 1 }

frUniFramerRowStatusEntry OBJECT-TYPE
   SYNTAX     FrUniFramerRowStatusEntry
   ACCESS     not-accessible
   STATUS     mandatory
   DESCRIPTION
     "A single entry in the table represents a single 
      frUniFramer component."
   INDEX {
      frUniIndex,
      frUniFramerIndex }
::= { frUniFramerRowStatusTable 1 }

FrUniFramerRowStatusEntry ::= SEQUENCE {
   frUniFramerRowStatus
      RowStatus,
   frUniFramerComponentName
      DisplayString,
   frUniFramerStorageType
      StorageType,
   frUniFramerIndex
      NonReplicated }

frUniFramerRowStatus OBJECT-TYPE
   SYNTAX     RowStatus 
   ACCESS     read-write
   STATUS     mandatory
   DESCRIPTION
     "This variable is used as the basis for SNMP naming of
      frUniFramer components.
      These components can be added and deleted."
::= { frUniFramerRowStatusEntry 1 }

frUniFramerComponentName OBJECT-TYPE
   SYNTAX     DisplayString 
   ACCESS     read-only
   STATUS     mandatory
   DESCRIPTION
     "This variable provides the component's string name for
      use with the ASCII Console Interface"
::= { frUniFramerRowStatusEntry 2 }

frUniFramerStorageType OBJECT-TYPE
   SYNTAX     StorageType 
   ACCESS     read-only
   STATUS     mandatory
   DESCRIPTION
     "This variable represents the storage type value for the
      frUniFramer tables."
::= { frUniFramerRowStatusEntry 4 }

frUniFramerIndex OBJECT-TYPE
   SYNTAX     NonReplicated 
   ACCESS     not-accessible
   STATUS     mandatory
   DESCRIPTION
     "This variable represents the index for the frUniFramer tables."
::= { frUniFramerRowStatusEntry 10 }

frUniFramerProvTable OBJECT-TYPE
   SYNTAX     SEQUENCE OF FrUniFramerProvEntry
   ACCESS     not-accessible
   STATUS     mandatory
   DESCRIPTION
     "This group contains the base provisioning data for the Framer 
      component. Application or hardware interface specific provisioning 
      data is contained in other provisionable Framer groups."
::= { frUniFramer 10 }

frUniFramerProvEntry OBJECT-TYPE
   SYNTAX     FrUniFramerProvEntry
   ACCESS     not-accessible
   STATUS     mandatory
   DESCRIPTION
     "An entry in the frUniFramerProvTable."
   INDEX {
      frUniIndex,
      frUniFramerIndex }
::= { frUniFramerProvTable 1 }

FrUniFramerProvEntry ::= SEQUENCE {
   frUniFramerInterfaceName
      Link }

frUniFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { frUniFramerProvEntry 1 }

frUniFramerLinkTable OBJECT-TYPE
   SYNTAX     SEQUENCE OF FrUniFramerLinkEntry
   ACCESS     not-accessible
   STATUS     mandatory
   DESCRIPTION
     "This group contains attributes defining the framing of data on the 
      link interface."
::= { frUniFramer 11 }

frUniFramerLinkEntry OBJECT-TYPE
   SYNTAX     FrUniFramerLinkEntry
   ACCESS     not-accessible
   STATUS     mandatory
   DESCRIPTION
     "An entry in the frUniFramerLinkTable."
   INDEX {
      frUniIndex,
      frUniFramerIndex }
::= { frUniFramerLinkTable 1 }

FrUniFramerLinkEntry ::= SEQUENCE {
   frUniFramerFlagsBetweenFrames
      Unsigned32 }

frUniFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { frUniFramerLinkEntry 4 }

frUniFramerStateTable OBJECT-TYPE
   SYNTAX     SEQUENCE OF FrUniFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frUniFramer 12 }

frUniFramerStateEntry OBJECT-TYPE
   SYNTAX     FrUniFramerStateEntry
   ACCESS     not-accessible
   STATUS     mandatory
   DESCRIPTION
     "An entry in the frUniFramerStateTable."
   INDEX {
      frUniIndex,
      frUniFramerIndex }
::= { frUniFramerStateTable 1 }

FrUniFramerStateEntry ::= SEQUENCE {
   frUniFramerAdminState
      INTEGER,
   frUniFramerOperationalState
      INTEGER,
   frUniFramerUsageState
      INTEGER }

frUniFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frUniFramerStateEntry 1 }

frUniFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frUniFramerStateEntry 2 }

frUniFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frUniFramerStateEntry 3 }

frUniFramerStatsTable OBJECT-TYPE
   SYNTAX     SEQUENCE OF FrUniFramerStatsEntry
   ACCESS     not-accessible
   STATUS     mandatory
   DESCRIPTION
     "This group contains the operational statistics data for a Framer 
      component."
::= { frUniFramer 13 }

frUniFramerStatsEntry OBJECT-TYPE
   SYNTAX     FrUniFramerStatsEntry
   ACCESS     not-accessible
   STATUS     mandatory
   DESCRIPTION
     "An entry in the frUniFramerStatsTable."
   INDEX {
      frUniIndex,
      frUniFramerIndex }
::= { frUniFramerStatsTable 1 }

FrUniFramerStatsEntry ::= SEQUENCE {
   frUniFramerFrmToIf
      Counter32,
   frUniFramerFrmFromIf
      Counter32,
   frUniFramerOctetFromIf
      Counter32,
   frUniFramerAborts
      Counter32,
   frUniFramerCrcErrors
      Counter32,
   frUniFramerLrcErrors
      Counter32,
   frUniFramerNonOctetErrors
      Counter32,
   frUniFramerOverruns
      Counter32,
   frUniFramerUnderruns
      Counter32,
   frUniFramerLargeFrmErrors
      Counter32,
   frUniFramerFrmModeErrors
      Counter32 }

frUniFramerFrmToIf OBJECT-TYPE
   SYNTAX     Counter32 
   ACCESS     read-only
   STATUS     mandatory
   DESCRIPTION
     "The number of frames transmitted to the link interface by Framer.
      
      Note: This does not include the number of frames transmitted 
      directly to the hardware queue, thus bypassing the Framer 
      component."
::= { frUniFramerStatsEntry 1 }

frUniFramerFrmFromIf OBJECT-TYPE
   SYNTAX     Counter32 
   ACCESS     read-only
   STATUS     mandatory
   DESCRIPTION
     "The number of frames received from the link interface by Framer."
::= { frUniFramerStatsEntry 2 }

frUniFramerOctetFromIf OBJECT-TYPE
   SYNTAX     Counter32 
   ACCESS     read-only
   STATUS     mandatory
   DESCRIPTION
     "The number of bytes received from the link interface by Framer."
::= { frUniFramerStatsEntry 3 }

frUniFramerAborts OBJECT-TYPE
   SYNTAX     Counter32 
   ACCESS     read-only
   STATUS     mandatory
   DESCRIPTION
     "This attribute is the total number of aborts received."
::= { frUniFramerStatsEntry 4 }

frUniFramerCrcErrors OBJECT-TYPE
   SYNTAX     Counter32 
   ACCESS     read-only
   STATUS     mandatory
   DESCRIPTION
     "This attribute is the total number of frames with CRC errors, 
      occurring in the receive direction from the link."
::= { frUniFramerStatsEntry 5 }

frUniFramerLrcErrors OBJECT-TYPE
   SYNTAX     Counter32 
   ACCESS     read-only
   STATUS     mandatory
   DESCRIPTION
     "This attribute is the total number of frames with LRC errors, 
      occurring in the Tx link prior to transmission onto the link."
::= { frUniFramerStatsEntry 6 }

frUniFramerNonOctetErrors OBJECT-TYPE
   SYNTAX     Counter32 
   ACCESS     read-only
   STATUS     mandatory
   DESCRIPTION
     "This attribute is the total number of frames that were non octet 
      aligned."
::= { frUniFramerStatsEntry 7 }

frUniFramerOverruns OBJECT-TYPE
   SYNTAX     Counter32 
   ACCESS     read-only
   STATUS     mandatory
   DESCRIPTION
     "This attribute is the total number of frames received from the link 
      for which overruns occurred."
::= { frUniFramerStatsEntry 8 }

frUniFramerUnderruns OBJECT-TYPE
   SYNTAX     Counter32 
   ACCESS     read-only
   STATUS     mandatory
   DESCRIPTION
     "This attribute is the total number of frames transmitted to the link 
      for which underruns occurred."
::= { frUniFramerStatsEntry 9 }

frUniFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { frUniFramerStatsEntry 10 }

frUniFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { frUniFramerStatsEntry 11 }

frUniFramerUtilTable OBJECT-TYPE
   SYNTAX     SEQUENCE OF FrUniFramerUtilEntry
   ACCESS     not-accessible
   STATUS     mandatory
   DESCRIPTION
     "This group contains the link utilizaiton operational data for a 
      Framer component."
::= { frUniFramer 14 }

frUniFramerUtilEntry OBJECT-TYPE
   SYNTAX     FrUniFramerUtilEntry
   ACCESS     not-accessible
   STATUS     mandatory
   DESCRIPTION
     "An entry in the frUniFramerUtilTable."
   INDEX {
      frUniIndex,
      frUniFramerIndex }
::= { frUniFramerUtilTable 1 }

FrUniFramerUtilEntry ::= SEQUENCE {
   frUniFramerNormPrioLinkUtilToIf
      Gauge32,
   frUniFramerNormPrioLinkUtilFromIf
      Gauge32 }

frUniFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities (TP) of 0, 6 and 9 and/or Emission Priority of 2 
      and 3. The utilization is the average for the last minute."
   DEFVAL     { 0 }
::= { frUniFramerUtilEntry 1 }

frUniFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { frUniFramerUtilEntry 3 }


-- FrUni/n LocalManagementInterface
-- FrNni/n LocalManagementInterface
-- FrAtm/n LocalManagementInterface
-- This component defines the parameters for implementing the Local 
-- Management Interface protocol.

frUniLmi OBJECT IDENTIFIER ::= { frUni 4 }



frUniLmiRowStatusTable OBJECT-TYPE
   SYNTAX     SEQUENCE OF FrUniLmiRowStatusEntry
   ACCESS     not-accessible
   STATUS     mandatory
   DESCRIPTION
     "This entry controls the addition and deletion of 
      frUniLmi components."
::= { frUniLmi 1 }

frUniLmiRowStatusEntry OBJECT-TYPE
   SYNTAX     FrUniLmiRowStatusEntry
   ACCESS     not-accessible
   STATUS     mandatory
   DESCRIPTION
     "A single entry in the table represents a single 
      frUniLmi component."
   INDEX {
      frUniIndex,
      frUniLmiIndex }
::= { frUniLmiRowStatusTable 1 }

FrUniLmiRowStatusEntry ::= SEQUENCE {
   frUniLmiRowStatus
      RowStatus,
   frUniLmiComponentName
      DisplayString,
   frUniLmiStorageType
      StorageType,
   frUniLmiIndex
      NonReplicated }

frUniLmiRowStatus OBJECT-TYPE
   SYNTAX     RowStatus 
   ACCESS     read-only
   STATUS     mandatory
   DESCRIPTION
     "This variable is used as the basis for SNMP naming of
      frUniLmi components.
      These components cannot be added nor deleted."
::= { frUniLmiRowStatusEntry 1 }

frUniLmiComponentName OBJECT-TYPE
   SYNTAX     DisplayString 
   ACCESS     read-only
   STATUS     mandatory
   DESCRIPTION
     "This variable provides the component's string name for
      use with the ASCII Console Interface"
::= { frUniLmiRowStatusEntry 2 }

frUniLmiStorageType OBJECT-TYPE
   SYNTAX     StorageType 
   ACCESS     read-only
   STATUS     mandatory
   DESCRIPTION
     "This variable represents the storage type value for the
      frUniLmi tables."
::= { frUniLmiRowStatusEntry 4 }

frUniLmiIndex OBJECT-TYPE
   SYNTAX     NonReplicated 
   ACCESS     not-accessible
   STATUS     mandatory
   DESCRIPTION
     "This variable represents the index for the frUniLmi tables."
::= { frUniLmiRowStatusEntry 10 }

frUniLmiParmsTable OBJECT-TYPE
   SYNTAX     SEQUENCE OF FrUniLmiParmsEntry
   ACCESS     not-accessible
   STATUS     mandatory
   DESCRIPTION
     "This group contains the provisionable attributes of the LMI 
      component."
::= { frUniLmi 10 }

frUniLmiParmsEntry OBJECT-TYPE
   SYNTAX     FrUniLmiParmsEntry
   ACCESS     not-accessible
   STATUS     mandatory
   DESCRIPTION
     "An entry in the frUniLmiParmsTable."
   INDEX {
      frUniIndex,
      frUniLmiIndex }
::= { frUniLmiParmsTable 1 }

FrUniLmiParmsEntry ::= SEQUENCE {
   frUniLmiProcedures
      INTEGER,
   frUniLmiAsyncStatusReport
      INTEGER,
   frUniLmiErrorEventThreshold
      Unsigned32,
   frUniLmiEventCount
      Unsigned32,
   frUniLmiCheckPointTimer
      Unsigned32,
   frUniLmiMessageCountTimer
      Unsigned32,
   frUniLmiIgnoreActiveBit
      INTEGER,
   frUniLmiSide
      INTEGER,
   frUniLmiPvcConfigParmsInFsr
      INTEGER }

frUniLmiProcedures OBJECT-TYPE
   SYNTAX     INTEGER  {
                 none(0),
                 vendorForum(1),
                 ansi(2),
                 itu(3),
                 autoConfigure(4) }
   ACCESS     read-write
   STATUS     mandatory
   DESCRIPTION
     "This attribute selects the procedures to be used for the Local 
      Management Interface. The following procedures are supported:
      
      none: no Local Management Interface procedures are running on 
      this interface. This accommodates Frame Relay user equipment that 
      has not implemented any LMI procedures. The remaining attributes 
      of this group are ignored.
      
      vendorForum: Local Management Interface procedures from the 
      Vendor Forum specification are supported on this interface. DLCI 
      1023 is used for the LMI protocol. This value cannot be used if the 
      side attribute is both.
      
      ansi: Local Management Interface procedures from the ANSI 
      specification are supported. DLCI 0 is used for the LMI protocol.
      
      itu: Local Management Interface procedures from the ITU-T 
      specification are supported. DLCI 0 is used for the LMI protocol. 
      Was previously ccitt.
      
      autoConfigure: The interface determines automatically which 
      Local Management Interface procedures to use. This value cannot 
      be used if the side attribute is user.
      
      The procedures currently in use can be seen in the operational 
      attribute opProcedures."
   DEFVAL     { autoConfigure }
::= { frUniLmiParmsEntry 1 }

frUniLmiAsyncStatusReport OBJECT-TYPE
   SYNTAX     INTEGER  {
                 off(0),
                 on(1) }
   ACCESS     read-write
   STATUS     mandatory
   DESCRIPTION
     "This attribute selects the use of asynchronous PVC status report 
      procedures as specified in ANSI, CCITT, and Vendor Forum. 
      
      This attribute can be set to on or off. If procedures is set to none, 
      this attribute is ignored."
   DEFVAL     { off }
::= { frUniLmiParmsEntry 2 }

frUniLmiErrorEventThreshold OBJECT-TYPE
   SYNTAX     Unsigned32 (1..10)
   ACCESS     read-write
   STATUS     mandatory
   DESCRIPTION
     "An event is defined as follows: (1) receipt of a STATUS ENQUIRY 
      message; or (2) expiration of timer T392. An error event is (1) 
      nonreceipt of STATUS ENQUIRY in T392 seconds; (2) invalid 
      contents of a LMI message; (3) invalid receive sequence number. 
      This attribute specifies the number of error events which, if they 
      occur within eventCount events, cause a protocol error condition. 
      The condition is cleared after eventCount sequential correct events 
      occur. This attribute corresponds to the nN2 parameter described in 
      the Vendor Forum Specification. 
      
      It must be less than or equal to eventCount."
   DEFVAL     { 3 }
::= { frUniLmiParmsEntry 3 }

frUniLmiEventCount OBJECT-TYPE
   SYNTAX     Unsigned32 (1..10)
   ACCESS     read-write
   STATUS     mandatory
   DESCRIPTION
     "This attribute specifies the number of contiguous events within 
      which no more than eventErrorThreshold error events are allowed. 
      This attribute corresponds to the nN3 parameter described in the 
      Vendor Forum Specification. 
      
      It must be greater than or equal to errorEventThreshold."
   DEFVAL     { 4 }
::= { frUniLmiParmsEntry 4 }

frUniLmiCheckPointTimer OBJECT-TYPE
   SYNTAX     Unsigned32 (5 | 10 | 15 | 20 | 25 | 30)
   ACCESS     read-write
   STATUS     mandatory
   DESCRIPTION
     "This attribute selects the time (in seconds) within which a STATUS 
      ENQUIRY message is expected. This attribute corresponds to the 
      nT2 parameter described in the Vendor Forum Specification.
      
      It must be less than messageCountTimer."
   DEFVAL     { 15 }
::= { frUniLmiParmsEntry 5 }

frUniLmiMessageCountTimer OBJECT-TYPE
   SYNTAX     Unsigned32 (5 | 10 | 15 | 20 | 25 | 30)
   ACCESS     read-write
   STATUS     mandatory
   DESCRIPTION
     "This attribute selects the time (in seconds) within which at most five 
      (this is a fixed value and corresponds to maximum message count in 
      VendorForum) STATUS ENQUIRY messages are expected. This 
      attribute applies only when the lmiProcedures is set to 
      vendorForum.
      
      messageCountTimer must always be greater than checkPointTimer."
   DEFVAL     { 20 }
::= { frUniLmiParmsEntry 6 }

frUniLmiIgnoreActiveBit OBJECT-TYPE
   SYNTAX     INTEGER  {
                 no(0),
                 yes(1) }
   ACCESS     read-write
   STATUS     mandatory
   DESCRIPTION
     "This attribute specifies whether the Frame Relay LMI Active Bit 
      (A-bit) has a bearing on the transfer of user data across this Frame 
      Relay interface for both directions of traffic flow.
      
      When this attribute is set to yes, the A-bit status of a user DLCI 
      connection does not affect data transfer.
      
      When this attribute is set to no, data received from the local 
      interface will be discarded if an A-bit =0 condition exists towards 
      the local user. Data being sent to the local interface is discarded if 
      an A-bit = 0 condition exists towards the subnet."
   DEFVAL     { no }
::= { frUniLmiParmsEntry 7 }

frUniLmiSide OBJECT-TYPE
   SYNTAX     INTEGER  {
                 network(0),
                 user(1),
                 both(2) }
   ACCESS     read-write
   STATUS     mandatory
   DESCRIPTION
     "This attribute can be set to user, network, or both. 
      
      When this attribute is set to user, USP LMI procedures are running. 
      When this attribute is set to network, NSP LMI procedures are 
      running. When this attribute is set to both, USPNSP LMI 
      procedures are running.
      When the value is both, the procedures attribute must not be set to 
      vendorForum. 
      Setting the value to user when the procedures attribute is set to 
      autoConfigure is disallowed semantically."
   DEFVAL     { network }
::= { frUniLmiParmsEntry 8 }

frUniLmiPvcConfigParmsInFsr OBJECT-TYPE
   SYNTAX     INTEGER  {
                 no(0),
                 yes(1) }
   ACCESS     read-write
   STATUS     mandatory
   DESCRIPTION
     "When this attribute is set to yes, additional Q.933 information 
      elements are included in the LMI Full Status message to facilitate 
      CPE PVC parameter configuring.
      
      When set to yes, the Check Prov command fails if the Lmi side is 
      not set to network.
      
      When set to yes, Check Prov fails if the number of DLCIs on the 
      FrUni is greater than 300.
      
      If the service is not a FrUni this attribute is ignored."
   DEFVAL     { no }
::= { frUniLmiParmsEntry 9 }

frUniLmiStateTable OBJECT-TYPE
   SYNTAX     SEQUENCE OF FrUniLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frUniLmi 11 }

frUniLmiStateEntry OBJECT-TYPE
   SYNTAX     FrUniLmiStateEntry
   ACCESS     not-accessible
   STATUS     mandatory
   DESCRIPTION
     "An entry in the frUniLmiStateTable."
   INDEX {
      frUniIndex,
      frUniLmiIndex }
::= { frUniLmiStateTable 1 }

FrUniLmiStateEntry ::= SEQUENCE {
   frUniLmiAdminState
      INTEGER,
   frUniLmiOperationalState
      INTEGER,
   frUniLmiUsageState
      INTEGER }

frUniLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frUniLmiStateEntry 1 }

frUniLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frUniLmiStateEntry 2 }

frUniLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frUniLmiStateEntry 3 }

frUniLmiPsiTable OBJECT-TYPE
   SYNTAX     SEQUENCE OF FrUniLmiPsiEntry
   ACCESS     not-accessible
   STATUS     mandatory
   DESCRIPTION
     "This group provides the protocol status of the Local Management 
      Interface."
::= { frUniLmi 12 }

frUniLmiPsiEntry OBJECT-TYPE
   SYNTAX     FrUniLmiPsiEntry
   ACCESS     not-accessible
   STATUS     mandatory
   DESCRIPTION
     "An entry in the frUniLmiPsiTable."
   INDEX {
      frUniIndex,
      frUniLmiIndex }
::= { frUniLmiPsiTable 1 }

FrUniLmiPsiEntry ::= SEQUENCE {
   frUniLmiProtocolStatus
      INTEGER,
   frUniLmiOpProcedures
      INTEGER }

frUniLmiProtocolStatus OBJECT-TYPE
   SYNTAX     INTEGER  {
                 errorCondition(0),
                 normalCondition(1),
                 configuring(2) }
   ACCESS     read-only
   STATUS     mandatory
   DESCRIPTION
     "This attribute indicates whether the LMI is in an error condition or 
      whether the LMI procedures are behaving normally. When 
      operating with no LMI protocol, this attribute is always set to 
      normalCondition. When operating with LMI procedures, this 
      attribute is set to errorCondition after n392 of the last n393 events 
      are in error. The consequence of an errorCondition is that all 
      DLCIs on this interface will become inactive in both directions. The 
      errorCondition is cleared and a normalCondition is indicated when 
      a sufficient number of events have occurred without error. In ANSI, 
      this occurs when n393 consecutive good events take place.
      
      If the procedures attribute is set to autoConfigure, this attribute is 
      set to configuring while adaptive LMI determines which LMI 
      procedures are running on the link. A single LMI error event during 
      auto configuration causes the attribute value to change to 
      errorCondition. If during configuring no LMI message is received, 
      an LMI errorCondition is raised after n392 x t392 seconds."
::= { frUniLmiPsiEntry 1 }

frUniLmiOpProcedures OBJECT-TYPE
   SYNTAX     INTEGER  {
                 none(0),
                 vendorForum(1),
                 ansi(2),
                 itu(3),
                 unknown(4) }
   ACCESS     read-only
   STATUS     mandatory
   DESCRIPTION
     "The opProcedures attribute indicates the procedures being used for 
      the Local Management Interface. This attribute should be ignored if 
      protocolStatus is not normalCondition. The following procedures 
      are supported:
      
      none: Local Management Interface procedures are not running on 
      this interface. This accommodates Frame Relay user equipment that 
      has not implemented any LMI procedures.
      
      vendorForum: Local Management Interface procedures from the 
      Vendor Forum specification are running on this interface. DLCI 
      1023 is used for the LMI protocol.
      
      ansi: Local Management Interface procedures from the ANSI 
      specification are running. DLCI 0 is used for the LMI protocol.
      
      itu: Local Management Interface procedures from the ITU-T 
      specification are running. DLCI 0 is used for the LMI protocol. Was 
      previously ccitt.
      
      unknown: Local Management Interface procedures have yet to be 
      determined by Adaptive LMI."
::= { frUniLmiPsiEntry 2 }

frUniLmiStatsTable OBJECT-TYPE
   SYNTAX     SEQUENCE OF FrUniLmiStatsEntry
   ACCESS     not-accessible
   STATUS     mandatory
   DESCRIPTION
     "This group contains the operational statistics for the Frame Relay 
      Local Management Interface."
::= { frUniLmi 13 }

frUniLmiStatsEntry OBJECT-TYPE
   SYNTAX     FrUniLmiStatsEntry
   ACCESS     not-accessible
   STATUS     mandatory
   DESCRIPTION
     "An entry in the frUniLmiStatsTable."
   INDEX {
      frUniIndex,
      frUniLmiIndex }
::= { frUniLmiStatsTable 1 }

FrUniLmiStatsEntry ::= SEQUENCE {
   frUniLmiKeepAliveStatusToIf
      Counter32,
   frUniLmiFullStatusToIf
      Counter32,
   frUniLmiKeepAliveStatusEnqFromIf
      Counter32,
   frUniLmiFullStatusEnqFromIf
      Counter32,
   frUniLmiNetworkSideEventHistory
      AsciiString,
   frUniLmiProtocolErrors
      Counter32,
   frUniLmiUnexpectedIes
      Counter32,
   frUniLmiSequenceErrors
      Counter32,
   frUniLmiUnexpectedReports
      Counter32,
   frUniLmiPollingVerifTimeouts
      Counter32,
   frUniLmiKeepAliveEnqToIf
      Counter32,
   frUniLmiFullStatusEnqToIf
      Counter32,
   frUniLmiUserSideEventHistory
      AsciiString,
   frUniLmiStatusSequenceErrors
      Counter32,
   frUniLmiNoStatusReportCount
      Counter32 }

frUniLmiKeepAliveStatusToIf OBJECT-TYPE
   SYNTAX     Counter32 
   ACCESS     read-only
   STATUS     mandatory
   DESCRIPTION
     "This attribute counts the number of Local Management Interface 
      keep alive status messages sent to the external user device in 
      response to a status enquiry for keep alive status. When the 
      maximum count is exceeded it wraps to zero."
::= { frUniLmiStatsEntry 1 }

frUniLmiFullStatusToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { frUniLmiStatsEntry 2 }

frUniLmiKeepAliveStatusEnqFromIf OBJECT-TYPE
   SYNTAX     Counter32 
   ACCESS     read-only
   STATUS     mandatory
   DESCRIPTION
     "This attribute counts the number of Local Management Interface 
      valid keep alive status enquiry messages received from the external 
      user device. When the maximum count is reached it wraps to zero."
::= { frUniLmiStatsEntry 3 }

frUniLmiFullStatusEnqFromIf OBJECT-TYPE
   SYNTAX     Counter32 
   ACCESS     read-only
   STATUS     mandatory
   DESCRIPTION
     "This attribute counts the number of Local Management Interface 
      valid full status enquiry messages received from the external user 
      device. When the maximum count is reached it wraps to zero."
::= { frUniLmiStatsEntry 4 }

frUniLmiNetworkSideEventHistory OBJECT-TYPE
   SYNTAX     AsciiString (SIZE (1..10))
   ACCESS     read-only
   STATUS     mandatory
   DESCRIPTION
     "This attribute displays the Local Management Interface network 
      side procedure event history in order of occurrence. An event is 
      represented by a single symbol. A '+' symbol indicates a good 
      event. An 'X' symbol indicates a protocol error event. The leftmost 
      event is the most recent to occur. The provisioned eventCount (nN3/
      N393) dictates the maximum number of events displayed. A good 
      event is triggered by receipt of a valid status enquiry message. An 
      error event is one of three possibilities, either a nT2/T392 timer 
      expiry, receipt of a status enquiry message with bad sequence 
      numbers, or when lmiProcedures is provisioned to vendorForum 
      and we receive more than nN4 status enquiry messages within the 
      provisioned messageCountTimer (nT3)."
::= { frUniLmiStatsEntry 5 }

frUniLmiProtocolErrors OBJECT-TYPE
   SYNTAX     Counter32 
   ACCESS     read-only
   STATUS     mandatory
   DESCRIPTION
     "This attribute counts the number of Local Management Interface 
      protocol errors. It is the sum of the sequence (sequenceErrors), 
      timeout (pollingVerifTimeouts) and too many status enquiry 
      messages received within the messageCountTimer (nT3) errors. The 
      too many status enquiries error only applies when lmiProcedures is 
      set to vendorForum. When the maximum count is exceeded it 
      wraps to zero."
::= { frUniLmiStatsEntry 6 }

frUniLmiUnexpectedIes OBJECT-TYPE
   SYNTAX     Counter32 
   ACCESS     read-only
   STATUS     mandatory
   DESCRIPTION
     "This attribute counts the number of Local Management Interface 
      frames received with an Information Element identifier that is 
      unknown or unexpected. An unexpected Information Element is not 
      a protocol error. When the maximum count is reached, this counter 
      wraps to zero."
::= { frUniLmiStatsEntry 7 }

frUniLmiSequenceErrors OBJECT-TYPE
   SYNTAX     Counter32 
   ACCESS     read-only
   STATUS     mandatory
   DESCRIPTION
     "This attribute counts the number of Local Management Interface 
      Status Enquiry message sequence errors. A sequence error is receipt 
      of a Status Enquiry message with a receive sequence number not 
      equal to the last send sequence number. When the maximum count 
      is reached the counter wraps to zero."
::= { frUniLmiStatsEntry 8 }

frUniLmiUnexpectedReports OBJECT-TYPE
   SYNTAX     Counter32 
   ACCESS     read-only
   STATUS     mandatory
   DESCRIPTION
     "This attribute counts the number of Local Management Interface 
      frames received with an unknown or unexpected report type. An 
      unexpected report type is not a protocol error. When the maximum 
      count is reached the counter wraps to zero."
::= { frUniLmiStatsEntry 9 }

frUniLmiPollingVerifTimeouts OBJECT-TYPE
   SYNTAX     Counter32 
   ACCESS     read-only
   STATUS     mandatory
   DESCRIPTION
     "This attribute counts the number of checkPointTImer (t392) timer 
      expiries occurring on the Local Management Interface. When the 
      maximum count is reached the counter wraps to zero."
::= { frUniLmiStatsEntry 10 }

frUniLmiKeepAliveEnqToIf OBJECT-TYPE
   SYNTAX     Counter32 
   ACCESS     read-only
   STATUS     mandatory
   DESCRIPTION
     "This attribute counts the number of Local Management Interface 
      keep alive enquiry status messages sent to the external user device 
      for keep alive status. When the maximum count is reached it wraps 
      to zero."
::= { frUniLmiStatsEntry 11 }

frUniLmiFullStatusEnqToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { frUniLmiStatsEntry 12 }

frUniLmiUserSideEventHistory OBJECT-TYPE
   SYNTAX     AsciiString (SIZE (1..10))
   ACCESS     read-only
   STATUS     mandatory
   DESCRIPTION
     "This attribute displays the Local Management Interface user side 
      procedure event history in order of occurrence. An event is 
      represented by a single symbol. A '+' symbol indicates a good 
      event. An 'X' symbol indicates a protocol error event. The left most 
      event is the most recent to occur. The provisioned eventCount (nN3/
      N393) dictates the maximum number of events displayed. A good 
      event is triggered by receipt of a valid status message. An error 
      event is either a nT1/T391 timer expiry or receipt of a status 
      message with bad sequence numbers."
::= { frUniLmiStatsEntry 13 }

frUniLmiStatusSequenceErrors OBJECT-TYPE
   SYNTAX     Counter32 
   ACCESS     read-only
   STATUS     mandatory
   DESCRIPTION
     "This attribute counts the number of Local Management Interface 
      Status message sequence errors. A sequence error is receipt of a 
      Status message with a receive sequence number not equal to the last 
      send sequence number. When the maximum count is reached the 
      counter wraps to zero."
::= { frUniLmiStatsEntry 14 }

frUniLmiNoStatusReportCount OBJECT-TYPE
   SYNTAX     Counter32 
   ACCESS     read-only
   STATUS     mandatory
   DESCRIPTION
     "This attribute counts the number of times when no status report or 
      an invalid status report comes from the external network. This 
      attribute is incremented in two cases: 
      i) after a status enquiry is sent out and T391 timer expires without 
      having a status report received.
      ii) an invalid status report is received.
      
      When the maximum count is reached it wraps to zero."
::= { frUniLmiStatsEntry 15 }

frUniLmiUspParmsTable OBJECT-TYPE
   SYNTAX     SEQUENCE OF FrUniLmiUspParmsEntry
   ACCESS     not-accessible
   STATUS     mandatory
   DESCRIPTION
     "This group contains the provisionable attributes of the Local 
      Management Interface user side procedure."
::= { frUniLmi 14 }

frUniLmiUspParmsEntry OBJECT-TYPE
   SYNTAX     FrUniLmiUspParmsEntry
   ACCESS     not-accessible
   STATUS     mandatory
   DESCRIPTION
     "An entry in the frUniLmiUspParmsTable."
   INDEX {
      frUniIndex,
      frUniLmiIndex }
::= { frUniLmiUspParmsTable 1 }

FrUniLmiUspParmsEntry ::= SEQUENCE {
   frUniLmiFullStatusPollingCycles
      Unsigned32,
   frUniLmiLinkVerificationTimer
      Unsigned32 }

frUniLmiFullStatusPollingCycles OBJECT-TYPE
   SYNTAX     Unsigned32 (1..255)
   ACCESS     read-write
   STATUS     mandatory
   DESCRIPTION
     "This attribute specifies how frequently the Frame Relay UNI service 
      should initiate a Status Enquiry for a full PVC status report. A 
      polling cycle is a Status Enquiry and Status Report exchange. 
      
      This attribute is used only if the side attribute is either user or both."
   DEFVAL     { 6 }
::= { frUniLmiUspParmsEntry 1 }

frUniLmiLinkVerificationTimer OBJECT-TYPE
   SYNTAX     Unsigned32 (5 | 10 | 15 | 20 | 25 | 30)
   ACCESS     read-write
   STATUS     mandatory
   DESCRIPTION
     "This attribute specifies how frequently the Frame Relay UNI service 
      should initiate a Status Enquiry for link integrity verification. It 
      must be less than checkPointTimer (t392).
      
      When the Lmi side is network, this attribute is ignored."
   DEFVAL     { 10 }
::= { frUniLmiUspParmsEntry 2 }


-- FrUni/n DataLinkConnectionIdentifier/n
-- This component represents a Data Link Connection Identifier. It is 
-- responsible for the Frame Relay U-plane (User-plane) protocol for 
-- the specified instance. There can be many instances of Dlci for each 
-- FrUni. The instance value is used to identify the logical connection, 
-- multiplexed within the physical channel, with which a frame is 
-- associated. All frames carried within a particular physical channel 
-- and having the same DLCI value are associated with the same 
-- logical connection.
-- 
-- A DLCI instance can be a permanent virtual circuit (PVC) added 
-- through provisioning, or a switched virtual circuit (SVC) which is 
-- created dynamically through signaling.

frUniDlci OBJECT IDENTIFIER ::= { frUni 5 }



frUniDlciRowStatusTable OBJECT-TYPE
   SYNTAX     SEQUENCE OF FrUniDlciRowStatusEntry
   ACCESS     not-accessible
   STATUS     mandatory
   DESCRIPTION
     "This entry controls the addition and deletion of 
      frUniDlci components."
::= { frUniDlci 1 }

frUniDlciRowStatusEntry OBJECT-TYPE
   SYNTAX     FrUniDlciRowStatusEntry
   ACCESS     not-accessible
   STATUS     mandatory
   DESCRIPTION
     "A single entry in the table represents a single 
      frUniDlci component."
   INDEX {
      frUniIndex,
      frUniDlciIndex }
::= { frUniDlciRowStatusTable 1 }

FrUniDlciRowStatusEntry ::= SEQUENCE {
   frUniDlciRowStatus
      RowStatus,
   frUniDlciComponentName
      DisplayString,
   frUniDlciStorageType
      StorageType,
   frUniDlciIndex
      Integer32 }

frUniDlciRowStatus OBJECT-TYPE
   SYNTAX     RowStatus 
   ACCESS     read-write
   STATUS     mandatory
   DESCRIPTION
     "This variable is used as the basis for SNMP naming of
      frUniDlci components.
      These components can be added and deleted."
::= { frUniDlciRowStatusEntry 1 }

frUniDlciComponentName OBJECT-TYPE
   SYNTAX     DisplayString 
   ACCESS     read-only
   STATUS     mandatory
   DESCRIPTION
     "This variable provides the component's string name for
      use with the ASCII Console Interface"
::= { frUniDlciRowStatusEntry 2 }

frUniDlciStorageType OBJECT-TYPE
   SYNTAX     StorageType 
   ACCESS     read-only
   STATUS     mandatory
   DESCRIPTION
     "This variable represents the storage type value for the
      frUniDlci tables."
::= { frUniDlciRowStatusEntry 4 }

frUniDlciIndex OBJECT-TYPE
   SYNTAX     Integer32 (16..1007)
   ACCESS     not-accessible
   STATUS     mandatory
   DESCRIPTION
     "This variable represents the index for the frUniDlci tables."
::= { frUniDlciRowStatusEntry 10 }

frUniDlciStateTable OBJECT-TYPE
   SYNTAX     SEQUENCE OF FrUniDlciStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { frUniDlci 10 }

frUniDlciStateEntry OBJECT-TYPE
   SYNTAX     FrUniDlciStateEntry
   ACCESS     not-accessible
   STATUS     mandatory
   DESCRIPTION
     "An entry in the frUniDlciStateTable."
   INDEX {
      frUniIndex,
      frUniDlciIndex }
::= { frUniDlciStateTable 1 }

FrUniDlciStateEntry ::= SEQUENCE {
   frUniDlciAdminState
      INTEGER,
   frUniDlciOperationalState
      INTEGER,
   frUniDlciUsageState
      INTEGER,
   frUniDlciAvailabilityStatus
      OCTET STRING,
   frUniDlciProceduralStatus
      OCTET STRING,
   frUniDlciControlStatus
      OCTET STRING,
   frUniDlciAlarmStatus
      OCTET STRING,
   frUniDlciStandbyStatus
      INTEGER,
   frUniDlciUnknownStatus
      INTEGER }

frUniDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { frUniDlciStateEntry 1 }

frUniDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { frUniDlciStateEntry 2 }

frUniDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { frUniDlciStateEntry 3 }

frUniDlciAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { frUniDlciStateEntry 4 }

frUniDlciProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { frUniDlciStateEntry 5 }

frUniDlciControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { frUniDlciStateEntry 6 }

frUniDlciAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { frUniDlciStateEntry 7 }

frUniDlciStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { frUniDlciStateEntry 8 }

frUniDlciUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { frUniDlciStateEntry 9 }

frUniDlciAbitTable OBJECT-TYPE
   SYNTAX     SEQUENCE OF FrUniDlciAbitEntry
   ACCESS     not-accessible
   STATUS     mandatory
   DESCRIPTION
     "This group contains the A-Bit status information for this Data Link 
      Connection Identifier.
      
      A-Bit status information is only applicable for PVCs. For SVCs, the 
      values of attributes under this group are all notApplicable."
::= { frUniDlci 12 }

frUniDlciAbitEntry OBJECT-TYPE
   SYNTAX     FrUniDlciAbitEntry
   ACCESS     not-accessible
   STATUS     mandatory
   DESCRIPTION
     "An entry in the frUniDlciAbitTable."
   INDEX {
      frUniIndex,
      frUniDlciIndex }
::= { frUniDlciAbitTable 1 }

FrUniDlciAbitEntry ::= SEQUENCE {
   frUniDlciABitStatusToIf
      INTEGER,
   frUniDlciABitReasonToIf
      INTEGER,
   frUniDlciABitStatusFromIf
      INTEGER,
   frUniDlciABitReasonFromIf
      INTEGER,
   frUniDlciLoopbackState
      INTEGER }

frUniDlciABitStatusToIf OBJECT-TYPE
   SYNTAX     INTEGER  {
                 inactive(0),
                 active(1),
                 notApplicable(2) }
   ACCESS     read-only
   STATUS     mandatory
   DESCRIPTION
     "This attribute is the most recent A-bit status sent to the interface. 
      The A-bit status is part of the LMI protocol, and indicates 
      willingness to accept data from the local interface. When an inactive 
      setting is sent out, the Frame Relay service will discard any data 
      offered from the local interface. When an active setting is sent out, 
      the Frame Relay service will try to process all data offered from the 
      local interface."
   DEFVAL     { inactive }
::= { frUniDlciAbitEntry 1 }

frUniDlciABitReasonToIf OBJECT-TYPE
   SYNTAX     INTEGER  {
                 notApplicable(0),
                 remoteUserSignaled(1),
                 localLmiError(2),
                 remoteLmiError(3),
                 localLinkDown(4),
                 remoteLinkDown(5),
                 pvcDown(6) }
   ACCESS     read-only
   STATUS     mandatory
   DESCRIPTION
     "This attribute provides the reason (if any) for an inactive status to be 
      sent to the interface. This reason is not applicable for an active 
      status."
   DEFVAL     { notApplicable }
::= { frUniDlciAbitEntry 2 }

frUniDlciABitStatusFromIf OBJECT-TYPE
   SYNTAX     INTEGER  {
                 inactive(0),
                 active(1),
                 notApplicable(2) }
   ACCESS     read-only
   STATUS     mandatory
   DESCRIPTION
     "This attribute is the most recent A-Bit status received from the 
      interface."
   DEFVAL     { inactive }
::= { frUniDlciAbitEntry 3 }

frUniDlciABitReasonFromIf OBJECT-TYPE
   SYNTAX     INTEGER  {
                 notApplicable(0),
                 remoteUserSignaled(1),
                 localLmiError(2),
                 localLinkDown(4),
                 missingFromLmiReport(7) }
   ACCESS     read-only
   STATUS     mandatory
   DESCRIPTION
     "This attribute provides the reason (if any) for an inactive status to be 
      sent to the subnet. This reason is not applicable for an active status."
   DEFVAL     { notApplicable }
::= { frUniDlciAbitEntry 4 }

frUniDlciLoopbackState OBJECT-TYPE
   SYNTAX     INTEGER  {
                 off(0),
                 on(1) }
   ACCESS     read-only
   STATUS     mandatory
   DESCRIPTION
     "This attribute has the value on when the DLCI is in loopback mode 
      and off otherwise. This loopback command verbs start and stop are 
      used to initiate and terminate the loopback mode for a DLCI. While 
      loopbackState is on, the local LMI will report to the interface the A-
      bit status as active. Also an active A-bit signal will be reliably 
      propagated across the subnet to the remote DLCI."
   DEFVAL     { off }
::= { frUniDlciAbitEntry 5 }

frUniDlciCalldTable OBJECT-TYPE
   SYNTAX     SEQUENCE OF FrUniDlciCalldEntry
   ACCESS     not-accessible
   STATUS     mandatory
   DESCRIPTION
     "This group of attributes describes the characteristics of the call such 
      as call type and call state."
::= { frUniDlci 13 }

frUniDlciCalldEntry OBJECT-TYPE
   SYNTAX     FrUniDlciCalldEntry
   ACCESS     not-accessible
   STATUS     mandatory
   DESCRIPTION
     "An entry in the frUniDlciCalldTable."
   INDEX {
      frUniIndex,
      frUniDlciIndex }
::= { frUniDlciCalldTable 1 }

FrUniDlciCalldEntry ::= SEQUENCE {
   frUniDlciCallType
      INTEGER,
   frUniDlciQ933CallState
      INTEGER,
   frUniDlciQ933CallReference
      Unsigned32 }

frUniDlciCallType OBJECT-TYPE
   SYNTAX     INTEGER  {
                 pvc(0),
                 svc(1) }
   ACCESS     read-only
   STATUS     mandatory
   DESCRIPTION
     "This attribute specifies whether this DLCI is a permancent virtual 
      circuit (PVC) or a switched virtual circuit (SVC)."
::= { frUniDlciCalldEntry 1 }

frUniDlciQ933CallState OBJECT-TYPE
   SYNTAX     INTEGER  {
                 null(0),
                 callInitiated(1),
                 outgoingCallProceeding(3),
                 callPresent(6),
                 incomingCallProceeding(9),
                 active(10),
                 disconnectRequest(11),
                 disconnectIndication(12),
                 releaseRequest(19),
                 notApplicable(20) }
   ACCESS     read-only
   STATUS     mandatory
   DESCRIPTION
     "This attribute specifies the Q.933 state of an SVC call. The value of 
      this attribute for a PVC is always notApplicable. In the description 
      that follows, 'local' refers to the user who has initiated the SETUP 
      request, and 'remote' refers to the user to whom the local user 
      wishes to connect.
      
      State description:
      In the null state, the network has neither received nor sent call setup 
      requests for this DLCI.
      In the callInitiated state, the network has received a SETUP 
      message from the local user.
      In the outgoingCallProceeding state, the network has sent a CALL 
      PROCEEDING message to the local user in response to the SETUP 
      message.
      In the callPresent state, the network has sent a SETUP message to 
      the remote user.
      In the incomingCallProceeding state, the network has received a 
      CALL PROCEEDING message from the remote user in response to 
      a SETUP message.
      In the active state, either the network has sent a CONNECT 
      message to the local user, or the network has received a CONNECT 
      from the remote user.
      In the disconnectRequest state, the network has received a 
      DISCONNECT message from the local user.
      In the disconnectIndication state, the network has sent a 
      DISCONNECT to the local user.
      In the releaseRequest state, the network has sent out a RELEASE 
      message to the local user."
::= { frUniDlciCalldEntry 2 }

frUniDlciQ933CallReference OBJECT-TYPE
   SYNTAX     Unsigned32 (0..32767)
   ACCESS     read-only
   STATUS     mandatory
   DESCRIPTION
     "This attribute specifies the Q.933 call reference number associated 
      with this DLCI. The value of this attribute for a PVC is always 0."
::= { frUniDlciCalldEntry 3 }

frUniDlciSpOpTable OBJECT-TYPE
   SYNTAX     SEQUENCE OF FrUniDlciSpOpEntry
   ACCESS     not-accessible
   STATUS     mandatory
   DESCRIPTION
     "This group contains the service parameters specific to this instance 
      of DLCI. For PVCs, the values of attributes with the exception of 
      measurementInterval should be identical to those in the group 
      FrsDataLinkConnectionProv under the 
      FrsUniServiceParametersProv component. For SVC's, the values of 
      attributes may be different from the values provisioned under the 
      Signaling subcomponent, if Q933 negotiations has ocurred to alter 
      service parameters.
      DESCRIPTION"
::= { frUniDlci 14 }

frUniDlciSpOpEntry OBJECT-TYPE
   SYNTAX     FrUniDlciSpOpEntry
   ACCESS     not-accessible
   STATUS     mandatory
   DESCRIPTION
     "An entry in the frUniDlciSpOpTable."
   INDEX {
      frUniIndex,
      frUniDlciIndex }
::= { frUniDlciSpOpTable 1 }

FrUniDlciSpOpEntry ::= SEQUENCE {
   frUniDlciMaximumFrameSize
      Unsigned32,
   frUniDlciRateEnforcement
      INTEGER,
   frUniDlciCommittedInformationRate
      Unsigned32,
   frUniDlciCommittedBurstSize
      Unsigned32,
   frUniDlciExcessBurstSize
      Unsigned32,
   frUniDlciMeasurementInterval
      Unsigned32,
   frUniDlciRateAdaptation
      INTEGER,
   frUniDlciAccounting
      INTEGER,
   frUniDlciEmissionPriorityToIf
      INTEGER,
   frUniDlciTransferPriToNwk
      Unsigned32,
   frUniDlciTransferPriFromNwk
      Unsigned32 }

frUniDlciMaximumFrameSize OBJECT-TYPE
   SYNTAX     Unsigned32 (1..8187)
   ACCESS     read-only
   STATUS     mandatory
   DESCRIPTION
     "This attribute specifies the maximum number of octets which may 
      be included in the information field. The frame relay header and 
      CRC octets are not included in this definition. This attribute 
      corresponds to the dN1 parameter described in the Vendor Forum 
      Specification."
::= { frUniDlciSpOpEntry 1 }

frUniDlciRateEnforcement OBJECT-TYPE
   SYNTAX     INTEGER  {
                 off(0),
                 on(1) }
   ACCESS     read-only
   STATUS     obsolete
   DESCRIPTION
     "This attribute is obsolete. It provided the same information as the 
      provisioning attribute rateEnforcement in dlci/* sp.
      DESCRIPTION"
::= { frUniDlciSpOpEntry 2 }

frUniDlciCommittedInformationRate OBJECT-TYPE
   SYNTAX     Unsigned32 (0..50000000)
   ACCESS     read-only
   STATUS     mandatory
   DESCRIPTION
     "This attribute specifies the committed information rate (CIR) in bits 
      per second (bit/s). When rateEnforcement is set to on, cir is the rate 
      at which the network agrees to transfer information under normal 
      conditions. This rate is measured over a measurement interval (T).
      
      This attribute should be ignored when rateEnforcement is off."
::= { frUniDlciSpOpEntry 3 }

frUniDlciCommittedBurstSize OBJECT-TYPE
   SYNTAX     Unsigned32 (0..50000000)
   ACCESS     read-only
   STATUS     mandatory
   DESCRIPTION
     "This attribute specifies the committed burst size (Bc) in bits. bc is 
      the amount of data that a network agrees to transfer under normal 
      conditions over a measurement interval (t). Data marked DE=1 is 
      not accounted for in Bc.
      
      This attribute should be ignored when rateEnforcement is off."
::= { frUniDlciSpOpEntry 4 }

frUniDlciExcessBurstSize OBJECT-TYPE
   SYNTAX     Unsigned32 (0..50000000)
   ACCESS     read-only
   STATUS     mandatory
   DESCRIPTION
     "This attribute specifies the excess burst size (Be) in bits. Be is the 
      amount of uncommitted data that the network will attempt to deliver 
      over measurement interval T. Data marked DE=1 by the user or by 
      the network is accounted for here.
      
      This attribute should be ignored when rateEnforcement is off."
::= { frUniDlciSpOpEntry 5 }

frUniDlciMeasurementInterval OBJECT-TYPE
   SYNTAX     Unsigned32 (0..4294967295)
   ACCESS     read-only
   STATUS     mandatory
   DESCRIPTION
     "This attribute specifies the time interval (in milliseconds) over 
      which rates and burst sizes are measured.
      
      This attribute should be ignored when rateEnforcement is off."
::= { frUniDlciSpOpEntry 6 }

frUniDlciRateAdaptation OBJECT-TYPE
   SYNTAX     INTEGER  {
                 off(0),
                 on(1),
                 eirOnly(2) }
   ACCESS     read-only
   STATUS     obsolete
   DESCRIPTION
     "This attribute is obsolete. It provided the information which is now 
      in the provision attribute rateAdaptation in dlci/* sp."
::= { frUniDlciSpOpEntry 7 }

frUniDlciAccounting OBJECT-TYPE
   SYNTAX     INTEGER  {
                 off(0),
                 on(1) }
   ACCESS     read-only
   STATUS     mandatory
   DESCRIPTION
     "This attribute specifies whether accounting data collection and 
      record generation is turned on at this DLCI. For accounting data 
      collection and record generation to be turned on, the accountingOn 
      bit and at least one of the accountCollection bits in the 
      DataNetworkAddress component must be set to on."
::= { frUniDlciSpOpEntry 8 }

frUniDlciEmissionPriorityToIf OBJECT-TYPE
   SYNTAX     INTEGER (0 | 1 | 2 | 3)
   ACCESS     read-only
   STATUS     mandatory
   DESCRIPTION
     "This attribute indicates the emission priority of frames sent to the 
      interface. A larger value denotes a higher priority."
::= { frUniDlciSpOpEntry 9 }

frUniDlciTransferPriToNwk OBJECT-TYPE
   SYNTAX     Unsigned32 (0..15)
   ACCESS     read-only
   STATUS     mandatory
   DESCRIPTION
     "This attribute indicates the priority at which data is transferred to 
      the network.
      
      The transfer priority is a preference configured for an application 
      according to its delay-sensitivity requirement. Frames with higher 
      transfer priority are served by the network before the frames with 
      lower priority. The transfer priority standard is defined to have 16 
      indices from 0 to 15.
      
      Each transfer priority n, where n indicates the transfer priority 
      index, contains a default setting for routing class of service 
      (multimedia, delay or throughput) and FR egress queue (depending 
      on the number of supported egress queues on the remote end 
      interface) specified by the routingClassOfService and 
      emissionPriority attributes provisioned in the Mod Frs DprsNet 
      Tpm/n component. The default mapping can be altered by a user if 
      required."
::= { frUniDlciSpOpEntry 10 }

frUniDlciTransferPriFromNwk OBJECT-TYPE
   SYNTAX     Unsigned32 (0..15)
   ACCESS     read-only
   STATUS     mandatory
   DESCRIPTION
     "This attribute indicates the priority at which data is transferred from 
      the network.
      
      The transfer priority is a preference configured for an application 
      according to its delay-sensitivity requirement. Frames with higher 
      transfer priority are served by the network before the frames with 
      lower priority. The transfer priority standard is defined to have 16 
      indices from 0 to 15.
      
      Each transfer priority n, where n specifies the transfer priority 
      index, contains a default setting for routing class of service 
      (multimedia, delay or throughput) and FR egress queue (depending 
      on the number of supported egress queues on the remote end 
      interface) specified by the routingClassOfService and 
      emissionPriority attributes provisioned in the Mod Frs DprsNet 
      Tpm/n component. The default mapping can be altered by a user if 
      required."
::= { frUniDlciSpOpEntry 11 }

frUniDlciStatsTable OBJECT-TYPE
   SYNTAX     SEQUENCE OF FrUniDlciStatsEntry
   ACCESS     not-accessible
   STATUS     mandatory
   DESCRIPTION
     "This group contains the operational statistics for the Frame Relay 
      Data Link Connection Identifier."
::= { frUniDlci 15 }

frUniDlciStatsEntry OBJECT-TYPE
   SYNTAX     FrUniDlciStatsEntry
   ACCESS     not-accessible
   STATUS     mandatory
   DESCRIPTION
     "An entry in the frUniDlciStatsTable."
   INDEX {
      frUniIndex,
      frUniDlciIndex }
::= { frUniDlciStatsTable 1 }

FrUniDlciStatsEntry ::= SEQUENCE {
   frUniDlciFrmToIf
      Unsigned32,
   frUniDlciFecnFrmToIf
      Unsigned32,
   frUniDlciBecnFrmToIf
      Unsigned32,
   frUniDlciBciToSubnet
      Unsigned32,
   frUniDlciDeFrmToIf
      Unsigned32,
   frUniDlciDiscCongestedToIf
      Unsigned32,
   frUniDlciDiscDeCongestedToIf
      Unsigned32,
   frUniDlciFrmFromIf
      Unsigned32,
   frUniDlciFecnFrmFromIf
      Unsigned32,
   frUniDlciBecnFrmFromIf
      Unsigned32,
   frUniDlciFciFromSubnet
      Unsigned32,
   frUniDlciBciFromSubnet
      Unsigned32,
   frUniDlciDeFrmFromIf
      Unsigned32,
   frUniDlciExcessFrmFromIf
      Unsigned32,
   frUniDlciDiscExcessFromIf
      Unsigned32,
   frUniDlciDiscFrameAbit
      Unsigned32,
   frUniDlciDiscCongestedFromIf
      Unsigned32,
   frUniDlciDiscDeCongestedFromIf
      Unsigned32,
   frUniDlciErrorShortFrmFromIf
      Unsigned32,
   frUniDlciErrorLongFrmFromIf
      Unsigned32,
   frUniDlciBecnFrmSetByService
      Unsigned32,
   frUniDlciBytesToIf
      Unsigned32,
   frUniDlciDeBytesToIf
      Unsigned32,
   frUniDlciDiscCongestedToIfBytes
      Unsigned32,
   frUniDlciDiscDeCongestedToIfBytes
      Unsigned32,
   frUniDlciBytesFromIf
      Unsigned32,
   frUniDlciDeBytesFromIf
      Unsigned32,
   frUniDlciExcessBytesFromIf
      Unsigned32,
   frUniDlciDiscExcessFromIfBytes
      Unsigned32,
   frUniDlciDiscByteAbit
      Unsigned32,
   frUniDlciDiscCongestedFromIfBytes
      Unsigned32,
   frUniDlciDiscDeCongestedFromIfBytes
      Unsigned32,
   frUniDlciErrorShortBytesFromIf
      Unsigned32,
   frUniDlciErrorLongBytesFromIf
      Unsigned32,
   frUniDlciRateAdaptReduct
      Unsigned32,
   frUniDlciRateAdaptReductPeriod
      Unsigned32,
   frUniDlciTransferPriorityToNetwork
      INTEGER,
   frUniDlciTransferPriorityFromNetwork
      INTEGER,
   frUniDlciCirPresent
      Unsigned32,
   frUniDlciEirPresent
      Unsigned32 }

frUniDlciFrmToIf OBJECT-TYPE
   SYNTAX     Unsigned32 (0..4294967295)
   ACCESS     read-only
   STATUS     mandatory
   DESCRIPTION
     "This attribute counts the frames sent out the interface. When the 
      maximum count is reached the count wraps to zero."
   DEFVAL     { 0 }
::= { frUniDlciStatsEntry 1 }

frUniDlciFecnFrmToIf OBJECT-TYPE
   SYNTAX     Unsigned32 (0..4294967295)
   ACCESS     read-only
   STATUS     mandatory
   DESCRIPTION
     "This attribute counts the frames sent to the interface with the 
      Forward Explicit Congestion Notification (FECN) bit set. When the 
      count reaches maximum it wraps to zero."
   DEFVAL     { 0 }
::= { frUniDlciStatsEntry 2 }

frUniDlciBecnFrmToIf OBJECT-TYPE
   SYNTAX     Unsigned32 (0..4294967295)
   ACCESS     read-only
   STATUS     mandatory
   DESCRIPTION
     "This attribute counts the frames sent to the interface with the 
      Backward Explicit Congestion Notification (BECN) bit set. When 
      the count reaches maximum it wraps to zero."
   DEFVAL     { 0 }
::= { frUniDlciStatsEntry 3 }

frUniDlciBciToSubnet OBJECT-TYPE
   SYNTAX     Unsigned32 (0..4294967295)
   ACCESS     read-only
   STATUS     mandatory
   DESCRIPTION
     "This attribute counts the frames sent into the network with the 
      Backward Congestion Indication (BCI) bit set. When the count 
      reaches maximum it wraps to zero."
   DEFVAL     { 0 }
::= { frUniDlciStatsEntry 4 }

frUniDlciDeFrmToIf OBJECT-TYPE
   SYNTAX     Unsigned32 (0..4294967295)
   ACCESS     read-only
   STATUS     mandatory
   DESCRIPTION
     "This attribute counts the frames sent to the interface with the 
      Discard Eligibility (DE) bit set. When the count reaches maximum 
      it wraps to zero."
   DEFVAL     { 0 }
::= { frUniDlciStatsEntry 5 }

frUniDlciDiscCongestedToIf OBJECT-TYPE
   SYNTAX     Unsigned32 (0..4294967295)
   ACCESS     read-only
   STATUS     mandatory
   DESCRIPTION
     "This attribute counts the number of frame discards at the Frame 
      Relay service due to local congestion in the direction toward the 
      interface. When this count reaches maximum, it wraps to zero."
   DEFVAL     { 0 }
::= { frUniDlciStatsEntry 6 }

frUniDlciDiscDeCongestedToIf OBJECT-TYPE
   SYNTAX     Unsigned32 (0..4294967295)
   ACCESS     read-only
   STATUS     mandatory
   DESCRIPTION
     "This attribute counts the number of discarded frames, with the 
      Discard Eligibility (DE) bit set, at the Frame Relay service, due to 
      local congestion in the direction toward the interface. When this 
      count reaches maximum, it wraps to zero."
   DEFVAL     { 0 }
::= { frUniDlciStatsEntry 7 }

frUniDlciFrmFromIf OBJECT-TYPE
   SYNTAX     Unsigned32 (0..4294967295)
   ACCESS     read-only
   STATUS     mandatory
   DESCRIPTION
     "This attribute counts the frames received from the interface. It 
      includes the frames that are discarded due to error or excess. When 
      the maximum count is reached the count wraps to zero."
   DEFVAL     { 0 }
::= { frUniDlciStatsEntry 8 }

frUniDlciFecnFrmFromIf OBJECT-TYPE
   SYNTAX     Unsigned32 (0..4294967295)
   ACCESS     read-only
   STATUS     mandatory
   DESCRIPTION
     "This attribute counts the frames received from the interface with the 
      Forward Explicit Congestion Notification (FECN) bit set. When the 
      count reaches maximum it wraps to zero."
   DEFVAL     { 0 }
::= { frUniDlciStatsEntry 9 }

frUniDlciBecnFrmFromIf OBJECT-TYPE
   SYNTAX     Unsigned32 (0..4294967295)
   ACCESS     read-only
   STATUS     mandatory
   DESCRIPTION
     "This attribute counts the frames received from the interface with the 
      Backward Explicit Congestion Notification (BECN) bit set. When 
      the count reaches maximum it wraps to zero."
   DEFVAL     { 0 }
::= { frUniDlciStatsEntry 10 }

frUniDlciFciFromSubnet OBJECT-TYPE
   SYNTAX     Unsigned32 (0..4294967295)
   ACCESS     read-only
   STATUS     mandatory
   DESCRIPTION
     "This attribute counts the frames received from the network with the 
      Forward Congestion Indication (FCI) bit set. When the count 
      reaches maximum it wraps to zero."
   DEFVAL     { 0 }
::= { frUniDlciStatsEntry 11 }

frUniDlciBciFromSubnet OBJECT-TYPE
   SYNTAX     Unsigned32 (0..4294967295)
   ACCESS     read-only
   STATUS     mandatory
   DESCRIPTION
     "This attribute counts the frames received from the network with the 
      Backward Congestion Indication (BCI) bit set. When the count 
      reaches maximum it wraps to zero."
   DEFVAL     { 0 }
::= { frUniDlciStatsEntry 12 }

frUniDlciDeFrmFromIf OBJECT-TYPE
   SYNTAX     Unsigned32 (0..4294967295)
   ACCESS     read-only
   STATUS     mandatory
   DESCRIPTION
     "This attribute counts the frames received from the interface with the 
      Discard Eligibility (DE) bit set. When the count reaches maximum 
      it wraps to zero."
   DEFVAL     { 0 }
::= { frUniDlciStatsEntry 13 }

frUniDlciExcessFrmFromIf OBJECT-TYPE
   SYNTAX     Unsigned32 (0..4294967295)
   ACCESS     read-only
   STATUS     mandatory
   DESCRIPTION
     "This attribute counts the frames received from the interface with the 
      Discard Eligibility (DE) bit clear, but subsequently set by the 
      network due to rate enforcement. When the count reaches 
      maximum it wraps to zero."
   DEFVAL     { 0 }
::= { frUniDlciStatsEntry 14 }

frUniDlciDiscExcessFromIf OBJECT-TYPE
   SYNTAX     Unsigned32 (0..4294967295)
   ACCESS     read-only
   STATUS     mandatory
   DESCRIPTION
     "This attribute counts the frames which were discarded due to rate 
      enforcement. When the count reaches maximum it wraps to zero."
   DEFVAL     { 0 }
::= { frUniDlciStatsEntry 15 }

frUniDlciDiscFrameAbit OBJECT-TYPE
   SYNTAX     Unsigned32 (0..4294967295)
   ACCESS     read-only
   STATUS     mandatory
   DESCRIPTION
     "This attribute counts the number of frame discards at the Frame 
      Relay Service, due to an inactive PVC status, in the direction 
      toward the network. When this count reaches maximum, it wraps to 
      zero."
   DEFVAL     { 0 }
::= { frUniDlciStatsEntry 16 }

frUniDlciDiscCongestedFromIf OBJECT-TYPE
   SYNTAX     Unsigned32 (0..4294967295)
   ACCESS     read-only
   STATUS     mandatory
   DESCRIPTION
     "This attribute counts the number of frame discards at the Frame 
      Relay service due to local congestion in the direction toward the 
      network. When this count reaches maximum, it wraps to zero."
   DEFVAL     { 0 }
::= { frUniDlciStatsEntry 17 }

frUniDlciDiscDeCongestedFromIf OBJECT-TYPE
   SYNTAX     Unsigned32 (0..4294967295)
   ACCESS     read-only
   STATUS     mandatory
   DESCRIPTION
     "This attribute counts the number of discarded frames, with the 
      Discard Eligibility (DE) bit set, at the Frame Relay service, due to 
      local congestion, in the direction toward the network. When this 
      count reaches maximum, it wraps to zero."
   DEFVAL     { 0 }
::= { frUniDlciStatsEntry 18 }

frUniDlciErrorShortFrmFromIf OBJECT-TYPE
   SYNTAX     Unsigned32 (0..4294967295)
   ACCESS     read-only
   STATUS     mandatory
   DESCRIPTION
     "This attribute counts the frames received with 0 octets in the 
      information field. When the count reaches maximum it wraps to 
      zero."
   DEFVAL     { 0 }
::= { frUniDlciStatsEntry 19 }

frUniDlciErrorLongFrmFromIf OBJECT-TYPE
   SYNTAX     Unsigned32 (0..4294967295)
   ACCESS     read-only
   STATUS     mandatory
   DESCRIPTION
     "This attribute counts the frames received with number of octets in 
      the information field greater than the subscribed maximum. When 
      the count reaches maximum it wraps to zero. Frames whose lengths 
      are greater than the hardware receive buffer are ignored by the 
      hardware and are therefore not included in this count."
   DEFVAL     { 0 }
::= { frUniDlciStatsEntry 20 }

frUniDlciBecnFrmSetByService OBJECT-TYPE
   SYNTAX     Unsigned32 (0..4294967295)
   ACCESS     read-only
   STATUS     mandatory
   DESCRIPTION
     "This attribute counts the number of frames with BECN set by the 
      Frame Relay service. It is incremented whenever the Frame Relay 
      service sets BECN on a frame upon detecting local congestion. This 
      count is incremented regardless of whether the frame already bears 
      a set BECN bit since its use is to determine the place of congestion. 
      When the count reaches maximum, it wraps to zero."
   DEFVAL     { 0 }
::= { frUniDlciStatsEntry 21 }

frUniDlciBytesToIf OBJECT-TYPE
   SYNTAX     Unsigned32 (0..4294967295)
   ACCESS     read-only
   STATUS     mandatory
   DESCRIPTION
     "This attribute counts the bytes sent out the interface. When the 
      maximum count is reached the count wraps to zero."
   DEFVAL     { 0 }
::= { frUniDlciStatsEntry 22 }

frUniDlciDeBytesToIf OBJECT-TYPE
   SYNTAX     Unsigned32 (0..4294967295)
   ACCESS     read-only
   STATUS     mandatory
   DESCRIPTION
     "This attribute counts the bytes sent to the interface with the Discard 
      Eligibility (DE) bit set. When the count reaches maximum it wraps 
      to zero."
   DEFVAL     { 0 }
::= { frUniDlciStatsEntry 23 }

frUniDlciDiscCongestedToIfBytes OBJECT-TYPE
   SYNTAX     Unsigned32 (0..4294967295)
   ACCESS     read-only
   STATUS     mandatory
   DESCRIPTION
     "This attribute counts the number of byte discards at the Frame 
      Relay service due to local congestion in the direction toward the 
      link. When this count reaches maximum, it wraps to zero."
   DEFVAL     { 0 }
::= { frUniDlciStatsEntry 24 }

frUniDlciDiscDeCongestedToIfBytes OBJECT-TYPE
   SYNTAX     Unsigned32 (0..4294967295)
   ACCESS     read-only
   STATUS     mandatory
   DESCRIPTION
     "This attribute counts the number of discard eligible (DE=1) byte 
      discards at the Frame Relay service due to local congestion in the 
      direction toward the link. When the maximum count is reached the 
      count wraps to zero."
   DEFVAL     { 0 }
::= { frUniDlciStatsEntry 25 }

frUniDlciBytesFromIf OBJECT-TYPE
   SYNTAX     Unsigned32 (0..4294967295)
   ACCESS     read-only
   STATUS     mandatory
   DESCRIPTION
     "This attribute counts the bytes received from the interface. Bytes 
      that are discarded due to error or excess are not counted. When the 
      maximum count is reached the count wraps to zero."
   DEFVAL     { 0 }
::= { frUniDlciStatsEntry 26 }

frUniDlciDeBytesFromIf OBJECT-TYPE
   SYNTAX     Unsigned32 (0..4294967295)
   ACCESS     read-only
   STATUS     mandatory
   DESCRIPTION
     "This attribute counts the bytes received from the interface with the 
      Discard Eligibility (DE) bit set. When the count reaches maximum 
      it wraps to zero."
   DEFVAL     { 0 }
::= { frUniDlciStatsEntry 27 }

frUniDlciExcessBytesFromIf OBJECT-TYPE
   SYNTAX     Unsigned32 (0..4294967295)
   ACCESS     read-only
   STATUS     mandatory
   DESCRIPTION
     "This attribute counts the bytes received from the interface with the 
      Discard Eligibility (DE) bit clear, but subsequently set by the 
      network due to rate enforcement. When the count reaches 
      maximum it wraps to zero."
   DEFVAL     { 0 }
::= { frUniDlciStatsEntry 28 }

frUniDlciDiscExcessFromIfBytes OBJECT-TYPE
   SYNTAX     Unsigned32 (0..4294967295)
   ACCESS     read-only
   STATUS     mandatory
   DESCRIPTION
     "This attribute counts the bytes which were discarded due to rate 
      enforcement. When the count reaches maximum it wraps to zero."
   DEFVAL     { 0 }
::= { frUniDlciStatsEntry 29 }

frUniDlciDiscByteAbit OBJECT-TYPE
   SYNTAX     Unsigned32 (0..4294967295)
   ACCESS     read-only
   STATUS     mandatory
   DESCRIPTION
     "This attribute counts the bytes which were discarded due to aBit 
      turned off."
   DEFVAL     { 0 }
::= { frUniDlciStatsEntry 30 }

frUniDlciDiscCongestedFromIfBytes OBJECT-TYPE
   SYNTAX     Unsigned32 (0..4294967295)
   ACCESS     read-only
   STATUS     mandatory
   DESCRIPTION
     "This attribute counts the number of byte discards at the Frame 
      Relay service due to local congestion in the direction toward the 
      network. When this count reaches maximum, it wraps to zero."
   DEFVAL     { 0 }
::= { frUniDlciStatsEntry 31 }

frUniDlciDiscDeCongestedFromIfBytes OBJECT-TYPE
   SYNTAX     Unsigned32 (0..4294967295)
   ACCESS     read-only
   STATUS     mandatory
   DESCRIPTION
     "This attribute counts the number of discard eligible (DE=1) byte 
      discards at the Frame Relay service due to local congestion in the 
      direction toward the network. When the maximum count is reached 
      the count wraps to zero."
   DEFVAL     { 0 }
::= { frUniDlciStatsEntry 32 }

frUniDlciErrorShortBytesFromIf OBJECT-TYPE
   SYNTAX     Unsigned32 (0..4294967295)
   ACCESS     read-only
   STATUS     mandatory
   DESCRIPTION
     "This attribute counts the bytes received with 0 octets in the 
      information field. When the count reaches maximum it wraps to 
      zero."
   DEFVAL     { 0 }
::= { frUniDlciStatsEntry 33 }

frUniDlciErrorLongBytesFromIf OBJECT-TYPE
   SYNTAX     Unsigned32 (0..4294967295)
   ACCESS     read-only
   STATUS     mandatory
   DESCRIPTION
     "This attribute counts the bytes received with number of octets in the 
      information field greater than the subscribed maximum. When the 
      count reaches maximum it wraps to zero. Bytes whose lengths are 
      greater than the hardware receive buffer are ignored by the 
      hardware and are therefore not included in this count."
   DEFVAL     { 0 }
::= { frUniDlciStatsEntry 34 }

frUniDlciRateAdaptReduct OBJECT-TYPE
   SYNTAX     Unsigned32 (0..4294967295)
   ACCESS     read-only
   STATUS     mandatory
   DESCRIPTION
     "This attribute counts the number of rate reductions due to rate 
      adaptation. Rate adaptation causes the allowed rate to be reduced in 
      steps. After each reduction, a period of time is awaited before 
      further action is taken. At the end of this period, the allowed rate is 
      further reduced if congestion is still prevalent. When this count 
      reaches maximum, it wraps to zero."
   DEFVAL     { 0 }
::= { frUniDlciStatsEntry 35 }

frUniDlciRateAdaptReductPeriod OBJECT-TYPE
   SYNTAX     Unsigned32 (0..4294967295)
   ACCESS     read-only
   STATUS     mandatory
   DESCRIPTION
     "This attribute provides a cumulative count of the amount of time 
      that rate adaptation procedures have been in effect. When this count 
      reaches maximum, it wraps to zero."
   DEFVAL     { 0 }
::= { frUniDlciStatsEntry 36 }

frUniDlciTransferPriorityToNetwork OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     obsolete
   DESCRIPTION
     "This attribute is obsolete. It is replaced by attribute 
      transferPriorityToNetwork under group 
      FrsNniDataLinkConnectionIdentifierServiceParametersOp."
::= { frUniDlciStatsEntry 37 }

frUniDlciTransferPriorityFromNetwork OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     obsolete
   DESCRIPTION
     "This attribute is obsolete. It is replaced by attribute 
      transferPriorityToNetwork under group 
      FrsNniDataLinkConnectionIdentifierServiceParametersOp."
::= { frUniDlciStatsEntry 38 }

frUniDlciCirPresent OBJECT-TYPE
   SYNTAX     Unsigned32 (0..4294967295)
   ACCESS     read-only
   STATUS     mandatory
   DESCRIPTION
     "This attribute provides the actual Committed Information Rate 
      (CIR) enforced for this DLCI. This number is in units of 800 bits/
      sec, since that is the internal resolution of Passport rate 
      enforcement. If rateEnforcement is off, then this number does not 
      have meaning. Normally, this attribute matches the provisioned CIR 
      for the DLCI. But when Rate Adaptation is active, then this number 
      will vary to represent the actual Allowed CIR at the moment that 
      this attribute is collected."
   DEFVAL     { 0 }
::= { frUniDlciStatsEntry 39 }

frUniDlciEirPresent OBJECT-TYPE
   SYNTAX     Unsigned32 (0..4294967295)
   ACCESS     read-only
   STATUS     mandatory
   DESCRIPTION
     "This attribute provides the actual Excess Information Rate (EIR) 
      enforced for this DLCI. This number is in units of 800 bits/sec, 
      since that is the internal resolution of Passport rate enforcement. If 
      rateEnforcement is off, then this number does not have meaning. 
      Normally, this attribute matches the provisioned EIR for the DLCI. 
      But when Rate Adaptation is active, then this number will vary to 
      represent the actual Allowed EIR at the moment that this attribute is 
      collected."
   DEFVAL     { 0 }
::= { frUniDlciStatsEntry 40 }

frUniDlciIntTable OBJECT-TYPE
   SYNTAX     SEQUENCE OF FrUniDlciIntEntry
   ACCESS     not-accessible
   STATUS     mandatory
   DESCRIPTION
     "This group contains the operational statistics for the Frame Relay 
      Data Link Connection Identifier interval data."
::= { frUniDlci 16 }

frUniDlciIntEntry OBJECT-TYPE
   SYNTAX     FrUniDlciIntEntry
   ACCESS     not-accessible
   STATUS     mandatory
   DESCRIPTION
     "An entry in the frUniDlciIntTable."
   INDEX {
      frUniIndex,
      frUniDlciIndex }
::= { frUniDlciIntTable 1 }

FrUniDlciIntEntry ::= SEQUENCE {
   frUniDlciStartTime
      EnterpriseDateAndTime,
   frUniDlciTotalIngressBytes
      Unsigned64,
   frUniDlciTotalEgressBytes
      Unsigned64,
   frUniDlciEirIngressBytes
      Unsigned64,
   frUniDlciEirEgressBytes
      Unsigned64,
   frUniDlciDiscardedBytes
      Unsigned64,
   frUniDlciTotalIngressSegFrm
      Unsigned32,
   frUniDlciTotalEgressSegFrm
      Unsigned32,
   frUniDlciEirIngressSegFrm
      Unsigned32,
   frUniDlciEirEgressSegFrm
      Unsigned32,
   frUniDlciDiscardedSegFrm
      Unsigned32,
   frUniDlciCirPresentObs
      Unsigned32,
   frUniDlciEirPresentObs
      Unsigned32,
   frUniDlciRateEnforcementPresent
      INTEGER,
   frUniDlciRateAdaptationPresent
      INTEGER,
   frUniDlciLocalRateAdaptOccurred
      Unsigned32,
   frUniDlciCallReferenceNumber
      Unsigned32,
   frUniDlciElapsedDifference
      Unsigned32 }

frUniDlciStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes. A new 
      interval period is started each time an accounting record is 
      generated."
::= { frUniDlciIntEntry 1 }

frUniDlciTotalIngressBytes OBJECT-TYPE
   SYNTAX     Unsigned64 (SIZE (8))
   ACCESS     read-only
   STATUS     mandatory
   DESCRIPTION
     "This attribute counts the total bytes received from the interface 
      since the start of the interval period. The start of the interval period 
      is captured in the startTime attribute. The count is reset to zero 
      when an accounting record is generated."
::= { frUniDlciIntEntry 2 }

frUniDlciTotalEgressBytes OBJECT-TYPE
   SYNTAX     Unsigned64 (SIZE (8))
   ACCESS     read-only
   STATUS     mandatory
   DESCRIPTION
     "This attribute counts the total bytes sent to the interface since the 
      start of the interval period. The start of the interval period is 
      captured in the startTime attribute. The count is reset to zero when 
      an accounting record is generated."
::= { frUniDlciIntEntry 3 }

frUniDlciEirIngressBytes OBJECT-TYPE
   SYNTAX     Unsigned64 (SIZE (8))
   ACCESS     read-only
   STATUS     mandatory
   DESCRIPTION
     "This attribute counts the total bytes with the Discard Eligibility 
      (DE) bit set sent to the subnet since the start of the interval period. 
      The start of the interval period is captured in the startTime attribute. 
      The count is reset to zero when an accounting record is generated."
::= { frUniDlciIntEntry 4 }

frUniDlciEirEgressBytes OBJECT-TYPE
   SYNTAX     Unsigned64 (SIZE (8))
   ACCESS     read-only
   STATUS     mandatory
   DESCRIPTION
     "This attribute counts the total bytes with the Discard Eligibility 
      (DE) bit set sent to the interface since the start of the interval 
      period. The start of the interval period is captured in the startTime 
      attribute. The count is reset to zero when an accounting record is 
      generated."
::= { frUniDlciIntEntry 5 }

frUniDlciDiscardedBytes OBJECT-TYPE
   SYNTAX     Unsigned64 (SIZE (8))
   ACCESS     read-only
   STATUS     mandatory
   DESCRIPTION
     "This attribute counts the total bytes in invalid frames received from 
      the interface and discarded at the DLCI since the start of the interval 
      period. This count is a sum of octets in frames discarded due to the 
      number of octets in the information field greater than the subscribed 
      maximum or equal to 0, due to aBit turned off, or due to rate 
      enforcement. The start of the interval period is captured in the 
      startTime attribute. The count is reset to zero when an accounting 
      record is generated."
::= { frUniDlciIntEntry 6 }

frUniDlciTotalIngressSegFrm OBJECT-TYPE
   SYNTAX     Unsigned32 (0..4294967295)
   ACCESS     read-only
   STATUS     mandatory
   DESCRIPTION
     "If the value of the unitsCounted attribute in moduleData component 
      is segments, this attribute counts the total number of segments in 
      frames received from the interface since the start of the interval 
      period. If the value of the unitsCounted attribute in moduleData 
      component is frames, this attribute counts the total number of 
      frames received from the interface since the start of the interval 
      period. The start of the interval period is captured in the startTime 
      attribute. The count is reset to zero when an accounting record is 
      generated"
   DEFVAL     { 0 }
::= { frUniDlciIntEntry 7 }

frUniDlciTotalEgressSegFrm OBJECT-TYPE
   SYNTAX     Unsigned32 (0..4294967295)
   ACCESS     read-only
   STATUS     mandatory
   DESCRIPTION
     "If the value of the unitsCounted attribute in moduleData component 
      is segments, this attribute counts the total number of segments in 
      frames sent to the interface since the start of the interval period. If 
      the value of the unitsCounted attribute in moduleData component is 
      frames, this attribute counts the total number of frames sent to the 
      interface since the start of the interval period. The start of the 
      interval period is captured in the startTime attribute. The count is 
      reset to zero when an accounting record is generated"
   DEFVAL     { 0 }
::= { frUniDlciIntEntry 8 }

frUniDlciEirIngressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the subnet since the 
      start of the interval period. If the value of the unitsCounted attribute 
      in moduleData component is frames, this attribute counts the 
      number of frames with the Discard Eligibility (DE) bit set sent to 
      the subnet since the start of the interval period. The start of the 
      interval period is captured in the startTime attribute. The count is 
      reset to zero when an accounting record is generated"
   DEFVAL     { 0 }
::= { frUniDlciIntEntry 9 }

frUniDlciEirEgressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the interface since 
      the start of the interval period. If the value of the unitsCounted 
      attribute in moduleData component is frames, this attribute counts 
      the number of frames with the Discard Eligibility (DE) bit set sent 
      to the interface since the start of the interval period. The start of the 
      interval period is captured in the startTime attribute. The count is 
      reset to zero when an accounting record is generated."
   DEFVAL     { 0 }
::= { frUniDlciIntEntry 10 }

frUniDlciDiscardedSegFrm OBJECT-TYPE
   SYNTAX     Unsigned32 (0..4294967295)
   ACCESS     read-only
   STATUS     mandatory
   DESCRIPTION
     "If the value of the unitsCounted attribute in moduleData component 
      is segments, this attribute counts the number of segments in invalid 
      frames received from the interface and discarded at the DLCI. If the 
      value of the unitsCounted attribute in moduleData component is 
      frames, this attribute counts the number of invalid frames received 
      from the interface and discarded at the DLCI. Segments of frames 
      are counted since the start of the interval period. The count is reset 
      to zero when an accounting record is generated. The count is a sum 
      of segments in frames or frames discarded due to the number of 
      octets in the information field greater than the subscribed maximum 
      or equal to 0, due to aBit turned off, or due to rate enforcement."
   DEFVAL     { 0 }
::= { frUniDlciIntEntry 11 }

frUniDlciCirPresentObs OBJECT-TYPE
   SYNTAX     Unsigned32 (0..4294967295)
   ACCESS     read-only
   STATUS     obsolete
   DESCRIPTION
     "This attribute has moved to the statistics subgroup. See cirPresent."
   DEFVAL     { 0 }
::= { frUniDlciIntEntry 12 }

frUniDlciEirPresentObs OBJECT-TYPE
   SYNTAX     Unsigned32 (0..4294967295)
   ACCESS     read-only
   STATUS     obsolete
   DESCRIPTION
     "This attribute has moved to the statistics subgroup. See eirPresent."
   DEFVAL     { 0 }
::= { frUniDlciIntEntry 13 }

frUniDlciRateEnforcementPresent OBJECT-TYPE
   SYNTAX     INTEGER  {
                 no(0),
                 yes(1) }
   ACCESS     read-only
   STATUS     obsolete
   DESCRIPTION
     "This attribute is obsolete. It is the same as the provisioned 
      rateEnforcement attribute."
   DEFVAL     { no }
::= { frUniDlciIntEntry 14 }

frUniDlciRateAdaptationPresent OBJECT-TYPE
   SYNTAX     INTEGER  {
                 no(0),
                 yes(1) }
   ACCESS     read-only
   STATUS     obsolete
   DESCRIPTION
     "This attribute is obsolete. See the provisioning attribute 
      rateAdaptation for the data that it intended to provide."
   DEFVAL     { no }
::= { frUniDlciIntEntry 15 }

frUniDlciLocalRateAdaptOccurred OBJECT-TYPE
   SYNTAX     Unsigned32 (0..1)
   ACCESS     read-only
   STATUS     mandatory
   DESCRIPTION
     "This attribute specifies whether rate adaptation has occurred on this 
      user Data Link Connection on this Frame Relay interface.The count 
      is reset to 0 when an accounting record is generated."
   DEFVAL     { 0 }
::= { frUniDlciIntEntry 16 }

frUniDlciCallReferenceNumber OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
   DEFVAL     { 0 }
::= { frUniDlciIntEntry 17 }

frUniDlciElapsedDifference OBJECT-TYPE
   SYNTAX     Unsigned32 (0..4294967295)
   ACCESS     read-only
   STATUS     mandatory
   DESCRIPTION
     "This attribute displays the elapsed time representing the period of 
      this interval data. It is elapsed time in 0.1 second increments since 
      the call started."
   DEFVAL     { 0 }
::= { frUniDlciIntEntry 18 }


-- FrUni/n Dlci/n DirectCall
-- FrNni/n Dlci/n DirectCall 
-- This component defines direct call options for calls issued without 
-- operator intervention. Connection is complete and can be initiated 
-- automatically. Frequency of connection tries is controlled by retry 
-- timer.

frUniDlciDc OBJECT IDENTIFIER ::= { frUniDlci 2 }



frUniDlciDcRowStatusTable OBJECT-TYPE
   SYNTAX     SEQUENCE OF FrUniDlciDcRowStatusEntry
   ACCESS     not-accessible
   STATUS     mandatory
   DESCRIPTION
     "This entry controls the addition and deletion of 
      frUniDlciDc components."
::= { frUniDlciDc 1 }

frUniDlciDcRowStatusEntry OBJECT-TYPE
   SYNTAX     FrUniDlciDcRowStatusEntry
   ACCESS     not-accessible
   STATUS     mandatory
   DESCRIPTION
     "A single entry in the table represents a single 
      frUniDlciDc component."
   INDEX {
      frUniIndex,
      frUniDlciIndex,
      frUniDlciDcIndex }
::= { frUniDlciDcRowStatusTable 1 }

FrUniDlciDcRowStatusEntry ::= SEQUENCE {
   frUniDlciDcRowStatus
      RowStatus,
   frUniDlciDcComponentName
      DisplayString,
   frUniDlciDcStorageType
      StorageType,
   frUniDlciDcIndex
      NonReplicated }

frUniDlciDcRowStatus OBJECT-TYPE
   SYNTAX     RowStatus 
   ACCESS     read-only
   STATUS     mandatory
   DESCRIPTION
     "This variable is used as the basis for SNMP naming of
      frUniDlciDc components.
      These components cannot be added nor deleted."
::= { frUniDlciDcRowStatusEntry 1 }

frUniDlciDcComponentName OBJECT-TYPE
   SYNTAX     DisplayString 
   ACCESS     read-only
   STATUS     mandatory
   DESCRIPTION
     "This variable provides the component's string name for
      use with the ASCII Console Interface"
::= { frUniDlciDcRowStatusEntry 2 }

frUniDlciDcStorageType OBJECT-TYPE
   SYNTAX     StorageType 
   ACCESS     read-only
   STATUS     mandatory
   DESCRIPTION
     "This variable represents the storage type value for the
      frUniDlciDc tables."
::= { frUniDlciDcRowStatusEntry 4 }

frUniDlciDcIndex OBJECT-TYPE
   SYNTAX     NonReplicated 
   ACCESS     not-accessible
   STATUS     mandatory
   DESCRIPTION
     "This variable represents the index for the frUniDlciDc tables."
::= { frUniDlciDcRowStatusEntry 10 }

frUniDlciDcOptionsTable OBJECT-TYPE
   SYNTAX     SEQUENCE OF FrUniDlciDcOptionsEntry
   ACCESS     not-accessible
   STATUS     mandatory
   DESCRIPTION
     "Options group defines attributes associated with direct call. It 
      defines complete connection in terms of path and call options. This 
      connection can be permanent (pvc) or switched (svc). It can have 
      facilities. The total number of bytes of facilities including the 
      facility codes, and all of the facility data from all of the four classes 
      of facilities:
      CCITT_Facilities
      DTE_Facilities
      National_Facilities
      International_Facilities
      must not exceed 512 bytes."
::= { frUniDlciDc 10 }

frUniDlciDcOptionsEntry OBJECT-TYPE
   SYNTAX     FrUniDlciDcOptionsEntry
   ACCESS     not-accessible
   STATUS     mandatory
   DESCRIPTION
     "An entry in the frUniDlciDcOptionsTable."
   INDEX {
      frUniIndex,
      frUniDlciIndex,
      frUniDlciDcIndex }
::= { frUniDlciDcOptionsTable 1 }

FrUniDlciDcOptionsEntry ::= SEQUENCE {
   frUniDlciDcRemoteNpi
      INTEGER,
   frUniDlciDcRemoteDna
      DigitString,
   frUniDlciDcRemoteDlci
      Unsigned32,
   frUniDlciDcType
      INTEGER,
   frUniDlciDcTransferPriority
      INTEGER,
   frUniDlciDcDiscardPriority
      INTEGER,
   frUniDlciDcDeDiscardPriority
      INTEGER,
   frUniDlciDcDataPath
      INTEGER,
   frUniDlciDcCugIndex
      Unsigned32,
   frUniDlciDcCugType
      INTEGER }

frUniDlciDcRemoteNpi OBJECT-TYPE
   SYNTAX     INTEGER  {
                 x121(0),
                 e164(1) }
   ACCESS     read-write
   STATUS     mandatory
   DESCRIPTION
     "Destination Numbering Plan Indicator (Npi) indicates the 
      numbering plan used in the remoteDna."
   DEFVAL     { x121 }
::= { frUniDlciDcOptionsEntry 3 }

frUniDlciDcRemoteDna OBJECT-TYPE
   SYNTAX     DigitString (SIZE (1..15))
   ACCESS     read-write
   STATUS     mandatory
   DESCRIPTION
     "This attribute specifies the Data Network Address (DNA) of the 
      remote. This is the called (destination) DTE address (DNA) to 
      which this direct call will be sent. Initially, the called DTE address 
      attribute must be present, that is, there must be a valid destination 
      address. However, it may be possible in the future to configure the 
      direct call with a mnemonic address, in which case, this attribute 
      will contain a zero-length DNA, and the mnemonic address will be 
      carried as one of the facilities."
::= { frUniDlciDcOptionsEntry 4 }

frUniDlciDcRemoteDlci OBJECT-TYPE
   SYNTAX     Unsigned32 (16..1007)
   ACCESS     read-write
   STATUS     mandatory
   DESCRIPTION
     "L(LCN) of the destination.
      This attribute provides the remote LCN (Logical Channel Number) 
      - it is used only for PVCs, where the parameter Type is set to a 
      value of PVC."
::= { frUniDlciDcOptionsEntry 5 }

frUniDlciDcType OBJECT-TYPE
   SYNTAX     INTEGER  {
                 permanentMaster(1),
                 permanentSlave(2),
                 permanentBackupSlave(3),
                 permanentSlaveWithBackup(4) }
   ACCESS     read-write
   STATUS     mandatory
   DESCRIPTION
     "This attribute specifies the type of Vc call:
      permanentMaster, 
      permanentSlave, 
      permanentSlaveWithBackup,
      permanentBackupSlave. 
      
      If the value is set to permanentMaster, then a permanent 
      connection will be established between 2 ends. The remote end 
      must be defined as a permanentSlave, permanentBackupSlave or 
      permanentSlaveWithBackup. The Connection cannot be 
      established if the remote end is defined as anything else. The end 
      defined as permanentMaster always initiates the calls. It will 
      attempt to call once per minute.
      
      If the value is set to permanentSlave then a permanent connection 
      will be established between 2 ends. The remote end must be defined 
      as a permanentMaster. The Connection cannot be established if the 
      remote end is defined as anything else. The permanentSlave end 
      will attempt to call once per minute.
      
      If the value is set to permanentSlaveWithBackup then a permanent 
      connection will be established between the two ends. The remote 
      end must be defined as a permanentMaster. The connection cannot 
      be established if the remote interface end is defined as anything 
      else. The permanentSlaveWithBackup end will attempt to call once 
      per minute. When type is set to permanentSlaveWithBackup 
      connection will be cleared if interface becomes unavailable. This 
      enables a retry of the connection which can be redirected to 
      permanentBackupSlave.
      
      If the value is set to permanentBackupSlave then a permanent 
      connection will be established between the 2 ends only if the 
      permanentMaster end is disconnected from the 
      permanentSlaveWithBackup end and a backup call is established 
      by the redirection system. If the permanentSlaveWithBackup 
      interface becomes visible again, the permanentBackupSlave end is 
      disconnected and the permanentSlaveWithBackup end is 
      reconnected to the permanentMaster end. The 
      permanentBackupSlave end does not try to establish pvc call."
   DEFVAL     { permanentMaster }
::= { frUniDlciDcOptionsEntry 6 }

frUniDlciDcTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 useDnaDefTP(255) }
   ACCESS     read-write
   STATUS     mandatory
   DESCRIPTION
     "This attribute specifies the transfer priority to network for the 
      outgoing calls using this particular DLCI. It overRides the 
      defaultTransferPriority provisioned in its associated Dna 
      component.
      
      The transfer priority is a preference configured for an application 
      according to its delay-sensitivity requirement. Frames with higher 
      transfer priority are served by the network before the frames with 
      lower priority. The transfer priority standard is defined to have 16 
      levels from 0 to 15.
      
      Each transfer priority n, where n is the transfer priority index, 
      contains a default setting for routing class of service (multimedia, 
      delay or throughput) and frame relay egress queue (depending on 
      the number of supported egress queues on the remote end interface) 
      specified by the routingClassOfService and emissionPriority 
      attributes provisioned under the Mod Frs DprsNet Tpm/n 
      component. The default mapping can be altered by a user if 
      required.
      
      The default of transferPriority is useDnaDefTP. It means using the 
      provisioning value under defaultTransferPriority of its associated 
      Dna for this DLCI."
   DEFVAL     { useDnaDefTP }
::= { frUniDlciDcOptionsEntry 9 }

frUniDlciDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority are discarded 
      first than the traffic with high priority. The Dna default value 
      (provisioned by outDefaultPriority) is taken if this attribute is set to 
      the value useDnaDefPriority.
      
      The default of discardPriority is useDnaDefPriority."
   DEFVAL     { useDnaDefPriority }
::= { frUniDlciDcOptionsEntry 10 }

frUniDlciDcDeDiscardPriority OBJECT-TYPE
   SYNTAX     INTEGER  {
                 lowest(0),
                 determinedByDiscardPriority(1) }
   ACCESS     read-write
   STATUS     mandatory
   DESCRIPTION
     "This attribute specifies whether the discardPriority applies to DE 
      frames for this DLCI.
      
      If deDiscardPriority is set to determinedByDiscardPriority, traffic 
      with DE bit set will be discarded according to the setting of the 
      discardPriority.
      
      If deDiscardPriority is set to lowest, all traffic with DE bit set will 
      be treated the same and be sent to the subnet at the lowest discard 
      priority."
   DEFVAL     { determinedByDiscardPriority }
::= { frUniDlciDcOptionsEntry 11 }

frUniDlciDcDataPath OBJECT-TYPE
   SYNTAX     INTEGER  {
                 dprsOnly(0),
                 dprsMcsOnly(1),
                 dprsMcsFirst(2),
                 useDnaValue(3) }
   ACCESS     read-write
   STATUS     mandatory
   DESCRIPTION
     "This attribute specifies the data path to be used by Virtual Circuits 
      on this interface. The value of the dataPath attribute in the Dna 
      component is overridden by this attribute if the value is not 
      useDnaValue.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used.
      
      useDnaValue - use the value provisioned in Dna component."
   DEFVAL     { useDnaValue }
::= { frUniDlciDcOptionsEntry 12 }

frUniDlciDcCugIndex OBJECT-TYPE
   SYNTAX     Unsigned32 (0..255)
   ACCESS     read-write
   STATUS     mandatory
   DESCRIPTION
     "This attribute specifies the CUG index which is to be signalled in 
      PVC call requests to the remote end.
      
      The type of CUG signalling is defined in attribute cugType in this 
      component."
   DEFVAL     { 0 }
::= { frUniDlciDcOptionsEntry 13 }

frUniDlciDcCugType OBJECT-TYPE
   SYNTAX     INTEGER  {
                 doNotSignal(0),
                 cug(3),
                 cugOa(9) }
   ACCESS     read-write
   STATUS     mandatory
   DESCRIPTION
     "This attribute specifies the type of CUG signalling to be used in 
      PVC call request. Index of CUG to be used is defined in attribute 
      cugIndex in this component.
      
      Possible values are:
      cug - signal cug
      cugOa - signal cug with outgoing access
      doNotSignal - no CUG in call request"
   DEFVAL     { doNotSignal }
::= { frUniDlciDcOptionsEntry 14 }

frUniDlciDcNfaTable OBJECT-TYPE
   SYNTAX     SEQUENCE OF FrUniDlciDcNfaEntry
   ACCESS     not-accessible
   STATUS     obsolete
   DESCRIPTION
     "This is the i'th National facility required for this direct call. Within 
      the provisioning system, the user specifies the facility code along 
      with the facility parameters. The facility is represented internally as 
      a hexadecimal string following the X.25 CCITT representation for 
      facility data.
      
      Two explicit attributes discardPriority and pathSensitivity are 
      created to replace H.01 and H.30 in the group 
      VcsDirectCallOptionsProv of this file. The migrate escape here 
      (DcComponent::migrateFaxEscape) propagates the old provisioning 
      data under H.01 and H.30 into discardPriority and transferPriority. 
      
      The rule of the above propagation are: 0 in H.01 is equivalent to 
      discardPriority 0; 1 in H.01 is equivalent to discardPriority 1. And 0 
      in H.30 is equivalent to transferPriority throughput; 1 in H.30 is 
      equivalent to pathSensitivity delay.
      
      Please refer to discardPriority and pathSensitivity for more 
      information on how to use them."
::= { frUniDlciDc 202 }

frUniDlciDcNfaEntry OBJECT-TYPE
   SYNTAX     FrUniDlciDcNfaEntry
   ACCESS     not-accessible
   STATUS     obsolete
   DESCRIPTION
     "An entry in the frUniDlciDcNfaTable."
   INDEX {
      frUniIndex,
      frUniDlciIndex,
      frUniDlciDcIndex,
      frUniDlciDcNfaIndex }
::= { frUniDlciDcNfaTable 1 }

FrUniDlciDcNfaEntry ::= SEQUENCE {
   frUniDlciDcNfaIndex
      Integer32,
   frUniDlciDcNfaValue
      HexString,
   frUniDlciDcNfaRowStatus
      RowStatus }

frUniDlciDcNfaIndex OBJECT-TYPE
   SYNTAX     Integer32 (1 | 48)
   ACCESS     not-accessible
   STATUS     obsolete
   DESCRIPTION
     "This variable represents the index for the frUniDlciDcNfaTable."
::= { frUniDlciDcNfaEntry 1 }

frUniDlciDcNfaValue OBJECT-TYPE
   SYNTAX     HexString (SIZE (0..128))
   ACCESS     read-write
   STATUS     obsolete
   DESCRIPTION
     "This variable represents an individual value for the
      frUniDlciDcNfaTable."
::= { frUniDlciDcNfaEntry 2 }

frUniDlciDcNfaRowStatus OBJECT-TYPE
   SYNTAX     RowStatus 
   ACCESS     write-only
   STATUS     obsolete
   DESCRIPTION
     "This variable is used to control the addition and deletion 
      of individual values of the frUniDlciDcNfaTable."
::= { frUniDlciDcNfaEntry 3 }


-- This component defines attributes collected by Frame Relay Vc.

frUniDlciVc OBJECT IDENTIFIER ::= { frUniDlci 3 }



frUniDlciVcRowStatusTable OBJECT-TYPE
   SYNTAX     SEQUENCE OF FrUniDlciVcRowStatusEntry
   ACCESS     not-accessible
   STATUS     mandatory
   DESCRIPTION
     "This entry controls the addition and deletion of 
      frUniDlciVc components."
::= { frUniDlciVc 1 }

frUniDlciVcRowStatusEntry OBJECT-TYPE
   SYNTAX     FrUniDlciVcRowStatusEntry
   ACCESS     not-accessible
   STATUS     mandatory
   DESCRIPTION
     "A single entry in the table represents a single 
      frUniDlciVc component."
   INDEX {
      frUniIndex,
      frUniDlciIndex,
      frUniDlciVcIndex }
::= { frUniDlciVcRowStatusTable 1 }

FrUniDlciVcRowStatusEntry ::= SEQUENCE {
   frUniDlciVcRowStatus
      RowStatus,
   frUniDlciVcComponentName
      DisplayString,
   frUniDlciVcStorageType
      StorageType,
   frUniDlciVcIndex
      NonReplicated }

frUniDlciVcRowStatus OBJECT-TYPE
   SYNTAX     RowStatus 
   ACCESS     read-only
   STATUS     mandatory
   DESCRIPTION
     "This variable is used as the basis for SNMP naming of
      frUniDlciVc components.
      These components cannot be added nor deleted."
::= { frUniDlciVcRowStatusEntry 1 }

frUniDlciVcComponentName OBJECT-TYPE
   SYNTAX     DisplayString 
   ACCESS     read-only
   STATUS     mandatory
   DESCRIPTION
     "This variable provides the component's string name for
      use with the ASCII Console Interface"
::= { frUniDlciVcRowStatusEntry 2 }

frUniDlciVcStorageType OBJECT-TYPE
   SYNTAX     StorageType 
   ACCESS     read-only
   STATUS     mandatory
   DESCRIPTION
     "This variable represents the storage type value for the
      frUniDlciVc tables."
::= { frUniDlciVcRowStatusEntry 4 }

frUniDlciVcIndex OBJECT-TYPE
   SYNTAX     NonReplicated 
   ACCESS     not-accessible
   STATUS     mandatory
   DESCRIPTION
     "This variable represents the index for the frUniDlciVc tables."
::= { frUniDlciVcRowStatusEntry 10 }

frUniDlciVcCadTable OBJECT-TYPE
   SYNTAX     SEQUENCE OF FrUniDlciVcCadEntry
   ACCESS     not-accessible
   STATUS     mandatory
   DESCRIPTION
     "This group represents operational call data related to Frame Relay 
      Vc. It can be displayed only for Frame Relay Vc which is created by 
      application."
::= { frUniDlciVc 10 }

frUniDlciVcCadEntry OBJECT-TYPE
   SYNTAX     FrUniDlciVcCadEntry
   ACCESS     not-accessible
   STATUS     mandatory
   DESCRIPTION
     "An entry in the frUniDlciVcCadTable."
   INDEX {
      frUniIndex,
      frUniDlciIndex,
      frUniDlciVcIndex }
::= { frUniDlciVcCadTable 1 }

FrUniDlciVcCadEntry ::= SEQUENCE {
   frUniDlciVcType
      INTEGER,
   frUniDlciVcState
      INTEGER,
   frUniDlciVcPreviousState
      INTEGER,
   frUniDlciVcDiagnosticCode
      Unsigned32,
   frUniDlciVcPreviousDiagnosticCode
      Unsigned32,
   frUniDlciVcCalledNpi
      INTEGER,
   frUniDlciVcCalledDna
      DigitString,
   frUniDlciVcCalledLcn
      Unsigned32,
   frUniDlciVcCallingNpi
      INTEGER,
   frUniDlciVcCallingDna
      DigitString,
   frUniDlciVcCallingLcn
      Unsigned32,
   frUniDlciVcAccountingEnabled
      INTEGER,
   frUniDlciVcFastSelectCall
      INTEGER,
   frUniDlciVcPathReliability
      INTEGER,
   frUniDlciVcAccountingEnd
      INTEGER,
   frUniDlciVcPriority
      INTEGER,
   frUniDlciVcSegmentSize
      Unsigned32,
   frUniDlciVcMaxSubnetPktSize
      Unsigned32,
   frUniDlciVcRcosToNetwork
      INTEGER,
   frUniDlciVcRcosFromNetwork
      INTEGER,
   frUniDlciVcEmissionPriorityToNetwork
      INTEGER,
   frUniDlciVcEmissionPriorityFromNetwork
      INTEGER,
   frUniDlciVcDataPath
      AsciiString }

frUniDlciVcType OBJECT-TYPE
   SYNTAX     INTEGER  {
                 svc(0),
                 pvc(1),
                 spvc(2) }
   ACCESS     read-only
   STATUS     mandatory
   DESCRIPTION
     "This attribute displays the type of call, pvc,svc or spvc."
::= { frUniDlciVcCadEntry 1 }

frUniDlciVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { frUniDlciVcCadEntry 2 }

frUniDlciVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { frUniDlciVcCadEntry 3 }

frUniDlciVcDiagnosticCode OBJECT-TYPE
   SYNTAX     Unsigned32 (0..255)
   ACCESS     read-only
   STATUS     mandatory
   DESCRIPTION
     "This attribute displays the internal substate of call control. It is used 
      to further refine state of call processing."
::= { frUniDlciVcCadEntry 4 }

frUniDlciVcPreviousDiagnosticCode OBJECT-TYPE
   SYNTAX     Unsigned32 (0..255)
   ACCESS     read-only
   STATUS     mandatory
   DESCRIPTION
     "This attribute displays the internal substate of call control. It is used 
      to further refine state of call processing."
::= { frUniDlciVcCadEntry 5 }

frUniDlciVcCalledNpi OBJECT-TYPE
   SYNTAX     INTEGER  {
                 x121(0),
                 e164(1) }
   ACCESS     read-only
   STATUS     mandatory
   DESCRIPTION
     "This attribute displays the Numbering Plan Indicator (NPI) of the 
      called end."
::= { frUniDlciVcCadEntry 6 }

frUniDlciVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { frUniDlciVcCadEntry 7 }

frUniDlciVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { frUniDlciVcCadEntry 8 }

frUniDlciVcCallingNpi OBJECT-TYPE
   SYNTAX     INTEGER  {
                 x121(0),
                 e164(1) }
   ACCESS     read-only
   STATUS     mandatory
   DESCRIPTION
     "This attribute displays the Numbering Plan Indicator (NPI) of the 
      calling end."
::= { frUniDlciVcCadEntry 9 }

frUniDlciVcCallingDna OBJECT-TYPE
   SYNTAX     DigitString (SIZE (1..15))
   ACCESS     read-only
   STATUS     mandatory
   DESCRIPTION
     "This attribute displays the Data Network Address (Dna) of the 
      calling end."
::= { frUniDlciVcCadEntry 10 }

frUniDlciVcCallingLcn OBJECT-TYPE
   SYNTAX     Unsigned32 (1..65535)
   ACCESS     read-only
   STATUS     mandatory
   DESCRIPTION
     "This attribute displays the Logical Channel Number of the calling 
      end."
::= { frUniDlciVcCadEntry 11 }

frUniDlciVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { frUniDlciVcCadEntry 12 }

frUniDlciVcFastSelectCall OBJECT-TYPE
   SYNTAX     INTEGER  {
                 no(0),
                 yes(1) }
   ACCESS     read-only
   STATUS     mandatory
   DESCRIPTION
     "This attribute displays that this is a fast select call."
::= { frUniDlciVcCadEntry 13 }

frUniDlciVcPathReliability OBJECT-TYPE
   SYNTAX     INTEGER  {
                 high(0),
                 normal(1) }
   ACCESS     read-only
   STATUS     mandatory
   DESCRIPTION
     "This attribute displays the path reliability."
::= { frUniDlciVcCadEntry 19 }

frUniDlciVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { frUniDlciVcCadEntry 20 }

frUniDlciVcPriority OBJECT-TYPE
   SYNTAX     INTEGER  {
                 normal(0),
                 high(1) }
   ACCESS     read-only
   STATUS     mandatory
   DESCRIPTION
     "This attribute displays whether the call is a normal or a high 
      priority call."
::= { frUniDlciVcCadEntry 21 }

frUniDlciVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { frUniDlciVcCadEntry 22 }

frUniDlciVcMaxSubnetPktSize OBJECT-TYPE
   SYNTAX     Unsigned32 (0..4096)
   ACCESS     read-only
   STATUS     mandatory
   DESCRIPTION
     "This attribute indicates the maximum packet size allowed on the Vc."
::= { frUniDlciVcCadEntry 27 }

frUniDlciVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { frUniDlciVcCadEntry 28 }

frUniDlciVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { frUniDlciVcCadEntry 29 }

frUniDlciVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { frUniDlciVcCadEntry 30 }

frUniDlciVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { frUniDlciVcCadEntry 31 }

frUniDlciVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { frUniDlciVcCadEntry 32 }

frUniDlciVcIntdTable OBJECT-TYPE
   SYNTAX     SEQUENCE OF FrUniDlciVcIntdEntry
   ACCESS     not-accessible
   STATUS     mandatory
   DESCRIPTION
     "This group defines display of interval data collected by Vc. Data in 
      this group is variable and may depend on time when this display 
      command is issued."
::= { frUniDlciVc 11 }

frUniDlciVcIntdEntry OBJECT-TYPE
   SYNTAX     FrUniDlciVcIntdEntry
   ACCESS     not-accessible
   STATUS     mandatory
   DESCRIPTION
     "An entry in the frUniDlciVcIntdTable."
   INDEX {
      frUniIndex,
      frUniDlciIndex,
      frUniDlciVcIndex }
::= { frUniDlciVcIntdTable 1 }

FrUniDlciVcIntdEntry ::= SEQUENCE {
   frUniDlciVcCallReferenceNumber
      Hex,
   frUniDlciVcElapsedTimeTillNow
      Unsigned32,
   frUniDlciVcSegmentsRx
      Unsigned32,
   frUniDlciVcSegmentsSent
      Unsigned32,
   frUniDlciVcStartTime
      EnterpriseDateAndTime }

frUniDlciVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { frUniDlciVcIntdEntry 1 }

frUniDlciVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { frUniDlciVcIntdEntry 2 }

frUniDlciVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { frUniDlciVcIntdEntry 3 }

frUniDlciVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { frUniDlciVcIntdEntry 4 }

frUniDlciVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { frUniDlciVcIntdEntry 5 }

frUniDlciVcFrdTable OBJECT-TYPE
   SYNTAX     SEQUENCE OF FrUniDlciVcFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { frUniDlciVc 12 }

frUniDlciVcFrdEntry OBJECT-TYPE
   SYNTAX     FrUniDlciVcFrdEntry
   ACCESS     not-accessible
   STATUS     mandatory
   DESCRIPTION
     "An entry in the frUniDlciVcFrdTable."
   INDEX {
      frUniIndex,
      frUniDlciIndex,
      frUniDlciVcIndex }
::= { frUniDlciVcFrdTable 1 }

FrUniDlciVcFrdEntry ::= SEQUENCE {
   frUniDlciVcFrmCongestedToSubnet
      Unsigned32,
   frUniDlciVcCannotForwardToSubnet
      Unsigned32,
   frUniDlciVcNotDataXferToSubnet
      Unsigned32,
   frUniDlciVcOutOfRangeFrmFromSubnet
      Unsigned32,
   frUniDlciVcCombErrorsFromSubnet
      Unsigned32,
   frUniDlciVcDuplicatesFromSubnet
      Unsigned32,
   frUniDlciVcNotDataXferFromSubnet
      Unsigned32,
   frUniDlciVcFrmLossTimeouts
      Unsigned32,
   frUniDlciVcOoSeqByteCntExceeded
      Unsigned32,
   frUniDlciVcPeakOoSeqPktCount
      Unsigned32,
   frUniDlciVcPeakOoSeqFrmForwarded
      Unsigned32,
   frUniDlciVcSendSequenceNumber
      Unsigned32,
   frUniDlciVcPktRetryTimeouts
      Unsigned32,
   frUniDlciVcPeakRetryQueueSize
      Unsigned32,
   frUniDlciVcSubnetRecoveries
      Unsigned32,
   frUniDlciVcOoSeqPktCntExceeded
      Unsigned32,
   frUniDlciVcPeakOoSeqByteCount
      Unsigned32 }

frUniDlciVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { frUniDlciVcFrdEntry 2 }

frUniDlciVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { frUniDlciVcFrdEntry 3 }

frUniDlciVcNotDataXferToSubnet OBJECT-TYPE
   SYNTAX     Unsigned32 (0..5000)
   ACCESS     read-only
   STATUS     mandatory
   DESCRIPTION
     "This attribute records the number of frames from link discarded 
      when the Vc tries to recover from internal path failure."
::= { frUniDlciVcFrdEntry 4 }

frUniDlciVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { frUniDlciVcFrdEntry 5 }

frUniDlciVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { frUniDlciVcFrdEntry 6 }

frUniDlciVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { frUniDlciVcFrdEntry 7 }

frUniDlciVcNotDataXferFromSubnet OBJECT-TYPE
   SYNTAX     Unsigned32 (0..5000)
   ACCESS     read-only
   STATUS     mandatory
   DESCRIPTION
     "This attribute displays the number of subnet packets discarded when 
      data transfer is suspended in Vc recovery."
::= { frUniDlciVcFrdEntry 8 }

frUniDlciVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { frUniDlciVcFrdEntry 9 }

frUniDlciVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { frUniDlciVcFrdEntry 10 }

frUniDlciVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { frUniDlciVcFrdEntry 11 }

frUniDlciVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { frUniDlciVcFrdEntry 12 }

frUniDlciVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { frUniDlciVcFrdEntry 13 }

frUniDlciVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { frUniDlciVcFrdEntry 15 }

frUniDlciVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { frUniDlciVcFrdEntry 16 }

frUniDlciVcSubnetRecoveries OBJECT-TYPE
   SYNTAX     Unsigned32 (0..5000)
   ACCESS     read-only
   STATUS     mandatory
   DESCRIPTION
     "This attribute displays the number of successful Vc recovery 
      attempts."
::= { frUniDlciVcFrdEntry 17 }

frUniDlciVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { frUniDlciVcFrdEntry 19 }

frUniDlciVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { frUniDlciVcFrdEntry 20 }

frUniDlciVcDmepTable OBJECT-TYPE
   SYNTAX     SEQUENCE OF FrUniDlciVcDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { frUniDlciVc 417 }

frUniDlciVcDmepEntry OBJECT-TYPE
   SYNTAX     FrUniDlciVcDmepEntry
   ACCESS     not-accessible
   STATUS     mandatory
   DESCRIPTION
     "An entry in the frUniDlciVcDmepTable."
   INDEX {
      frUniIndex,
      frUniDlciIndex,
      frUniDlciVcIndex,
      frUniDlciVcDmepValue }
::= { frUniDlciVcDmepTable 1 }

FrUniDlciVcDmepEntry ::= SEQUENCE {
   frUniDlciVcDmepValue
      RowPointer }

frUniDlciVcDmepValue OBJECT-TYPE
   SYNTAX     RowPointer 
   ACCESS     read-only
   STATUS     mandatory
   DESCRIPTION
     "This variable represents both the value and the index for the
      frUniDlciVcDmepTable."
::= { frUniDlciVcDmepEntry 1 }


-- FrUni/n Dlci/n ServiceParametersProv
-- This component contains the provisionable traffic control attributes 
-- for its parent Dlci component.

frUniDlciSp OBJECT IDENTIFIER ::= { frUniDlci 4 }



frUniDlciSpRowStatusTable OBJECT-TYPE
   SYNTAX     SEQUENCE OF FrUniDlciSpRowStatusEntry
   ACCESS     not-accessible
   STATUS     mandatory
   DESCRIPTION
     "This entry controls the addition and deletion of 
      frUniDlciSp components."
::= { frUniDlciSp 1 }

frUniDlciSpRowStatusEntry OBJECT-TYPE
   SYNTAX     FrUniDlciSpRowStatusEntry
   ACCESS     not-accessible
   STATUS     mandatory
   DESCRIPTION
     "A single entry in the table represents a single 
      frUniDlciSp component."
   INDEX {
      frUniIndex,
      frUniDlciIndex,
      frUniDlciSpIndex }
::= { frUniDlciSpRowStatusTable 1 }

FrUniDlciSpRowStatusEntry ::= SEQUENCE {
   frUniDlciSpRowStatus
      RowStatus,
   frUniDlciSpComponentName
      DisplayString,
   frUniDlciSpStorageType
      StorageType,
   frUniDlciSpIndex
      NonReplicated }

frUniDlciSpRowStatus OBJECT-TYPE
   SYNTAX     RowStatus 
   ACCESS     read-only
   STATUS     mandatory
   DESCRIPTION
     "This variable is used as the basis for SNMP naming of
      frUniDlciSp components.
      These components cannot be added nor deleted."
::= { frUniDlciSpRowStatusEntry 1 }

frUniDlciSpComponentName OBJECT-TYPE
   SYNTAX     DisplayString 
   ACCESS     read-only
   STATUS     mandatory
   DESCRIPTION
     "This variable provides the component's string name for
      use with the ASCII Console Interface"
::= { frUniDlciSpRowStatusEntry 2 }

frUniDlciSpStorageType OBJECT-TYPE
   SYNTAX     StorageType 
   ACCESS     read-only
   STATUS     mandatory
   DESCRIPTION
     "This variable represents the storage type value for the
      frUniDlciSp tables."
::= { frUniDlciSpRowStatusEntry 4 }

frUniDlciSpIndex OBJECT-TYPE
   SYNTAX     NonReplicated 
   ACCESS     not-accessible
   STATUS     mandatory
   DESCRIPTION
     "This variable represents the index for the frUniDlciSp tables."
::= { frUniDlciSpRowStatusEntry 10 }

frUniDlciSpParmsTable OBJECT-TYPE
   SYNTAX     SEQUENCE OF FrUniDlciSpParmsEntry
   ACCESS     not-accessible
   STATUS     mandatory
   DESCRIPTION
     "This group contains the provisionable attributes for the Data Link 
      Connection Identifier. These attributes reflect the service parameters 
      specific to this instance of DLCI. The congestion control attributes 
      in this group are defined in T1.606 Addendum 1."
::= { frUniDlciSp 11 }

frUniDlciSpParmsEntry OBJECT-TYPE
   SYNTAX     FrUniDlciSpParmsEntry
   ACCESS     not-accessible
   STATUS     mandatory
   DESCRIPTION
     "An entry in the frUniDlciSpParmsTable."
   INDEX {
      frUniIndex,
      frUniDlciIndex,
      frUniDlciSpIndex }
::= { frUniDlciSpParmsTable 1 }

FrUniDlciSpParmsEntry ::= SEQUENCE {
   frUniDlciSpMaximumFrameSize
      Unsigned32,
   frUniDlciSpRateEnforcement
      INTEGER,
   frUniDlciSpCommittedInformationRate
      Gauge32,
   frUniDlciSpCommittedBurstSize
      Gauge32,
   frUniDlciSpExcessBurstSize
      Gauge32,
   frUniDlciSpMeasurementInterval
      Unsigned32,
   frUniDlciSpRateAdaptation
      INTEGER,
   frUniDlciSpAccounting
      INTEGER,
   frUniDlciSpRaSensitivity
      Unsigned32,
   frUniDlciSpUpdateBCI
      INTEGER }

frUniDlciSpMaximumFrameSize OBJECT-TYPE
   SYNTAX     Unsigned32 (1..8187)
   ACCESS     read-write
   STATUS     mandatory
   DESCRIPTION
     "This attribute specifies the maximum number of octets which may 
      be included in the information field. The frame relay header and 
      CRC octets are not included in this definition. This attribute 
      corresponds to the dN1 parameter described in the Vendor Forum 
      Specification."
   DEFVAL     { 2100 }
::= { frUniDlciSpParmsEntry 1 }

frUniDlciSpRateEnforcement OBJECT-TYPE
   SYNTAX     INTEGER  {
                 off(0),
                 on(1) }
   ACCESS     read-write
   STATUS     mandatory
   DESCRIPTION
     "This attribute specifies whether rate enforcement is in effect for this 
      user Data Link Connection on this Frame Relay interface. Turning 
      on rate enforcement means that CIR and DE=1 traffic will be 
      measured and enforced. Turning off rate enforcement means that all 
      frames from the user will be accepted and no modifications to the 
      frame with respect to the DE bit will be made."
   DEFVAL     { on }
::= { frUniDlciSpParmsEntry 2 }

frUniDlciSpCommittedInformationRate OBJECT-TYPE
   SYNTAX     Gauge32 (0..50000000)
   ACCESS     read-write
   STATUS     mandatory
   DESCRIPTION
     "This attribute specifies the committed information rate (CIR) in bits 
      per second (bit/s). When rateEnforcement is set to on, cir is the rate 
      at which the network agrees to transfer information under normal 
      conditions. This rate is measured over a measurement interval (t) 
      that is determined internally based on CIR and the committed burst 
      size (Bc). An exception to this occurs when CIR is provisioned to 
      be zero, in which case the measurement interval (t) must be 
      provisioned explicitly.
      
      This attribute is ignored when rateEnforcement is off. If 
      rateEnforcement is on and this attribute is 0, Bc must also be 0."
   DEFVAL     { 64000 }
::= { frUniDlciSpParmsEntry 3 }

frUniDlciSpCommittedBurstSize OBJECT-TYPE
   SYNTAX     Gauge32 (0..50000000)
   ACCESS     read-write
   STATUS     mandatory
   DESCRIPTION
     "This attribute specifies the committed burst size (Bc) in bits. bc is 
      the amount of data that a network agrees to transfer under normal 
      conditions over a measurement interval (t). Data marked DE=1 is 
      not accounted for in Bc.
      
      This attribute is ignored when rateEnforcement is off. If 
      rateEnforcement is on and this attribute is 0, cir must also be 0."
   DEFVAL     { 64000 }
::= { frUniDlciSpParmsEntry 4 }

frUniDlciSpExcessBurstSize OBJECT-TYPE
   SYNTAX     Gauge32 (0..50000000)
   ACCESS     read-write
   STATUS     mandatory
   DESCRIPTION
     "This attribute specifies the excess burst size (Be) in bits. Be is the 
      amount of uncommitted data that the network will attempt to deliver 
      over measurement interval T. Data marked DE=1 by the user or by 
      the network is accounted for here.
      
      CIR, Bc, and Be cannot all be zero when rateEnforcement is on."
   DEFVAL     { 0 }
::= { frUniDlciSpParmsEntry 5 }

frUniDlciSpMeasurementInterval OBJECT-TYPE
   SYNTAX     Unsigned32 (0..25500)
   ACCESS     read-write
   STATUS     mandatory
   DESCRIPTION
     "When cir and bc are zero and rateEnforcement is on, this attribute 
      must be provisioned to specify the time interval (in milliseconds) 
      over which rates and burst sizes are measured.
      
      When cir and bc are non-zero, the time interval is internally 
      calculated and is not shown. In that situation, this field is ignored, 
      and is not representative of the time interval.
      
      This attribute is ignored when rateEnforcement is off, or when cir 
      and bc are non-zero. If rateEnforcement is on and both cir and bc 
      are zero, this field must be non-zero."
   DEFVAL     { 0 }
::= { frUniDlciSpParmsEntry 6 }

frUniDlciSpRateAdaptation OBJECT-TYPE
   SYNTAX     INTEGER  {
                 off(0),
                 on(1),
                 eirOnly(2),
                 cirProportionate(3) }
   ACCESS     read-write
   STATUS     mandatory
   DESCRIPTION
     "This attribute specifies whether rate adaptation is in effect for this 
      user Data Link Connection on this Frame Relay interface. Rate 
      adaptation is a feature that, in periods of congestion, adapts the rate 
      at which the user is allowed to send data into the network to that 
      which the network is able to handle at that time. This pro-active 
      measure of handling congestion optimizes network resources by 
      causing the ingress to discard frames that would otherwise be 
      discarded in the network.
      
      If this attribute is set to on, then, at the onset of congestion, the 
      excess information rate (EIR) is reduced to a very low rate. If 
      congestion persists, then the allowed CIR is reduced geometrically 
      by 25% of the current value at that time. The minimum to which 
      CIR can be reduced is 1/16th (6.25%) of the provisioned value. As 
      congestion alleviates, CIR is increased linearly by 6.25% of the 
      provisioned value specified in committedInformationRate.
      
      If set to eirOnly, then rate adaptation will only apply to the excess 
      information rate (EIR). At the onset of congestion, the allowed EIR 
      is reduced by 25% of its provisioned value. If congestion persists, 
      EIR is reduced geometrically by 25% of the current value at that 
      time. As congestion alleviates, EIR is gradually increased linearly 
      by 6.25% of the provisioned EIR.
      
      If set to cirProportionate, then rate adaptation will also only apply 
      to the excess information rate (EIR). At the onset of congestion the 
      initial allowed EIR is set to a multiple of the provisioned CIR. If 
      congestion persists, the allowed EIR is reduced geometrically by 
      25% of the current value at that time. As congestion alleviates, EIR 
      is gradually increased linearly by 6.25% of the provisioned EIR. 
      Note that the allowed EIR may be set higher than the provisioned 
      EIR, since it is calculated initially using another parameter, the 
      provisioned CIR. If the allowed EIR at the moment is higher than 
      the provisioned EIR, then the provisioned EIR is used instead.
      
      This attribute can only be set to on eirOnly or cirProportionate if 
      rateEnforcement is turned on."
   DEFVAL     { off }
::= { frUniDlciSpParmsEntry 7 }

frUniDlciSpAccounting OBJECT-TYPE
   SYNTAX     INTEGER  {
                 off(0),
                 on(1) }
   ACCESS     read-write
   STATUS     mandatory
   DESCRIPTION
     "This attribute specifies whether accounting data collection and 
      record generation is turned on at this DLCI. For accounting data 
      collection and record generation to be turned on, the accountingOn 
      bit and at least one of the accountCollection bits in the 
      DataNetworkAddress component must be set to on."
   DEFVAL     { on }
::= { frUniDlciSpParmsEntry 8 }

frUniDlciSpRaSensitivity OBJECT-TYPE
   SYNTAX     Unsigned32 (1..20)
   ACCESS     read-write
   STATUS     mandatory
   DESCRIPTION
     "This attribute specifies the sensitivity of the rate adaptation system. 
      A higher number indicates a higher sensitivity and therefore a 
      quicker reaction time to network conditions. A quicker reaction 
      time allows the network to discard frames at the access and protect 
      network resources, but can lead to false alarms and a greater 
      fluctuation of the allowed rate. A higher setting therefore tends to 
      favour the protection of the network over the allowed throughput of 
      the user.
      
      A lower number indicates a lower sensitivity and therefore a slower 
      reaction to network conditions. A slower reaction time results in a 
      greater amount of user traffic allowed into the network, but can lead 
      to a waste of network bandwidth since the traffic may be discarded 
      at the congested resource. A lower setting therefore tends to favour 
      the allowed throughput of the user over the protection of the 
      network.
      
      This attribute is applicable for adapting EIR when rateAdaptation is 
      eirOnly or cirProportionate, or CIR when rateAdaptation is on.
      
      This attribute is ignored if rateAdaptation is turned off."
   DEFVAL     { 7 }
::= { frUniDlciSpParmsEntry 9 }

frUniDlciSpUpdateBCI OBJECT-TYPE
   SYNTAX     INTEGER  {
                 off(0),
                 on(1) }
   ACCESS     read-write
   STATUS     mandatory
   DESCRIPTION
     "This attribute specifies whether internal Backward Congestion 
      Indication (BCI) bits will report congestion external to the Passport 
      network, as communicated through incoming BECN bits.
      
      If updateBCI is set to on, then BCI bits for incoming frames will be 
      set if the BECN on the frame is set. If updatBCI is set to off, then 
      incoming BECN bits will have no effect.
      
      Setting updateBCI on for a DLCI means that the remote end of the 
      DLCI, which is specified by the remotedna and remotedlci attributes 
      of the dc component of the dlci, may perform Rate Adaptation 
      using the flow of incoming BECN bits, in addition to internal 
      Passport congestion management systems.
      
      If the rateAdaptation attribute of the remote dlci is provisioned as 
      eirOnly, cirProportionate, or on, then congestion from another 
      network connected to a Passport network may trigger dynamic 
      congestion management. If the rateAdaptation attribute of the 
      remote dlci is provisioned to off, then the setting of updateBCI 
      attribute here will have no effect.."
   DEFVAL     { off }
::= { frUniDlciSpParmsEntry 10 }


-- FrUni/n Dlci/n LoopBack	
-- FrNni/n Dlci/n LoopBack		
-- This component is the data loopback tool for the parent DLCI.

frUniDlciLb OBJECT IDENTIFIER ::= { frUniDlci 5 }



frUniDlciLbRowStatusTable OBJECT-TYPE
   SYNTAX     SEQUENCE OF FrUniDlciLbRowStatusEntry
   ACCESS     not-accessible
   STATUS     mandatory
   DESCRIPTION
     "This entry controls the addition and deletion of 
      frUniDlciLb components."
::= { frUniDlciLb 1 }

frUniDlciLbRowStatusEntry OBJECT-TYPE
   SYNTAX     FrUniDlciLbRowStatusEntry
   ACCESS     not-accessible
   STATUS     mandatory
   DESCRIPTION
     "A single entry in the table represents a single 
      frUniDlciLb component."
   INDEX {
      frUniIndex,
      frUniDlciIndex,
      frUniDlciLbIndex }
::= { frUniDlciLbRowStatusTable 1 }

FrUniDlciLbRowStatusEntry ::= SEQUENCE {
   frUniDlciLbRowStatus
      RowStatus,
   frUniDlciLbComponentName
      DisplayString,
   frUniDlciLbStorageType
      StorageType,
   frUniDlciLbIndex
      NonReplicated }

frUniDlciLbRowStatus OBJECT-TYPE
   SYNTAX     RowStatus 
   ACCESS     read-only
   STATUS     mandatory
   DESCRIPTION
     "This variable is used as the basis for SNMP naming of
      frUniDlciLb components.
      These components cannot be added nor deleted."
::= { frUniDlciLbRowStatusEntry 1 }

frUniDlciLbComponentName OBJECT-TYPE
   SYNTAX     DisplayString 
   ACCESS     read-only
   STATUS     mandatory
   DESCRIPTION
     "This variable provides the component's string name for
      use with the ASCII Console Interface"
::= { frUniDlciLbRowStatusEntry 2 }

frUniDlciLbStorageType OBJECT-TYPE
   SYNTAX     StorageType 
   ACCESS     read-only
   STATUS     mandatory
   DESCRIPTION
     "This variable represents the storage type value for the
      frUniDlciLb tables."
::= { frUniDlciLbRowStatusEntry 4 }

frUniDlciLbIndex OBJECT-TYPE
   SYNTAX     NonReplicated 
   ACCESS     not-accessible
   STATUS     mandatory
   DESCRIPTION
     "This variable represents the index for the frUniDlciLb tables."
::= { frUniDlciLbRowStatusEntry 10 }

frUniDlciLbStatsTable OBJECT-TYPE
   SYNTAX     SEQUENCE OF FrUniDlciLbStatsEntry
   ACCESS     not-accessible
   STATUS     mandatory
   DESCRIPTION
     "This group contains all the statistics for the data loopback tool."
::= { frUniDlciLb 10 }

frUniDlciLbStatsEntry OBJECT-TYPE
   SYNTAX     FrUniDlciLbStatsEntry
   ACCESS     not-accessible
   STATUS     mandatory
   DESCRIPTION
     "An entry in the frUniDlciLbStatsTable."
   INDEX {
      frUniIndex,
      frUniDlciIndex,
      frUniDlciLbIndex }
::= { frUniDlciLbStatsTable 1 }

FrUniDlciLbStatsEntry ::= SEQUENCE {
   frUniDlciLbLocalTotalFrm
      Unsigned32,
   frUniDlciLbLocalTotalBytes
      Unsigned32,
   frUniDlciLbLocalFecnFrm
      Unsigned32,
   frUniDlciLbLocalBecnFrm
      Unsigned32,
   frUniDlciLbLocalDeFrm
      Unsigned32,
   frUniDlciLbLocalDeBytes
      Unsigned32,
   frUniDlciLbRemoteTotalFrm
      Unsigned32,
   frUniDlciLbRemoteTotalBytes
      Unsigned32,
   frUniDlciLbRemoteFecnFrm
      Unsigned32,
   frUniDlciLbRemoteBecnFrm
      Unsigned32,
   frUniDlciLbRemoteDeFrm
      Unsigned32,
   frUniDlciLbRemoteDeBytes
      Unsigned32 }

frUniDlciLbLocalTotalFrm OBJECT-TYPE
   SYNTAX     Unsigned32 (0..4294967295)
   ACCESS     read-only
   STATUS     mandatory
   DESCRIPTION
     "This attribute records the number of frames looped back to the link 
      since loopback was last started."
   DEFVAL     { 0 }
::= { frUniDlciLbStatsEntry 1 }

frUniDlciLbLocalTotalBytes OBJECT-TYPE
   SYNTAX     Unsigned32 (0..4294967295)
   ACCESS     read-only
   STATUS     mandatory
   DESCRIPTION
     "This attribute records the number of bytes looped back to the link 
      since loopback mode was started."
   DEFVAL     { 0 }
::= { frUniDlciLbStatsEntry 2 }

frUniDlciLbLocalFecnFrm OBJECT-TYPE
   SYNTAX     Unsigned32 (0..4294967295)
   ACCESS     read-only
   STATUS     mandatory
   DESCRIPTION
     "This attribute records the number of frames with the Forward 
      Explicit Congestion Notification (FECN) bit set, looped back to the 
      link since the loopback mode was started."
   DEFVAL     { 0 }
::= { frUniDlciLbStatsEntry 3 }

frUniDlciLbLocalBecnFrm OBJECT-TYPE
   SYNTAX     Unsigned32 (0..4294967295)
   ACCESS     read-only
   STATUS     mandatory
   DESCRIPTION
     "This attribute records the number of frames with the Backward 
      Explicit Congestion Notification (BECN) bit set, looped back to the 
      link since the loopback mode was started."
   DEFVAL     { 0 }
::= { frUniDlciLbStatsEntry 4 }

frUniDlciLbLocalDeFrm OBJECT-TYPE
   SYNTAX     Unsigned32 (0..4294967295)
   ACCESS     read-only
   STATUS     mandatory
   DESCRIPTION
     "This attribute records the number of frames with the Discard 
      Eligibility (DE) bit set, looped back to the link since the loopback 
      mode was started."
   DEFVAL     { 0 }
::= { frUniDlciLbStatsEntry 5 }

frUniDlciLbLocalDeBytes OBJECT-TYPE
   SYNTAX     Unsigned32 (0..4294967295)
   ACCESS     read-only
   STATUS     mandatory
   DESCRIPTION
     "This attribute records the number of bytes in frames with the 
      Discard Eligibility (DE) bit set, looped back to the link since the 
      loopback mode was started."
   DEFVAL     { 0 }
::= { frUniDlciLbStatsEntry 6 }

frUniDlciLbRemoteTotalFrm OBJECT-TYPE
   SYNTAX     Unsigned32 (0..4294967295)
   ACCESS     read-only
   STATUS     mandatory
   DESCRIPTION
     "This attribute records the number of frames looped back to the 
      subnet since loopback was last started."
   DEFVAL     { 0 }
::= { frUniDlciLbStatsEntry 7 }

frUniDlciLbRemoteTotalBytes OBJECT-TYPE
   SYNTAX     Unsigned32 (0..4294967295)
   ACCESS     read-only
   STATUS     mandatory
   DESCRIPTION
     "This attribute records the number of bytes looped back to the subnet 
      since loopback was last started."
   DEFVAL     { 0 }
::= { frUniDlciLbStatsEntry 8 }

frUniDlciLbRemoteFecnFrm OBJECT-TYPE
   SYNTAX     Unsigned32 (0..4294967295)
   ACCESS     read-only
   STATUS     mandatory
   DESCRIPTION
     "This attribute records the number of frames with the Forward 
      Explicit Congestion Notification (FECN) bit set, looped back to the 
      subnet since the loopback mode was started."
   DEFVAL     { 0 }
::= { frUniDlciLbStatsEntry 9 }

frUniDlciLbRemoteBecnFrm OBJECT-TYPE
   SYNTAX     Unsigned32 (0..4294967295)
   ACCESS     read-only
   STATUS     mandatory
   DESCRIPTION
     "This attribute records the number of frames with the Backward 
      Explicit Congestion Notification (BECN) bit set, looped back to the 
      subnet since the loopback mode was started."
   DEFVAL     { 0 }
::= { frUniDlciLbStatsEntry 10 }

frUniDlciLbRemoteDeFrm OBJECT-TYPE
   SYNTAX     Unsigned32 (0..4294967295)
   ACCESS     read-only
   STATUS     mandatory
   DESCRIPTION
     "This attribute records the number of frames with the Discard 
      Eligibility (DE) bit set, looped back to the subnet since the 
      loopback mode was started."
   DEFVAL     { 0 }
::= { frUniDlciLbStatsEntry 13 }

frUniDlciLbRemoteDeBytes OBJECT-TYPE
   SYNTAX     Unsigned32 (0..4294967295)
   ACCESS     read-only
   STATUS     mandatory
   DESCRIPTION
     "This attribute records the number of bytes in frames with the 
      Discard Eligibility (DE) bit set, looped back to the subnet since the 
      loopback mode was started."
   DEFVAL     { 0 }
::= { frUniDlciLbStatsEntry 14 }


-- 
-- FrUni/n Signaling
-- This component defines the Q.933 and Q.922 (LAPF) parameters 
-- for Frame Relay switched virtual circuits at the User-Network 
-- interface.

frUniSig OBJECT IDENTIFIER ::= { frUni 6 }



frUniSigRowStatusTable OBJECT-TYPE
   SYNTAX     SEQUENCE OF FrUniSigRowStatusEntry
   ACCESS     not-accessible
   STATUS     mandatory
   DESCRIPTION
     "This entry controls the addition and deletion of 
      frUniSig components."
::= { frUniSig 1 }

frUniSigRowStatusEntry OBJECT-TYPE
   SYNTAX     FrUniSigRowStatusEntry
   ACCESS     not-accessible
   STATUS     mandatory
   DESCRIPTION
     "A single entry in the table represents a single 
      frUniSig component."
   INDEX {
      frUniIndex,
      frUniSigIndex }
::= { frUniSigRowStatusTable 1 }

FrUniSigRowStatusEntry ::= SEQUENCE {
   frUniSigRowStatus
      RowStatus,
   frUniSigComponentName
      DisplayString,
   frUniSigStorageType
      StorageType,
   frUniSigIndex
      NonReplicated }

frUniSigRowStatus OBJECT-TYPE
   SYNTAX     RowStatus 
   ACCESS     read-write
   STATUS     mandatory
   DESCRIPTION
     "This variable is used as the basis for SNMP naming of
      frUniSig components.
      These components can be added and deleted."
::= { frUniSigRowStatusEntry 1 }

frUniSigComponentName OBJECT-TYPE
   SYNTAX     DisplayString 
   ACCESS     read-only
   STATUS     mandatory
   DESCRIPTION
     "This variable provides the component's string name for
      use with the ASCII Console Interface"
::= { frUniSigRowStatusEntry 2 }

frUniSigStorageType OBJECT-TYPE
   SYNTAX     StorageType 
   ACCESS     read-only
   STATUS     mandatory
   DESCRIPTION
     "This variable represents the storage type value for the
      frUniSig tables."
::= { frUniSigRowStatusEntry 4 }

frUniSigIndex OBJECT-TYPE
   SYNTAX     NonReplicated 
   ACCESS     not-accessible
   STATUS     mandatory
   DESCRIPTION
     "This variable represents the index for the frUniSig tables."
::= { frUniSigRowStatusEntry 10 }

frUniSigRangeTable OBJECT-TYPE
   SYNTAX     SEQUENCE OF FrUniSigRangeEntry
   ACCESS     not-accessible
   STATUS     mandatory
   DESCRIPTION
     "This group contains the provisionable attribute to define the range 
      of DLCIs for PVCs and SVCs. The purpose of this range is to 
      prevent DLCI collisions between the provisioned PVCs and the 
      dynamic SVCs."
::= { frUniSig 11 }

frUniSigRangeEntry OBJECT-TYPE
   SYNTAX     FrUniSigRangeEntry
   ACCESS     not-accessible
   STATUS     mandatory
   DESCRIPTION
     "An entry in the frUniSigRangeTable."
   INDEX {
      frUniIndex,
      frUniSigIndex }
::= { frUniSigRangeTable 1 }

FrUniSigRangeEntry ::= SEQUENCE {
   frUniSigHighestPvcDlci
      Unsigned32 }

frUniSigHighestPvcDlci OBJECT-TYPE
   SYNTAX     Unsigned32 (0 | 16..1007)
   ACCESS     read-write
   STATUS     mandatory
   DESCRIPTION
     "This attribute specifies the highest DLCI value that can be 
      provisioned for a PVC. If the operator defines a PVC DLCI number 
      higher than this value, the provisioning will be rejected. The value 0 
      is used to indicate that no PVCs are allowed on the interface."
   DEFVAL     { 500 }
::= { frUniSigRangeEntry 1 }

frUniSigServParmsTable OBJECT-TYPE
   SYNTAX     SEQUENCE OF FrUniSigServParmsEntry
   ACCESS     not-accessible
   STATUS     mandatory
   DESCRIPTION
     "This group contains the provisionable Q.933 service parameters."
::= { frUniSig 12 }

frUniSigServParmsEntry OBJECT-TYPE
   SYNTAX     FrUniSigServParmsEntry
   ACCESS     not-accessible
   STATUS     mandatory
   DESCRIPTION
     "An entry in the frUniSigServParmsTable."
   INDEX {
      frUniIndex,
      frUniSigIndex }
::= { frUniSigServParmsTable 1 }

FrUniSigServParmsEntry ::= SEQUENCE {
   frUniSigMaximumAggregateSvcCir
      Unsigned32,
   frUniSigMaximumAggregateSvcEir
      Unsigned32,
   frUniSigMaximumFrameSize
      Unsigned32,
   frUniSigDefaultMaximumFrameSize
      Unsigned32,
   frUniSigDefaultCommittedInformationRate
      Unsigned32,
   frUniSigDefaultCommittedBurstSize
      Unsigned32,
   frUniSigDefaultExcessBurstSize
      Unsigned32,
   frUniSigUnlimitedAggregateEir
      INTEGER,
   frUniSigRateEnforcement
      INTEGER,
   frUniSigRateAdaptation
      INTEGER,
   frUniSigMaximumAggregateSvcCirNormalQ
      Unsigned32,
   frUniSigMaximumAggregateSvcCirHighQ
      Unsigned32,
   frUniSigMaximumAggregateSvcCirInterruptQ
      Unsigned32,
   frUniSigMaximumAggregateSvcEirNormalQ
      Unsigned32,
   frUniSigMaximumAggregateSvcEirHighQ
      Unsigned32,
   frUniSigMaximumAggregateSvcEirInterruptQ
      Unsigned32,
   frUniSigX213IeHandling
      INTEGER,
   frUniSigRaSensitivity
      Unsigned32,
   frUniSigUpdateBCI
      INTEGER,
   frUniSigDefaultLocCheck
      INTEGER }

frUniSigMaximumAggregateSvcCir OBJECT-TYPE
   SYNTAX     Unsigned32 (0..10000)
   ACCESS     read-write
   STATUS     obsolete
   DESCRIPTION
     "This attribute specifies the maximum aggregate user to network 
      direction CIR allowed for SVCs on the interface. It is provisioned 
      as a percentage of the access link speed. This attribute is used to 
      limit the amount of guaranteed SVC throughput allowed into the 
      network at this interface.
      This attribute is obsoleted, during the migration, the value of this 
      attribute will be transfered to maximumAggregateSvcCirNormalQ 
      or maximumAggregateSvcCirHighQ depending on the value of the 
      attribute outDefaultPathSensitivity under DNA component."
   DEFVAL     { 1000 }
::= { frUniSigServParmsEntry 1 }

frUniSigMaximumAggregateSvcEir OBJECT-TYPE
   SYNTAX     Unsigned32 (0..4294967295)
   ACCESS     read-write
   STATUS     obsolete
   DESCRIPTION
     "This attribute specifies the maximum aggregate user to network 
      direction EIR allowed for SVCs on the interface. It is provisioned as 
      a percentage of the access link speed. This attribute is ignored if 
      unlimitedAggregateEir, another attribute under the same group, is 
      set to yes. This attribute is used to limit the amount of excess SVC 
      throughput allowed into the network at this interface.
      This attribute is obsoleted, during the migration, the value of this 
      attribute will be transfered to maximumAggregateSvcEirNormalQ 
      or maximumAggregateSvcEirHighQ depending on the value of the 
      attribute outDefaultPathSensitivity under DNA component."
   DEFVAL     { 10000 }
::= { frUniSigServParmsEntry 2 }

frUniSigMaximumFrameSize OBJECT-TYPE
   SYNTAX     Unsigned32 (1..8187)
   ACCESS     read-write
   STATUS     mandatory
   DESCRIPTION
     "This attribute specifies the maximum number of octets that may be 
      included in the information field of the user DLCI assigned for this 
      call. Its value must not be smaller than the value of 
      defaultMaximumFrameSize."
   DEFVAL     { 4096 }
::= { frUniSigServParmsEntry 3 }

frUniSigDefaultMaximumFrameSize OBJECT-TYPE
   SYNTAX     Unsigned32 (1..8187)
   ACCESS     read-write
   STATUS     mandatory
   DESCRIPTION
     "This attribute specifies the default maximum number of octets that 
      may be included in the information field of the user DLCI assigned 
      for this call. This value is used during call parameter negotiation for 
      SVC calls on this interface when the maximum frame size is not 
      specified in the user's SETUP message. The value of this attribute 
      must not exceed the value of the maximumFrameSize attribute."
   DEFVAL     { 2100 }
::= { frUniSigServParmsEntry 4 }

frUniSigDefaultCommittedInformationRate OBJECT-TYPE
   SYNTAX     Unsigned32 (0..52000000)
   ACCESS     read-write
   STATUS     mandatory
   DESCRIPTION
     "This attribute specifies the default user to network direction CIR. 
      This value is used during call parameter negotiation for SVC calls 
      on this interface when the CIR is not specified in the user's SETUP 
      message."
   DEFVAL     { 64000 }
::= { frUniSigServParmsEntry 5 }

frUniSigDefaultCommittedBurstSize OBJECT-TYPE
   SYNTAX     Unsigned32 (0..52000000)
   ACCESS     read-write
   STATUS     mandatory
   DESCRIPTION
     "This attribute specifies the default user to network direction Bc. 
      This value is used during call parameter negotiation for SVC calls 
      on this interface when the Bc is not specified in the user's SETUP 
      message."
   DEFVAL     { 64000 }
::= { frUniSigServParmsEntry 6 }

frUniSigDefaultExcessBurstSize OBJECT-TYPE
   SYNTAX     Unsigned32 (0..52000000)
   ACCESS     read-write
   STATUS     mandatory
   DESCRIPTION
     "This attribute specifies the default user to network direction Be. 
      This value is used during call parameter negotiation for SVC calls 
      on this interface when the Be is not specified in the user's SETUP 
      message."
   DEFVAL     { 0 }
::= { frUniSigServParmsEntry 7 }

frUniSigUnlimitedAggregateEir OBJECT-TYPE
   SYNTAX     INTEGER  {
                 no(0),
                 yes(1) }
   ACCESS     read-write
   STATUS     mandatory
   DESCRIPTION
     "This attribute specifies whether the network will enforce aggregate 
      EIR during SVC call establishment. The network keeps track of the 
      sum of user to network EIRs for all the SVC DLCIs at this 
      interface. 
      
      If this attribute is set to no, then the requested EIR for each new 
      SVC call will be adjusted if the resulting aggregate EIR exceeds the 
      value contained in one of the following attributes (depending on the 
      requested Transfer Priority): maximumAggregateSvcEirNormalQ, 
      maximumAggregateSvcEirHighQ or 
      maximumAggregateSvcEirInterruptQ. This may lead to a rejection 
      of the call setup.
      
      If this value is set to yes, then no checks will take place."
   DEFVAL     { yes }
::= { frUniSigServParmsEntry 8 }

frUniSigRateEnforcement OBJECT-TYPE
   SYNTAX     INTEGER  {
                 off(0),
                 on(1) }
   ACCESS     read-write
   STATUS     mandatory
   DESCRIPTION
     "This attribute specifies whether rate enforcement is in effect for 
      SVCs on this interface."
   DEFVAL     { on }
::= { frUniSigServParmsEntry 9 }

frUniSigRateAdaptation OBJECT-TYPE
   SYNTAX     INTEGER  {
                 off(0),
                 on(1),
                 eirOnly(2),
                 cirProportionate(3) }
   ACCESS     read-write
   STATUS     mandatory
   DESCRIPTION
     "This attribute specifies whether closed-loop rate adaptation is in 
      effect for SVCs on this interface. Rate adaptation is a feature that, in 
      periods of congestion, adapts the rate at which the user is allowed to 
      send data into the network to that which the network is able to 
      handle at that time. This pro-active measure of handling congestion 
      optimizes network resources by causing the ingress to discard 
      frames that would otherwise be discarded in the network.
      
      If this attribute is set to on, then, at the onset of congestion, the 
      excess information rate (EIR) is reduced to a very low rate. If 
      congestion persists, then the allowed CIR is reduced geometrically 
      by 25% of the current value at that time. The minimum to which 
      CIR can be reduced is 1/16th (6.25%) of the provisioned value. As 
      congestion alleviates, CIR is increased linearly by 6.25% of the 
      provisioned value specified in committedInformationRate.
      
      If set to eirOnly, then rate adaptation will only apply to the excess 
      information rate (EIR). At the onset of congestion, the allowed EIR 
      is reduced by 25% of its provisioned value. If congestion persists, 
      EIR is reduced geometrically by 25% of the current value at that 
      time. As congestion alleviates, EIR is gradually increased linearly 
      by 6.25% of the provisioned EIR.
      
      If set to cirProportionate, then rate adaptation will also only apply 
      to the excess information rate (EIR). At the onset of congestion the 
      initial allowed EIR is set to a multiple of the provisioned CIR. If 
      congestion persists, the allowed EIR is reduced geometrically by 
      25% of the current value at that time. As congestion alleviates, EIR 
      is gradually increased linearly by 6.25% of the provisioned EIR. 
      Note that the allowed EIR may be set higher than the provisioned 
      EIR, since it is calculated initially using another parameter, the 
      provisioned CIR. If the allowed EIR at the moment is higher than 
      the provisioned EIR, then the provisioned EIR is used instead.
      
      This attribute can only be turned on or eirOnly if rateEnforcement 
      is turned on."
   DEFVAL     { off }
::= { frUniSigServParmsEntry 10 }

frUniSigMaximumAggregateSvcCirNormalQ OBJECT-TYPE
   SYNTAX     Unsigned32 (0..10000)
   ACCESS     read-write
   STATUS     mandatory
   DESCRIPTION
     "This attribute specifies the maximum aggregate user to network 
      direction CIR allowed for SVCs on the interface. It is provisioned 
      as a percentage of the access link speed. This attribute is used to 
      limit, at this interface, the amount of guaranteed SVC throughput 
      allowed into the network through the normal priority queue."
   DEFVAL     { 1000 }
::= { frUniSigServParmsEntry 11 }

frUniSigMaximumAggregateSvcCirHighQ OBJECT-TYPE
   SYNTAX     Unsigned32 (0..10000)
   ACCESS     read-write
   STATUS     mandatory
   DESCRIPTION
     "This attribute specifies the maximum aggregate user to network 
      direction CIR allowed for SVCs on the interface. It is provisioned 
      as a percentage of the link access speed. This attribute is used to 
      limit, at this interface, the amount of guaranteed SVC throughput 
      allowed into the network through the high priority queue."
   DEFVAL     { 1000 }
::= { frUniSigServParmsEntry 12 }

frUniSigMaximumAggregateSvcCirInterruptQ OBJECT-TYPE
   SYNTAX     Unsigned32 (0..10000)
   ACCESS     read-write
   STATUS     mandatory
   DESCRIPTION
     "This attribute specifies the maximum aggregate user to network 
      direction CIR allowed for SVCs on the interface. It is provisioned 
      as a percentage of the link access speed. This attribute is used to 
      limit, at this interface, the amount of guaranteed SVC throughput 
      allowed into the network through the interrupting queue."
   DEFVAL     { 1000 }
::= { frUniSigServParmsEntry 13 }

frUniSigMaximumAggregateSvcEirNormalQ OBJECT-TYPE
   SYNTAX     Unsigned32 (0..4294967295)
   ACCESS     read-write
   STATUS     mandatory
   DESCRIPTION
     "This attribute specifies the maximum aggregate user to network 
      direction EIR allowed for SVCs on the interface. It is provisioned as 
      a percentage of the access link speed. This attribute is ignored if 
      unlimitedAggregateEir, another attribute under the same group, is 
      set to yes. This attribute is used to limit, at this interface, the amount 
      of excess SVC throughput allowed into the network through the 
      normal priority queue."
   DEFVAL     { 10000 }
::= { frUniSigServParmsEntry 14 }

frUniSigMaximumAggregateSvcEirHighQ OBJECT-TYPE
   SYNTAX     Unsigned32 (0..4294967295)
   ACCESS     read-write
   STATUS     mandatory
   DESCRIPTION
     "This attribute specifies the maximum aggregate user to network 
      direction EIR allowed for SVCs on the interface. It is provisioned as 
      a percentage of the access link speed. This attribute is ignored if 
      unlimitedAggregateEir, another attribute under the same group, is 
      set to yes. This attribute is used to limit, at this interface, the amount 
      of excess SVC throughput allowed into the network through the 
      high priority queue."
   DEFVAL     { 10000 }
::= { frUniSigServParmsEntry 15 }

frUniSigMaximumAggregateSvcEirInterruptQ OBJECT-TYPE
   SYNTAX     Unsigned32 (0..4294967295)
   ACCESS     read-write
   STATUS     mandatory
   DESCRIPTION
     "This attribute specifies the maximum aggregate user to network 
      direction EIR allowed for SVCs on the interface. It is provisioned as 
      a percentage of the access link speed. This attribute is ignored if 
      unlimitedAggregateEir, another attribute under the same group, is 
      set to yes. This attribute is used to limit, at this interface, the amount 
      of excess SVC throughput allowed into the network through the 
      interrupting queue."
   DEFVAL     { 10000 }
::= { frUniSigServParmsEntry 16 }

frUniSigX213IeHandling OBJECT-TYPE
   SYNTAX     INTEGER  {
                 notSupported(0),
                 proprietary(1) }
   ACCESS     read-write
   STATUS     mandatory
   DESCRIPTION
     "The x213IeHandling attribute specifies how Frame Relay handles 
      the X.213 Priority IE when it is in the Q.933 setup message. 
      
      When the attribute is set to notSupported, the X.213 Priority IE will 
      not be recognized in the setup message. A Q.933 status message 
      will be sent to the calling DTE, with the indication that an 
      unrecognized IE was encountered. The call setup then proceeds as 
      normal, and the X.213 Priority IE does not appear in the setup 
      message at the called end.
      
      When the attribute is set to proprietary, and the X.213 Priority IE is 
      present in the Q.933 setup message, it will be recognized. If there is 
      no Frame Transfer Priority IE in the setup message, the first data 
      byte of the X.213 Priority IE is used to select the transfer and 
      discard priority values for the connection and the X.213 Priority IE 
      is signaled to the called end in the setup message. If the Frame 
      Transfer Priority IE is present in the Q.933 setup message, its value 
      is used to select the transfer priority, the discard priority is taken 
      from the FRUNI Dna component, and the X.213 Priority IE is 
      ignored.
      
      Refer to the related Application Note for further details before 
      setting the attribute value to proprietary."
   DEFVAL     { notSupported }
::= { frUniSigServParmsEntry 17 }

frUniSigRaSensitivity OBJECT-TYPE
   SYNTAX     Unsigned32 (1..20)
   ACCESS     read-write
   STATUS     mandatory
   DESCRIPTION
     "This attribute specifies the sensitivity of the rate adaptation system 
      for Svc's on this interface. Since this attribute is in the Sig 
      Component of an FR Uni component, all SVC DLCI's created for 
      this FR Uni Service will take the raSensitivity attribute provisioned 
      here.
      
      A higher number indicates a higher sensitivity and therefore a 
      quicker reaction time to network conditions. A quicker reaction 
      time allows the network to discard frames at the access and protect 
      network resources, but can lead to false alarms and a greater 
      fluctuation of the allowed rate. A higher setting therefore tends to 
      favour the protection of the network over the allowed throughput of 
      the user.
      
      A lower number indicates a lower sensitivity and therefore a slower 
      reaction to network conditions. A slower reaction time results in a 
      greater amount of user traffic allowed into the network, but can lead 
      to a waste of network bandwidth since the traffic may be discarded 
      at the congested resource. A lower setting therefore tends to favour 
      the allowed throughput of the user over the protection of the 
      network.
      
      This attribute is applicable for adapting EIR when rateAdaptation is 
      eirOnly or cirProportionate, or CIR when rateAdaptation is on. 
      
      This attribute is ignored if rateAdaptation is turned off."
   DEFVAL     { 7 }
::= { frUniSigServParmsEntry 18 }

frUniSigUpdateBCI OBJECT-TYPE
   SYNTAX     INTEGER  {
                 off(0),
                 on(1) }
   ACCESS     read-write
   STATUS     mandatory
   DESCRIPTION
     "This attribute specifies whether internal Backward Congestion 
      Indication (BCI) bits will report congestion external to the Passport 
      network, as communicated through incoming BECN bits.
      
      If updateBCI is set to on, then BCI bits for incoming frames will be 
      set if the BECN on the frame is set. If updatBCI is set to off, then 
      incoming BECN bits will have no effect.
      
      Setting updateBCI on for a DLCI means that the remote end of the 
      DLCI, which is specified by the remotedna and remotedlci attributes 
      of the dc component of the dlci, may perform Rate Adaptation 
      using the flow of incoming BECN bits, in addition to internal 
      Passport congestion management systems.
      
      If the rateAdaptation attribute of the remote dlci is provisioned as 
      eirOnly, cirProportionate, or on, then congestion from another 
      network connected to a Passport network may trigger dynamic 
      congestion management. If the rateAdaptation attribute of the 
      remote dlci is provisioned to off, then the setting of updateBCI 
      attribute here will have no effect.."
   DEFVAL     { off }
::= { frUniSigServParmsEntry 19 }

frUniSigDefaultLocCheck OBJECT-TYPE
   SYNTAX     INTEGER  {
                 off(0),
                 on(1) }
   ACCESS     read-write
   STATUS     mandatory
   DESCRIPTION
     "This attribute specifies whether Passport needs to check the location 
      of Cause IE in a Release or a Disc message issued by local DTE. If 
      this bit is set to on, then Passport will check the location of Cause 
      IE issued by the local DTE and overwrite it by 'user'. If it is set to 
      off, then Passport will not check the location in Cause IE."
   DEFVAL     { on }
::= { frUniSigServParmsEntry 20 }

frUniSigSysParmsTable OBJECT-TYPE
   SYNTAX     SEQUENCE OF FrUniSigSysParmsEntry
   ACCESS     not-accessible
   STATUS     mandatory
   DESCRIPTION
     "This group contains the provisionable Q.933 system parameters."
::= { frUniSig 13 }

frUniSigSysParmsEntry OBJECT-TYPE
   SYNTAX     FrUniSigSysParmsEntry
   ACCESS     not-accessible
   STATUS     mandatory
   DESCRIPTION
     "An entry in the frUniSigSysParmsTable."
   INDEX {
      frUniIndex,
      frUniSigIndex }
::= { frUniSigSysParmsTable 1 }

FrUniSigSysParmsEntry ::= SEQUENCE {
   frUniSigCallSetupTimer
      Unsigned32,
   frUniSigDisconnectTimer
      Unsigned32,
   frUniSigReleaseTimer
      Unsigned32,
   frUniSigCallProceedingTimer
      Unsigned32,
   frUniSigNetworkType
      INTEGER }

frUniSigCallSetupTimer OBJECT-TYPE
   SYNTAX     Unsigned32 (1..255)
   ACCESS     read-write
   STATUS     mandatory
   DESCRIPTION
     "This attribute specifies the time the network will wait for a response 
      to the SETUP message sent to the called user. Upon timer expiry, 
      the SETUP message is retransmitted. The second expiry of this 
      timer causes the call to be cleared. This value is specified in 
      seconds."
   DEFVAL     { 4 }
::= { frUniSigSysParmsEntry 1 }

frUniSigDisconnectTimer OBJECT-TYPE
   SYNTAX     Unsigned32 (1..255)
   ACCESS     read-write
   STATUS     mandatory
   DESCRIPTION
     "This attribute specifies the time the network will wait for a response 
      to the DISCONNECT message sent to the user. Upon timer expiry, 
      the RELEASE message is sent. This value is specified in seconds."
   DEFVAL     { 30 }
::= { frUniSigSysParmsEntry 2 }

frUniSigReleaseTimer OBJECT-TYPE
   SYNTAX     Unsigned32 (1..255)
   ACCESS     read-write
   STATUS     mandatory
   DESCRIPTION
     "This attribute specifies the time the network will wait for a response 
      to the RELEASE message sent to the user. Upon timer expiry, the 
      RELEASE message is retransmitted. The second expiry of the timer 
      causes the call to be released. This value is specified in seconds."
   DEFVAL     { 4 }
::= { frUniSigSysParmsEntry 3 }

frUniSigCallProceedingTimer OBJECT-TYPE
   SYNTAX     Unsigned32 (1..255)
   ACCESS     read-write
   STATUS     mandatory
   DESCRIPTION
     "This attribute specifies the time the network will wait for the 
      CONNECT message from the called user after the network has 
      received the optional CALL PROCEEDING message from the 
      called user. Upon timer expiry, the call is cleared. This value is 
      specified in seconds."
   DEFVAL     { 10 }
::= { frUniSigSysParmsEntry 4 }

frUniSigNetworkType OBJECT-TYPE
   SYNTAX     INTEGER  {
                 private(1),
                 public(2) }
   ACCESS     read-write
   STATUS     mandatory
   DESCRIPTION
     "This attribute specifies whether this Frame Relay service is running 
      on a public or a private network. This value is used solely in 
      populating applicable information elements within those Q.933 
      messages that require a public or private network indication."
   DEFVAL     { private }
::= { frUniSigSysParmsEntry 5 }

frUniSigLapfSysTable OBJECT-TYPE
   SYNTAX     SEQUENCE OF FrUniSigLapfSysEntry
   ACCESS     not-accessible
   STATUS     mandatory
   DESCRIPTION
     "This group contains the provisionable attributes for the SVC data 
      link layer. The data link layer is governed primarily through ITU 
      specification Q.922, and operates over DLCI 0.."
::= { frUniSig 14 }

frUniSigLapfSysEntry OBJECT-TYPE
   SYNTAX     FrUniSigLapfSysEntry
   ACCESS     not-accessible
   STATUS     mandatory
   DESCRIPTION
     "An entry in the frUniSigLapfSysTable."
   INDEX {
      frUniIndex,
      frUniSigIndex }
::= { frUniSigLapfSysTable 1 }

FrUniSigLapfSysEntry ::= SEQUENCE {
   frUniSigWindowSize
      Unsigned32,
   frUniSigRetransmitLimit
      Unsigned32,
   frUniSigAckTimer
      Unsigned32,
   frUniSigAckDelayTimer
      Unsigned32,
   frUniSigIdleProbeTimer
      Unsigned32 }

frUniSigWindowSize OBJECT-TYPE
   SYNTAX     Unsigned32 (1..127)
   ACCESS     read-write
   STATUS     mandatory
   DESCRIPTION
     "This attribute specifies the window size. This is the maximum 
      number of unacknowledged sequenced frames that may be 
      outstanding from or to this interface at any one time."
   DEFVAL     { 7 }
::= { frUniSigLapfSysEntry 2 }

frUniSigRetransmitLimit OBJECT-TYPE
   SYNTAX     Unsigned32 (0..20)
   ACCESS     read-write
   STATUS     mandatory
   DESCRIPTION
     "This attribute specifies the number of times a frame can be 
      retransmitted by the SVC data link layer before appropriate 
      recovery action is taken."
   DEFVAL     { 3 }
::= { frUniSigLapfSysEntry 3 }

frUniSigAckTimer OBJECT-TYPE
   SYNTAX     Unsigned32 (1000..10000)
   ACCESS     read-write
   STATUS     mandatory
   DESCRIPTION
     "This attribute specifies the period in milliseconds that the network 
      will wait for an acknowledgment to a sent frame. The value set for 
      ackTimer must be less than the value set for idleProbeTimer."
   DEFVAL     { 1500 }
::= { frUniSigLapfSysEntry 4 }

frUniSigAckDelayTimer OBJECT-TYPE
   SYNTAX     Unsigned32 (0..10000)
   ACCESS     read-write
   STATUS     mandatory
   DESCRIPTION
     "This attribute specifies the maximum period in milliseconds that the 
      network will wait before sending an acknowledgment for a received 
      in-sequence I-frame. A value of 0 means there will be no delay in 
      acknowledgment."
   DEFVAL     { 0 }
::= { frUniSigLapfSysEntry 5 }

frUniSigIdleProbeTimer OBJECT-TYPE
   SYNTAX     Unsigned32 (1000..65535000)
   ACCESS     read-write
   STATUS     mandatory
   DESCRIPTION
     "This attribute specifies the time period in milliseconds the link will 
      be permitted to remain idle (that is, no frames are exchanged on the 
      data link). Upon expiry of this timer, the network's side link layer 
      polls its peer for status. The value set for idleProbeTimer must be 
      greater than the value set for ackTimer."
   DEFVAL     { 30000 }
::= { frUniSigLapfSysEntry 6 }

frUniSigStateTable OBJECT-TYPE
   SYNTAX     SEQUENCE OF FrUniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frUniSig 15 }

frUniSigStateEntry OBJECT-TYPE
   SYNTAX     FrUniSigStateEntry
   ACCESS     not-accessible
   STATUS     mandatory
   DESCRIPTION
     "An entry in the frUniSigStateTable."
   INDEX {
      frUniIndex,
      frUniSigIndex }
::= { frUniSigStateTable 1 }

FrUniSigStateEntry ::= SEQUENCE {
   frUniSigAdminState
      INTEGER,
   frUniSigOperationalState
      INTEGER,
   frUniSigUsageState
      INTEGER }

frUniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frUniSigStateEntry 1 }

frUniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frUniSigStateEntry 2 }

frUniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frUniSigStateEntry 3 }

frUniSigStatsTable OBJECT-TYPE
   SYNTAX     SEQUENCE OF FrUniSigStatsEntry
   ACCESS     not-accessible
   STATUS     mandatory
   DESCRIPTION
     "This group contains the statistics related to the SVC signaling layer 
      at the interface level."
::= { frUniSig 16 }

frUniSigStatsEntry OBJECT-TYPE
   SYNTAX     FrUniSigStatsEntry
   ACCESS     not-accessible
   STATUS     mandatory
   DESCRIPTION
     "An entry in the frUniSigStatsTable."
   INDEX {
      frUniIndex,
      frUniSigIndex }
::= { frUniSigStatsTable 1 }

FrUniSigStatsEntry ::= SEQUENCE {
   frUniSigCurrentNumberOfSvcCalls
      Unsigned32,
   frUniSigInCalls
      Counter32,
   frUniSigInCallsRefused
      Counter32,
   frUniSigOutCalls
      Counter32,
   frUniSigOutCallsFailed
      Counter32,
   frUniSigProtocolErrors
      Counter32,
   frUniSigQualityOfServiceNotAvailable
      Counter32,
   frUniSigSetupTimeout
      Counter32,
   frUniSigLastCauseInStatusMsgReceived
      Unsigned32,
   frUniSigLastStateInStatusMsgReceived
      INTEGER,
   frUniSigLastDlciReceivedStatus
      Unsigned32,
   frUniSigLastQ933StateReceivedStatus
      INTEGER,
   frUniSigLastTimeMsgBlockCongested
      EnterpriseDateAndTime,
   frUniSigLastDlciWithMsgBlockCongestion
      Unsigned32,
   frUniSigCurrentAggregateSvcCirNormalQ
      Unsigned32,
   frUniSigCurrentAggregateSvcCirHighQ
      Unsigned32,
   frUniSigCurrentAggregateSvcCirInterruptQ
      Unsigned32,
   frUniSigCurrentAggregateSvcEirNormalQ
      Unsigned32,
   frUniSigCurrentAggregateSvcEirHighQ
      Unsigned32,
   frUniSigCurrentAggregateSvcEirInterruptQ
      Unsigned32 }

frUniSigCurrentNumberOfSvcCalls OBJECT-TYPE
   SYNTAX     Unsigned32 (0..992)
   ACCESS     read-only
   STATUS     mandatory
   DESCRIPTION
     "This attribute shows the number of Frame Relay SVCs currently 
      existing on this interface."
::= { frUniSigStatsEntry 1 }

frUniSigInCalls OBJECT-TYPE
   SYNTAX     Counter32 
   ACCESS     read-only
   STATUS     mandatory
   DESCRIPTION
     "This attribute shows the current number of incoming SVCs on this 
      interface (i.e. the number of SVCs for which this interface 
      represents the destination end of the call)."
::= { frUniSigStatsEntry 4 }

frUniSigInCallsRefused OBJECT-TYPE
   SYNTAX     Counter32 
   ACCESS     read-only
   STATUS     mandatory
   DESCRIPTION
     "This attribute counts the number of incoming SVC call requests that 
      are rejected by either this interface or by the called user. When this 
      count reaches maximum, it wraps to zero."
::= { frUniSigStatsEntry 5 }

frUniSigOutCalls OBJECT-TYPE
   SYNTAX     Counter32 
   ACCESS     read-only
   STATUS     mandatory
   DESCRIPTION
     "This attribute shows the current number of outgoing SVCs on this 
      interface (i.e. the number of SVCs for which this interface 
      represents the source end of the call)."
::= { frUniSigStatsEntry 6 }

frUniSigOutCallsFailed OBJECT-TYPE
   SYNTAX     Counter32 
   ACCESS     read-only
   STATUS     mandatory
   DESCRIPTION
     "This attribute counts the number of outgoing SVC call requests that 
      are rejected by either this interface, or by the network side of the 
      destination end, or by the called user. When this count reaches 
      maximum, it wraps to zero."
::= { frUniSigStatsEntry 7 }

frUniSigProtocolErrors OBJECT-TYPE
   SYNTAX     Counter32 
   ACCESS     read-only
   STATUS     mandatory
   DESCRIPTION
     "This attribute counts the number of times a Q.933 protocol error has 
      occurred. Any one of the following events constitutes a protocol 
      error:
      1. In the user-signaled Link Layer Core Parameters IE within the
      SETUP or CONNECT messages, Cir, Bc and Be are all zero;
      2. In the user-signaled Link Layer Core Parameters IE within the
      SETUP or CONNECT messages, Cir is zero but Bc is 
      non-zero, or Bc is zero but Cir is non-zero;
      3. In the user-signaled Link Layer Core Parameters IE within the
      SETUP or CONNECT messages, the minimum acceptable Cir
      is greater than Cir;
      4. At the destination end, any of the destination to source direction 
      link layer core parameters has been increased in the 
      CONNECT message from the called user;
      5. At the destination end, the destination to source direction Cir
      in the CONNECT message is smaller than the corresponding 
      minimum acceptable Cir signaled to the called user;
      6. At the source end, any of the source to destination direction 
      link layer core parameters in the CONNECT message from the 
      destination end has been increased;
      7. At the source end, the source to destination direction Cir, after
      negotiation, is smaller than the corresponding minimum
      acceptable Cir;
      8. The network has received a STATUS message from the user
      with an incompatible Q.933 state.	
      
      When this count reaches maximum, it wraps to zero."
::= { frUniSigStatsEntry 8 }

frUniSigQualityOfServiceNotAvailable OBJECT-TYPE
   SYNTAX     Counter32 
   ACCESS     read-only
   STATUS     mandatory
   DESCRIPTION
     "This attribute counts the number of incoming and outgoing SVCs 
      that are rejected because the quality of service requested cannot be 
      met by the network. When this count reaches maximum, it wraps to 
      zero."
::= { frUniSigStatsEntry 9 }

frUniSigSetupTimeout OBJECT-TYPE
   SYNTAX     Counter32 
   ACCESS     read-only
   STATUS     mandatory
   DESCRIPTION
     "This attribute counts the number of times the T303 setup timer has 
      expired. When this count reaches maximum, it wraps to zero."
::= { frUniSigStatsEntry 10 }

frUniSigLastCauseInStatusMsgReceived OBJECT-TYPE
   SYNTAX     Unsigned32 (0..255)
   ACCESS     read-only
   STATUS     mandatory
   DESCRIPTION
     "This attribute shows the cause value in the last received user's 
      STATUS message to an existing call. The DLCI to which this 
      STATUS message applies is specified in the lastDlciReceivedStatus 
      attribute.
      
      The initial value of this attribute is 0 which means that no STATUS 
      message has been received for an existing call yet."
::= { frUniSigStatsEntry 11 }

frUniSigLastStateInStatusMsgReceived OBJECT-TYPE
   SYNTAX     INTEGER  {
                 null(0),
                 callInitiated(1),
                 n2(2),
                 outgoingCallProceeding(3),
                 n4(4),
                 n5(5),
                 callPresent(6),
                 n7(7),
                 n8(8),
                 incomingCallProceeding(9),
                 active(10),
                 disconnectRequest(11),
                 disconnectIndication(12),
                 n13(13),
                 n14(14),
                 n15(15),
                 n16(16),
                 n17(17),
                 n18(18),
                 releaseRequest(19),
                 notApplicable(20),
                 n21(21),
                 n22(22),
                 n23(23),
                 n24(24),
                 n25(25),
                 n26(26),
                 n27(27),
                 n28(28),
                 n29(29),
                 n30(30),
                 n31(31),
                 n32(32),
                 n33(33),
                 n34(34),
                 n35(35),
                 n36(36),
                 n37(37),
                 n38(38),
                 n39(39),
                 n40(40),
                 n41(41),
                 n42(42),
                 n43(43),
                 n44(44),
                 n45(45),
                 n46(46),
                 n47(47),
                 n48(48),
                 n49(49),
                 n50(50),
                 n51(51),
                 n52(52),
                 n53(53),
                 n54(54),
                 n55(55),
                 n56(56),
                 n57(57),
                 n58(58),
                 n59(59),
                 n60(60),
                 n61(61),
                 n62(62),
                 n63(63) }
   ACCESS     read-only
   STATUS     mandatory
   DESCRIPTION
     "This attribute shows the state value in the last received user's 
      STATUS message to an existing call. The DLCI to which this 
      STATUS message applies is specified in the lastDlciReceivedStatus 
      attribute.
      
      The initial value of this attribute is notApplicable."
::= { frUniSigStatsEntry 12 }

frUniSigLastDlciReceivedStatus OBJECT-TYPE
   SYNTAX     Unsigned32 (0 | 16..1007)
   ACCESS     read-only
   STATUS     mandatory
   DESCRIPTION
     "This attribute shows the value of the DLCI that has most recently 
      received a STATUS message from the user.
      
      The initial value of this attribute is 0."
::= { frUniSigStatsEntry 13 }

frUniSigLastQ933StateReceivedStatus OBJECT-TYPE
   SYNTAX     INTEGER  {
                 null(0),
                 callInitiated(1),
                 outgoingCallProceeding(3),
                 callPresent(6),
                 incomingCallProceeding(9),
                 active(10),
                 disconnectRequest(11),
                 disconnectIndication(12),
                 releaseRequest(19),
                 notApplicable(20) }
   ACCESS     read-only
   STATUS     mandatory
   DESCRIPTION
     "This attribute shows the network Q.933 state of the DLCI that has 
      most recently received a STATUS message from the user. The DLCI 
      to which this STATUS message applies is specified in the 
      lastDlciReceivedStatus attribute.
      
      The initial value of this attribute is notApplicable."
::= { frUniSigStatsEntry 14 }

frUniSigLastTimeMsgBlockCongested OBJECT-TYPE
   SYNTAX     EnterpriseDateAndTime (SIZE (0 | 16))
   ACCESS     read-only
   STATUS     mandatory
   DESCRIPTION
     "This attribute displays the most recent time that an SVC DLCI has 
      failed to get a message block due to message block congestion. 
      Exceptional behavior can occur due to this. The DLCI that has most 
      recently encountered this is indicated by the 
      lastDlciWithMsgBlockCongestion attribute. However, all SVC 
      DLCIs may be affected.
      
      The initial value of this attribute is 0000-00-00 00:00."
::= { frUniSigStatsEntry 15 }

frUniSigLastDlciWithMsgBlockCongestion OBJECT-TYPE
   SYNTAX     Unsigned32 (0 | 16..1007)
   ACCESS     read-only
   STATUS     mandatory
   DESCRIPTION
     "This attribute shows the value of the DLCI that has most recently 
      failed to get a message block due to message block congestion.
      
      The initial value of this attribute is 0."
::= { frUniSigStatsEntry 16 }

frUniSigCurrentAggregateSvcCirNormalQ OBJECT-TYPE
   SYNTAX     Unsigned32 (0..4294967295)
   ACCESS     read-only
   STATUS     mandatory
   DESCRIPTION
     "This attribute shows the aggregate SVC CIR (for traffic transiting in 
      the network through normal priority queue) assigned to existing 
      SVCs on the interface.
      
      The value of currentAggregateSvcCirNormalQ could be greater 
      than the provisionable value of maximumAggregateSvcCiNormalQ 
      if the value of maximumAggregateSvcCirNormalQ has been 
      changed during the service of this FrUni."
::= { frUniSigStatsEntry 17 }

frUniSigCurrentAggregateSvcCirHighQ OBJECT-TYPE
   SYNTAX     Unsigned32 (0..4294967295)
   ACCESS     read-only
   STATUS     mandatory
   DESCRIPTION
     "This attribute shows the aggregate SVC CIR (for traffic transiting in 
      the network through high priority queue) assigned to existing SVCs 
      on the interface.
      
      The value of currentAggregateSvcCirHighQ could be greater than 
      the provisionable value of maximumAggregateSvcCirHighQ if the 
      value of maximumAggregateSvcCirHighQ has been changed during 
      the service of this FrUni."
::= { frUniSigStatsEntry 18 }

frUniSigCurrentAggregateSvcCirInterruptQ OBJECT-TYPE
   SYNTAX     Unsigned32 (0..4294967295)
   ACCESS     read-only
   STATUS     mandatory
   DESCRIPTION
     "This attribute shows the aggregate SVC CIR (for traffic transiting in 
      the network through interrupting queue) assigned to existing SVCs 
      on the interface.
      
      The value of currentAggregateSvcCirInterruptQ could be greater 
      than the provisionable value of 
      maximumAggregateSvcCirInterruptQ if the value of 
      maximumAggregateSvcCirInterruptQ has been changed during the 
      service of this FrUni."
::= { frUniSigStatsEntry 19 }

frUniSigCurrentAggregateSvcEirNormalQ OBJECT-TYPE
   SYNTAX     Unsigned32 (0..4294967295)
   ACCESS     read-only
   STATUS     mandatory
   DESCRIPTION
     "This attribute shows the aggregate SVC EIR (for excess traffic 
      transiting in the network through normal priority queue) assigned to 
      existing SVCs on the interface.
      
      The value of currentAggregateSvcEirNormalQ could be greater 
      than the provisionable value of maximumAggregateSvcEirNormalQ 
      if the value of maximumAggregateSvcEiNormalQ has been changed 
      during the service of this FrUni or unlimitedAggregateEir is set to 
      yes."
::= { frUniSigStatsEntry 20 }

frUniSigCurrentAggregateSvcEirHighQ OBJECT-TYPE
   SYNTAX     Unsigned32 (0..4294967295)
   ACCESS     read-only
   STATUS     mandatory
   DESCRIPTION
     "This attribute shows the aggregate SVC EIR (for excess traffic 
      transiting in the network through high priority queue) assigned to 
      existing SVCs on the interface.
      
      The value of currentAggregateSvcEirHighQ could be greater than 
      the provisionable value of maximumAggregateSvcEirHighQ if the 
      value of maximumAggregateSvcEirHighQ has been changed during 
      the service of this FrUni or unlimitedAggregateEir is set to yes."
::= { frUniSigStatsEntry 21 }

frUniSigCurrentAggregateSvcEirInterruptQ OBJECT-TYPE
   SYNTAX     Unsigned32 (0..4294967295)
   ACCESS     read-only
   STATUS     mandatory
   DESCRIPTION
     "This attribute shows the aggregate SVC EIR (for excess traffic 
      transiting in the network through interrupting queue) assigned to 
      existing SVCs on the interface.
      
      The value of currentAggregateSvcEirInterruptQ could be greater 
      than the provisionable value of 
      maximumAggregateSvcEirInterruptQ if the value of 
      maximumAggregateSvcEirInterruptQ has been changed during the 
      service of this FrUni or unlimitedAggregateEir is set to yes."
::= { frUniSigStatsEntry 22 }

frUniSigLapfStatusTable OBJECT-TYPE
   SYNTAX     SEQUENCE OF FrUniSigLapfStatusEntry
   ACCESS     not-accessible
   STATUS     mandatory
   DESCRIPTION
     "This group contains the Q.922 SVC data link layer status."
::= { frUniSig 17 }

frUniSigLapfStatusEntry OBJECT-TYPE
   SYNTAX     FrUniSigLapfStatusEntry
   ACCESS     not-accessible
   STATUS     mandatory
   DESCRIPTION
     "An entry in the frUniSigLapfStatusTable."
   INDEX {
      frUniIndex,
      frUniSigIndex }
::= { frUniSigLapfStatusTable 1 }

FrUniSigLapfStatusEntry ::= SEQUENCE {
   frUniSigCurrentState
      INTEGER,
   frUniSigLastStateChangeReason
      INTEGER,
   frUniSigFrmrReceive
      HexString,
   frUniSigCurrentQueueSize
      Counter32 }

frUniSigCurrentState OBJECT-TYPE
   SYNTAX     INTEGER  {
                 disconnected(1),
                 linkSetup(2),
                 disconnectRequest(4),
                 informationTransfer(5),
                 waitingAck(7) }
   ACCESS     read-only
   STATUS     mandatory
   DESCRIPTION
     "This attribute shows the current state of the SVC data link layer 
      interface."
::= { frUniSigLapfStatusEntry 1 }

frUniSigLastStateChangeReason OBJECT-TYPE
   SYNTAX     INTEGER  {
                 notStarted(1),
                 abmeEntered(3),
                 abmeReset(5),
                 dmReceived(6),
                 dmSent(7),
                 discReceived(8),
                 discSent(9),
                 frmrReceived(10),
                 n200RetranTimeOut(12),
                 other(13) }
   ACCESS     read-only
   STATUS     mandatory
   DESCRIPTION
     "This attribute shows the reason for the most recent state change.
      notStarted - this is the default state after SVC data link has just been 
      created.
      abmeEntered - SVC data link has entered Asynchronous Balanced 
      Mode after SABME or UA has been received.
      abmeReset - the data link has been reset.
      dmReceived - DM response received.
      dmSent - DM sent.
      discReceived - DISC response received.
      discSent - DISC sent.
      frmrReceived - FRMR received.
      n200RetranTimeOut - retransmitLimit has been exceeded.
      other - unspecified state change reasons. The most likely reason for 
      this is the transition from state waitingAck to state 
      informationTransfer."
::= { frUniSigLapfStatusEntry 2 }

frUniSigFrmrReceive OBJECT-TYPE
   SYNTAX     HexString (SIZE (0..8))
   ACCESS     read-only
   STATUS     mandatory
   DESCRIPTION
     "This attribute shows the information field of the FRMR most 
      recently received."
::= { frUniSigLapfStatusEntry 3 }

frUniSigCurrentQueueSize OBJECT-TYPE
   SYNTAX     Counter32 
   ACCESS     read-only
   STATUS     mandatory
   DESCRIPTION
     "This attribute shows the current number of frames in the SVC data 
      link layer transmit queue."
::= { frUniSigLapfStatusEntry 4 }

frUniSigLapfStatsTable OBJECT-TYPE
   SYNTAX     SEQUENCE OF FrUniSigLapfStatsEntry
   ACCESS     not-accessible
   STATUS     mandatory
   DESCRIPTION
     "This group contains the statistics for the SVC data link layer."
::= { frUniSig 18 }

frUniSigLapfStatsEntry OBJECT-TYPE
   SYNTAX     FrUniSigLapfStatsEntry
   ACCESS     not-accessible
   STATUS     mandatory
   DESCRIPTION
     "An entry in the frUniSigLapfStatsTable."
   INDEX {
      frUniIndex,
      frUniSigIndex }
::= { frUniSigLapfStatsTable 1 }

FrUniSigLapfStatsEntry ::= SEQUENCE {
   frUniSigStateChange
      Counter32,
   frUniSigRemoteBusy
      Counter32,
   frUniSigReceiveRejectFrame
      Counter32,
   frUniSigAckTimeout
      Counter32,
   frUniSigIFramesTransmitted
      Counter32,
   frUniSigIFramesTxDiscarded
      Counter32,
   frUniSigIFramesReceived
      Counter32,
   frUniSigIFramesRcvdDiscarded
      Counter32 }

frUniSigStateChange OBJECT-TYPE
   SYNTAX     Counter32 
   ACCESS     read-only
   STATUS     mandatory
   DESCRIPTION
     "This attribute counts the number of times the SVC data link layer 
      interface has changed state. Frequent state changes may indicate a 
      problem with the line quality. While the data link layer is in 
      informationTransfer state, this counter will increment on each 
      expiry of idleProbeTimer as its state goes from 
      informationTransfer to waitingAck and back. When this count 
      reaches maximum, it wraps to zero."
::= { frUniSigLapfStatsEntry 1 }

frUniSigRemoteBusy OBJECT-TYPE
   SYNTAX     Counter32 
   ACCESS     read-only
   STATUS     mandatory
   DESCRIPTION
     "This attribute counts the number of times transmission of an I-frame 
      was unsuccessful due to a perceived remote busy condition 
      (window closed or remote busy). When this count reaches 
      maximum, it wraps to zero."
::= { frUniSigLapfStatsEntry 2 }

frUniSigReceiveRejectFrame OBJECT-TYPE
   SYNTAX     Counter32 
   ACCESS     read-only
   STATUS     mandatory
   DESCRIPTION
     "This attribute counts the number of REJ frames received by the 
      interface. When this count reaches maximum, it wraps to zero."
::= { frUniSigLapfStatsEntry 3 }

frUniSigAckTimeout OBJECT-TYPE
   SYNTAX     Counter32 
   ACCESS     read-only
   STATUS     mandatory
   DESCRIPTION
     "This attribute counts the number of times the ackTimer has expired. 
      Frequent increments of this counter indicate a problem at the link or 
      improper values have been chosen for ackTimer and ackDelayTimer 
      between the local and remote sides. When this count reaches 
      maximum, it wraps to zero."
::= { frUniSigLapfStatsEntry 4 }

frUniSigIFramesTransmitted OBJECT-TYPE
   SYNTAX     Counter32 
   ACCESS     read-only
   STATUS     mandatory
   DESCRIPTION
     "This attribute counts the number of SVC I-frames transmitted to the 
      interface on DLCI 0. An I-frame may be counted more than once if 
      there are retransmissions at the SVC data link layer. When this 
      count reaches maximum, it wraps to zero."
::= { frUniSigLapfStatsEntry 5 }

frUniSigIFramesTxDiscarded OBJECT-TYPE
   SYNTAX     Counter32 
   ACCESS     read-only
   STATUS     mandatory
   DESCRIPTION
     "This attribute counts the number of SVC I-frames that are bound for 
      the link but have been discarded. Discard reasons may be one of the 
      following:
      1.	the frame length is beyond allow limit.
      2.	the SVC data link layer is in disconnected state.
      3. 	the transmit queue has been purged because the queue length 
      has reached the reset threshold.
      4.	the transmit queue or the queue waiting for acknowledgment
      has been 			purged because the link cannot be re-established.
      
      When this count reaches maximum, it wraps to zero."
::= { frUniSigLapfStatsEntry 6 }

frUniSigIFramesReceived OBJECT-TYPE
   SYNTAX     Counter32 
   ACCESS     read-only
   STATUS     mandatory
   DESCRIPTION
     "This attribute counts the number of SVC I-frames received from the 
      interface. When this count reaches maximum, it wraps to zero."
::= { frUniSigLapfStatsEntry 7 }

frUniSigIFramesRcvdDiscarded OBJECT-TYPE
   SYNTAX     Counter32 
   ACCESS     read-only
   STATUS     mandatory
   DESCRIPTION
     "This attribute counts the number of SVC I-frames received but have 
      been discarded. The discard reasons are:
      1.	 incorrect frame size
      2. frame is out of sequence
      3. frame received while the network side of the SVC data link
      layer is not in the informationTransfer or waitingAck state.
      
      When this count reaches maximum, it wraps to zero."
::= { frUniSigLapfStatsEntry 8 }

frUniSigSvcaccTable OBJECT-TYPE
   SYNTAX     SEQUENCE OF FrUniSigSvcaccEntry
   ACCESS     not-accessible
   STATUS     mandatory
   DESCRIPTION
     "This group contains the provisionable attribute to define the 
      defaultAccounting attribute.."
::= { frUniSig 19 }

frUniSigSvcaccEntry OBJECT-TYPE
   SYNTAX     FrUniSigSvcaccEntry
   ACCESS     not-accessible
   STATUS     mandatory
   DESCRIPTION
     "An entry in the frUniSigSvcaccTable."
   INDEX {
      frUniIndex,
      frUniSigIndex }
::= { frUniSigSvcaccTable 1 }

FrUniSigSvcaccEntry ::= SEQUENCE {
   frUniSigDefaultAccounting
      INTEGER }

frUniSigDefaultAccounting OBJECT-TYPE
   SYNTAX     INTEGER  {
                 off(0),
                 on(1) }
   ACCESS     read-write
   STATUS     mandatory
   DESCRIPTION
     "This attribute specifies whether accounting data collection and 
      record generation is turned on at this DLCI. For accounting data 
      collection and record generation to be turned on, the 
      defaultAccounting bit and at least one of the accountCollection 
      bits in the DataNetworkAddress component must be set to on."
   DEFVAL     { on }
::= { frUniSigSvcaccEntry 1 }

frUniSigCodesTable OBJECT-TYPE
   SYNTAX     SEQUENCE OF FrUniSigCodesEntry
   ACCESS     not-accessible
   STATUS     mandatory
   DESCRIPTION
     "This group contains the remote data network address, the last SVC 
      clear cause and the last SVC diagnostic code coming from the 
      subnet or the local VC."
::= { frUniSig 20 }

frUniSigCodesEntry OBJECT-TYPE
   SYNTAX     FrUniSigCodesEntry
   ACCESS     not-accessible
   STATUS     mandatory
   DESCRIPTION
     "An entry in the frUniSigCodesTable."
   INDEX {
      frUniIndex,
      frUniSigIndex }
::= { frUniSigCodesTable 1 }

FrUniSigCodesEntry ::= SEQUENCE {
   frUniSigLastClearRemoteDataNetworkAddress
      DigitString,
   frUniSigLastClearCause
      Unsigned32,
   frUniSigLastDiagnosticCode
      Unsigned32 }

frUniSigLastClearRemoteDataNetworkAddress OBJECT-TYPE
   SYNTAX     DigitString (SIZE (0..15))
   ACCESS     read-only
   STATUS     mandatory
   DESCRIPTION
     "This attribute indicates the Data Network Address (DNA) of the
      remote (the other end of the SVC connection) of the call which 
      cleared last and whose clear and diagnostic codes were recorded."
::= { frUniSigCodesEntry 1 }

frUniSigLastClearCause OBJECT-TYPE
   SYNTAX     Unsigned32 (0..255)
   ACCESS     read-only
   STATUS     mandatory
   DESCRIPTION
     "This attribute indicates the last SVC clear cause signalled at the end 
      of the connection or failure to connect. It is updated only if the clear 
      request comes from the subnet or the call is rejected locally by the 
      VC. The same set of possible values provides the clear cause field 
      in the accounting record."
   DEFVAL     { 0 }
::= { frUniSigCodesEntry 2 }

frUniSigLastDiagnosticCode OBJECT-TYPE
   SYNTAX     Unsigned32 (0..255)
   ACCESS     read-only
   STATUS     mandatory
   DESCRIPTION
     "This attribute indicates the last SVC diagnostic code signalled at the 
      end of the connection or failure to connect. It is updated if the clear 
      request comes from the subnet or the call is rejected locally by the 
      VC. The same set of possible values provides the diagnostic code 
      field in the accounting record."
   DEFVAL     { 0 }
::= { frUniSigCodesEntry 3 }


-- FrUni/n VirtualFramer
-- FrDte/n VirtualFramer
-- The VirtualFramer component binds two services together to 
-- provide data transfer between them. It is mutually exclusive from 
-- Framer component. 

frUniVFramer OBJECT IDENTIFIER ::= { frUni 8 }



frUniVFramerRowStatusTable OBJECT-TYPE
   SYNTAX     SEQUENCE OF FrUniVFramerRowStatusEntry
   ACCESS     not-accessible
   STATUS     mandatory
   DESCRIPTION
     "This entry controls the addition and deletion of 
      frUniVFramer components."
::= { frUniVFramer 1 }

frUniVFramerRowStatusEntry OBJECT-TYPE
   SYNTAX     FrUniVFramerRowStatusEntry
   ACCESS     not-accessible
   STATUS     mandatory
   DESCRIPTION
     "A single entry in the table represents a single 
      frUniVFramer component."
   INDEX {
      frUniIndex,
      frUniVFramerIndex }
::= { frUniVFramerRowStatusTable 1 }

FrUniVFramerRowStatusEntry ::= SEQUENCE {
   frUniVFramerRowStatus
      RowStatus,
   frUniVFramerComponentName
      DisplayString,
   frUniVFramerStorageType
      StorageType,
   frUniVFramerIndex
      NonReplicated }

frUniVFramerRowStatus OBJECT-TYPE
   SYNTAX     RowStatus 
   ACCESS     read-write
   STATUS     mandatory
   DESCRIPTION
     "This variable is used as the basis for SNMP naming of
      frUniVFramer components.
      These components can be added and deleted."
::= { frUniVFramerRowStatusEntry 1 }

frUniVFramerComponentName OBJECT-TYPE
   SYNTAX     DisplayString 
   ACCESS     read-only
   STATUS     mandatory
   DESCRIPTION
     "This variable provides the component's string name for
      use with the ASCII Console Interface"
::= { frUniVFramerRowStatusEntry 2 }

frUniVFramerStorageType OBJECT-TYPE
   SYNTAX     StorageType 
   ACCESS     read-only
   STATUS     mandatory
   DESCRIPTION
     "This variable represents the storage type value for the
      frUniVFramer tables."
::= { frUniVFramerRowStatusEntry 4 }

frUniVFramerIndex OBJECT-TYPE
   SYNTAX     NonReplicated 
   ACCESS     not-accessible
   STATUS     mandatory
   DESCRIPTION
     "This variable represents the index for the frUniVFramer tables."
::= { frUniVFramerRowStatusEntry 10 }

frUniVFramerProvTable OBJECT-TYPE
   SYNTAX     SEQUENCE OF FrUniVFramerProvEntry
   ACCESS     not-accessible
   STATUS     mandatory
   DESCRIPTION
     "This group contains provisionable attributes for the VirtualFramer 
      component."
::= { frUniVFramer 10 }

frUniVFramerProvEntry OBJECT-TYPE
   SYNTAX     FrUniVFramerProvEntry
   ACCESS     not-accessible
   STATUS     mandatory
   DESCRIPTION
     "An entry in the frUniVFramerProvTable."
   INDEX {
      frUniIndex,
      frUniVFramerIndex }
::= { frUniVFramerProvTable 1 }

FrUniVFramerProvEntry ::= SEQUENCE {
   frUniVFramerOtherVirtualFramer
      Link,
   frUniVFramerLogicalProcessor
      Link }

frUniVFramerOtherVirtualFramer OBJECT-TYPE
   SYNTAX     Link 
   ACCESS     read-write
   STATUS     mandatory
   DESCRIPTION
     "This attribute specifies the other VirtualFramer to which the service 
      is linked, for example, FrUni/n VirtualFramer, FrDte/n 
      VirtualFramer."
::= { frUniVFramerProvEntry 1 }

frUniVFramerLogicalProcessor OBJECT-TYPE
   SYNTAX     Link 
   ACCESS     read-write
   STATUS     mandatory
   DESCRIPTION
     "This attribute specifies the logical processor on which the service 
      component will reside."
::= { frUniVFramerProvEntry 2 }

frUniVFramerStateTable OBJECT-TYPE
   SYNTAX     SEQUENCE OF FrUniVFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frUniVFramer 11 }

frUniVFramerStateEntry OBJECT-TYPE
   SYNTAX     FrUniVFramerStateEntry
   ACCESS     not-accessible
   STATUS     mandatory
   DESCRIPTION
     "An entry in the frUniVFramerStateTable."
   INDEX {
      frUniIndex,
      frUniVFramerIndex }
::= { frUniVFramerStateTable 1 }

FrUniVFramerStateEntry ::= SEQUENCE {
   frUniVFramerAdminState
      INTEGER,
   frUniVFramerOperationalState
      INTEGER,
   frUniVFramerUsageState
      INTEGER }

frUniVFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frUniVFramerStateEntry 1 }

frUniVFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frUniVFramerStateEntry 2 }

frUniVFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frUniVFramerStateEntry 3 }

frUniVFramerStatsTable OBJECT-TYPE
   SYNTAX     SEQUENCE OF FrUniVFramerStatsEntry
   ACCESS     not-accessible
   STATUS     mandatory
   DESCRIPTION
     "This group contains the operational statistics data for a 
      VirtualFramer component."
::= { frUniVFramer 12 }

frUniVFramerStatsEntry OBJECT-TYPE
   SYNTAX     FrUniVFramerStatsEntry
   ACCESS     not-accessible
   STATUS     mandatory
   DESCRIPTION
     "An entry in the frUniVFramerStatsTable."
   INDEX {
      frUniIndex,
      frUniVFramerIndex }
::= { frUniVFramerStatsTable 1 }

FrUniVFramerStatsEntry ::= SEQUENCE {
   frUniVFramerFrmToOtherVFramer
      PassportCounter64,
   frUniVFramerFrmFromOtherVFramer
      PassportCounter64,
   frUniVFramerOctetFromOtherVFramer
      PassportCounter64 }

frUniVFramerFrmToOtherVFramer OBJECT-TYPE
   SYNTAX     PassportCounter64 
   ACCESS     read-only
   STATUS     mandatory
   DESCRIPTION
     "This attribute counts the frames transmitted to the 
      otherVirtualFramer."
::= { frUniVFramerStatsEntry 2 }

frUniVFramerFrmFromOtherVFramer OBJECT-TYPE
   SYNTAX     PassportCounter64 
   ACCESS     read-only
   STATUS     mandatory
   DESCRIPTION
     "This attribute counts the frames received from the 
      otherVirtualFramer."
::= { frUniVFramerStatsEntry 3 }

frUniVFramerOctetFromOtherVFramer OBJECT-TYPE
   SYNTAX     PassportCounter64 
   ACCESS     read-only
   STATUS     mandatory
   DESCRIPTION
     "This attribute counts the octets received from the 
      otherVirtualFramer."
::= { frUniVFramerStatsEntry 5 }


-- FrUni/n LoadTestSystem
-- FrNni/n LoadTestSystem
-- This component defines an instance of the Frame Relay Load Test 
-- System (UNI) service. The component instance value n is a unique 
-- positive integer within a module.

frUniLts OBJECT IDENTIFIER ::= { frUni 9 }



frUniLtsRowStatusTable OBJECT-TYPE
   SYNTAX     SEQUENCE OF FrUniLtsRowStatusEntry
   ACCESS     not-accessible
   STATUS     mandatory
   DESCRIPTION
     "This entry controls the addition and deletion of 
      frUniLts components."
::= { frUniLts 1 }

frUniLtsRowStatusEntry OBJECT-TYPE
   SYNTAX     FrUniLtsRowStatusEntry
   ACCESS     not-accessible
   STATUS     mandatory
   DESCRIPTION
     "A single entry in the table represents a single 
      frUniLts component."
   INDEX {
      frUniIndex,
      frUniLtsIndex }
::= { frUniLtsRowStatusTable 1 }

FrUniLtsRowStatusEntry ::= SEQUENCE {
   frUniLtsRowStatus
      RowStatus,
   frUniLtsComponentName
      DisplayString,
   frUniLtsStorageType
      StorageType,
   frUniLtsIndex
      NonReplicated }

frUniLtsRowStatus OBJECT-TYPE
   SYNTAX     RowStatus 
   ACCESS     read-write
   STATUS     mandatory
   DESCRIPTION
     "This variable is used as the basis for SNMP naming of
      frUniLts components.
      These components can be added and deleted."
::= { frUniLtsRowStatusEntry 1 }

frUniLtsComponentName OBJECT-TYPE
   SYNTAX     DisplayString 
   ACCESS     read-only
   STATUS     mandatory
   DESCRIPTION
     "This variable provides the component's string name for
      use with the ASCII Console Interface"
::= { frUniLtsRowStatusEntry 2 }

frUniLtsStorageType OBJECT-TYPE
   SYNTAX     StorageType 
   ACCESS     read-only
   STATUS     mandatory
   DESCRIPTION
     "This variable represents the storage type value for the
      frUniLts tables."
::= { frUniLtsRowStatusEntry 4 }

frUniLtsIndex OBJECT-TYPE
   SYNTAX     NonReplicated 
   ACCESS     not-accessible
   STATUS     mandatory
   DESCRIPTION
     "This variable represents the index for the frUniLts tables."
::= { frUniLtsRowStatusEntry 10 }

frUniLtsSetupTable OBJECT-TYPE
   SYNTAX     SEQUENCE OF FrUniLtsSetupEntry
   ACCESS     not-accessible
   STATUS     mandatory
   DESCRIPTION
     "This attribute group contains the parameters used to configure the 
      behavior of the Frame Relay Load Test System."
::= { frUniLts 10 }

frUniLtsSetupEntry OBJECT-TYPE
   SYNTAX     FrUniLtsSetupEntry
   ACCESS     not-accessible
   STATUS     mandatory
   DESCRIPTION
     "An entry in the frUniLtsSetupTable."
   INDEX {
      frUniIndex,
      frUniLtsIndex }
::= { frUniLtsSetupTable 1 }

FrUniLtsSetupEntry ::= SEQUENCE {
   frUniLtsDuration
      Unsigned32,
   frUniLtsAlgorithm
      INTEGER,
   frUniLtsBurstSize
      Unsigned32,
   frUniLtsTimeInterval
      Unsigned32 }

frUniLtsDuration OBJECT-TYPE
   SYNTAX     Unsigned32 (0..4294967295)
   ACCESS     read-write
   STATUS     mandatory
   DESCRIPTION
     "This attribute specifies the duration of the test in milliseconds. The 
      test will run until the duration expires or the STOP command is 
      issued. A value of 0 is used to indicate infinity."
   DEFVAL     { 0 }
::= { frUniLtsSetupEntry 200 }

frUniLtsAlgorithm OBJECT-TYPE
   SYNTAX     INTEGER  {
                 continousBurst(0),
                 intervalBurst(1),
                 delayBurst(2),
                 fixedBurst(3) }
   ACCESS     read-write
   STATUS     mandatory
   DESCRIPTION
     "This attribute specifies which algorithm is used to generate the 
      frames.
      
      ContinuousBurst
      This mode of traffic generation creates traffic at the maximum rate 
      possible until all of the frames have been sent. The generator then 
      waits until the end of the timeInterval to begin again.
      
      IntervalBurst
      This algorithm attempts to generate 10 ms bursts of burstSize 
      frames. It will generate as many of the burstSize frames as it can per 
      sub-interval.
      
      DelayedBurst
      This algorithm generates bursts of burstSize frames separated by 10 
      ms delays.
      
      FixedBurst
      This aglorithm is similar to IntervalBurst, except a fixed burst size 
      of 12 frames is used.
      
      delayMeasurement
      This algorithm is used to measure delay. The specified number of 
      frames in the indicated pattern are generated, one at a time, with a 
      maximum wait of maxDelay before sending the next frame.
      This algorithm is not implemented yet."
   DEFVAL     { continousBurst }
::= { frUniLtsSetupEntry 201 }

frUniLtsBurstSize OBJECT-TYPE
   SYNTAX     Unsigned32 (1..250)
   ACCESS     read-write
   STATUS     mandatory
   DESCRIPTION
     "This attribute specifies the number of frames per burst under the 
      delayedBurst and intervalBurst algorithms."
   DEFVAL     { 50 }
::= { frUniLtsSetupEntry 204 }

frUniLtsTimeInterval OBJECT-TYPE
   SYNTAX     Unsigned32 (1..60000)
   ACCESS     read-write
   STATUS     mandatory
   DESCRIPTION
     "This attribute specifies the time interval to the specified number of 
      seconds. Granuality is in centiseconds. Maximum is 1 minute."
   DEFVAL     { 100 }
::= { frUniLtsSetupEntry 205 }

frUniLtsStateTable OBJECT-TYPE
   SYNTAX     SEQUENCE OF FrUniLtsStateEntry
   ACCESS     not-accessible
   STATUS     mandatory
   DESCRIPTION
     "This group contains the operation statistics of the load generator."
::= { frUniLts 11 }

frUniLtsStateEntry OBJECT-TYPE
   SYNTAX     FrUniLtsStateEntry
   ACCESS     not-accessible
   STATUS     mandatory
   DESCRIPTION
     "An entry in the frUniLtsStateTable."
   INDEX {
      frUniIndex,
      frUniLtsIndex }
::= { frUniLtsStateTable 1 }

FrUniLtsStateEntry ::= SEQUENCE {
   frUniLtsGeneratorState
      INTEGER,
   frUniLtsCycleIncomplete
      INTEGER,
   frUniLtsLastActiveInterval
      Unsigned32,
   frUniLtsLoad
      FixedPoint3,
   frUniLtsElapsedGenerationTime
      Unsigned32 }

frUniLtsGeneratorState OBJECT-TYPE
   SYNTAX     INTEGER  {
                 stopped(0),
                 running(1) }
   ACCESS     read-only
   STATUS     mandatory
   DESCRIPTION
     "This attribute indicates whether the Lts is generating traffic."
   DEFVAL     { stopped }
::= { frUniLtsStateEntry 200 }

frUniLtsCycleIncomplete OBJECT-TYPE
   SYNTAX     INTEGER  {
                 false(0),
                 true(1) }
   ACCESS     read-only
   STATUS     mandatory
   DESCRIPTION
     "This attribute indicates whether the time required to generate all of 
      the enabled patterns is more than timeInterval by a true value. 
      Otherwise, this flag is set to false. Default is True."
   DEFVAL     { true }
::= { frUniLtsStateEntry 201 }

frUniLtsLastActiveInterval OBJECT-TYPE
   SYNTAX     Unsigned32 (0..4294967295)
   ACCESS     read-only
   STATUS     mandatory
   DESCRIPTION
     "This attribute indicates the actual time it took to generate all of the 
      enabled patterns in the last cycle. If cycleIncomplete is true, this 
      value should be zero."
::= { frUniLtsStateEntry 202 }

frUniLtsLoad OBJECT-TYPE
   SYNTAX     FixedPoint3 (0..4294967295)
   ACCESS     read-only
   STATUS     mandatory
   DESCRIPTION
     "This attribute indicates the load being generated. This value 
      represents that calculated using the set number of ticks. The actual 
      burstTimeInterval may differ. One entire cycle of the patterns is 
      completed in activeInterval and thus most of the load may be 
      concentrated early in the set interval."
::= { frUniLtsStateEntry 204 }

frUniLtsElapsedGenerationTime OBJECT-TYPE
   SYNTAX     Unsigned32 (0..4294967295)
   ACCESS     read-only
   STATUS     mandatory
   DESCRIPTION
     "This attribute indicates how many milliseconds have elapsed since 
      the start of this test."
::= { frUniLtsStateEntry 205 }

frUniLtsResultsTable OBJECT-TYPE
   SYNTAX     SEQUENCE OF FrUniLtsResultsEntry
   ACCESS     not-accessible
   STATUS     mandatory
   DESCRIPTION
     "This group contains the frame counting attributes for the LTS 
      component."
::= { frUniLts 12 }

frUniLtsResultsEntry OBJECT-TYPE
   SYNTAX     FrUniLtsResultsEntry
   ACCESS     not-accessible
   STATUS     mandatory
   DESCRIPTION
     "An entry in the frUniLtsResultsTable."
   INDEX {
      frUniIndex,
      frUniLtsIndex }
::= { frUniLtsResultsTable 1 }

FrUniLtsResultsEntry ::= SEQUENCE {
   frUniLtsFramesTx
      Counter32,
   frUniLtsBytesTx
      Unsigned32,
   frUniLtsBitRateTx
      FixedPoint3,
   frUniLtsFrameRateTx
      Unsigned32 }

frUniLtsFramesTx OBJECT-TYPE
   SYNTAX     Counter32 
   ACCESS     read-only
   STATUS     mandatory
   DESCRIPTION
     "This attribute specifies the number of frames send to the network 
      since the last time these statistics were cleared. This is similar to the 
      framesToIf attribute of the FRAMER component."
::= { frUniLtsResultsEntry 200 }

frUniLtsBytesTx OBJECT-TYPE
   SYNTAX     Unsigned32 (0..4294967295)
   ACCESS     read-only
   STATUS     mandatory
   DESCRIPTION
     "This attribute indicates the number of bytes sent."
   DEFVAL     { 0 }
::= { frUniLtsResultsEntry 204 }

frUniLtsBitRateTx OBJECT-TYPE
   SYNTAX     FixedPoint3 (0..4294967295)
   ACCESS     read-only
   STATUS     mandatory
   DESCRIPTION
     "This attribute indicates the bit rate being sent to the link. It should 
      only differ from the load if the burstTimeInterval would be >= the 
      timeInterval or burstSize frames cannot be generated in 10ms 
      (intervalBurst algorithm)."
   DEFVAL     { 0 }
::= { frUniLtsResultsEntry 208 }

frUniLtsFrameRateTx OBJECT-TYPE
   SYNTAX     Unsigned32 (0..4294967295)
   ACCESS     read-only
   STATUS     mandatory
   DESCRIPTION
     "This attribute indicates the frame rate being sent to the link. It is 
      calculated using the number of frames sent to the link in one cycle 
      of the patterns."
   DEFVAL     { 0 }
::= { frUniLtsResultsEntry 209 }


-- FrUni/n Lts Pattern
-- FrNni/n Lts Pattern
-- Each instance of this component specifies a pattern to be generated 
-- as part of each cycle.  One cycle represents one pass through each 
-- pattern.

frUniLtsPat OBJECT IDENTIFIER ::= { frUniLts 2 }



frUniLtsPatRowStatusTable OBJECT-TYPE
   SYNTAX     SEQUENCE OF FrUniLtsPatRowStatusEntry
   ACCESS     not-accessible
   STATUS     mandatory
   DESCRIPTION
     "This entry controls the addition and deletion of 
      frUniLtsPat components."
::= { frUniLtsPat 1 }

frUniLtsPatRowStatusEntry OBJECT-TYPE
   SYNTAX     FrUniLtsPatRowStatusEntry
   ACCESS     not-accessible
   STATUS     mandatory
   DESCRIPTION
     "A single entry in the table represents a single 
      frUniLtsPat component."
   INDEX {
      frUniIndex,
      frUniLtsIndex,
      frUniLtsPatIndex }
::= { frUniLtsPatRowStatusTable 1 }

FrUniLtsPatRowStatusEntry ::= SEQUENCE {
   frUniLtsPatRowStatus
      RowStatus,
   frUniLtsPatComponentName
      DisplayString,
   frUniLtsPatStorageType
      StorageType,
   frUniLtsPatIndex
      Integer32 }

frUniLtsPatRowStatus OBJECT-TYPE
   SYNTAX     RowStatus 
   ACCESS     read-write
   STATUS     mandatory
   DESCRIPTION
     "This variable is used as the basis for SNMP naming of
      frUniLtsPat components.
      These components can be added and deleted."
::= { frUniLtsPatRowStatusEntry 1 }

frUniLtsPatComponentName OBJECT-TYPE
   SYNTAX     DisplayString 
   ACCESS     read-only
   STATUS     mandatory
   DESCRIPTION
     "This variable provides the component's string name for
      use with the ASCII Console Interface"
::= { frUniLtsPatRowStatusEntry 2 }

frUniLtsPatStorageType OBJECT-TYPE
   SYNTAX     StorageType 
   ACCESS     read-only
   STATUS     mandatory
   DESCRIPTION
     "This variable represents the storage type value for the
      frUniLtsPat tables."
::= { frUniLtsPatRowStatusEntry 4 }

frUniLtsPatIndex OBJECT-TYPE
   SYNTAX     Integer32 (0..29)
   ACCESS     not-accessible
   STATUS     mandatory
   DESCRIPTION
     "This variable represents the index for the frUniLtsPat tables."
::= { frUniLtsPatRowStatusEntry 10 }

frUniLtsPatDefaultsTable OBJECT-TYPE
   SYNTAX     SEQUENCE OF FrUniLtsPatDefaultsEntry
   ACCESS     not-accessible
   STATUS     mandatory
   DESCRIPTION
     "This attribute group contains the specifications of the pattern."
::= { frUniLtsPat 10 }

frUniLtsPatDefaultsEntry OBJECT-TYPE
   SYNTAX     FrUniLtsPatDefaultsEntry
   ACCESS     not-accessible
   STATUS     mandatory
   DESCRIPTION
     "An entry in the frUniLtsPatDefaultsTable."
   INDEX {
      frUniIndex,
      frUniLtsIndex,
      frUniLtsPatIndex }
::= { frUniLtsPatDefaultsTable 1 }

FrUniLtsPatDefaultsEntry ::= SEQUENCE {
   frUniLtsPatDefaultDlci
      Unsigned32,
   frUniLtsPatDefaultNumFrames
      Unsigned32,
   frUniLtsPatDefaultDataSize
      Unsigned32,
   frUniLtsPatDefaultHeaderBits
      OCTET STRING,
   frUniLtsPatDefaultHeaderLength
      Unsigned32,
   frUniLtsPatDefaultEABits
      Hex,
   frUniLtsPatDefaultPayloadPattern
      HexString,
   frUniLtsPatDefaultRfc1490Header
      INTEGER,
   frUniLtsPatDefaultUseBadLrc
      INTEGER }

frUniLtsPatDefaultDlci OBJECT-TYPE
   SYNTAX     Unsigned32 (16..1007)
   ACCESS     read-write
   STATUS     mandatory
   DESCRIPTION
     "This attribute specifies for which dlci (on the local end) the frames 
      are destined."
   DEFVAL     { 16 }
::= { frUniLtsPatDefaultsEntry 200 }

frUniLtsPatDefaultNumFrames OBJECT-TYPE
   SYNTAX     Unsigned32 (0..4294967295)
   ACCESS     read-write
   STATUS     mandatory
   DESCRIPTION
     "This attribute specifies the number of frames in this pattern.  This is 
      the number of frames of this type which will be generated in one 
      timeInterval."
   DEFVAL     { 100 }
::= { frUniLtsPatDefaultsEntry 201 }

frUniLtsPatDefaultDataSize OBJECT-TYPE
   SYNTAX     Unsigned32 (0..8200)
   ACCESS     read-write
   STATUS     mandatory
   DESCRIPTION
     "This attribute specifies the payload size of each frame in bytes.  
      This is in excess to the header."
   DEFVAL     { 512 }
::= { frUniLtsPatDefaultsEntry 202 }

frUniLtsPatDefaultHeaderBits OBJECT-TYPE
   SYNTAX     OCTET STRING (SIZE (1))
   ACCESS     read-write
   STATUS     mandatory
   DESCRIPTION
     "This attribute specifies whether the following bits are on/off in the 
      header of each frame. The following bits can be set:
      BeCn, C/R, De, FeCn

      Description of bits:
      becn(0)
      fecn(1)
      cr(2)
      de(3)"
::= { frUniLtsPatDefaultsEntry 203 }

frUniLtsPatDefaultHeaderLength OBJECT-TYPE
   SYNTAX     Unsigned32 (0 | 2..4)
   ACCESS     read-write
   STATUS     mandatory
   DESCRIPTION
     "This attribute specifies the size of the frame relay header in bytes.  
      Passport currently only supports a 2-byte header."
   DEFVAL     { 2 }
::= { frUniLtsPatDefaultsEntry 204 }

frUniLtsPatDefaultEABits OBJECT-TYPE
   SYNTAX     Hex (0..15)
   ACCESS     read-write
   STATUS     mandatory
   DESCRIPTION
     "This attribute specifies how the address field extension bits are set in 
      the frame header.  Consider the value to be a four bit binary number.  
      For example, 4 = 0100.  Only the first headerLength bits are used. 
      For instance, suppose headerLength is 3, then the appropriate 
      EABits is 2, or 0010.  This attribute can be used to create a header 
      of length greater than two bytes or to specify incorrect EABits in 
      the header."
   DEFVAL     { 4 }
::= { frUniLtsPatDefaultsEntry 205 }

frUniLtsPatDefaultPayloadPattern OBJECT-TYPE
   SYNTAX     HexString (SIZE (1..12))
   ACCESS     read-write
   STATUS     mandatory
   DESCRIPTION
     "This attribute specifies the payload of each frame.  The value 
      specified is in hexadecimal, where every two digits represent a byte.  
      A maximum of 24 digits (12 bytes) may be set, after which the 
      pattern will repeat in the payload (depending on repeatPattern 
      attribute). 
      NOTE: If a RFC 1490 header is specified, via the 1490Header 
      attribute, the specified pattern will begin following the header (i.e. 
      at the 9th byte in the payload)."
   DEFVAL     { '55'H }  -- "55"
::= { frUniLtsPatDefaultsEntry 206 }

frUniLtsPatDefaultRfc1490Header OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 n16(16),
                 n17(17),
                 none(18) }
   ACCESS     read-write
   STATUS     mandatory
   DESCRIPTION
     "This attribute specifies the appropriate RFC 1490 encapsulated 
      header of the frame.  A value of 0 indicates no 1490 header.
      NOTE: This header resides in the first 8 bytes of the payload.  If the 
      specified value is non-zero, then the payload pattern provisioned 
      will begin at the 9th byte."
   DEFVAL     { none }
::= { frUniLtsPatDefaultsEntry 207 }

frUniLtsPatDefaultUseBadLrc OBJECT-TYPE
   SYNTAX     INTEGER  {
                 no(0),
                 yes(1) }
   ACCESS     read-write
   STATUS     mandatory
   DESCRIPTION
     "This attribute specifies whether the frames from this pattern are to 
      have a bad LRC prior to being sent to the framer.  The LRC is 
      checked while the frame is being put onto the link and the failure 
      should cause an abort frame to be sent."
   DEFVAL     { no }
::= { frUniLtsPatDefaultsEntry 208 }

frUniLtsPatSetupTable OBJECT-TYPE
   SYNTAX     SEQUENCE OF FrUniLtsPatSetupEntry
   ACCESS     not-accessible
   STATUS     mandatory
   DESCRIPTION
     "This attribute group contains the specifications of the pattern."
::= { frUniLtsPat 11 }

frUniLtsPatSetupEntry OBJECT-TYPE
   SYNTAX     FrUniLtsPatSetupEntry
   ACCESS     not-accessible
   STATUS     mandatory
   DESCRIPTION
     "An entry in the frUniLtsPatSetupTable."
   INDEX {
      frUniIndex,
      frUniLtsIndex,
      frUniLtsPatIndex }
::= { frUniLtsPatSetupTable 1 }

FrUniLtsPatSetupEntry ::= SEQUENCE {
   frUniLtsPatDlci
      Unsigned32,
   frUniLtsPatNumFrames
      Unsigned32,
   frUniLtsPatDataSize
      Unsigned32,
   frUniLtsPatHeaderBits
      OCTET STRING,
   frUniLtsPatHeaderLength
      Unsigned32,
   frUniLtsPatEaBits
      Hex,
   frUniLtsPatPayloadPattern
      HexString,
   frUniLtsPatRfc1490Header
      INTEGER,
   frUniLtsPatUseBadLrc
      INTEGER }

frUniLtsPatDlci OBJECT-TYPE
   SYNTAX     Unsigned32 (16..1007)
   ACCESS     read-write
   STATUS     mandatory
   DESCRIPTION
     "This attribute specifies for which dlci (on the local end) the frames 
      are destined."
   DEFVAL     { 16 }
::= { frUniLtsPatSetupEntry 200 }

frUniLtsPatNumFrames OBJECT-TYPE
   SYNTAX     Unsigned32 (0..4294967295)
   ACCESS     read-write
   STATUS     mandatory
   DESCRIPTION
     "This attribute specifies the number of frames in this pattern.  This is 
      the number of frames of this type which will be generated in one 
      timeInterval."
   DEFVAL     { 100 }
::= { frUniLtsPatSetupEntry 201 }

frUniLtsPatDataSize OBJECT-TYPE
   SYNTAX     Unsigned32 (0..8200)
   ACCESS     read-write
   STATUS     mandatory
   DESCRIPTION
     "This attribute specifies the payload size of each frame in bytes.  
      This is in excess to the header."
   DEFVAL     { 512 }
::= { frUniLtsPatSetupEntry 202 }

frUniLtsPatHeaderBits OBJECT-TYPE
   SYNTAX     OCTET STRING (SIZE (1))
   ACCESS     read-write
   STATUS     mandatory
   DESCRIPTION
     "This attribute specifies whether the following bits are on/off in the 
      header of each frame. The following bits can be set:
      BeCn, C/R, De, FeCn

      Description of bits:
      becn(0)
      fecn(1)
      cr(2)
      de(3)"
::= { frUniLtsPatSetupEntry 203 }

frUniLtsPatHeaderLength OBJECT-TYPE
   SYNTAX     Unsigned32 (0 | 2..4)
   ACCESS     read-write
   STATUS     mandatory
   DESCRIPTION
     "This attribute specifies the size of the frame relay header in bytes.  
      Passport currently only supports a 2-byte header.  Valid values are 
      0, 2, 3, 4.  0 indicates to use no header.  That is, the frame will start 
      with either the payload or rfc1490 header."
   DEFVAL     { 2 }
::= { frUniLtsPatSetupEntry 204 }

frUniLtsPatEaBits OBJECT-TYPE
   SYNTAX     Hex (0..15)
   ACCESS     read-write
   STATUS     mandatory
   DESCRIPTION
     "This attribute specifies how the address field extension bits are set in 
      the frame header.  Consider the value to be a four bit binary number.  
      For example, 4 = 0100.  Only the first headerLength bits are used. 
      For instance, suppose headerLength is 3, then the appropriate eaBits 
      is 2, or 0010.  This attribute can be used to create a header of length 
      greater than two bytes or to specify incorrect eaBits in the header."
   DEFVAL     { 4 }
::= { frUniLtsPatSetupEntry 205 }

frUniLtsPatPayloadPattern OBJECT-TYPE
   SYNTAX     HexString (SIZE (1..12))
   ACCESS     read-write
   STATUS     mandatory
   DESCRIPTION
     "This attribute specifies the payload of each frame.  The value 
      specified is in hexadecimal, where every two digits represent a byte.  
      A maximum of 24 digits (12 bytes) may be set, after which the 
      pattern will repeat in the payload (depending on repeatPattern 
      attribute). 
      NOTE: If a RFC 1490 header is specified, via the 1490Header 
      attribute, the specified pattern will begin following the header (i.e. 
      at the 9th byte in the payload)."
   DEFVAL     { '55'H }  -- "55"
::= { frUniLtsPatSetupEntry 206 }

frUniLtsPatRfc1490Header OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 n16(16),
                 n17(17),
                 none(18) }
   ACCESS     read-write
   STATUS     mandatory
   DESCRIPTION
     "This attribute specifies the appropriate RFC 1490 encapsulated 
      header of the frame.  A value of 0 indicates no 1490 header.
      NOTE: This header resides in the first 8 bytes of the payload.  If the 
      specified value is non-zero, then the payload pattern provisioned 
      will begin at the 9th byte."
   DEFVAL     { none }
::= { frUniLtsPatSetupEntry 207 }

frUniLtsPatUseBadLrc OBJECT-TYPE
   SYNTAX     INTEGER  {
                 no(0),
                 yes(1) }
   ACCESS     read-write
   STATUS     mandatory
   DESCRIPTION
     "This attribute specifies whether the frames from this pattern are to 
      have a bad LRC prior to being sent to the framer.  The LRC is 
      checked while the frame is being put onto the link and the failure 
      should cause an abort frame to be sent."
   DEFVAL     { no }
::= { frUniLtsPatSetupEntry 208 }

frUniLtsPatOpDataTable OBJECT-TYPE
   SYNTAX     SEQUENCE OF FrUniLtsPatOpDataEntry
   ACCESS     not-accessible
   STATUS     mandatory
   DESCRIPTION
     "This group contains the operational attributes which allow changing 
      the pattern outside of provisioning mode."
::= { frUniLtsPat 12 }

frUniLtsPatOpDataEntry OBJECT-TYPE
   SYNTAX     FrUniLtsPatOpDataEntry
   ACCESS     not-accessible
   STATUS     mandatory
   DESCRIPTION
     "An entry in the frUniLtsPatOpDataTable."
   INDEX {
      frUniIndex,
      frUniLtsIndex,
      frUniLtsPatIndex }
::= { frUniLtsPatOpDataTable 1 }

FrUniLtsPatOpDataEntry ::= SEQUENCE {
   frUniLtsPatFramePattern
      HexString,
   frUniLtsPatHdlcBitsInserted
      Unsigned32 }

frUniLtsPatFramePattern OBJECT-TYPE
   SYNTAX     HexString (SIZE (20..24))
   ACCESS     read-only
   STATUS     mandatory
   DESCRIPTION
     "This attribute displays the first 20 to 24 bytes of the frame payload, 
      depending on the frame relay header size selected.  This attribute 
      represents the frame if it were at least 20 to 24 bytes in size.  That 
      is, the actual frame may be smaller."
::= { frUniLtsPatOpDataEntry 200 }

frUniLtsPatHdlcBitsInserted OBJECT-TYPE
   SYNTAX     Unsigned32 (0..65535)
   ACCESS     read-only
   STATUS     mandatory
   DESCRIPTION
     "This attribute displays how many times a zero bit will be inserted 
      after 5 consecutive 1 bits when a frame from this pattern is sent out."
::= { frUniLtsPatOpDataEntry 201 }

frUniLtsPatOpStateTable OBJECT-TYPE
   SYNTAX     SEQUENCE OF FrUniLtsPatOpStateEntry
   ACCESS     not-accessible
   STATUS     mandatory
   DESCRIPTION
     "This group contains the attributes containing the operational 
      statistics of the pattern."
::= { frUniLtsPat 13 }

frUniLtsPatOpStateEntry OBJECT-TYPE
   SYNTAX     FrUniLtsPatOpStateEntry
   ACCESS     not-accessible
   STATUS     mandatory
   DESCRIPTION
     "An entry in the frUniLtsPatOpStateTable."
   INDEX {
      frUniIndex,
      frUniLtsIndex,
      frUniLtsPatIndex }
::= { frUniLtsPatOpStateTable 1 }

FrUniLtsPatOpStateEntry ::= SEQUENCE {
   frUniLtsPatLoad
      FixedPoint3,
   frUniLtsPatStatus
      INTEGER }

frUniLtsPatLoad OBJECT-TYPE
   SYNTAX     FixedPoint3 (0..4294967295)
   ACCESS     read-only
   STATUS     mandatory
   DESCRIPTION
     "This attribute indicates the load due to this particular pattern.  The 
      loads associated with all of the provisioned patterns are summed to 
      arrive at the FrLts load."
::= { frUniLtsPatOpStateEntry 200 }

frUniLtsPatStatus OBJECT-TYPE
   SYNTAX     INTEGER  {
                 enabled(0),
                 disabled(1) }
   ACCESS     read-write
   STATUS     mandatory
   DESCRIPTION
     "This attributes specifies the administrative state of the pattern.  A 
      disabled pattern will not be generated, although it can still be 
      triggered."
   DEFVAL     { enabled }
::= { frUniLtsPatOpStateEntry 201 }




-- 
-- Version and Compliance statements
-- 



-- Object-Group Statement:
-- A list of all current accessible leaf objects.

-- OBJECTS { frUniFramerOperationalState,
--           frUniSigIFramesTransmitted,
--           frUniSigLastCauseInStatusMsgReceived,
--           frUniSigLastClearRemoteDataNetworkAddress,
--           frUniDlciLbRemoteDeBytes,
--           frUniLtsPatFramePattern,
--           frUniDnaDefaultTransferPriority,
--           frUniFramerFrmModeErrors,
--           frUniDlciEirEgressSegFrm,
--           frUniSigMaximumAggregateSvcEirNormalQ,
--           frUniVFramerOperationalState,
--           frUniLmiProtocolStatus,
--           frUniDlciVcPriority,
--           frUniLtsCycleIncomplete,
--           frUniIfIndex,
--           frUniDlciBecnFrmSetByService,
--           frUniDlciDiscDeCongestedToIf,
--           frUniFramerLrcErrors,
--           frUniSigCallProceedingTimer,
--           frUniDnaStorageType,
--           frUniLmiFullStatusEnqToIf,
--           frUniDlciStartTime,
--           frUniLmiRowStatus,
--           frUniDlciLbStorageType,
--           frUniFramerAborts,
--           frUniDlciLbLocalTotalBytes,
--           frUniDlciABitStatusToIf,
--           frUniDlciEmissionPriorityToIf,
--           frUniSigIdleProbeTimer,
--           frUniDlciVcSendSequenceNumber,
--           frUniLtsDuration,
--           frUniSigCurrentAggregateSvcCirNormalQ,
--           frUniDnaHgMHgAddrStorageType,
--           frUniLtsPatNumFrames,
--           frUniSigX213IeHandling,
--           frUniSigReceiveRejectFrame,
--           frUniLmiUsageState,
--           frUniDlciSpRaSensitivity,
--           frUniDlciSpRowStatus,
--           frUniDnaEgressAccounting,
--           frUniDlciVcStartTime,
--           frUniAlarmStatus,
--           frUniDlciABitReasonToIf,
--           frUniLtsGeneratorState,
--           frUniDlciDcType,
--           frUniDlciDiscFrameAbit,
--           frUniLtsPatDefaultRfc1490Header,
--           frUniDnaHgMAvailabilityDelta,
--           frUniDlciBciToSubnet,
--           frUniDlciDcDataPath,
--           frUniDlciDiscCongestedToIf,
--           frUniSigRemoteBusy,
--           frUniLtsPatComponentName,
--           frUniDlciDeFrmToIf,
--           frUniLmiOperationalState,
--           frUniDnaCugComponentName,
--           frUniDlciVcEmissionPriorityToNetwork,
--           frUniLmiKeepAliveStatusToIf,
--           frUniDnaDataPath,
--           frUniFramerOctetFromIf,
--           frUniLmiUserSideEventHistory,
--           frUniDlciDiscDeCongestedFromIfBytes,
--           frUniDlciDiscByteAbit,
--           frUniLtsPatLoad,
--           frUniDlciDcRemoteDna,
--           frUniDlciVcCalledNpi,
--           frUniLmiMessageCountTimer,
--           frUniSigQualityOfServiceNotAvailable,
--           frUniSigCurrentAggregateSvcEirNormalQ,
--           frUniDlciSpMeasurementInterval,
--           frUniSigDefaultExcessBurstSize,
--           frUniVFramerAdminState,
--           frUniLmiNoStatusReportCount,
--           frUniVFramerStorageType,
--           frUniDlciProceduralStatus,
--           frUniDlciLbLocalTotalFrm,
--           frUniFramerOverruns,
--           frUniSigIFramesTxDiscarded,
--           frUniDlciTotalEgressBytes,
--           frUniDlciBytesToIf,
--           frUniSigLastDlciWithMsgBlockCongestion,
--           frUniDnaHgMAvailableDlcis,
--           frUniNumberOfEmissionQs,
--           frUniSigDisconnectTimer,
--           frUniDnaCugPreferential,
--           frUniLmiSequenceErrors,
--           frUniDlciLbRowStatus,
--           frUniLtsPatRfc1490Header,
--           frUniDlciMeasurementInterval,
--           frUniLtsPatHdlcBitsInserted,
--           frUniDlciVcRowStatus,
--           frUniVFramerOctetFromOtherVFramer,
--           frUniDlciDiscCongestedFromIfBytes,
--           frUniSigStateChange,
--           frUniDlciAdminState,
--           frUniFramerFrmToIf,
--           frUniDlciVcRcosToNetwork,
--           frUniDlciEirIngressBytes,
--           frUniDnaHgMComponentName,
--           frUniSigProtocolErrors,
--           frUniLmiStatusSequenceErrors,
--           frUniDlciVcNotDataXferFromSubnet,
--           frUniDlciCallReferenceNumber,
--           frUniDlciLbRemoteDeFrm,
--           frUniSigLastStateInStatusMsgReceived,
--           frUniDnaAccountClass,
--           frUniDlciVcAccountingEnabled,
--           frUniSigDefaultAccounting,
--           frUniDlciFrmToIf,
--           frUniDlciEirEgressBytes,
--           frUniLmiProtocolErrors,
--           frUniDlciSpStorageType,
--           frUniDlciVcNotDataXferToSubnet,
--           frUniDlciFecnFrmFromIf,
--           frUniDlciVcSegmentsRx,
--           frUniDlciVcCalledLcn,
--           frUniSigMaximumAggregateSvcCirNormalQ,
--           frUniSigDefaultCommittedBurstSize,
--           frUniSigCurrentAggregateSvcEirHighQ,
--           frUniLmiEventCount,
--           frUniDlciAvailabilityStatus,
--           frUniLtsPatEaBits,
--           frUniLtsPatDefaultDataSize,
--           frUniLmiCheckPointTimer,
--           frUniDlciUnknownStatus,
--           frUniDlciStandbyStatus,
--           frUniDlciDcStorageType,
--           frUniAvailabilityStatus,
--           frUniSigSetupTimeout,
--           frUniDnaCugRowStatus,
--           frUniComponentName,
--           frUniSnmpOperStatus,
--           frUniLmiSide,
--           frUniFramerNormPrioLinkUtilToIf,
--           frUniVFramerComponentName,
--           frUniLtsPatStorageType,
--           frUniDlciErrorShortBytesFromIf,
--           frUniLtsPatDefaultUseBadLrc,
--           frUniSigMaximumAggregateSvcEirHighQ,
--           frUniLtsStorageType,
--           frUniLmiLinkVerificationTimer,
--           frUniDlciVcPeakOoSeqByteCount,
--           frUniDlciErrorShortFrmFromIf,
--           frUniSigMaximumAggregateSvcCirHighQ,
--           frUniDlciDcDeDiscardPriority,
--           frUniDlciCommittedBurstSize,
--           frUniFramerCrcErrors,
--           frUniDlciQ933CallReference,
--           frUniLmiUnexpectedReports,
--           frUniDlciSpRateAdaptation,
--           frUniDlciVcDiagnosticCode,
--           frUniDnaHgMAvailabilityUpdateThreshold,
--           frUniLtsPatDefaultHeaderLength,
--           frUniSigAdminState,
--           frUniSigOutCalls,
--           frUniSigDefaultMaximumFrameSize,
--           frUniLtsPatDefaultNumFrames,
--           frUniSigNetworkType,
--           frUniFramerAdminState,
--           frUniDlciVcCallingLcn,
--           frUniDlciDcRemoteNpi,
--           frUniDlciSpRateEnforcement,
--           frUniLmiAsyncStatusReport,
--           frUniControlStatus,
--           frUniFramerLargeFrmErrors,
--           frUniSigLastStateChangeReason,
--           frUniFrmToIfByQueueValue,
--           frUniSigMaximumFrameSize,
--           frUniDlciLbComponentName,
--           frUniDlciDiscardedSegFrm,
--           frUniSigLastClearCause,
--           frUniDnaHgMHgAddrComponentName,
--           frUniDlciLbLocalBecnFrm,
--           frUniDlciVcType,
--           frUniRowStatus,
--           frUniLtsPatHeaderBits,
--           frUniDlciDiscDeCongestedFromIf,
--           frUniDlciDcRemoteDlci,
--           frUniSigMaximumAggregateSvcCirInterruptQ,
--           frUniDlciVcFrmLossTimeouts,
--           frUniSigStorageType,
--           frUniDlciDcDiscardPriority,
--           frUniFramerNonOctetErrors,
--           frUniDnaHgMMaximumAvailableAggregateCir,
--           frUniSigFrmrReceive,
--           frUniDnaOutAccess,
--           frUniDlciVcOoSeqPktCntExceeded,
--           frUniDlciVcPeakRetryQueueSize,
--           frUniSigCallSetupTimer,
--           frUniUsageState,
--           frUniDlciBciFromSubnet,
--           frUniVFramerLogicalProcessor,
--           frUniDlciDcTransferPriority,
--           frUniFramerStorageType,
--           frUniLtsBitRateTx,
--           frUniLmiStorageType,
--           frUniDlciVcOutOfRangeFrmFromSubnet,
--           frUniLmiKeepAliveStatusEnqFromIf,
--           frUniDlciDiscExcessFromIf,
--           frUniDlciExcessBurstSize,
--           frUniLtsPatRowStatus,
--           frUniDlciOperationalState,
--           frUniDlciEirPresent,
--           frUniLmiFullStatusToIf,
--           frUniLtsPatStatus,
--           frUniSigUnlimitedAggregateEir,
--           frUniDlciSpExcessBurstSize,
--           frUniOperationalState,
--           frUniLtsPatPayloadPattern,
--           frUniSigLastQ933StateReceivedStatus,
--           frUniDlciVcComponentName,
--           frUniDnaDataNetworkAddress,
--           frUniSigLastDlciReceivedStatus,
--           frUniDnaAccountCollection,
--           frUniDlciVcFastSelectCall,
--           frUniSigRateEnforcement,
--           frUniLtsPatUseBadLrc,
--           frUniDlciTotalIngressBytes,
--           frUniDnaCugType,
--           frUniDlciVcDmepValue,
--           frUniDnaHgMHgAddrDataNetworkAddress,
--           frUniDlciAlarmStatus,
--           frUniDnaOutDefaultPriority,
--           frUniDnaOutDefaultPathReliability,
--           frUniDlciVcPathReliability,
--           frUniDlciVcCannotForwardToSubnet,
--           frUniDlciSpMaximumFrameSize,
--           frUniSigCurrentAggregateSvcEirInterruptQ,
--           frUniDlciStorageType,
--           frUniDnaHgMAvailableAggregateCir,
--           frUniDlciCallType,
--           frUniDnaIncAccess,
--           frUniDlciDiscDeCongestedToIfBytes,
--           frUniDlciVcCallReferenceNumber,
--           frUniDlciFciFromSubnet,
--           frUniSigAckDelayTimer,
--           frUniSigCurrentState,
--           frUniLtsRowStatus,
--           frUniLtsPatDefaultEABits,
--           frUniLtsFrameRateTx,
--           frUniDlciCirPresent,
--           frUniSigDefaultCommittedInformationRate,
--           frUniLmiNetworkSideEventHistory,
--           frUniLtsElapsedGenerationTime,
--           frUniDnaRowStatus,
--           frUniDlciDiscCongestedToIfBytes,
--           frUniDlciRateAdaptReduct,
--           frUniSigOperationalState,
--           frUniLtsPatHeaderLength,
--           frUniDlciElapsedDifference,
--           frUniLtsComponentName,
--           frUniFramerFlagsBetweenFrames,
--           frUniDlciSpCommittedInformationRate,
--           frUniDlciDcRowStatus,
--           frUniLtsPatDefaultPayloadPattern,
--           frUniLmiPvcConfigParmsInFsr,
--           frUniLmiAdminState,
--           frUniDlciSpUpdateBCI,
--           frUniDnaHgMHgAddrRowStatus,
--           frUniDnaTransferPriorityOverRide,
--           frUniDlciTransferPriToNwk,
--           frUniSigCurrentAggregateSvcCirInterruptQ,
--           frUniDlciSpCommittedBurstSize,
--           frUniDlciSpComponentName,
--           frUniDnaCugInterlockCode,
--           frUniLtsFramesTx,
--           frUniDnaNumberingPlanIndicator,
--           frUniDnaServiceExchange,
--           frUniDlciVcStorageType,
--           frUniDlciSpAccounting,
--           frUniVFramerRowStatus,
--           frUniLmiFullStatusEnqFromIf,
--           frUniSigHighestPvcDlci,
--           frUniSigInCallsRefused,
--           frUniDlciFecnFrmToIf,
--           frUniDlciCommittedInformationRate,
--           frUniDnaCugOutCalls,
--           frUniDlciBecnFrmFromIf,
--           frUniDlciABitStatusFromIf,
--           frUniDnaHgMHgAddrNumberingPlanIndicator,
--           frUniDlciDcComponentName,
--           frUniLmiIgnoreActiveBit,
--           frUniDlciDiscardedBytes,
--           frUniDlciVcElapsedTimeTillNow,
--           frUniDlciComponentName,
--           frUniProceduralStatus,
--           frUniSigAckTimer,
--           frUniOctetToIfByQueueValue,
--           frUniDlciLbRemoteFecnFrm,
--           frUniLtsPatDlci,
--           frUniDlciABitReasonFromIf,
--           frUniDlciVcPreviousState,
--           frUniFramerComponentName,
--           frUniSigRaSensitivity,
--           frUniDlciVcPeakOoSeqPktCount,
--           frUniDlciLbLocalDeBytes,
--           frUniDlciDeBytesFromIf,
--           frUniSigRowStatus,
--           frUniLtsPatDefaultHeaderBits,
--           frUniDlciDiscCongestedFromIf,
--           frUniFramerUnderruns,
--           frUniLtsBurstSize,
--           frUniDlciDeFrmFromIf,
--           frUniDlciVcPreviousDiagnosticCode,
--           frUniSigLastDiagnosticCode,
--           frUniDlciVcEmissionPriorityFromNetwork,
--           frUniSigCurrentQueueSize,
--           frUniDlciVcCallingNpi,
--           frUniSigLastTimeMsgBlockCongested,
--           frUniVFramerUsageState,
--           frUniSigDefaultLocCheck,
--           frUniDnaCugStorageType,
--           frUniLtsAlgorithm,
--           frUniSigComponentName,
--           frUniLmiUnexpectedIes,
--           frUniVFramerOtherVirtualFramer,
--           frUniDlciVcCallingDna,
--           frUniSigIFramesReceived,
--           frUniDlciExcessBytesFromIf,
--           frUniSigRateAdaptation,
--           frUniDnaCugIncCalls,
--           frUniDlciMaximumFrameSize,
--           frUniLtsPatDataSize,
--           frUniDlciVcFrmCongestedToSubnet,
--           frUniDlciExcessFrmFromIf,
--           frUniDlciLocalRateAdaptOccurred,
--           frUniDlciAccounting,
--           frUniLtsTimeInterval,
--           frUniLmiPollingVerifTimeouts,
--           frUniSigCurrentNumberOfSvcCalls,
--           frUniDlciVcPeakOoSeqFrmForwarded,
--           frUniSigIFramesRcvdDiscarded,
--           frUniDlciLbRemoteTotalBytes,
--           frUniDlciBytesFromIf,
--           frUniDlciBecnFrmToIf,
--           frUniInvalidHeaderFramesFromIf,
--           frUniDlciDcCugIndex,
--           frUniDlciLbRemoteTotalFrm,
--           frUniDlciFrmFromIf,
--           frUniLtsLoad,
--           frUniLmiKeepAliveEnqToIf,
--           frUniDlciLbRemoteBecnFrm,
--           frUniDlciVcMaxSubnetPktSize,
--           frUniSigReleaseTimer,
--           frUniSigMaximumAggregateSvcEirInterruptQ,
--           frUniLtsPatDefaultDlci,
--           frUniSigAckTimeout,
--           frUniLmiComponentName,
--           frUniLmiErrorEventThreshold,
--           frUniLastUnknownDlci,
--           frUniFramerFrmFromIf,
--           frUniDlciVcRcosFromNetwork,
--           frUniUnknownStatus,
--           frUniStandbyStatus,
--           frUniLmiProcedures,
--           frUniDlciVcDuplicatesFromSubnet,
--           frUniSigCurrentAggregateSvcCirHighQ,
--           frUniStorageType,
--           frUniDlciRateAdaptReductPeriod,
--           frUniDlciControlStatus,
--           frUniDnaHgMStorageType,
--           frUniLtsBytesTx,
--           frUniDnaCugDnic,
--           frUniDnaComponentName,
--           frUniSigRetransmitLimit,
--           frUniDlciTotalIngressSegFrm,
--           frUniDlciQ933CallState,
--           frUniLmiFullStatusPollingCycles,
--           frUniDlciVcCalledDna,
--           frUniDlciRowStatus,
--           frUniDlciLbLocalFecnFrm,
--           frUniDlciVcOoSeqByteCntExceeded,
--           frUniDlciTransferPriFromNwk,
--           frUniDlciErrorLongBytesFromIf,
--           frUniDnaHgMRowStatus,
--           frUniAdminState,
--           frUniDlciVcPktRetryTimeouts,
--           frUniFramerRowStatus,
--           frUniDlciErrorLongFrmFromIf,
--           frUniDlciDcCugType,
--           frUniLtsLastActiveInterval,
--           frUniDlciTotalEgressSegFrm,
--           frUniDlciUsageState,
--           frUniDlciVcState,
--           frUniIfAdminStatus,
--           frUniVFramerFrmFromOtherVFramer,
--           frUniSigOutCallsFailed,
--           frUniDlciVcCombErrorsFromSubnet,
--           frUniCustomerIdentifier,
--           frUniDlciVcSegmentsSent,
--           frUniDlciVcAccountingEnd,
--           frUniSigInCalls,
--           frUniDlciVcDataPath,
--           frUniFramerUsageState,
--           frUniLmiOpProcedures,
--           frUniFramerNormPrioLinkUtilFromIf,
--           frUniVFramerFrmToOtherVFramer,
--           frUniDlciDeBytesToIf,
--           frUniSigWindowSize,
--           frUniDlciEirIngressSegFrm,
--           frUniDlciLbLocalDeFrm,
--           frUniSigUpdateBCI,
--           frUniFramerInterfaceName,
--           frUniDlciDiscExcessFromIfBytes,
--           frUniDlciVcSubnetRecoveries,
--           frUniDlciVcSegmentSize,
--           frUniDlciLoopbackState,
--           frUniUnknownDlciFramesFromIf,
--           frUniSigUsageState }
-- STATUS  mandatory
-- DESCRIPTION
--   "A list of all current accessible leaf objects."

frameRelayUniGroup OBJECT IDENTIFIER ::= { frameRelayUniMIB 1 }
frameRelayUniGroupBE OBJECT IDENTIFIER ::= { frameRelayUniGroup 5 }
frameRelayUniGroupBE01 OBJECT IDENTIFIER ::= { frameRelayUniGroupBE 2 }
frameRelayUniGroupBE01A OBJECT IDENTIFIER ::= { frameRelayUniGroupBE01 2 }



-- Agent-Capabilities Statement:

-- PRODUCT-RELEASE "Passport Release 7.0 FrameRelayUni."
-- STATUS          mandatory
-- DESCRIPTION     "FrameRelayUni MIB: MIB Version BE01A,
--                  Software Version BG00S4C."
-- SUPPORTS        Nortel-Magellan-Passport-FrameRelayUniMIB
--    INCLUDES     { frameRelayUniGroupBE01A }

frameRelayUniCapabilities OBJECT IDENTIFIER ::= { frameRelayUniMIB 3 }
frameRelayUniCapabilitiesBE OBJECT IDENTIFIER ::= { frameRelayUniCapabilities 5 }
frameRelayUniCapabilitiesBE01 OBJECT IDENTIFIER ::= { frameRelayUniCapabilitiesBE 2 }
frameRelayUniCapabilitiesBE01A OBJECT IDENTIFIER ::= { frameRelayUniCapabilitiesBE01 2 }





END
