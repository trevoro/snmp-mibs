-- ******************************************************************
--           Secure Computing Corporation Enterprise MIB
-- ******************************************************************
--
-- Title		SCC-MIB
-- Purpose:		This MIB defines the top-level structure of the 
-- 			SCC Enterprise Object Identifiers. This MIB module  
-- 			needs to be included when compiling other SCC 
--			Enterprise MIBs.
-- Required MIBs	rfc-1155.
-- Revision:		1.2
-- Date:		Nov. 17, 1997
--
-- SCC Support Contact:	1-800-700-8328
-- 			support@sctc.com
--
-- Version Description: 
-- 		v1.0:	Initial version of this MIB module.
--              v1.1:   Updated version to support scc-sw-mib.
--              v1.2:   Included bfs and titansecurezone.

SCC-MIB DEFINITIONS ::= BEGIN

IMPORTS
	enterprises
		FROM RFC1155-SMI;


-- 	scc is the root of the SCC MIB tree.

scc			OBJECT IDENTIFIER ::= { enterprises 1573 }


-- 	sccExperiment is reserved for proprietary MIB development usage.
--
-- 	sccProducts is the root Object Identifier from which 
--	sysObjectID values are assigned.
--
-- 	sccMibs is the subtree which contains the definitions of
-- 	the SCC prorietary MIBs. 

--      The Borderware Firewall Server does not currently support SNMP.
--      It's placed in the products and MIBs trees "just in case".


sccExperiment		OBJECT IDENTIFIER ::= { scc 1 }
sccProducts		OBJECT IDENTIFIER ::= { scc 2 }
sccMibs			OBJECT IDENTIFIER ::= { scc 3 }

sccSidewinder		OBJECT IDENTIFIER ::= { sccProducts 1 }
sccSns			OBJECT IDENTIFIER ::= { sccProducts 2 }
sccBfs 			OBJECT IDENTIFIER ::= { sccProducts 3 }
sccSecureZone           OBJECT IDENTIFIER ::= { sccProducts 4 }


--      sccMibSw defines the Sidewinder management objects.
--      sccMibSns defines the SNS management objects.
--      sccMibSecureZone defines the Secure Zone management objects.

sccMibSw		OBJECT IDENTIFIER ::= { sccMibs 1 }
-- sccMibSns		OBJECT IDENTIFIER ::= { sccMibs 2 }
-- sccMibBfs		OBJECT IDENTIFIER ::= { sccMibs 3 }
sccMibSecureZone	OBJECT IDENTIFIER ::= { sccMibs 4 }


END
