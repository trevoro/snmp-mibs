--------------------------------------------------------------------------
-- Copyright (c) 2000,2001,2006,2007 All rights reserved by
--
-- EMC Corporation
-- 171 South Street
-- Hopkinton, MA 01748 USA
--
-- This software is furnished under a license and may be used and copied
-- inclusion of the above copyright notice. This software or any other
-- only in accordance with the terms of such license and with the
-- copies thereof may not be provided or otherwise made available to any
-- other person. No title to and ownership of the software is hereby
-- transferred.
--
-- The information in this software is subject to change without notice
-- and should not be construed as a commitment by EMC Corporation.
--
-- EMC Corporation assumes no responsibility for the use or reliability
-- of this software.
--
----------------------------------------------------------------------------
--
-- EMC Gateway Management Information Base description
--
----------------------------------------------------------------------------
----------------------------------------------------------------------------
--
-- Author Identification
--
-- JDS John D. Sullivan, EMC
-- JCE John C. Ehn, EMC
--
----------------------------------------------------------------------------
--
--
-- 000 JDS 09-15-2000 Created Original Module
-- 001 JCE 07-14-2006 Added Imports for FCMGMT-MIB, Trap-Types
-- 002 JCE 08-21-2007 Added eccUnitDeletedTrap
--
---------------------------------------------------------------------------- 
EMCGATEWAY-MIB
DEFINITIONS ::= BEGIN
IMPORTS
enterprises
FROM RFC1155-SMI
OBJECT-TYPE
FROM RFC-1212 
TRAP-TYPE
FROM RFC-1215
connUnitId, connUnitEventId, connUnitEventType, connUnitEventObject,
connUnitEventSeverity, connUnitName, connUnitType,
connUnitEventDescr, connUnitStatus, connUnitState
FROM FCMGMT-MIB;
--Textual conventions for this MIB

DisplayString ::=
OCTET STRING
-- This data type is used to model textual information taken
-- from the NVT ASCII character set. By convention, objects
-- with this syntax are declared as having
--
-- SIZE (0..255)
emc OBJECT IDENTIFIER ::= { enterprises 1139 }
eccGateway OBJECT IDENTIFIER ::= { emc 3 }
eccGatewayRevision OBJECT-TYPE
SYNTAX DisplayString (SIZE (4))
ACCESS read-only
STATUS mandatory
DESCRIPTION
"This is the revision number for this MIB. The
format of the revision value is as follows
(0) = high order major revision number
(1) = low order major revision number
(2) = high order minor revision number
(3) = low order minor revision number
"
::= { eccGateway 1 }

eccUnitStatusChange TRAP-TYPE
ENTERPRISE eccGateway
VARIABLES { connUnitStatus,
connUnitState,
connUnitName,
connUnitType }
DESCRIPTION
"The overall status of the ControlCenter-monitored
device has changed.
Recommended severity level (for filtering): alert"
::= 1
eccUnitDeletedTrap TRAP-TYPE
ENTERPRISE eccGateway
VARIABLES { connUnitId,
connUnitName }
DESCRIPTION
"A ControlCenter-monitored device has been deleted from the Console.
Recommended severity level (for filtering): warning"
::= 3
eccUnitEventTrap TRAP-TYPE
ENTERPRISE eccGateway
VARIABLES { connUnitEventId,
connUnitEventType,
connUnitEventObject,
connUnitEventDescr,
connUnitEventSeverity,
connUnitName,
connUnitType }
DESCRIPTION
"An event has been generated by the
ControlCenter-monitored device.
Recommended severity level (for filtering): info"
::= 4
END
