-- This file is corresponding to Release 6.1.2.100 from 2001/09/26 00:00:00
-- (C)opyright 1991-1999 BinTec Communications AG, All Rights Reserved
--  $RCSfile: mibbipx,v $ 
-- $Revision: 1.7 $ 

BIANCA-BRICK-IPX-MIB DEFINITIONS ::= BEGIN

    IMPORTS
		DisplayString FROM SNMPv2-TC
	Counter
	    FROM RFC1155-SMI

	OBJECT-TYPE
	    FROM RFC-1212;

    org         OBJECT IDENTIFIER ::= { iso 3 }
    dod         OBJECT IDENTIFIER ::= { org 6 }
    internet    OBJECT IDENTIFIER ::= { dod 1 }
    private     OBJECT IDENTIFIER ::= { internet 4 }
    enterprises OBJECT IDENTIFIER ::= { private 1 }
    bintec      OBJECT IDENTIFIER ::= { enterprises 272 }
    bibo        OBJECT IDENTIFIER ::= { bintec 4 }
    biboipx     OBJECT IDENTIFIER
	::= { bibo 9 }

    -- Management Information for the IPX Subsystem of the BIANCA/BRICK

    ipxClientTable OBJECT-TYPE
	SYNTAX SEQUENCE OF IPXClientEntry
	ACCESS not-accessible
	STATUS mandatory
	DESCRIPTION
	    "Each entry describes a client that has connected 
	     via WAN 2"
	::= { biboipx 1 }

    ipxClientEntry OBJECT-TYPE
	SYNTAX IPXClientEntry
	ACCESS not-accessible
	STATUS mandatory
	DESCRIPTION ""
	INDEX {
	    ipxClientCircIndex
	}
	::= { ipxClientTable 1 }

    IPXClientEntry ::=
	SEQUENCE {
	    ipxClientNode      OCTET STRING,
	    ipxClientCircIndex INTEGER,
	    ipxClientReconns   Counter
	}

    ipxClientNode OBJECT-TYPE
	SYNTAX OCTET STRING (SIZE(6))
	ACCESS read-only
	STATUS mandatory
	DESCRIPTION "The dynamically assigned Node Id of the client"
	::= { ipxClientEntry 1 }

    ipxClientCircIndex OBJECT-TYPE
	SYNTAX INTEGER
	ACCESS read-only
	STATUS mandatory
	DESCRIPTION "The dynamically assigned Network Number of the client"
	::= { ipxClientEntry 2 }

    ipxClientReconns OBJECT-TYPE
	SYNTAX Counter
	ACCESS read-only
	STATUS mandatory
	DESCRIPTION "The number of reconnections"
	::= { ipxClientEntry 3 }



    ipxAllowTable OBJECT-TYPE
	SYNTAX SEQUENCE OF IPXAllowEntry
	ACCESS not-accessible
	STATUS mandatory
	DESCRIPTION
	    "Each entry describes  a rule for filtering
	     IPX packets. Only IPX packets matching all of those
	     rules will be delivered."
	::= { biboipx 2 }
	
    ipxAllowEntry OBJECT-TYPE
	SYNTAX IPXAllowEntry
	ACCESS not-accessible
	STATUS mandatory
	DESCRIPTION
	    ""
	INDEX {
	    ipxAllowPktTypeMode,
	    ipxAllowSrcIfIndexMode
	}
	::= { ipxAllowTable 1 }

    IPXAllowEntry ::=
	SEQUENCE {
	    ipxAllowPktTypeMode	    INTEGER,
	    ipxAllowPktType	    INTEGER,
	    ipxAllowDstIfStatus     INTEGER,
	    ipxAllowDstNetMode	    INTEGER,
	    ipxAllowDstNet	    INTEGER,
	    ipxAllowDstNodeMode     INTEGER,
	    ipxAllowDstNode	    OCTET STRING,
	    ipxAllowDstSockMode	    INTEGER,
	    ipxAllowDstSock	    INTEGER,
	    ipxAllowSrcIfIndexMode  INTEGER, 
	    ipxAllowSrcIfIndex	    INTEGER,
	    ipxAllowSrcNetMode	    INTEGER,
	    ipxAllowSrcNet	    INTEGER,
	    ipxAllowSrcNodeMode     INTEGER,
	    ipxAllowSrcNode	    OCTET STRING,
	    ipxAllowSrcSockMode	    INTEGER,
	    ipxAllowSrcSock	    INTEGER
	}

    ipxAllowPktTypeMode OBJECT-TYPE
	SYNTAX INTEGER { dont-verify(1), verify(2), delete(3) }
	ACCESS read-write
	STATUS mandatory
	DESCRIPTION 
	    "The IPX packet type will be checked if this field
	    is set to 'verify'"
    ::= { ipxAllowEntry 1 }

    ipxAllowPktType OBJECT-TYPE
	SYNTAX INTEGER {
	    unknown(256),
	    rip(1),
	    sap(4),
	    spx(5),
	    ncp(17),
	    netbios(20)
	}
	ACCESS read-write
	STATUS mandatory
	DESCRIPTION 
	    "The various IPX packet types"
    ::= { ipxAllowEntry 2 }

    ipxAllowDstIfStatus OBJECT-TYPE
	SYNTAX INTEGER { dont-verify(1), up(2) }
	ACCESS read-write
	STATUS mandatory
	DESCRIPTION
	    "Set this value to 'up', if packets should only be forwarded
	     to active (dialup-)links"
    ::= { ipxAllowEntry 3 }

    ipxAllowDstNetMode OBJECT-TYPE
	SYNTAX INTEGER { dont-verify(1), verify(2) }
	ACCESS read-write
	STATUS mandatory
	DESCRIPTION 
	    "The IPX destination network address will be checked if
	    this field is set to 'verify'"
    ::= { ipxAllowEntry 4 }

    ipxAllowDstNet OBJECT-TYPE
	SYNTAX INTEGER
	ACCESS read-write
	STATUS mandatory
	DESCRIPTION 
	    "The IPX destination network address"
    ::= { ipxAllowEntry 5 }

    ipxAllowDstNodeMode OBJECT-TYPE
	SYNTAX INTEGER { dont-verify(1), verify(2) }
	ACCESS read-write
	STATUS mandatory
	DESCRIPTION 
	    "The IPX destination node address will be checked if
	    this field is set to 'verify'"
    ::= { ipxAllowEntry 6 }

    ipxAllowDstNode OBJECT-TYPE
	SYNTAX OCTET STRING (SIZE(6))
	ACCESS read-write
	STATUS mandatory
	DESCRIPTION 
	    "The IPX destination node address"
    ::= { ipxAllowEntry 7 }

    ipxAllowDstSockMode OBJECT-TYPE
	SYNTAX INTEGER { dont-verify(1), verify(2) }
	ACCESS read-write
	STATUS mandatory
	DESCRIPTION 
	    "The IPX destination socket number will be checked if
	    this field is set to 'verify'"
    ::= { ipxAllowEntry 8 }

    ipxAllowDstSock OBJECT-TYPE
	SYNTAX INTEGER
	ACCESS read-write
	STATUS mandatory
	DESCRIPTION 
	    "The destination socket"
    ::= { ipxAllowEntry 9 }

    ipxAllowSrcIfIndexMode OBJECT-TYPE
	SYNTAX INTEGER { dont-verify(1), verify(2) }
	ACCESS read-write
	STATUS mandatory
	DESCRIPTION 
	    "The index of the receiving interface will be checked if
	    this field is set to 'verify'"
    ::= { ipxAllowEntry 10 }

    ipxAllowSrcIfIndex OBJECT-TYPE
	SYNTAX INTEGER
	ACCESS read-write
	STATUS mandatory
	DESCRIPTION 
	    "The index of the receiving interface"
    ::= { ipxAllowEntry 11 }

    ipxAllowSrcNetMode OBJECT-TYPE
	SYNTAX INTEGER { dont-verify(1), verify(2) }
	ACCESS read-write
	STATUS mandatory
	DESCRIPTION 
	    "The IPX source network address will be checked if
	    this field is set to 'verify'"
    ::= { ipxAllowEntry 12 }

    ipxAllowSrcNet OBJECT-TYPE
	SYNTAX INTEGER
	ACCESS read-write
	STATUS mandatory
	DESCRIPTION 
	    "The IPX source network address"
    ::= { ipxAllowEntry 13 }

    ipxAllowSrcNodeMode OBJECT-TYPE
	SYNTAX INTEGER { dont-verify(1), verify(2) }
	ACCESS read-write
	STATUS mandatory
	DESCRIPTION 
	    "The IPX source node address will be checked if
	    this field is set to 'verify'"
    ::= { ipxAllowEntry 14 }

    ipxAllowSrcNode OBJECT-TYPE
	SYNTAX OCTET STRING (SIZE(6))
	ACCESS read-write
	STATUS mandatory
	DESCRIPTION 
	    "The IPX source node address"
    ::= { ipxAllowEntry 15 }

    ipxAllowSrcSockMode OBJECT-TYPE
	SYNTAX INTEGER { dont-verify(1), verify(2) }
	ACCESS read-write
	STATUS mandatory
	DESCRIPTION 
	    "The IPX source socket number will be checked if
	    this field is set to 'verify'"
    ::= { ipxAllowEntry 16 }

    ipxAllowSrcSock OBJECT-TYPE
	SYNTAX INTEGER
	ACCESS read-write
	STATUS mandatory
	DESCRIPTION 
	    "The source socket"
    ::= { ipxAllowEntry 17 }


    ipxDenyTable OBJECT-TYPE
	SYNTAX SEQUENCE OF IPXDenyEntry
	ACCESS not-accessible
	STATUS mandatory
	DESCRIPTION
	    "Each entry describes  a rule for filtering
	     IPX packets. IPX packets matching any of those
	     rules will be discarded."
	::= { biboipx 3 }
	
    ipxDenyEntry OBJECT-TYPE
	SYNTAX IPXDenyEntry
	ACCESS not-accessible
	STATUS mandatory
	DESCRIPTION
	    ""
	INDEX {
	    ipxDenyPktTypeMode,
	    ipxDenySrcIfIndexMode
	}
	::= { ipxDenyTable 1 }

    IPXDenyEntry ::=
	SEQUENCE {
	    ipxDenyPktTypeMode	    INTEGER,
	    ipxDenyPktType	    INTEGER,
	    ipxDenyDstNetMode	    INTEGER,
	    ipxDenyDstIfStatus      INTEGER,
	    ipxDenyDstNet	    INTEGER,
	    ipxDenyDstNodeMode      INTEGER,
	    ipxDenyDstNode	    OCTET STRING,
	    ipxDenyDstSockMode	    INTEGER,
	    ipxDenyDstSock	    INTEGER,
	    ipxDenySrcIfIndexMode   INTEGER, 
	    ipxDenySrcIfIndex	    INTEGER,
	    ipxDenySrcNetMode	    INTEGER,
	    ipxDenySrcNet	    INTEGER,
	    ipxDenySrcNodeMode      INTEGER,
	    ipxDenySrcNode	    OCTET STRING,
	    ipxDenySrcSockMode	    INTEGER,
	    ipxDenySrcSock	    INTEGER
	}

    ipxDenyPktTypeMode OBJECT-TYPE
	SYNTAX INTEGER { dont-verify(1), verify(2), delete(3) }
	ACCESS read-write
	STATUS mandatory
	DESCRIPTION 
	    "The IPX packet type will be checked if this field
	    is set to 'verify'"
    ::= { ipxDenyEntry 1 }

    ipxDenyPktType OBJECT-TYPE
	SYNTAX INTEGER {
	    unknown(256),
	    rip(1),
	    sap(4),
	    spx(5),
	    ncp(17),
	    netbios(20)
	}
	ACCESS read-write
	STATUS mandatory
	DESCRIPTION 
	    "The various IPX packet types"
    ::= { ipxDenyEntry 2 }

    ipxDenyDstIfStatus OBJECT-TYPE
	SYNTAX INTEGER { dont-verify(1), dormant(2) }
	ACCESS read-write
	STATUS mandatory
	DESCRIPTION
	    "Set this value to 'dormant', if packets should not be forwarded
	     to sleeping (dialup-)links"
    ::= { ipxDenyEntry 3 }

    ipxDenyDstNetMode OBJECT-TYPE
	SYNTAX INTEGER { dont-verify(1), verify(2) }
	ACCESS read-write
	STATUS mandatory
	DESCRIPTION 
	    "The IPX destination network address will be checked if
	    this field is set to 'verify'"
    ::= { ipxDenyEntry 4 }

    ipxDenyDstNet OBJECT-TYPE
	SYNTAX INTEGER
	ACCESS read-write
	STATUS mandatory
	DESCRIPTION 
	    "The IPX destination network address"
    ::= { ipxDenyEntry 5 }

    ipxDenyDstNodeMode OBJECT-TYPE
	SYNTAX INTEGER { dont-verify(1), verify(2) }
	ACCESS read-write
	STATUS mandatory
	DESCRIPTION 
	    "The IPX destination node address will be checked if
	    this field is set to 'verify'"
    ::= { ipxDenyEntry 6 }

    ipxDenyDstNode OBJECT-TYPE
	SYNTAX OCTET STRING (SIZE(6))
	ACCESS read-write
	STATUS mandatory
	DESCRIPTION 
	    "The IPX destination node address"
    ::= { ipxDenyEntry 7 }

    ipxDenyDstSockMode OBJECT-TYPE
	SYNTAX INTEGER { dont-verify(1), verify(2) }
	ACCESS read-write
	STATUS mandatory
	DESCRIPTION 
	    "The destination socket will be checked if
	    this field is set to 'verify'"
    ::= { ipxDenyEntry 8 }

    ipxDenyDstSock OBJECT-TYPE
	SYNTAX INTEGER
	ACCESS read-write
	STATUS mandatory
	DESCRIPTION 
	    "The destination socket"
    ::= { ipxDenyEntry 9 }

    ipxDenySrcIfIndexMode OBJECT-TYPE
	SYNTAX INTEGER { dont-verify(1), verify(2) }
	ACCESS read-write
	STATUS mandatory
	DESCRIPTION 
	    "The index of the receiving interface will be checked if
	    this field is set to 'verify'"
    ::= { ipxDenyEntry 10 }

    ipxDenySrcIfIndex OBJECT-TYPE
	SYNTAX INTEGER
	ACCESS read-write
	STATUS mandatory
	DESCRIPTION 
	    "The index of the receiving interface"
    ::= { ipxDenyEntry 11 }

    ipxDenySrcNetMode OBJECT-TYPE
	SYNTAX INTEGER { dont-verify(1), verify(2) }
	ACCESS read-write
	STATUS mandatory
	DESCRIPTION 
	    "The IPX source socket number will be checked if
	    this field is set to 'verify'"
    ::= { ipxDenyEntry 12 }

    ipxDenySrcNet OBJECT-TYPE
	SYNTAX INTEGER
	ACCESS read-write
	STATUS mandatory
	DESCRIPTION 
	    "The IPX source network address"
    ::= { ipxDenyEntry 13 }

    ipxDenySrcNodeMode OBJECT-TYPE
	SYNTAX INTEGER { dont-verify(1), verify(2) }
	ACCESS read-write
	STATUS mandatory
	DESCRIPTION 
	    "The IPX destination node address will be checked if
	    this field is set to 'verify'"
    ::= { ipxDenyEntry 14 }

    ipxDenySrcNode OBJECT-TYPE
	SYNTAX OCTET STRING (SIZE(6))
	ACCESS read-write
	STATUS mandatory
	DESCRIPTION 
	    "The IPX destination node address"
    ::= { ipxDenyEntry 15 }

    ipxDenySrcSockMode OBJECT-TYPE
	SYNTAX INTEGER { dont-verify(1), verify(2) }
	ACCESS read-write
	STATUS mandatory
	DESCRIPTION 
	    "The IPX source socket number will be checked if
	    this field is set to 'verify'"
    ::= { ipxDenyEntry 16 }

    ipxDenySrcSock OBJECT-TYPE
	SYNTAX INTEGER
	ACCESS read-write
	STATUS mandatory
	DESCRIPTION 
	    "The source socket"
    ::= { ipxDenyEntry 17 }


-- various IPX/SPX settings


    ipxAdmin OBJECT IDENTIFIER
	::= { biboipx 4 }

	ipxAdmSpxSpoofing OBJECT-TYPE
	    SYNTAX INTEGER { on(1), off(2) }
	    ACCESS read-write
	    STATUS mandatory
	    DESCRIPTION
		"Enable/disable SPX watchdog spoofing (on WAN links only)"
	::= { ipxAdmin 1 }

	ipxAdmIpxSpoofing OBJECT-TYPE
	    SYNTAX INTEGER { on(1), off(2) }
	    ACCESS read-write
	    STATUS mandatory
	    DESCRIPTION
		"Enable/disable IPX watchdog spoofing (on WAN links only)"
	::= { ipxAdmin 2 }

	ipxAdmNETBIOSRepl OBJECT-TYPE
	    SYNTAX INTEGER { on(1), off(2), lan-only(3) }
	    ACCESS read-write
	    STATUS mandatory
	    DESCRIPTION
		"Handling of replicated NetBIOS broadcasts:
		 
		 off     :   dont replicate at all
		 on      :   enable normal replication
		 lan_only:   dont replicate on WAN links"
	::= { ipxAdmin 3 }

	ipxAdmSpxVerTimeout OBJECT-TYPE
	    SYNTAX INTEGER
	    ACCESS read-write
	    STATUS mandatory

	    DESCRIPTION
		"Idle time SPX will wait before sending a watchdog" 
	::= { ipxAdmin 4 }

	ipxAdmSpxAbrTimeout OBJECT-TYPE
	    SYNTAX INTEGER
	    ACCESS read-write
	    STATUS mandatory

	    DESCRIPTION
		"Idle time SPX will wait before aborting the connection"
	::= { ipxAdmin 5 }

	ipxAdmRIPSAPOffset OBJECT-TYPE
	    SYNTAX INTEGER
	    ACCESS read-write
	    STATUS mandatory

	    DESCRIPTION
		"Offset interval between RIP-Response and SAP-Response"
	::= { ipxAdmin 6 }

	ipxAdmLearnStatics OBJECT-TYPE
	    SYNTAX INTEGER { done(1),
			     rip(2),
			     sap(3),
			     both(4) }
	    ACCESS read-write
	    STATUS mandatory

	    DESCRIPTION
		"take entries from ipxDestTable and/or ipxDestServTable
		 and put them into ipxStaticRoute-/ipxStaticServTable"
	::= { ipxAdmin 7 }

	ipxAdmSpxConns OBJECT-TYPE
	    SYNTAX INTEGER
	    ACCESS read-only
	    STATUS mandatory
	    DESCRIPTION
		"Number of spoofed SPX connections"
	::= { ipxAdmin 8 }

-- SAP filter

-- SAP allow

    sapAllowTable OBJECT-TYPE
	SYNTAX SEQUENCE OF SAPAllowEntry
	ACCESS not-accessible
	STATUS mandatory
	DESCRIPTION
	    "Each entry describes  a rule for filtering
	     services. Only services matching any of those
	     rules will be learned/forwarded."
    ::= { biboipx 5 }
	
    sapAllowEntry OBJECT-TYPE
	SYNTAX SAPAllowEntry
	ACCESS not-accessible
	STATUS mandatory
	DESCRIPTION
	    ""
	INDEX {
	    sapAllowIfIndex
	}
	::= { sapAllowTable 1 }

    SAPAllowEntry ::=
	SEQUENCE {
	    sapAllowIfIndexMode	    INTEGER,
	    sapAllowIfIndex	    INTEGER,
	    sapAllowDirection	    INTEGER,
	    sapAllowTypeMode        INTEGER,
	    sapAllowType	    OCTET STRING,
	    sapAllowNetMode         INTEGER,
	    sapAllowNet		    OCTET STRING,
	    sapAllowNodeMode        INTEGER,
	    sapAllowNode	    OCTET STRING,
	    sapAllowSockMode	    INTEGER,
	    sapAllowSock	    OCTET STRING,
	    sapAllowName	    DisplayString
	}

    sapAllowIfIndexMode OBJECT-TYPE
	SYNTAX INTEGER {
	    dont-verify(1),
	    verify(2),
	    delete(3)
	}
	ACCESS read-write
	STATUS mandatory
	DESCRIPTION 
	"
	    dont_verify:  the interface index is not verified
	    verify:       check interface index
	    delete:       delete this rule
	"
    ::= { sapAllowEntry 1 }

    sapAllowIfIndex OBJECT-TYPE
	SYNTAX INTEGER 
	ACCESS read-write
	STATUS mandatory
	DESCRIPTION 
	    "This rule is applied to services originating and/or
	    (see sapAllowDirection) destined for the interface
	    with this index. "
    ::= { sapAllowEntry 2 }

    sapAllowDirection OBJECT-TYPE
	SYNTAX INTEGER {
	    dont-verify(1),
	    outgoing(2),
	    incoming(3),
	    both(4)
	}
	ACCESS read-write
	STATUS mandatory
	DESCRIPTION 
	"
	    dont_verify:  the interface index is not verified
	    outgoing:     this rule is applied to services being sent
	    incoming:     this rule is applied to incoming services
	    both:         this rule is applied to incoming and outgoing services
	"
    ::= { sapAllowEntry 3 }

    sapAllowTypeMode OBJECT-TYPE
	SYNTAX INTEGER {
	    dont-verify(1),
	    verify(2)
	}
	ACCESS read-write
	STATUS mandatory
	DESCRIPTION
	    "
	    dont_verify: don't check service type
	    verify:      check service type
	    "
    ::= { sapAllowEntry 4 }

    sapAllowType OBJECT-TYPE
	SYNTAX OCTET STRING (SIZE(2))
	ACCESS read-write
	STATUS mandatory
	DESCRIPTION
	"The service type to be checked. Examples: 
	 4: file server
	 7: print server
	"
    ::= { sapAllowEntry 5 }

    sapAllowNetMode OBJECT-TYPE
	SYNTAX INTEGER {
	    dont-verify(1),
	    verify(2)
	}
	ACCESS read-write
	STATUS mandatory
	DESCRIPTION
	    "
	    dont_verify: don't check network number
	    verify:      check network number
	    "
    ::= { sapAllowEntry 6 }

    sapAllowNet OBJECT-TYPE
	SYNTAX OCTET STRING (SIZE(4))
	ACCESS read-write
	STATUS mandatory
	DESCRIPTION
	    "
	    the service's network number to be checked
	    "
    ::= { sapAllowEntry 7 }

    sapAllowNodeMode OBJECT-TYPE
	SYNTAX INTEGER {
	    dont-verify(1),
	    verify(2)
	}
	ACCESS read-write
	STATUS mandatory
	DESCRIPTION
	    "
	    dont_verify: don't check node number
	    verify:      check node number
	    "
    ::= { sapAllowEntry 8 }

    sapAllowNode OBJECT-TYPE
	SYNTAX OCTET STRING (SIZE(6))
	ACCESS read-write
	STATUS mandatory
	DESCRIPTION
	    "
	    the service's node number to be checked
	    "
    ::= { sapAllowEntry 9 }

    sapAllowSockMode OBJECT-TYPE
	SYNTAX INTEGER {
	    dont-verify(1),
	    verify(2)
	}
	ACCESS read-write
	STATUS mandatory
	DESCRIPTION
	    "
	    dont_verify: don't check socket number
	    verify:      check socket number
	    "
    ::= { sapAllowEntry 10 }

    sapAllowSock OBJECT-TYPE
	SYNTAX OCTET STRING (SIZE(2))
	ACCESS read-write
	STATUS mandatory
	DESCRIPTION
	    "
	    the service's socket number to be checked
	    "
    ::= { sapAllowEntry 11 }

    sapAllowName OBJECT-TYPE
	SYNTAX DisplayString (SIZE(1..48))
	ACCESS read-write
	STATUS mandatory
	DESCRIPTION
	    "
	    Instead of entering Type/Net/Node/Socket directly,
	    you could fill in the server name here. The
	    Type/Net/Node/Socket fields will then be looked
	    up in the ipxDestServTable. If a service of this
	    name exists, the values of this rule will be set.
	    Caution: the Brick IPX does not use this name field
	    for filtering. It is just meant for easier usage.
	    Only Type/Net/Node/Socket fields above
	    will be checked (according to the dont_verify/verify fields)
	    "
    ::= { sapAllowEntry 12 }

-- SAP Deny

    sapDenyTable OBJECT-TYPE
	SYNTAX SEQUENCE OF SAPDenyEntry
	ACCESS not-accessible
	STATUS mandatory
	DESCRIPTION
	    "Each entry describes  a rule for filtering
	     services. Services matching any of those
	     rules will be discarded."
	::= { biboipx 6 }
	
    sapDenyEntry OBJECT-TYPE
	SYNTAX SAPDenyEntry
	ACCESS not-accessible
	STATUS mandatory
	DESCRIPTION
	    ""
	INDEX {
	    sapDenyIfIndex
	}
	::= { sapDenyTable 1 }

    SAPDenyEntry ::=
	SEQUENCE {
	    sapDenyIfIndexMode	    INTEGER,
	    sapDenyIfIndex	    INTEGER,
	    sapDenyDirection	    INTEGER,
	    sapDenyTypeMode         INTEGER,
	    sapDenyType		    OCTET STRING,
	    sapDenyNetMode          INTEGER,
	    sapDenyNet		    OCTET STRING,
	    sapDenyNodeMode         INTEGER,
	    sapDenyNode		    OCTET STRING,
	    sapDenySockMode	    INTEGER,
	    sapDenySock		    OCTET STRING,
	    sapDenyName		    DisplayString
	}

    sapDenyIfIndexMode OBJECT-TYPE
	SYNTAX INTEGER {
	    dont-verify(1),
	    verify(2),
	    delete(3)
	}
	ACCESS read-write
	STATUS mandatory
	DESCRIPTION 
	"
	    dont_verify:  the interface index is not verified
	    verify:       the interface index is not verified
	    delete:       delete this rule
	"
    ::= { sapDenyEntry 1 }

    sapDenyIfIndex OBJECT-TYPE
	SYNTAX INTEGER 
	ACCESS read-write
	STATUS mandatory
	DESCRIPTION 
	    "This rule is applied to services originating and/or
	    (see sapDenyDirection) destined for the interface
	    with this index. "
    ::= { sapDenyEntry 2 }

    sapDenyDirection OBJECT-TYPE
	SYNTAX INTEGER {
	    dont-verify(1),
	    outgoing(2),
	    incoming(3),
	    both(4)
	}
	ACCESS read-write
	STATUS mandatory
	DESCRIPTION 
	"
	    dont_verify:  the direction is not verified
	    outgoing:     this rule is applied to services being sent
	    incoming:     this rule is applied to incoming services
	    both:         this rule is applied to incoming and outgoing services
	"
    ::= { sapDenyEntry 3 }

    sapDenyTypeMode OBJECT-TYPE
	SYNTAX INTEGER {
	    dont-verify(1),
	    verify(2)
	}
	ACCESS read-write
	STATUS mandatory
	DESCRIPTION
	    "
	    dont_verify: don't check service type
	    verify:      check service type
	    "
    ::= { sapDenyEntry 4 }

    sapDenyType OBJECT-TYPE
	SYNTAX OCTET STRING (SIZE(2))
	ACCESS read-write
	STATUS mandatory
	DESCRIPTION
	"The service type to be checked. Examples: 
	 4: file server
	 7: print server
	"
    ::= { sapDenyEntry 5 }

    sapDenyNetMode OBJECT-TYPE
	SYNTAX INTEGER {
	    dont-verify(1),
	    verify(2)
	}
	ACCESS read-write
	STATUS mandatory
	DESCRIPTION
	    "
	    dont_verify: don't check network number
	    verify:      check network number
	    "
    ::= { sapDenyEntry 6 }

    sapDenyNet OBJECT-TYPE
	SYNTAX OCTET STRING (SIZE(4))
	ACCESS read-write
	STATUS mandatory
	DESCRIPTION
	    "
	    the service's network number to be checked
	    "
    ::= { sapDenyEntry 7 }

    sapDenyNodeMode OBJECT-TYPE
	SYNTAX INTEGER {
	    dont-verify(1),
	    verify(2)
	}
	ACCESS read-write
	STATUS mandatory
	DESCRIPTION
	    "
	    dont_verify: don't check node number
	    verify:      check node number
	    "
    ::= { sapDenyEntry 8 }

    sapDenyNode OBJECT-TYPE
	SYNTAX OCTET STRING (SIZE(6))
	ACCESS read-write
	STATUS mandatory
	DESCRIPTION
	    "
	    the service's node number to be checked
	    "
    ::= { sapDenyEntry 9 }

    sapDenySockMode OBJECT-TYPE
	SYNTAX INTEGER {
	    dont-verify(1),
	    verify(2)
	}
	ACCESS read-write
	STATUS mandatory
	DESCRIPTION
	    "
	    dont_verify: don't check socket number
	    verify:      check socket number
	    "
    ::= { sapDenyEntry 10 }

    sapDenySock OBJECT-TYPE
	SYNTAX OCTET STRING (SIZE(2))
	ACCESS read-write
	STATUS mandatory
	DESCRIPTION
	    "
	    the service's socket number to be checked
	    "
    ::= { sapDenyEntry 11 }

    sapDenyName OBJECT-TYPE
	SYNTAX DisplayString (SIZE(1..48))
	ACCESS read-write
	STATUS mandatory
	DESCRIPTION
	    "
	    Instead of entering Type/Net/Node/Socket directly,
	    you could fill in the server name here. The
	    Type/Net/Node/Socket fields will then be looked
	    up in the ipxDestServTable. If a service of this
	    name exists, the values of this rule will be set.
	    Caution: the Brick IPX does not use this name field
	    for filtering. It is just meant for easier usage.
	    Only Type/Net/Node/Socket fields above
	    will be checked (according to the dont_verify/verify fields)
	    "
    ::= { sapDenyEntry 12 }

END
