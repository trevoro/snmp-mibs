ACC-ALARMS DEFINITIONS ::= BEGIN

    IMPORTS
	 OBJECT-TYPE, Counter FROM RFC1155-SMI
                      accTrapLogSeqNum FROM ACC-SYSTEM
	 accBRG, DisplayString, RowStatus, IfIndex, SmdsAddress
             FROM ACC-MIB;

-- ACC Alarms MIB Group
accAlarms	OBJECT IDENTIFIER  ::= { accBRG 53 }
-- Alarm Table Objects
        accAlarmTable OBJECT-TYPE
                SYNTAX SEQUENCE OF AccAlarmEntry
                ACCESS not-accessible
                STATUS mandatory
                DESCRIPTION
                        " Alarm table entries to identify
                        network equipment troubles in a Newbridge/ 
                        Bellcore-style format."
                ::= { accAlarms 1 }
        accAlarmEntry OBJECT-TYPE
                SYNTAX AccAlarmEntry
                ACCESS not-accessible
                STATUS mandatory
                DESCRIPTION
                        "Alarm entry - identifies alarm
                        and provides timestamp and identifier."
                INDEX { INTEGER }
                ::= { accAlarmTable 1 }
        AccAlarmEntry ::= SEQUENCE {
                accAlarmSeqNum        INTEGER,
         -- deprecated:  accAlarmDate          OCTET STRING,
         	accAlarmDateY2K       OCTET STRING,
                accAlarmAck           INTEGER,
                accAlarmPriority      INTEGER,
                accAlarmDescription   DisplayString,
                accAlarmSubCode       OCTET STRING,
                accAlarmParameter     OCTET STRING
                }
        accAlarmSeqNum	OBJECT-TYPE
                SYNTAX  INTEGER
                ACCESS  read-only
                STATUS  mandatory
                DESCRIPTION
                        "Alarm sequence number ranges from
                         1 to 200 to identify alarm entry."
                ::= { accAlarmEntry 1 }
--        accAlarmDate	OBJECT-TYPE
--                SYNTAX  OCTET STRING
--                ACCESS  read-only
--                STATUS  deprecated
--                DESCRIPTION
--                        "Date when alarm occurred
--                        in the format DD-MMM-YY. 
--			This object is being deprecated in favour of
--			the object accAlarmDateY2K."
--                ::= { accAlarmEntry 2 }
        accAlarmAck	OBJECT-TYPE
                SYNTAX  INTEGER {
                        yes (1),
                        no (2)
                        }
                ACCESS  read-write
                STATUS  mandatory
                DESCRIPTION
                        "Acknowledgment string: Yes or No."
                ::= { accAlarmEntry 3 }
        accAlarmPriority	OBJECT-TYPE
                SYNTAX  INTEGER {
                        cri (4),  -- Critical Alarm
                        maj (3),  -- Major Alarm
                        min (2),  -- Minor Alarm
                        dia (1)   -- Diagnostic (Non-Alarmed)
                        }
                ACCESS  read-only
                STATUS  mandatory
                DESCRIPTION
                        "Alarm priority."
                ::= { accAlarmEntry 4 }
        accAlarmDescription	OBJECT-TYPE
                SYNTAX  DisplayString
                ACCESS  read-only
                STATUS  mandatory
                DESCRIPTION
                        "Description of alarm."
                ::= { accAlarmEntry 5 }
        accAlarmSubCode	OBJECT-TYPE
                SYNTAX  OCTET STRING
                ACCESS  read-only
                STATUS  mandatory
                DESCRIPTION
                        "Alarm identification identifier: 
                        Slot.Interface.Circuit"
                ::= { accAlarmEntry 6 }
        accAlarmParameter OBJECT-TYPE
                SYNTAX  OCTET STRING
                ACCESS  read-only
                STATUS  mandatory
                DESCRIPTION
                        "IP Address - a unique identifier 
                        for network equipment."
                ::= { accAlarmEntry 7 }
        accAlarmDateY2K	OBJECT-TYPE
                SYNTAX  OCTET STRING
                ACCESS  read-only
                STATUS  mandatory
                DESCRIPTION
                        "Year 2000 compliant date and time when alarm occurred.
                  	 The seven byte long octet string is laid out in the 
			 following structured format:
				2 Byte unsigned short value of year
				1 Byte value of month
				1 Byte value of day of the month
				1 Byte value of hour
				1 Byte value of minutes
				1 Byte value of seconds "
                ::= { accAlarmEntry 8 }
-- Alarm Summary Table Objects
        accAlarmSumTable OBJECT-TYPE
                SYNTAX SEQUENCE OF AccAlarmSumEntry
                ACCESS not-accessible
                STATUS mandatory
                DESCRIPTION
                        " Alarm summary table presenting a summary of
			  all major and minor alarms."
                ::= { accAlarms 2 }
        accAlarmSumEntry OBJECT-TYPE
                SYNTAX AccAlarmSumEntry
                ACCESS not-accessible
                STATUS mandatory
                DESCRIPTION
                        "Alarm summary entry"  
                INDEX { INTEGER }
                ::= { accAlarmSumTable 1 }
        AccAlarmSumEntry ::= SEQUENCE {
           --deprecated:     accAlarmSumDate       OCTET STRING,
                accAlarmSumDateY2K    OCTET STRING,
                accAlarmSumCriOuts    Counter,
                accAlarmSumCriTots    Counter,
                accAlarmSumMajOuts    Counter,
                accAlarmSumMajTots    Counter,
                accAlarmSumMinOuts    Counter,
                accAlarmSumMinTots    Counter,
                accAlarmSumDiaTots    Counter
                }
--        accAlarmSumDate	OBJECT-TYPE
--                SYNTAX  OCTET STRING
--                ACCESS  read-only
--                STATUS  deprecated
--                DESCRIPTION
--                        "Date of summary display
--                        in the format DD-MMM-YY.
--			This object is being deprecated in favour of
--			the object accAlarmSumDateY2K"
--                ::= { accAlarmSumEntry 1 }
        accAlarmSumCriOuts	OBJECT-TYPE
                SYNTAX  Counter
                ACCESS  read-only
                STATUS  mandatory
                DESCRIPTION
                        "Count of Critical outstanding 
                        alarms."
                ::= { accAlarmSumEntry 2 }
        accAlarmSumCriTots	OBJECT-TYPE
                SYNTAX  Counter
                ACCESS  read-only
                STATUS  mandatory
                DESCRIPTION
                        "Count of Critical outstanding
                        (non-acknowledged) and acknowledged
                        alarms."
                ::= { accAlarmSumEntry 3 }
        accAlarmSumMajOuts	OBJECT-TYPE
                SYNTAX  Counter
                ACCESS  read-only
                STATUS  mandatory
                DESCRIPTION
                        "Count of Major outstanding
                        alarms."
                ::= { accAlarmSumEntry 4 }
        accAlarmSumMajTots	OBJECT-TYPE
                SYNTAX  Counter
                ACCESS  read-only
                STATUS  mandatory
                DESCRIPTION
                        "Count of Major outstanding
                        (non-acknowledged) and acknowledged
                        alarms."
                ::= { accAlarmSumEntry 5 }
        accAlarmSumMinOuts	OBJECT-TYPE
                SYNTAX  Counter
                ACCESS  read-only
                STATUS  mandatory
                DESCRIPTION
                        "Count of Minor outstanding
                        alarms."
                ::= { accAlarmSumEntry 6 }
        accAlarmSumMinTots	OBJECT-TYPE
                SYNTAX  Counter
                ACCESS  read-only
                STATUS  mandatory
                DESCRIPTION
                        "Count of Minor outstanding
                        (non-acknowledged) and acknowledged
                        alarms."
                ::= { accAlarmSumEntry 7 }
        accAlarmSumDiaTots	OBJECT-TYPE
                SYNTAX  Counter
                ACCESS  read-only
                STATUS  mandatory
                DESCRIPTION
                        "Total count of Diagnostic 
                        alarms."
                ::= { accAlarmSumEntry 8 }
        accAlarmSumDateY2K	OBJECT-TYPE
                SYNTAX  OCTET STRING
                ACCESS  read-only
                STATUS  mandatory
                DESCRIPTION
                        "Year 2000 compliant date and time of summary display.
                  	 The seven byte long octet string is laid out in the 
			 following structured format:
				2 Byte unsigned short value of year
				1 Byte value of month
				1 Byte value of day of the month
				1 Byte value of hour
				1 Byte value of minutes
				1 Byte value of seconds"
                ::= { accAlarmSumEntry 9 }
-- Alarm Table Acknowledge Timer Object
        accAlarmTableAckTimers	OBJECT-TYPE
                SYNTAX  Counter
                ACCESS  read-only
                STATUS  mandatory
                DESCRIPTION
                        "Alarm table acknowledgment countdown timer."
                ::= { accAlarms 3 }
-- Alarm Table Clear Timer Object
        accAlarmTableClrTimers	OBJECT-TYPE
                SYNTAX  Counter
                ACCESS  read-only
                STATUS  mandatory
                DESCRIPTION
                        "Alarm table clearing countdown timer."
                ::= { accAlarms 4 }
-- Alarm Table Save Timer Object
        accAlarmTableSavTimers	OBJECT-TYPE
                SYNTAX  Counter
                ACCESS  read-only
                STATUS  mandatory
                DESCRIPTION
                        "Alarm table save countdown timer."
                ::= { accAlarms 5 }

END
