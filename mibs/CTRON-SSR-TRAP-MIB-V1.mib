-- $Id: ctron-ssr-trap-v1.txt,v 1.5 2000/07/14 08:14:12 hyung Exp $

CTRON-SSR-TRAP-MIB-V1 DEFINITIONS ::= BEGIN

--  Revision: 3
-- LAST-UPDATED "200006270000Z"  June 27, 2000
--    ORGANIZATION "Cabletron Systems, Inc"
--    CONTACT-INFO
--    "Riverstone Networks, Inc
--     5200 Great America Parkway
--     Santa Clara, CA 95054
--     (408) 878-6500
--     nms-eng@riverstonenet.com
--     http://www.riverstonenet.com"

--  This module provides authoritative definitions for Enterasys
--  SSR and Riverstone RS product lines.
--
--  This module will be extended, as required.

--  Cabletron Systems reserves the right to make changes in
--  specification and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.

--  Copyright Cabletron Systems, Inc 1999-2000.


IMPORTS
      TRAP-TYPE
      FROM RFC-1215
      ssrTraps
      FROM CTRON-SSR-SMI-MIB
      sysHwPowerSupply, sysHwFan, sysHwTemperature, sysHwModuleSlotNumber
      FROM CTRON-SSR-HARDWARE-MIB;

   envPowerSupplyFailed TRAP-TYPE
        ENTERPRISE ssrTraps
        VARIABLES { 
                  sysHwPowerSupply 
               }
        DESCRIPTION
           "A power supply on the sending device has failed. The 
            sysHwPowerSupply object identifies the failed supply.
            Poll sysHwPowerSupply to obtain current status of power
            supplies"
	::=  1 

    envPowerSupplyRecovered TRAP-TYPE
        ENTERPRISE ssrTraps
        VARIABLES { 
                   sysHwPowerSupply 
               }
        DESCRIPTION
           "A power supply on the sending device has recovered 
            after failure. The sysHwPowerSupply object identifies 
            the recovered supply. Poll sysHwPowerSupply to obtain
            current status of power supplies"
	::= 2

    envFanFailed TRAP-TYPE
        ENTERPRISE ssrTraps
        VARIABLES { 
                    sysHwFan 
               }
        DESCRIPTION
           "A Fan tray on the sending device has failed. The
            sysHwFan object identifies the failed fan tray.
            Poll sysHwFan to obtain current status."
        ::= 3
 
    envFanRecovered TRAP-TYPE
        ENTERPRISE ssrTraps
        VARIABLES {
                  sysHwFan
                }
        DESCRIPTION
           "A Fan tray on the sending device has recovered
            after failure. The sysHwFan object identifies
            the recovered Fan tray. Poll sysHwFan to obtain
            current status."
        ::= 4
 
    envTempExceeded TRAP-TYPE
        ENTERPRISE ssrTraps
        VARIABLES {
                  sysHwTemperature
                }
        DESCRIPTION
           "A temperature inside the chassis on the sending device has exceeded
            normal operating temperature. The sysHwTemperature object
            identifies the current status. Poll sysHwTemperature to 
            obtain current status."
        ::= 5
 
    envTempNormal TRAP-TYPE
        ENTERPRISE ssrTraps
        VARIABLES {
                  sysHwTemperature
                }
        DESCRIPTION
           "A temperature inside the chassis on the sending device has returned
            to normal operating temperature. The sysHwTemperature
            object identifies the current status. Poll sysHwTemperature to 
            obtain current status."
        ::= 6

    envHotSwapIn TRAP-TYPE
        ENTERPRISE ssrTraps
        VARIABLES {
                  sysHwModuleSlotNumber
                }
        DESCRIPTION
           "A module has been inserted into the chassis.
            sysHwModuleSlotNumber identifies the slot the module was inserted into.
            Poll sysHwLastHotSwapEvent to monitor hotswap events. "
        ::= 7

    envHotSwapOut TRAP-TYPE
        ENTERPRISE ssrTraps
        VARIABLES {
                  sysHwModuleSlotNumber
                }
        DESCRIPTION
           "A module has been turned off or removed from the chassis.
            sysHwModuleSlotNumber identifies the slot the module was removed from.
            Poll sysHwLastHotSwapEvent to monitor hotswap events. "
        ::= 8

    envBackupControlModuleOnline TRAP-TYPE
        ENTERPRISE ssrTraps
        VARIABLES {
                  sysHwModuleSlotNumber
                }
        DESCRIPTION
           "A backup control module that was in standby mode has taken over 
            for a failed primary control module. Poll sysHwControlModuleBackupState 
            for current state of backup control module. sysHwModuleSlotNumber is the index
            into the sysHwModuleTable for the now active control module."
        ::= 9

END
