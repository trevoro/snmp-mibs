Nortel-MsCarrier-MscPassport-DisdnNISMIB
DEFINITIONS ::= BEGIN



IMPORTS

      OBJECT-TYPE
   FROM RFC-1212

      mscPassportMIBs
   FROM Nortel-MsCarrier-MscPassport-UsefulDefinitionsMIB

      DisplayString,
      StorageType,
      RowStatus,
      Unsigned32
   FROM Nortel-MsCarrier-MscPassport-StandardTextualConventionsMIB

      NonReplicated,
      Link
   FROM Nortel-MsCarrier-MscPassport-TextualConventionsMIB

      mscDataSigChanIndex,
      mscDataSigChan
   FROM Nortel-MsCarrier-MscPassport-DataIsdnMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DisdnNIS Enterprise MIB."

disdnNISMIB OBJECT IDENTIFIER ::= { mscPassportMIBs 127 }










-- DataSigChan/n Nis
-- The Nis component defines the operational characteristics of the 
-- signalling channel's connection to the external equipment.

mscDataSigChanNis OBJECT IDENTIFIER ::= { mscDataSigChan 13 }



mscDataSigChanNisRowStatusTable OBJECT-TYPE
   SYNTAX     SEQUENCE OF MscDataSigChanNisRowStatusEntry
   ACCESS     not-accessible
   STATUS     mandatory
   DESCRIPTION
     "This entry controls the addition and deletion of 
      mscDataSigChanNis components."
::= { mscDataSigChanNis 1 }

mscDataSigChanNisRowStatusEntry OBJECT-TYPE
   SYNTAX     MscDataSigChanNisRowStatusEntry
   ACCESS     not-accessible
   STATUS     mandatory
   DESCRIPTION
     "A single entry in the table represents a single 
      mscDataSigChanNis component."
   INDEX {
      mscDataSigChanIndex,
      mscDataSigChanNisIndex }
::= { mscDataSigChanNisRowStatusTable 1 }

MscDataSigChanNisRowStatusEntry ::= SEQUENCE {
   mscDataSigChanNisRowStatus
      RowStatus,
   mscDataSigChanNisComponentName
      DisplayString,
   mscDataSigChanNisStorageType
      StorageType,
   mscDataSigChanNisIndex
      NonReplicated }

mscDataSigChanNisRowStatus OBJECT-TYPE
   SYNTAX     RowStatus 
   ACCESS     read-write
   STATUS     mandatory
   DESCRIPTION
     "This variable is used as the basis for SNMP naming of
      mscDataSigChanNis components.
      These components can be added and deleted."
::= { mscDataSigChanNisRowStatusEntry 1 }

mscDataSigChanNisComponentName OBJECT-TYPE
   SYNTAX     DisplayString 
   ACCESS     read-only
   STATUS     mandatory
   DESCRIPTION
     "This variable provides the component's string name for
      use with the ASCII Console Interface"
::= { mscDataSigChanNisRowStatusEntry 2 }

mscDataSigChanNisStorageType OBJECT-TYPE
   SYNTAX     StorageType 
   ACCESS     read-only
   STATUS     mandatory
   DESCRIPTION
     "This variable represents the storage type value for the
      mscDataSigChanNis tables."
::= { mscDataSigChanNisRowStatusEntry 4 }

mscDataSigChanNisIndex OBJECT-TYPE
   SYNTAX     NonReplicated 
   ACCESS     not-accessible
   STATUS     mandatory
   DESCRIPTION
     "This variable represents the index for the mscDataSigChanNis tables."
::= { mscDataSigChanNisRowStatusEntry 10 }

mscDataSigChanNisL2Table OBJECT-TYPE
   SYNTAX     SEQUENCE OF MscDataSigChanNisL2Entry
   ACCESS     not-accessible
   STATUS     mandatory
   DESCRIPTION
     "This group represents the provisionable Layer 2 attributes of the 
      Q931 CCITT protocol."
::= { mscDataSigChanNis 11 }

mscDataSigChanNisL2Entry OBJECT-TYPE
   SYNTAX     MscDataSigChanNisL2Entry
   ACCESS     not-accessible
   STATUS     mandatory
   DESCRIPTION
     "An entry in the mscDataSigChanNisL2Table."
   INDEX {
      mscDataSigChanIndex,
      mscDataSigChanNisIndex }
::= { mscDataSigChanNisL2Table 1 }

MscDataSigChanNisL2Entry ::= SEQUENCE {
   mscDataSigChanNisT23
      Unsigned32,
   mscDataSigChanNisT200
      Unsigned32,
   mscDataSigChanNisN200
      Unsigned32,
   mscDataSigChanNisT203
      Unsigned32,
   mscDataSigChanNisN201
      Unsigned32,
   mscDataSigChanNisCircuitSwitchedK
      Unsigned32 }

mscDataSigChanNisT23 OBJECT-TYPE
   SYNTAX     Unsigned32 (1..15)
   ACCESS     read-write
   STATUS     mandatory
   DESCRIPTION
     "This attribute specifies the layer2 enable request timer."
   DEFVAL     { 10 }
::= { mscDataSigChanNisL2Entry 1 }

mscDataSigChanNisT200 OBJECT-TYPE
   SYNTAX     Unsigned32 (1..20)
   ACCESS     read-write
   STATUS     mandatory
   DESCRIPTION
     "This attribute specifies the maximum time between a layer 2 frame 
      and its acknowledgement"
   DEFVAL     { 2 }
::= { mscDataSigChanNisL2Entry 2 }

mscDataSigChanNisN200 OBJECT-TYPE
   SYNTAX     Unsigned32 (1..8)
   ACCESS     read-write
   STATUS     mandatory
   DESCRIPTION
     "This attribute specifies the maximum number of re-transmissions of 
      a layer2 frame."
   DEFVAL     { 3 }
::= { mscDataSigChanNisL2Entry 3 }

mscDataSigChanNisT203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { mscDataSigChanNisL2Entry 4 }

mscDataSigChanNisN201 OBJECT-TYPE
   SYNTAX     Unsigned32 (4..260)
   ACCESS     read-write
   STATUS     mandatory
   DESCRIPTION
     "This attribute specifies the maximum number of octets in an 
      information field."
   DEFVAL     { 260 }
::= { mscDataSigChanNisL2Entry 5 }

mscDataSigChanNisCircuitSwitchedK OBJECT-TYPE
   SYNTAX     Unsigned32 (1..632)
   ACCESS     read-write
   STATUS     mandatory
   DESCRIPTION
     "This attribute specifies the maximum number of frames for B 
      channel use."
   DEFVAL     { 7 }
::= { mscDataSigChanNisL2Entry 6 }

mscDataSigChanNisProvTable OBJECT-TYPE
   SYNTAX     SEQUENCE OF MscDataSigChanNisProvEntry
   ACCESS     not-accessible
   STATUS     mandatory
   DESCRIPTION
     "This group defines the general options of the d-channel signalling 
      link."
::= { mscDataSigChanNis 13 }

mscDataSigChanNisProvEntry OBJECT-TYPE
   SYNTAX     MscDataSigChanNisProvEntry
   ACCESS     not-accessible
   STATUS     mandatory
   DESCRIPTION
     "An entry in the mscDataSigChanNisProvTable."
   INDEX {
      mscDataSigChanIndex,
      mscDataSigChanNisIndex }
::= { mscDataSigChanNisProvTable 1 }

MscDataSigChanNisProvEntry ::= SEQUENCE {
   mscDataSigChanNisSide
      INTEGER }

mscDataSigChanNisSide OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { mscDataSigChanNisProvEntry 1 }

mscDataSigChanNisOperTable OBJECT-TYPE
   SYNTAX     SEQUENCE OF MscDataSigChanNisOperEntry
   ACCESS     not-accessible
   STATUS     mandatory
   DESCRIPTION
     "This group provides the operational attributes for the signalling 
      protocol."
::= { mscDataSigChanNis 15 }

mscDataSigChanNisOperEntry OBJECT-TYPE
   SYNTAX     MscDataSigChanNisOperEntry
   ACCESS     not-accessible
   STATUS     mandatory
   DESCRIPTION
     "An entry in the mscDataSigChanNisOperTable."
   INDEX {
      mscDataSigChanIndex,
      mscDataSigChanNisIndex }
::= { mscDataSigChanNisOperTable 1 }

MscDataSigChanNisOperEntry ::= SEQUENCE {
   mscDataSigChanNisActiveChannels
      Unsigned32,
   mscDataSigChanNisPeakActiveChannels
      Unsigned32,
   mscDataSigChanNisDChanStatus
      INTEGER }

mscDataSigChanNisActiveChannels OBJECT-TYPE
   SYNTAX     Unsigned32 (0..128)
   ACCESS     read-only
   STATUS     mandatory
   DESCRIPTION
     "This attribute indicates the number of currently active channels. 
      This includes data and voice channels."
   DEFVAL     { 0 }
::= { mscDataSigChanNisOperEntry 1 }

mscDataSigChanNisPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { mscDataSigChanNisOperEntry 4 }

mscDataSigChanNisDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { mscDataSigChanNisOperEntry 7 }

mscDataSigChanNisToolsTable OBJECT-TYPE
   SYNTAX     SEQUENCE OF MscDataSigChanNisToolsEntry
   ACCESS     not-accessible
   STATUS     mandatory
   DESCRIPTION
     "This group contains a series of operational attributes which turn on 
      and off several kinds of tracing."
::= { mscDataSigChanNis 16 }

mscDataSigChanNisToolsEntry OBJECT-TYPE
   SYNTAX     MscDataSigChanNisToolsEntry
   ACCESS     not-accessible
   STATUS     mandatory
   DESCRIPTION
     "An entry in the mscDataSigChanNisToolsTable."
   INDEX {
      mscDataSigChanIndex,
      mscDataSigChanNisIndex }
::= { mscDataSigChanNisToolsTable 1 }

MscDataSigChanNisToolsEntry ::= SEQUENCE {
   mscDataSigChanNisTracing
      OCTET STRING }

mscDataSigChanNisTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { mscDataSigChanNisToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

mscDataSigChanNisFramer OBJECT IDENTIFIER ::= { mscDataSigChanNis 2 }



mscDataSigChanNisFramerRowStatusTable OBJECT-TYPE
   SYNTAX     SEQUENCE OF MscDataSigChanNisFramerRowStatusEntry
   ACCESS     not-accessible
   STATUS     mandatory
   DESCRIPTION
     "This entry controls the addition and deletion of 
      mscDataSigChanNisFramer components."
::= { mscDataSigChanNisFramer 1 }

mscDataSigChanNisFramerRowStatusEntry OBJECT-TYPE
   SYNTAX     MscDataSigChanNisFramerRowStatusEntry
   ACCESS     not-accessible
   STATUS     mandatory
   DESCRIPTION
     "A single entry in the table represents a single 
      mscDataSigChanNisFramer component."
   INDEX {
      mscDataSigChanIndex,
      mscDataSigChanNisIndex,
      mscDataSigChanNisFramerIndex }
::= { mscDataSigChanNisFramerRowStatusTable 1 }

MscDataSigChanNisFramerRowStatusEntry ::= SEQUENCE {
   mscDataSigChanNisFramerRowStatus
      RowStatus,
   mscDataSigChanNisFramerComponentName
      DisplayString,
   mscDataSigChanNisFramerStorageType
      StorageType,
   mscDataSigChanNisFramerIndex
      NonReplicated }

mscDataSigChanNisFramerRowStatus OBJECT-TYPE
   SYNTAX     RowStatus 
   ACCESS     read-only
   STATUS     mandatory
   DESCRIPTION
     "This variable is used as the basis for SNMP naming of
      mscDataSigChanNisFramer components.
      These components cannot be added nor deleted."
::= { mscDataSigChanNisFramerRowStatusEntry 1 }

mscDataSigChanNisFramerComponentName OBJECT-TYPE
   SYNTAX     DisplayString 
   ACCESS     read-only
   STATUS     mandatory
   DESCRIPTION
     "This variable provides the component's string name for
      use with the ASCII Console Interface"
::= { mscDataSigChanNisFramerRowStatusEntry 2 }

mscDataSigChanNisFramerStorageType OBJECT-TYPE
   SYNTAX     StorageType 
   ACCESS     read-only
   STATUS     mandatory
   DESCRIPTION
     "This variable represents the storage type value for the
      mscDataSigChanNisFramer tables."
::= { mscDataSigChanNisFramerRowStatusEntry 4 }

mscDataSigChanNisFramerIndex OBJECT-TYPE
   SYNTAX     NonReplicated 
   ACCESS     not-accessible
   STATUS     mandatory
   DESCRIPTION
     "This variable represents the index for the mscDataSigChanNisFramer tables."
::= { mscDataSigChanNisFramerRowStatusEntry 10 }

mscDataSigChanNisFramerProvTable OBJECT-TYPE
   SYNTAX     SEQUENCE OF MscDataSigChanNisFramerProvEntry
   ACCESS     not-accessible
   STATUS     mandatory
   DESCRIPTION
     "This group contains the base provisioning data for the Framer 
      component. Application or hardware interface specific provisioning 
      data is contained in other provisionable Framer groups."
::= { mscDataSigChanNisFramer 10 }

mscDataSigChanNisFramerProvEntry OBJECT-TYPE
   SYNTAX     MscDataSigChanNisFramerProvEntry
   ACCESS     not-accessible
   STATUS     mandatory
   DESCRIPTION
     "An entry in the mscDataSigChanNisFramerProvTable."
   INDEX {
      mscDataSigChanIndex,
      mscDataSigChanNisIndex,
      mscDataSigChanNisFramerIndex }
::= { mscDataSigChanNisFramerProvTable 1 }

MscDataSigChanNisFramerProvEntry ::= SEQUENCE {
   mscDataSigChanNisFramerInterfaceName
      Link }

mscDataSigChanNisFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscDataSigChanNisFramerProvEntry 1 }

mscDataSigChanNisFramerStateTable OBJECT-TYPE
   SYNTAX     SEQUENCE OF MscDataSigChanNisFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDataSigChanNisFramer 12 }

mscDataSigChanNisFramerStateEntry OBJECT-TYPE
   SYNTAX     MscDataSigChanNisFramerStateEntry
   ACCESS     not-accessible
   STATUS     mandatory
   DESCRIPTION
     "An entry in the mscDataSigChanNisFramerStateTable."
   INDEX {
      mscDataSigChanIndex,
      mscDataSigChanNisIndex,
      mscDataSigChanNisFramerIndex }
::= { mscDataSigChanNisFramerStateTable 1 }

MscDataSigChanNisFramerStateEntry ::= SEQUENCE {
   mscDataSigChanNisFramerAdminState
      INTEGER,
   mscDataSigChanNisFramerOperationalState
      INTEGER,
   mscDataSigChanNisFramerUsageState
      INTEGER }

mscDataSigChanNisFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDataSigChanNisFramerStateEntry 1 }

mscDataSigChanNisFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDataSigChanNisFramerStateEntry 2 }

mscDataSigChanNisFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDataSigChanNisFramerStateEntry 3 }

mscDataSigChanNisFramerStatsTable OBJECT-TYPE
   SYNTAX     SEQUENCE OF MscDataSigChanNisFramerStatsEntry
   ACCESS     not-accessible
   STATUS     mandatory
   DESCRIPTION
     "This group contains the operational statistics data for a Framer 
      component."
::= { mscDataSigChanNisFramer 13 }

mscDataSigChanNisFramerStatsEntry OBJECT-TYPE
   SYNTAX     MscDataSigChanNisFramerStatsEntry
   ACCESS     not-accessible
   STATUS     mandatory
   DESCRIPTION
     "An entry in the mscDataSigChanNisFramerStatsTable."
   INDEX {
      mscDataSigChanIndex,
      mscDataSigChanNisIndex,
      mscDataSigChanNisFramerIndex }
::= { mscDataSigChanNisFramerStatsTable 1 }

MscDataSigChanNisFramerStatsEntry ::= SEQUENCE {
   mscDataSigChanNisFramerFrmToIf
      Unsigned32,
   mscDataSigChanNisFramerFrmFromIf
      Unsigned32,
   mscDataSigChanNisFramerOctetFromIf
      Unsigned32,
   mscDataSigChanNisFramerAborts
      Unsigned32,
   mscDataSigChanNisFramerCrcErrors
      Unsigned32,
   mscDataSigChanNisFramerLrcErrors
      Unsigned32,
   mscDataSigChanNisFramerNonOctetErrors
      Unsigned32,
   mscDataSigChanNisFramerOverruns
      Unsigned32,
   mscDataSigChanNisFramerUnderruns
      Unsigned32,
   mscDataSigChanNisFramerLargeFrmErrors
      Unsigned32 }

mscDataSigChanNisFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { mscDataSigChanNisFramerStatsEntry 1 }

mscDataSigChanNisFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { mscDataSigChanNisFramerStatsEntry 2 }

mscDataSigChanNisFramerOctetFromIf OBJECT-TYPE
   SYNTAX     Unsigned32 (0..4294967295)
   ACCESS     read-only
   STATUS     mandatory
   DESCRIPTION
     "The number of bytes received from the link interface by Framer."
   DEFVAL     { 0 }
::= { mscDataSigChanNisFramerStatsEntry 3 }

mscDataSigChanNisFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { mscDataSigChanNisFramerStatsEntry 4 }

mscDataSigChanNisFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { mscDataSigChanNisFramerStatsEntry 5 }

mscDataSigChanNisFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { mscDataSigChanNisFramerStatsEntry 6 }

mscDataSigChanNisFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { mscDataSigChanNisFramerStatsEntry 7 }

mscDataSigChanNisFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { mscDataSigChanNisFramerStatsEntry 8 }

mscDataSigChanNisFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { mscDataSigChanNisFramerStatsEntry 9 }

mscDataSigChanNisFramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { mscDataSigChanNisFramerStatsEntry 10 }




-- 
-- Version and Compliance statements
-- 



-- Object-Group Statement:
-- A list of all current accessible leaf objects.

-- OBJECTS { mscDataSigChanNisRowStatus,
--           mscDataSigChanNisN201,
--           mscDataSigChanNisFramerFrmToIf,
--           mscDataSigChanNisFramerNonOctetErrors,
--           mscDataSigChanNisPeakActiveChannels,
--           mscDataSigChanNisFramerUsageState,
--           mscDataSigChanNisFramerComponentName,
--           mscDataSigChanNisN200,
--           mscDataSigChanNisSide,
--           mscDataSigChanNisFramerFrmFromIf,
--           mscDataSigChanNisFramerInterfaceName,
--           mscDataSigChanNisFramerStorageType,
--           mscDataSigChanNisCircuitSwitchedK,
--           mscDataSigChanNisFramerUnderruns,
--           mscDataSigChanNisComponentName,
--           mscDataSigChanNisFramerCrcErrors,
--           mscDataSigChanNisStorageType,
--           mscDataSigChanNisFramerOperationalState,
--           mscDataSigChanNisT200,
--           mscDataSigChanNisActiveChannels,
--           mscDataSigChanNisFramerOctetFromIf,
--           mscDataSigChanNisT203,
--           mscDataSigChanNisDChanStatus,
--           mscDataSigChanNisFramerAdminState,
--           mscDataSigChanNisT23,
--           mscDataSigChanNisFramerLrcErrors,
--           mscDataSigChanNisFramerLargeFrmErrors,
--           mscDataSigChanNisFramerOverruns,
--           mscDataSigChanNisFramerRowStatus,
--           mscDataSigChanNisTracing,
--           mscDataSigChanNisFramerAborts }
-- STATUS  mandatory
-- DESCRIPTION
--   "A list of all current accessible leaf objects."

disdnNISGroup OBJECT IDENTIFIER ::= { disdnNISMIB 1 }
disdnNISGroupCA OBJECT IDENTIFIER ::= { disdnNISGroup 1 }
disdnNISGroupCA02 OBJECT IDENTIFIER ::= { disdnNISGroupCA 3 }
disdnNISGroupCA02A OBJECT IDENTIFIER ::= { disdnNISGroupCA02 2 }



-- Agent-Capabilities Statement:

-- PRODUCT-RELEASE "MscPassport Release 1.2 DisdnNIS."
-- STATUS          mandatory
-- DESCRIPTION     "Carrier Passport DisdnNIS MIB: MIB Version CA02A,
--                  Software Version CA02S9C."
-- SUPPORTS        Nortel-MsCarrier-MscPassport-DisdnNISMIB
--    INCLUDES     { disdnNISGroupCA02A }

disdnNISCapabilities OBJECT IDENTIFIER ::= { disdnNISMIB 3 }
disdnNISCapabilitiesCA OBJECT IDENTIFIER ::= { disdnNISCapabilities 1 }
disdnNISCapabilitiesCA02 OBJECT IDENTIFIER ::= { disdnNISCapabilitiesCA 3 }
disdnNISCapabilitiesCA02A OBJECT IDENTIFIER ::= { disdnNISCapabilitiesCA02 2 }





END
