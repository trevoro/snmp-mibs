--	$Header: $

OVERLAND-NEXTGEN 
DEFINITIONS ::= BEGIN

IMPORTS
	MODULE-IDENTITY, OBJECT-TYPE, NOTIFICATION-TYPE, Integer32
		FROM SNMPv2-SMI
	OBJECT-GROUP, NOTIFICATION-GROUP
		FROM SNMPv2-CONF
	DisplayString
		FROM SNMPv2-TC;

-- UTC time format is YYMMDDHHmmZ
overlandGlobalRegModule MODULE-IDENTITY
	LAST-UPDATED	"9807090845Z"
	ORGANIZATION	"Overland Data, Inc."
	CONTACT-INFO	"Robert Kingsley
			 email: bkingsley@overlanddata.com"
	DESCRIPTION
		"The Overland Data central registration module."
	::= {overlandModules 1}

overlandRoot OBJECT IDENTIFIER ::= {1 3 6 1 4 1 3351 1}

overlandReg			OBJECT IDENTIFIER ::= {overlandRoot 1}
overlandGeneric		OBJECT IDENTIFIER ::= {overlandRoot 2}
overlandProducts	OBJECT IDENTIFIER ::= {overlandRoot 3}
overlandCaps		OBJECT IDENTIFIER ::= {overlandRoot 4}
overlandReqs		OBJECT IDENTIFIER ::= {overlandRoot 5}
overlandExpr		OBJECT IDENTIFIER ::= {overlandRoot 6}

overlandModules		OBJECT IDENTIFIER ::= {overlandReg 1}

-- now for the actual product MIBS
overlandNextGen			OBJECT IDENTIFIER ::= {overlandProducts 2}

overlandNextGenActions		OBJECT IDENTIFIER ::= {overlandNextGen 1}
overlandNextGenStatistics	OBJECT IDENTIFIER ::= {overlandNextGen 2}
overlandNextGenState		OBJECT IDENTIFIER ::= {overlandNextGen 3}
overlandNextGenComponents	OBJECT IDENTIFIER ::= {overlandNextGen 4}
overlandNextGenAttributes	OBJECT IDENTIFIER ::= {overlandNextGen 5}
overlandNextGenEvents		OBJECT IDENTIFIER ::= {overlandNextGen 6}
overlandNextGenGroups		OBJECT IDENTIFIER ::= {overlandNextGen 7}


-------------------------------------------------------------------------------------------
-- 1st group of OIDS are actions which the library may be commanded to perform
--	(overlandNextGenActions)

overlandLoopback OBJECT-TYPE
	SYNTAX DisplayString    (SIZE (1..32))
	MAX-ACCESS read-write
	STATUS current
	DESCRIPTION
		"Sends or retrieves a loopback string to the target."
	::= {overlandNextGenActions 1}

overlandActionGroup OBJECT-GROUP
	OBJECTS {
		overlandLoopback
	}
	STATUS current
	DESCRIPTION
		"Current library status which may be queried."
	::= {overlandNextGenGroups 1}


-------------------------------------------------------------------------------------------
-- 2nd group of OIDS report the statistics for the library
--	(overlandNextGenStatistics)


-------------------------------------------------------------------------------------------
-- 3rd group of OIDs report the state of the library
--	(overlandNextGenState)

driveStatusTable OBJECT-TYPE
	SYNTAX SEQUENCE OF DriveStatusEntry
	MAX-ACCESS not-accessible
	STATUS current
	DESCRIPTION
		"Table containing various drive status."
	::= {overlandNextGenState 1}

driveStatusEntry OBJECT-TYPE
	SYNTAX DriveStatusEntry
	MAX-ACCESS not-accessible
	STATUS current
	DESCRIPTION
		"A row in the drive status table."
	INDEX {dstIndex}
	::= {driveStatusTable 1}

DriveStatusEntry ::= SEQUENCE
{
	dstRowValid				DisplayString,
	dstIndex				Integer32,
	dstState				INTEGER,
	dstMotion				DisplayString,
	dstCodeRevDrive			Integer32,
	dstCodeRevController	Integer32,
	dstScsiId				Integer32,
	dstSerialNum			DisplayString,
	dstCleanRequested		INTEGER
}

dstRowValid	OBJECT-TYPE
	SYNTAX DisplayString
	MAX-ACCESS read-only
	STATUS current
	DESCRIPTION
		"Provides an INVALID indication if no drives are installed
		or if the drive type is unknown; otherwise, an indication of the drive
		type is provided."
	::= {driveStatusEntry 1}

dstIndex OBJECT-TYPE
	SYNTAX Integer32(1..32)
	MAX-ACCESS read-only
	STATUS current
	DESCRIPTION
		"Index to drive status fields."
	::= {driveStatusEntry 2}

dstState OBJECT-TYPE
	SYNTAX INTEGER {
		initializedNoError(0),		-- initialized, SCSI id is set
		initializedWithError(1),	-- initialized, with some error
		notInitialized(2),			-- powered on, but SCSI id not set 
		notInstalled(3),			-- inserted, but not powered on
		notInserted(4)				-- physically removed from library	
	}
	MAX-ACCESS read-only
	STATUS current
	DESCRIPTION
		"Current state of the drive."
	::= {driveStatusEntry 3}

dstMotion	OBJECT-TYPE
	SYNTAX DisplayString
	MAX-ACCESS read-only
	STATUS current
	DESCRIPTION
		"ASCII msg describing current drive tape motion."
	::= {driveStatusEntry 4}

dstCodeRevDrive	OBJECT-TYPE
	SYNTAX Integer32 
	MAX-ACCESS read-only
	STATUS current
	DESCRIPTION
		"Revision number of the drive code."
	::= {driveStatusEntry 5}

dstCodeRevController	OBJECT-TYPE
	SYNTAX Integer32 
	MAX-ACCESS read-only
	STATUS current
	DESCRIPTION
		"Revision number of the drive controller code."
	::= {driveStatusEntry 6}

dstScsiId	OBJECT-TYPE
	SYNTAX Integer32(0..15) 
	MAX-ACCESS read-only
	STATUS current
	DESCRIPTION
		"SCSI Id number of drive."
	::= {driveStatusEntry 7}

dstSerialNum	OBJECT-TYPE
	SYNTAX DisplayString  
	MAX-ACCESS read-only
	STATUS current
	DESCRIPTION
		"Serial number of this drive."
	::= {driveStatusEntry 8}

dstCleanRequested	OBJECT-TYPE
	SYNTAX INTEGER { cleanNotNeeded(0), cleanNeeded(1) }
	MAX-ACCESS read-only
	STATUS current
	DESCRIPTION
		"The drive heads needs to be cleaned with a
		cleaning cartridge."
	::= {driveStatusEntry 9}

libraryStatusTable OBJECT-TYPE
	SYNTAX SEQUENCE OF LibraryStatusEntry
	MAX-ACCESS not-accessible
	STATUS current
	DESCRIPTION
		"Table containing fault code, severity and ACSII
		error messages displayed on front panel of library."
	::= {overlandNextGenState 2}

libraryStatusEntry OBJECT-TYPE
	SYNTAX LibraryStatusEntry
	MAX-ACCESS not-accessible
	STATUS current
	DESCRIPTION
		"A row in the library status table."
	INDEX {lstIndex}
	::= {libraryStatusTable 1}

LibraryStatusEntry ::= SEQUENCE
{
	lstIndex			Integer32,
	lstConfig			INTEGER,
	lstScsiId			Integer32,
	lstStatus			DisplayString,
	lstChangerStatus	Integer32,
	lstLibraryState		INTEGER
}

lstIndex OBJECT-TYPE
	SYNTAX Integer32 (1)
	MAX-ACCESS read-only
	STATUS current
	DESCRIPTION
		"Index to table of library status."
	::= {libraryStatusEntry 1}

lstConfig OBJECT-TYPE
	SYNTAX INTEGER { standalone(0), multimodule(1) }
	MAX-ACCESS read-only
	STATUS current
	DESCRIPTION
		"Indicates if library is standalone or multi-module."
	::= {libraryStatusEntry 2}

lstScsiId OBJECT-TYPE
	SYNTAX Integer32(0..15)
	MAX-ACCESS read-only
	STATUS current
	DESCRIPTION
		"Indicates library SCSI bus ID."
	::= {libraryStatusEntry 3}

lstStatus	OBJECT-TYPE
	SYNTAX DisplayString
	MAX-ACCESS read-only
	STATUS current
	DESCRIPTION
		"Indication of current library status."
	::= {libraryStatusEntry 4}

lstChangerStatus	OBJECT-TYPE
	SYNTAX Integer32
	MAX-ACCESS read-only
	STATUS current
	DESCRIPTION
		"Bit-mapped indication of current changer status:
			bit 0 - cartridge map valid
			bit 1 - initializing
			bit 2 - door open
			bit 3 - front panel mode
			bit 4 - door closed
			bit 5 - browser mode
			bit 6 - master busy"
	::= {libraryStatusEntry 5}

lstLibraryState	OBJECT-TYPE
	SYNTAX INTEGER { initializing(0), online(1), offline(2) }
	MAX-ACCESS read-only
	STATUS current
	DESCRIPTION
		"Indication of current library state."
	::= {libraryStatusEntry 6}

errorTable OBJECT-TYPE
	SYNTAX SEQUENCE OF ErrorEntry
	MAX-ACCESS not-accessible
	STATUS current
	DESCRIPTION
		"Table containing fault code, severity and ACSII
	error messages displayed on front panel of library."
	::= {overlandNextGenState 3}

errorEntry OBJECT-TYPE
	SYNTAX ErrorEntry
	MAX-ACCESS not-accessible
	STATUS current
	DESCRIPTION
		"A row in the error info table."
	INDEX {errIndex}
	::= {errorTable 1}

ErrorEntry ::= SEQUENCE
{
	errIndex		Integer32,
	errCode			Integer32,
	errSeverity		INTEGER,
	errMsg			DisplayString,
	errActionMsg	DisplayString
}

errIndex OBJECT-TYPE
	SYNTAX Integer32 (1)
	MAX-ACCESS read-only
	STATUS current
	DESCRIPTION
		"Index to table of library error information."
	::= {errorEntry 1}

errCode OBJECT-TYPE
	SYNTAX Integer32 
	MAX-ACCESS read-only
	STATUS current
	DESCRIPTION
		"Hex code unique to the reported error."
	::= {errorEntry 2}

errSeverity OBJECT-TYPE
	SYNTAX INTEGER { informational(0), mild(1), hard(2), severe(3)}
	MAX-ACCESS read-only
	STATUS current
	DESCRIPTION
		"Indication of how serious the reported error is:
			0 = informational error, not very severe
			1 = mild error, operator intervention not necessary
			2 = hard error, may be corrected remotely
			3 = very severe, power cycle required to clear"
	::= {errorEntry 3}

errMsg OBJECT-TYPE
    SYNTAX  DisplayString
	MAX-ACCESS read-only
	STATUS current
	DESCRIPTION
		"ASCII message naming the current error."
	::= {errorEntry 4}

errActionMsg OBJECT-TYPE
    SYNTAX  DisplayString
	MAX-ACCESS read-only
	STATUS current
	DESCRIPTION
		"ASCII message providing additional information about current
		error and possibly some suggestions for correcting it."
	::= {errorEntry 5}

overlandStateGroup OBJECT-GROUP
	OBJECTS {
		errIndex, errCode, errSeverity, errMsg, errActionMsg,
		dstRowValid, dstIndex, dstState, dstMotion, dstCodeRevDrive, dstCodeRevController, dstScsiId, dstSerialNum, dstCleanRequested,
		lstIndex, lstConfig, lstScsiId, lstStatus, lstChangerStatus, lstLibraryState
	}
	STATUS current
	DESCRIPTION
		"Current library states which may be queried."
	::= {overlandNextGenGroups 3}
	 

-------------------------------------------------------------------------------------------
-- 4th group of OIDs report the components in the library
--	(overlandNextGenComponents)


-------------------------------------------------------------------------------------------
-- 5th group of OIDs report the attributes of the library
--	(overlandNextGenAttributes)

numModules OBJECT-TYPE
	SYNTAX Integer32 (0..256)
	MAX-ACCESS read-only
	STATUS current
	DESCRIPTION
		"Reads the total number of modules available
		in the attached library."
	::= {overlandNextGenAttributes 1}

numBins OBJECT-TYPE
	SYNTAX Integer32 (0..256)
	MAX-ACCESS read-only
	STATUS current
	DESCRIPTION
		"Reads the total number of cartridge storage slots available
		in the attached library."
	::= {overlandNextGenAttributes 2}

numDrives OBJECT-TYPE
	SYNTAX Integer32 (0..128)
	MAX-ACCESS read-only
	STATUS current
	DESCRIPTION
		"Reads the total number of drives available in the attached
		library."
	::= {overlandNextGenAttributes 3}

numMailSlots OBJECT-TYPE 
	SYNTAX Integer32 (0..15)
	MAX-ACCESS read-only
	STATUS current
	DESCRIPTION
		"Returns the total number of mail slots available in the
		attached library."
	::= {overlandNextGenAttributes 4}

moduleGeometryTable OBJECT-TYPE
	SYNTAX SEQUENCE OF ModuleGeometryEntry
	MAX-ACCESS not-accessible
	STATUS current
	DESCRIPTION
		"Table containing library module geometry."
	::= {overlandNextGenAttributes 5}

moduleGeometryEntry OBJECT-TYPE
	SYNTAX ModuleGeometryEntry
	MAX-ACCESS not-accessible
	STATUS current
	DESCRIPTION
		"A row in the library module geometry table."
	INDEX {modIndex}
	::= {moduleGeometryTable 1}

ModuleGeometryEntry ::= SEQUENCE
{
	modDesc			DisplayString,
	modIndex		Integer32,
	modAttached		INTEGER,
	modStatus		DisplayString,
	modConfig		INTEGER,
	modFwRev		Integer32,
	modNumBins		Integer32,
	modNumDrives	Integer32,
	modNumMailSlots	Integer32
}

modDesc OBJECT-TYPE
    SYNTAX  DisplayString
	MAX-ACCESS read-only
	STATUS current
	DESCRIPTION
		"If library geometry is valid, an ASCII message desribing
		the module."
	::= {moduleGeometryEntry 1}

modIndex OBJECT-TYPE
	SYNTAX Integer32 (0..7|8)
	MAX-ACCESS read-only
	STATUS current
	DESCRIPTION
		"Index to table of library module geometry:
			 8  = Master or Standalone module
			0-7 = Slave Module"
	::= {moduleGeometryEntry 2}

modAttached OBJECT-TYPE
	SYNTAX INTEGER { isNotAttached(0), isAttached(1) }
	MAX-ACCESS read-only
	STATUS current
	DESCRIPTION
		"Indication of whether or not module is attached."
	::= {moduleGeometryEntry 3}

modStatus OBJECT-TYPE
    SYNTAX  DisplayString
	MAX-ACCESS read-only
	STATUS current
	DESCRIPTION
		"ASCII message desribing the current status of the module."
	::= {moduleGeometryEntry 4}

modConfig OBJECT-TYPE
	SYNTAX INTEGER { unknown(0), lightning(1), thunder(2), invalid(3)}
	MAX-ACCESS read-only
	STATUS current
	DESCRIPTION
		"Indication of this module's type."
	::= {moduleGeometryEntry 5}

modFwRev OBJECT-TYPE
	SYNTAX Integer32
	MAX-ACCESS read-only
	STATUS current
	DESCRIPTION
		"Indication of this module's firmware revision level."
	::= {moduleGeometryEntry 6}

modNumBins OBJECT-TYPE
	SYNTAX Integer32
	MAX-ACCESS read-only
	STATUS current
	DESCRIPTION
		"Indication of the number of bins within this module."
	::= {moduleGeometryEntry 7}

modNumDrives OBJECT-TYPE
	SYNTAX Integer32
	MAX-ACCESS read-only
	STATUS current
	DESCRIPTION
		"Indication of the number of drives within this module."
	::= {moduleGeometryEntry 8}

modNumMailSlots OBJECT-TYPE
	SYNTAX Integer32
	MAX-ACCESS read-only
	STATUS current
	DESCRIPTION
		"Indication of the number of mailslots within this module."
	::= {moduleGeometryEntry 9}

overlandAttributesGroup OBJECT-GROUP
	OBJECTS {
		numModules, numBins, numDrives, numMailSlots,
		modDesc, modIndex, modAttached, modStatus, modConfig, modFwRev, modNumBins, modNumDrives, modNumMailSlots
	}
	STATUS current
	DESCRIPTION
		"Current library info which may be queried."
	::= {overlandNextGenGroups 4}


-------------------------------------------------------------------------------------------
-- 6th (and last) group of OIDs are events which may be reported by the library
--	(overlandNextGenEvents)

eventDoorOpen NOTIFICATION-TYPE
	STATUS  current
	DESCRIPTION
		"A library door has been opened."
	::= {overlandNextGenEvents 1}

eventMailSlotAccessed NOTIFICATION-TYPE
	STATUS  current
	DESCRIPTION
		"A mail slot is being accessed."
	::= {overlandNextGenEvents 2}

eventHardFault NOTIFICATION-TYPE
	STATUS  current
	DESCRIPTION
		"The library has posted a hard fault."
	::= {overlandNextGenEvents 3}

eventSlaveFailed NOTIFICATION-TYPE
	STATUS  current
	DESCRIPTION
		"A slave module has faulted."
	::= {overlandNextGenEvents 4}

eventPowerSupplyFailed NOTIFICATION-TYPE
	STATUS  current
	DESCRIPTION
		"One of the redundant power supplies has failed."
	::= {overlandNextGenEvents 5}

eventRequestDriveClean NOTIFICATION-TYPE
	STATUS  current
	DESCRIPTION
		"One of the library tape drives has requested a
		cleaning cycle to ensure continued data reliability."
	::= {overlandNextGenEvents 6}

eventFanStalled NOTIFICATION-TYPE
	STATUS  current
	DESCRIPTION
		"A tape drive fan has stalled."
	::= {overlandNextGenEvents 7}

eventDriveError NOTIFICATION-TYPE
	STATUS  current
	DESCRIPTION
		"A tape drive error has occurred."
	::= {overlandNextGenEvents 8}

eventDriveRemoved NOTIFICATION-TYPE
	STATUS  current
	DESCRIPTION
		"A tape drive has been removed from the library."
	::= {overlandNextGenEvents 9}

eventSlaveRemoved NOTIFICATION-TYPE
	STATUS  current
	DESCRIPTION
		"A slave module has been removed from the library."
	::= {overlandNextGenEvents 10}

eventFailedOver NOTIFICATION-TYPE
	STATUS  current
	DESCRIPTION
		"The library is failed over to the Secondary Master."
	::= {overlandNextGenEvents 11}

eventLoaderRetriesExcessive NOTIFICATION-TYPE
	STATUS  current
	DESCRIPTION
		"The library has detected excessive loader retries."
	::= {overlandNextGenEvents 12}


overlandNotificationGroup NOTIFICATION-GROUP
	NOTIFICATIONS {
		eventDoorOpen, eventMailSlotAccessed, eventHardFault, eventSlaveFailed, eventPowerSupplyFailed, eventRequestDriveClean,
		eventFanStalled, eventDriveError, eventDriveRemoved, eventSlaveRemoved, eventFailedOver, eventLoaderRetriesExcessive
	}
	STATUS	current
	DESCRIPTION
		"Trap events returned by the browser."
	::= {overlandNextGenGroups 7}

END
