WG102-MIB DEFINITIONS ::= BEGIN

IMPORTS
        enterprises, IpAddress             
                        FROM RFC1155-SMI
        DisplayString, PhysAddress
                        FROM RFC1213-MIB
        OBJECT-TYPE                         FROM RFC-1212
        TRAP-TYPE                           FROM RFC-1215
        ifIndex	    					    FROM RFC1213-MIB
		  Unsigned32, MODULE-IDENTITY FROM SNMPv2-SMI;

 

netgear			        OBJECT IDENTIFIER ::= { enterprises 4526 }
wirelessProducts		OBJECT IDENTIFIER ::= { netgear 4 }


wg102     OBJECT IDENTIFIER ::= { wirelessProducts 3 }

version MODULE-IDENTITY
    LAST-UPDATED	"200409081800Z"
    ORGANIZATION	"NETGEAR Inc."
    CONTACT-INFO
		"4500 Great America Parkway
		Santa Clara, California 95054
		Phone: (408) 907-8000
		Fax: (408) 907-8097
		Web Site: http://www.netgear.com "
    DESCRIPTION
        "The MIB module for 802.11g ProSafe Wireless Access Point entities."
         ::= { wg102 1000 }

wirelessAPSystemGroup	OBJECT IDENTIFIER ::= { version 1 }
wirelessAPManageGroup	OBJECT IDENTIFIER ::= { version 2 }
wirelessAP24GGroup	    OBJECT IDENTIFIER ::= { version 3 }


apMacAddress    OBJECT-TYPE
	SYNTAX		PhysAddress
	ACCESS		read-only
	STATUS		mandatory
	DESCRIPTION
		"Access Point MAC address, It will be like '00c002003009'"
	::= { wirelessAPSystemGroup 1 }

apFirmwareVersion       OBJECT-TYPE
	SYNTAX		DisplayString
	ACCESS		read-only
	STATUS		mandatory
	DESCRIPTION
		""
	::= { wirelessAPSystemGroup 2 }

apIPaddress             OBJECT-TYPE
	SYNTAX	IpAddress
	ACCESS	read-write
	STATUS		mandatory
	DESCRIPTION
		""
	::= { wirelessAPSystemGroup 6 }

apIPsubnetMask          OBJECT-TYPE
	SYNTAX	IpAddress
	ACCESS	read-write
	STATUS		mandatory
	DESCRIPTION
		""
	::= { wirelessAPSystemGroup 7 }

apGateway               OBJECT-TYPE
	SYNTAX	IpAddress
	ACCESS	read-write
	STATUS		mandatory
	DESCRIPTION
		""
	::= { wirelessAPSystemGroup 8 }

apDNSServerIPAddress    OBJECT-TYPE
	SYNTAX	IpAddress
	ACCESS	read-write
	STATUS		mandatory
	DESCRIPTION
		""
	::= { wirelessAPSystemGroup 9 }	
	
apDHCPMode              OBJECT-TYPE
	SYNTAX	INTEGER 
	{
        disable(0),
        dhcp-Client(1)
    }
	ACCESS	read-write
	STATUS	mandatory
	DESCRIPTION
		""
	::= { wirelessAPSystemGroup 10 }

apSystemName            OBJECT-TYPE
	SYNTAX		DisplayString (SIZE(0..15))
	ACCESS		read-write
	STATUS		mandatory
	DESCRIPTION    
		"Wireless Access Point Name"
	::= { wirelessAPSystemGroup 11 }

apTimeZone      OBJECT-TYPE
	SYNTAX		DisplayString (SIZE(0..4))
	ACCESS		read-write
	STATUS		mandatory
	DESCRIPTION
	"  Input the numeric  
	0     UK,GreenWich,Casablanca,Monrovia (GMT),
    -12   Eniwetok,Kwajalein (GMT-12:00),
    -11   Midway I., Samoa (GMT-11:00),
    -10   Hawaii (GMT-10:00),
    -9.5  Marqesas Is. (GMT-09:30),
    -9    Alaska (GMT-09:00),
    -8.5  Pitciarn Is. (GMT-08:30),
    -8    Pacific Time ..US and Canada (GMT-08:00),
    -7    MountainTime(USA),Arizona (GMT-07:00),
    -6    CentralTime(USA),Mexico City,Tequciqalpa (GMT-06:00),
    -5    EasternTime(USA),Bogota,Lima,Quito,Indiana East (GMT-05:00),
    -4    Caracas,La Paz (GMT-04:00),
    -3.5  Newfoundland (GMT-03:30),
    -3    Brasilia,Beunos Aires,Georgetown (GMT-03:00),
    -2    Mid-Atlantic (GMT-02:00),
    -1    Azores,Cape Verde Is. (GMT-01:00),
    1     Europe (GMT+01:00),
    2     Egypt,Finland,Romania,Turkey,Greece,Israel,Jordan(GMT+02:00),
    3     Iraq, Syria,Russia (GMT+03:00),
    3.5   Iran (GMT+03:30),
    4     Armenia, Azerbaijan (GMT+04:00),
    4.5   Afghanistan (GMT+04:30),
    5     Russia,Pakistan (GMT+05:00),
    5.5   India (GMT+05:30),
    6     Bangladesh,Russia (GMT+06:00),
    6.5   Burma (GMT+06:30),
    7     Russia,Thailand, Combodia, Laos (GMT+07:00),
    8     Russia,China,Mongolia,Indonesia,Philippines,Taiwan,WA (GMT+08:00),
    9     Russia,Japan,Korea (GMT+09:00),
    9.5   Adelaide,Darwin (GMT+09:30),
    10    Eastern Standard(Aust),Russia,Gaum,Papua New Guinea (GMT+10:00)
	"
	::= { wirelessAPSystemGroup 13 }
	
apDaylightSaving               OBJECT-TYPE
	SYNTAX	INTEGER 
	{
        disable(0),
        enable(1)
    }
	ACCESS	read-write
	STATUS	mandatory
	DESCRIPTION
		""
	::= { wirelessAPSystemGroup 14 }

apCountryDomain OBJECT-TYPE
	SYNTAX	INTEGER 
	{
        asia(410),
        australia(36),
        canada(124),
        denmark(208),
        europe(40),
        finland(246),
        france(250),
        germany(276),
        ireland(372),
        italy(380),
        japan(392),
        mexico(484),
        netherlands(528),
        newZealand(554),
        norway(578),
        puertoRico(630),
        southAmerica(340),
        spain(724),
        sweden(752),
        switzerland(756),
        unitedKingdom(826),
        unitedStates(840)
    }
	ACCESS	read-write
	STATUS		mandatory
	DESCRIPTION
		"Wireless Access Point Country Domain"
	::= { wirelessAPSystemGroup 15 } 
	
apDateTime OBJECT-TYPE
        SYNTAX      DisplayString
        ACCESS      read-only
        STATUS      mandatory
        DESCRIPTION
        ""   
    ::= { wirelessAPSystemGroup 16 }

--apSystemUpTime OBJECT-TYPE
--	  SYNTAX  	TimeTicks
--      ACCESS    read-only
--      STATUS  	mandatory
--      DESCRIPTION
--           "The time (in hundredths of a second) since the
--            network management portion of the system was last
--            re-initialized. 
--            It will like '11223533' in the unit of 1/100second.
--		This object value is the same as MIB-II sysUpTime object"
--	::= { wirelessAPSystemGroup 17 }     			

apConnectedStation OBJECT IDENTIFIER ::= { wirelessAPSystemGroup 19 }

apConnectedStationTable	    OBJECT-TYPE
	SYNTAX		SEQUENCE OF ApConnectedStationEntry
	ACCESS	not-accessible
	STATUS		mandatory
	DESCRIPTION
		"Wireless AP Connected Station Table Object"
	::= { apConnectedStation 1 }
    
apConnectedStationEntry	OBJECT-TYPE
	SYNTAX		ApConnectedStationEntry
	ACCESS	    not-accessible
	STATUS		mandatory
	DESCRIPTION
		"An entry containing information for Wireless AP Connected Station Table"
	INDEX {ifIndex}
	::= { apConnectedStationTable 1 }
	
ApConnectedStationEntry ::=
	SEQUENCE 
	{
		apConnectedStationMacAddr		PhysAddress,
		apConnectedStationStatus		INTEGER
    }	

apConnectedStationMacAddr		OBJECT-TYPE
	SYNTAX		PhysAddress
	ACCESS	    read-only
	STATUS		mandatory
	DESCRIPTION
		"Wireless Connected Station Mac Address"
	::= { apConnectedStationEntry 1 }

apConnectedStationStatus		OBJECT-TYPE
	SYNTAX		INTEGER 
	{
		dot1xAuthenticated(0),
		macAuthenticated(1),
		authenticating(2),
		allow(3),
		blocked(4)
    }
	ACCESS	read-only
	STATUS		mandatory
	DESCRIPTION
		"Wireless Connected Station Status"
	::= { apConnectedStationEntry 2 }
         
--
apRebootNow OBJECT-TYPE
        SYNTAX      INTEGER  
        {
            not-reboot(0),
            reboot(1)
        }
                    
        ACCESS  read-write
        STATUS      mandatory
        DESCRIPTION
            "Setting this object to true(1) causes the device to reset.
             Reading this object always returns false(2)."
        ::= { wirelessAPManageGroup 1 }

apResetToFactoryDefault OBJECT-TYPE
        SYNTAX      INTEGER
        {
            not-reset(0),
            reset(1)
        }
        ACCESS  read-write
        STATUS      mandatory
        DESCRIPTION
            "Setting this object to true(1) causes the device to reset
            to factory default value. Reading this object always
            returns false(2)."
        ::= { wirelessAPManageGroup 2 }

apTrapReceiveIpAddress OBJECT-TYPE
        SYNTAX  IpAddress
        ACCESS read-write
        STATUS mandatory
        DESCRIPTION
            " "
        ::= {wirelessAPManageGroup 5 }

apSNMPEnable OBJECT-TYPE
        SYNTAX	INTEGER 
        {
            disable(0),
            enable(1)   
        }
        ACCESS read-write
        STATUS mandatory
        DESCRIPTION
            " "
        ::= {wirelessAPManageGroup 6 }

apSNMPReadCommunity OBJECT-TYPE
        SYNTAX DisplayString (SIZE(0..32))
        ACCESS read-write
        STATUS mandatory
        DESCRIPTION
            " "
        ::= {wirelessAPManageGroup 7 }
        
apSNMPWriteCommunity OBJECT-TYPE
        SYNTAX DisplayString (SIZE(0..32))
        ACCESS read-write
        STATUS mandatory
        DESCRIPTION
            " "
        ::= {wirelessAPManageGroup 8 }
apAccessControl	                OBJECT-TYPE
	SYNTAX	INTEGER 
	{
		off(0),
	    loacl(1),
	    radiusBased(2)
    }
	ACCESS	read-write
	STATUS	mandatory
	DESCRIPTION
		"Wireless Access Point Control"
	DEFVAL { 0}
 	::= { wirelessAPManageGroup 12 }

apAccessControlList OBJECT IDENTIFIER ::= { wirelessAPManageGroup 13 }

apAccessControlListTable OBJECT-TYPE
	SYNTAX		SEQUENCE OF ApAccessControlListEntry	
	ACCESS	    not-accessible
	STATUS		mandatory
	DESCRIPTION
		"Wireless Access Point Control List Table Object"
	::= { apAccessControlList 1 }

apAccessControlListEntry OBJECT-TYPE
	SYNTAX		ApAccessControlListEntry
	ACCESS	    not-accessible
	STATUS		mandatory
	DESCRIPTION
		"An entry containing information for Wireless Access Point Control List Table Object"
	INDEX {ifIndex}
	::= { apAccessControlListTable 1 }

    ApAccessControlListEntry ::= SEQUENCE 
    {
	    apAccessControlListMacAddr		PhysAddress
    }
        
		
apAccessControlListMacAddr OBJECT-TYPE
		SYNTAX		PhysAddress
		ACCESS	    read-only
		STATUS		mandatory
		DESCRIPTION
			"Wireless Access Point Control List Mac Address"
		::= { apAccessControlListEntry 1 }




apCtlOperate OBJECT IDENTIFIER ::= {wirelessAPManageGroup 14}

apAddACLMacAddr OBJECT-TYPE
        SYNTAX  PhysAddress
        ACCESS read-write
        STATUS mandatory
        DESCRIPTION
            "The added entry's Physical Address, 
             Reading this object always return '000000000000'"
        ::= {apCtlOperate 1}

apDelACLMacAddr OBJECT-TYPE
        SYNTAX  PhysAddress
        ACCESS read-write
        STATUS mandatory
        DESCRIPTION
            "The deleted entry's Physical Address, 
             Reading this object always return '000000000000'"
        ::= {apCtlOperate 2}	        
	
apSyslog OBJECT-TYPE
    SYNTAX	INTEGER 
	{
		disable(0),
		enable(1)
    }
	ACCESS	read-write
	STATUS	mandatory
	DESCRIPTION
		""
	DEFVAL { 0 }
	::= { wirelessAPManageGroup 25 }
	
apSyslogPort 	OBJECT-TYPE
	SYNTAX	INTEGER (0..65535)
	ACCESS	read-write
	STATUS	mandatory
	DESCRIPTION
		"Syslog Port"
	::= { wirelessAPManageGroup  26 }	
	
apSyslogServer OBJECT-TYPE
	SYNTAX	DisplayString (SIZE(0..15))
	ACCESS		read-write
	STATUS		mandatory
	DESCRIPTION
		""
	::= { wirelessAPManageGroup 27 }
        
apWirelessSettingGroup 	OBJECT IDENTIFIER ::= { wirelessAP24GGroup 1 }
apWirelessSecurityGroup 	OBJECT IDENTIFIER ::= { wirelessAP24GGroup 2 }

apWirelessMode   OBJECT-TYPE
	SYNTAX	INTEGER 
	{
        disable(0),
		b-and-g(1),
		b(2),
		g(3)
    }
	ACCESS	    read-write
	STATUS		mandatory
	DESCRIPTION
		""
	::= { apWirelessSettingGroup  1 }
	
apOperateMode 	OBJECT-TYPE
	SYNTAX	INTEGER 
	{
        wirelessAccessPoint(0),
        pointToPoint(2),
        pointToMultiPoint(3),
        repeaterAccessPoint(4)
    }
	ACCESS	read-write
	STATUS	mandatory
	DESCRIPTION
		"AP Operation Mode"
	::= { apWirelessSettingGroup  2 }	
	
apBridgeWlanClientAsoc 	OBJECT-TYPE
	SYNTAX	INTEGER 
	{
        disable(0),
        enable(1)
    }
	ACCESS	read-write
	STATUS	mandatory
	DESCRIPTION
		""
	::= { apWirelessSettingGroup  3 }	
	
apSSID  OBJECT-TYPE
	SYNTAX 	DisplayString (SIZE(0..32))
	ACCESS 	read-write
	STATUS 	mandatory
	DESCRIPTION
		"Wireless Access Point SSID
		This object value should be the same as 
		IEEE 802.11 MIB dot11DesiredSSID"
	::= { apWirelessSettingGroup  4 }
	
apChannelNo  OBJECT-TYPE
	SYNTAX INTEGER (0..14)
	ACCESS	read-write
	STATUS		mandatory
	DESCRIPTION
		"Wireless Access Point Channel No
		Auto(0) default"
	DEFVAL { 0 }
	::= { apWirelessSettingGroup  5 }
	
apRemoteMacAddress  OBJECT-TYPE
	SYNTAX		PhysAddress
	ACCESS		read-write
	STATUS		mandatory
	DESCRIPTION
		"The Destination Address When one operation mode is selected which the remote address necessary."
	::= { apWirelessSettingGroup  6 }	
	
apChildMacAddress  OBJECT-TYPE
	SYNTAX		PhysAddress
	ACCESS		read-write
	STATUS		mandatory
	DESCRIPTION
		""
	::= { apWirelessSettingGroup  7 }	
	
apBroadcastSSID      OBJECT-TYPE
	SYNTAX	INTEGER 
	{
		disabled(0),
		enabled(1)
    }
	ACCESS	read-write
	STATUS	mandatory
	DESCRIPTION
		"Enabled or disabled Wireless Access Point Broadcast 
		Wireless Network Name SSID"
	DEFVAL { 1 }
	::= { apWirelessSettingGroup  8 }	
	
apWirelessSeparation      OBJECT-TYPE
	SYNTAX	INTEGER 
	{
		disabled(0),
		enabled(1)
    }
	ACCESS	read-write
	STATUS	mandatory
	DESCRIPTION
		""
	DEFVAL { 0 }
	::= { apWirelessSettingGroup  9 }		
	
apFragmentationLength 	OBJECT-TYPE
	SYNTAX	INTEGER (256..2346)
	ACCESS	read-write
	STATUS	mandatory
	DESCRIPTION
		""
	::= { apWirelessSettingGroup  10 }	
	
apBeaconInterval 	OBJECT-TYPE
	SYNTAX	INTEGER (20..3000)
	ACCESS	read-write
	STATUS	mandatory
	DESCRIPTION
		""
	::= { apWirelessSettingGroup  11 }				
	
apRTSThreshold 	OBJECT-TYPE
	SYNTAX	INTEGER (256..2346)
	ACCESS	read-write
	STATUS	mandatory
	DESCRIPTION
		""
	::= { apWirelessSettingGroup  12 }		
	
apPreambleType      OBJECT-TYPE
	SYNTAX	INTEGER 
	{
		long(0),
		auto(1)
    }
	ACCESS	read-write
	STATUS	mandatory
	DESCRIPTION
		""
	DEFVAL { 0 }
	::= { apWirelessSettingGroup  13 }
	
apOutputPowerLevel  OBJECT-TYPE
	SYNTAX	INTEGER 
	{
		full(0),
		half(1),
		quarter(2),
		eighth(3),
		minimum(4)
	}
	ACCESS 	read-write
	STATUS 	mandatory
	DESCRIPTION
		""
	DEFVAL { 0 }
	::= { apWirelessSettingGroup  14 }	

apDTIM 	OBJECT-TYPE
	SYNTAX	INTEGER (1..255)
	ACCESS	read-write
	STATUS	mandatory
	DESCRIPTION
		""
	::= { apWirelessSettingGroup  15 }		

apSuperG   OBJECT-TYPE
	SYNTAX	INTEGER 
	{
		disable(0),
		enable(1)
	}
	ACCESS 	read-write
	STATUS 	mandatory
	DESCRIPTION
		""
	DEFVAL { 0 }
	::= { apWirelessSettingGroup  16 }	
	
apHTTPRedirect   OBJECT-TYPE
	SYNTAX	INTEGER 
	{
		disable(0),
		enable(1)
	}
	ACCESS 	read-write
	STATUS 	mandatory
	DESCRIPTION
		""
	DEFVAL { 0 }
	::= { apWirelessSettingGroup  17 }	

apHTTPRedirectURL  OBJECT-TYPE
	SYNTAX 	DisplayString (SIZE(0..32))
	ACCESS 	read-write
	STATUS 	mandatory
	DESCRIPTION
		""
	::= { apWirelessSettingGroup  18 }
	
apDataRate         OBJECT-TYPE
	SYNTAX	INTEGER 
	{
		auto-negotiate(0),
		rate-1Mbps(1),
		rate-2Mbps(2),
		rate-5dot5Mbps(3),
		rate-11Mbps(4),
		rate-6Mbps(5),
		rate-9Mbps(6),
		rate-12Mbps(7),
		rate-18Mbps(8),
		rate-24Mbps(9),
		rate-36Mbps(10),
		rate-48Mbps(11),
		rate-54Mbps(12),
        rate-108Mbps(13)
	}
	ACCESS	read-write
	STATUS	mandatory
	DESCRIPTION
		""
	DEFVAL { 0 }
	::= { apWirelessSettingGroup 19 }	

apStatistic OBJECT IDENTIFIER ::=  { apWirelessSettingGroup 20 }

apWiredEthernetStat OBJECT IDENTIFIER ::= { apStatistic 1 }

apLanRecvPacket  OBJECT-TYPE
        SYNTAX Unsigned32
        MAX-ACCESS read-only
        STATUS current
        DESCRIPTION
	"the field indicates the sum of received packets."
	::= { apWiredEthernetStat 1 }

apLanTransPacket  OBJECT-TYPE
        SYNTAX Unsigned32
        MAX-ACCESS read-only
        STATUS current
        DESCRIPTION
	"the field indicates the sum of transmitted packets."
	::= { apWiredEthernetStat 2 }

apLanRecvBytes  OBJECT-TYPE
        SYNTAX Unsigned32
        MAX-ACCESS read-only
        STATUS current
        DESCRIPTION
	"the field indicates the sum of received bytes."
	::= { apWiredEthernetStat 3 }

apLanTransBytes  OBJECT-TYPE
        SYNTAX Unsigned32
        MAX-ACCESS read-only
        STATUS current
        DESCRIPTION
	"the field indicates the sum of transmitted bytes."
	::= { apWiredEthernetStat 4 }

apWirelessStat OBJECT IDENTIFIER ::= { apStatistic 2 }

apWlanRecvUnicastPacket  OBJECT-TYPE
        SYNTAX Unsigned32
        MAX-ACCESS read-only
        STATUS current
        DESCRIPTION
	"the field indicates the sum of received unicast packets."
	::= { apWirelessStat 1 }

apWlanTransUnicastPacket  OBJECT-TYPE
        SYNTAX Unsigned32
        MAX-ACCESS read-only
        STATUS current
        DESCRIPTION
	"the field indicates the sum of transmitted unicast packets."
	::= { apWirelessStat 2 }

apWlanRecvBroadcastPsacket  OBJECT-TYPE
        SYNTAX Unsigned32
        MAX-ACCESS read-only
        STATUS current
        DESCRIPTION
	"the field indicates the sum of received broadcast packets."
	::= { apWirelessStat 3 }

apWlanTransBroadcastPacket  OBJECT-TYPE
        SYNTAX Unsigned32
        MAX-ACCESS read-only
        STATUS current
        DESCRIPTION
	"the field indicates the sum of transmitted broadcast packets."
	::= { apWirelessStat 4 }

apWlanRecvMulticastPacket  OBJECT-TYPE
        SYNTAX Unsigned32
        MAX-ACCESS read-only
        STATUS current
        DESCRIPTION
	"the field indicates the sum of received multicast packets."
	::= { apWirelessStat 5 }

apWlanTransMulticastPacket  OBJECT-TYPE
        SYNTAX Unsigned32
        MAX-ACCESS read-only
        STATUS current
        DESCRIPTION
	"the field indicates the sum of transmitted multicast packets."
	::= { apWirelessStat 6 }

apWlanRecvPacket  OBJECT-TYPE
        SYNTAX Unsigned32
        MAX-ACCESS read-only
        STATUS current
        DESCRIPTION
	"the field indicates the sum of received packets."
	::= { apWirelessStat 7 }

apWlanTransPacket  OBJECT-TYPE
        SYNTAX Unsigned32
        MAX-ACCESS read-only
        STATUS current
        DESCRIPTION
	"the field indicates the sum of transmitted packets."
	::= { apWirelessStat 8 }

apWlanRecvBytes  OBJECT-TYPE
        SYNTAX Unsigned32
        MAX-ACCESS read-only
        STATUS current
        DESCRIPTION
	"the field indicates the sum of received bytes."
	::= { apWirelessStat 9 }

apWlanTransBytes  OBJECT-TYPE
        SYNTAX Unsigned32
        MAX-ACCESS read-only
        STATUS current
        DESCRIPTION
	"the field indicates the sum of transmitted bytes."
	::= { apWirelessStat 10 }

apPTMPallowList 	OBJECT IDENTIFIER ::= { apWirelessSettingGroup  27 }

mac1  OBJECT-TYPE
	SYNTAX		PhysAddress
	ACCESS		read-write
	STATUS		mandatory
	DESCRIPTION
		""
	::= { apPTMPallowList  1 }
	
mac2  OBJECT-TYPE
	SYNTAX		PhysAddress
	ACCESS		read-write
	STATUS		mandatory
	DESCRIPTION
		""
	::= { apPTMPallowList  2 }
	
mac3  OBJECT-TYPE
	SYNTAX		PhysAddress
	ACCESS		read-write
	STATUS		mandatory
	DESCRIPTION
		""
	::= { apPTMPallowList  3 }
	
mac4  OBJECT-TYPE
	SYNTAX		PhysAddress
	ACCESS		read-write
	STATUS		mandatory
	DESCRIPTION
		""
	::= { apPTMPallowList  4 }			

    -------------------------------------------------------------------------------	
    
apSecuritySystem 	    OBJECT-TYPE
	SYNTAX	INTEGER 
	{
		none(0),
		wep(1),
		wpa-psk(2),
		wpa-802dot1x(3),
		dot1x(4)
    }
	ACCESS	read-write
	STATUS	mandatory
	DESCRIPTION
		""
	DEFVAL { 0 }
	::= { apWirelessSecurityGroup  1 }
	
ap802dot1xWEPKeySize  OBJECT-TYPE
	SYNTAX	INTEGER 
	{
	    none(0),
		bit64(1),
		bit128(2),
		bit152(3)
    }
	ACCESS 	read-write
	STATUS 	mandatory
	DESCRIPTION
		""
	DEFVAL { 0 }
	::= { apWirelessSecurityGroup  2 }	
	
apWEPMode   OBJECT-TYPE
	SYNTAX	INTEGER 
	{
        open-64WEP-MODE(0),
        open-128WEP-MODE(1),
        open-152WEP-MODE(6),
        share-64WEP-MODE(2),
        share-128WEP-MODE(3),
        share-152WEP-MODE(7)
    }
	ACCESS	read-write
	STATUS	mandatory
	DESCRIPTION
		""
	::= { apWirelessSecurityGroup  3 }
	
apWEPKeysSet  OBJECT IDENTIFIER ::= { apWirelessSecurityGroup  4 }
	
apKeys24GSetTable	    OBJECT-TYPE
	SYNTAX	SEQUENCE OF ApKeys24GSetEntry
	ACCESS	not-accessible
	STATUS		mandatory
	DESCRIPTION
		""
	::= { apWEPKeysSet  1 }

apKeys24GSetEntry	OBJECT-TYPE
	SYNTAX	ApKeys24GSetEntry
	ACCESS	not-accessible
	STATUS		mandatory
	DESCRIPTION
		""
	INDEX	{ ifIndex  }
	::= { apKeys24GSetTable 1 }

    ApKeys24GSetEntry ::=
	SEQUENCE 
	{
		apKeysSetEnabled 	INTEGER,
		apKeys 			DisplayString
	}

apKeysSetEnabled  OBJECT-TYPE
	SYNTAX	INTEGER 
	{
		disabled(0),
		enabled(1)
    }
	ACCESS	read-write
	STATUS	mandatory
	DESCRIPTION
		""
	DEFVAL { 0 }
	::= { apKeys24GSetEntry 1 }

apKeys 	OBJECT-TYPE
	SYNTAX	OCTET STRING (SIZE(0..13))
	ACCESS	read-write
	STATUS	mandatory
	DESCRIPTION
		""
	::= { apKeys24GSetEntry 2 }	
	
apWPANetworkKey 	OBJECT-TYPE
	SYNTAX	DisplayString (SIZE(0..32))
	ACCESS	read-write
	STATUS	mandatory
	DESCRIPTION
		""
	::= { apWirelessSecurityGroup  6 }	
	
apWPAEncryption  OBJECT-TYPE
	SYNTAX	INTEGER 
	{
		tkip(0),
		aes-ccmp(3)
	}
	ACCESS	read-write
	STATUS	mandatory
	DESCRIPTION
		""
	DEFVAL { 0 }
	::= { apWirelessSecurityGroup  7 }	

apWPAGroupKeyUpdate 	OBJECT-TYPE
	SYNTAX	INTEGER 
	{
		disable(0),
		enable(1)
	}
	ACCESS	read-write
	STATUS	mandatory
	DESCRIPTION
		""
	::= { apWirelessSecurityGroup  10 }	

apWPAGroupKeyLifetime 	OBJECT-TYPE
	SYNTAX	INTEGER (5..200)
	ACCESS	read-write
	STATUS	mandatory
	DESCRIPTION
		""
	::= { apWirelessSecurityGroup  11 }	
	
apWPAMembershipTerminatedGroupKeyUpdate  OBJECT-TYPE
	SYNTAX	INTEGER 
	{
		disabled(0),
		enabled(1)
	}
	ACCESS	read-write
	STATUS	mandatory
	DESCRIPTION
		""
	DEFVAL { 0 }
	::= { apWirelessSecurityGroup  12 }	
	
apPrimaryRadiusServer 	OBJECT-TYPE
	SYNTAX	DisplayString
	ACCESS	read-write
	STATUS	mandatory
	DESCRIPTION
		""
	::= { apWirelessSecurityGroup  13 }

apPrimaryRadiusPort 	OBJECT-TYPE
	SYNTAX	INTEGER (0..65535)
	ACCESS	read-write
	STATUS	mandatory
	DESCRIPTION
		"Radius Port"
	::= {apWirelessSecurityGroup  14 }

apPrimaryRadiusSharedKey 	OBJECT-TYPE
	SYNTAX	DisplayString (SIZE(0..32))
	ACCESS	read-write
	STATUS	mandatory
	DESCRIPTION
		"Radius Server Shared Key"
	::= { apWirelessSecurityGroup  15 }

apPrimaryRadiusAccountServer 	OBJECT-TYPE
	SYNTAX	DisplayString
	ACCESS	read-write
	STATUS	mandatory
	DESCRIPTION
		""
	::= { apWirelessSecurityGroup  16 }

apPrimaryRadiusAccountPort 	OBJECT-TYPE
	SYNTAX	INTEGER (0..65535)
	ACCESS	read-write
	STATUS	mandatory
	DESCRIPTION
		""
	::= { apWirelessSecurityGroup  17 }
	
apPrimaryRadiusAccountSharedKey 	OBJECT-TYPE
	SYNTAX	DisplayString (SIZE(0..32))
	ACCESS	read-write
	STATUS	mandatory
	DESCRIPTION
		"Radius Server Shared Key"
	::= { apWirelessSecurityGroup  18 }
	
apSecondaryRadiusServer 	OBJECT-TYPE
	SYNTAX	DisplayString
	ACCESS	read-write
	STATUS	mandatory
	DESCRIPTION
		""
	::= { apWirelessSecurityGroup  19 }

apSecondaryRadiusPort 	OBJECT-TYPE
	SYNTAX	INTEGER (0..65535)
	ACCESS	read-write
	STATUS	mandatory
	DESCRIPTION
		"Radius Port"
	::= { apWirelessSecurityGroup  20 }

apSecondaryRadiusSharedKey 	OBJECT-TYPE
	SYNTAX	DisplayString (SIZE(0..32))
	ACCESS	read-write
	STATUS	mandatory
	DESCRIPTION
		"Radius Server Shared Key"
	::= { apWirelessSecurityGroup  21 }

apSecondaryRadiusAccountServer 	OBJECT-TYPE
	SYNTAX	DisplayString
	ACCESS	read-write
	STATUS	mandatory
	DESCRIPTION
		""
	::= { apWirelessSecurityGroup  22 }

apSecondaryRadiusAccountPort 	OBJECT-TYPE
	SYNTAX	INTEGER (0..65535)
	ACCESS	read-write
	STATUS	mandatory
	DESCRIPTION
		""
	::= { apWirelessSecurityGroup  23 }
	
apSecondaryRadiusAccountSharedKey 	OBJECT-TYPE
	SYNTAX	DisplayString (SIZE(0..32))
	ACCESS	read-write
	STATUS	mandatory
	DESCRIPTION
		"Radius Server Shared Key"
	::= { apWirelessSecurityGroup  24 }	
	
apReauthenticationTime 	OBJECT-TYPE
	SYNTAX	INTEGER (1800..36000)
	ACCESS	read-write
	STATUS	mandatory
	DESCRIPTION
		""
	::= { apWirelessSecurityGroup  27 }
	
END
