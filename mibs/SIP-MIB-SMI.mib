SIP-MIB-SMI DEFINITIONS ::= BEGIN

   IMPORTS 
        MODULE-IDENTITY, 
        mib-2 
             FROM SNMPv2-SMI; 

   sipMIB MODULE-IDENTITY 
        LAST-UPDATED   "200007080000Z" 
        ORGANIZATION   "IETF SIP Working Group, SIP MIB Team" 
        CONTACT-INFO 
                "SIP MIB Team email: sip-mib@egroups.com 

                 Co-editor  Kevin Lingle 
                            Cisco Systems, Inc. 
                 postal:    7025 Kit Creek Road 

Lingle/Maeng/Walker                                                  5 
Internet Draft            SIP-MIB                          July, 2000 

                            P.O. Box 14987 
                            Research Triangle Park, NC 27709 
                            USA 
                 email:     klingle@cisco.com 
                 phone:     +1-919-392-2029 

                 Co-editor  Joon Maeng 
                            VTEL Corporation 
                 postal:    108 Wild Basin Rd. 
                            Austin, TX 78746 
                            USA 
                 email:     joon_maeng@vtel.com 
                 phone:     +1-512-437-4567 

                 Co-editor  Dave Walker 
                            SS8 Networks, Inc. 
                 postal:    80 Hines Road 
                            Kanata, ON  K2K 2T8 
                            Canada 
                 email:     drwalker@ss8networks.com 
                 phone:     +1 613 592 2100" 
        DESCRIPTION 
                "Initial version of Session Initiation Protocol (SIP) 
                 MIB module that defines base OID for all other 
                 SIP-related MIB Modules." 
        ::= { mib-2 9998 } -- to be assigned by IANA 

END
