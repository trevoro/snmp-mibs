-- *****************************************************************
--
-- stn-log.mib:  
--      Spring Tide Networks Log MIB file.
--
--
--      Copyright (c) 1999, 2000 by Spring Tide Networks, Inc.
--                      ALL RIGHTS RESERVED       
--
-- *****************************************************************

-- MIB Object definitions for Spring Tide Network Loger

STN-LOG-MIB DEFINITIONS ::= BEGIN

    IMPORTS
        MODULE-IDENTITY,
        OBJECT-TYPE,
        NOTIFICATION-TYPE, 
        IpAddress,
        Integer32
                FROM SNMPv2-SMI

        DisplayString,
		TruthValue
                FROM SNMPv2-TC

        MODULE-COMPLIANCE
                FROM SNMPv2-CONF

        stnSystems,
        stnNotification
                FROM SPRING-TIDE-NETWORKS-SMI

        stnEngineIndex, 
        stnEngineSlot,
        stnEngineCpu
                FROM STN-CHASSIS-MIB;


    stnLog       MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION
              "The MIB module that describes managed objects of
               Spring Tide Networks Event Logger."
        ::= { stnSystems 13 }


    --
    -- Top Level STN Event Log MIB Objects
    --
    stnLogObjects	    OBJECT IDENTIFIER ::= { stnLog 1 }
    stnLogMibConformance    OBJECT IDENTIFIER ::= { stnLog 2 }


    --
    -- Logger configuration
    --
    stnLogState OBJECT-TYPE
        SYNTAX        INTEGER { 
                                enabled(1), 
                                disabled(2)
                              } 
        MAX-ACCESS    read-only
        STATUS        current
        DESCRIPTION   "Indicates whether the system logging is enabled."
        DEFVAL { enabled }
        ::= { stnLogObjects 1 }

    stnLogFlushTimer OBJECT-TYPE
        SYNTAX          Integer32
        MAX-ACCESS      read-only
        STATUS          current
        DESCRIPTION     "The log flush time interval in seconds."
        ::= { stnLogObjects 2 }

    stnLogMaxDisplay OBJECT-TYPE
        SYNTAX          Integer32
        MAX-ACCESS      read-only
        STATUS          current
        DESCRIPTION     "The maximum number of rows in stnLogEventTable."
        ::= { stnLogObjects 3 }


    --
    -- Logger Server Table
    --
    stnLogServerTable OBJECT-TYPE
        SYNTAX        SEQUENCE OF StnLogServerEntry
        MAX-ACCESS    not-accessible
        STATUS        current
        DESCRIPTION   "A list of flush servers for the Event Logger."
        ::= { stnLogObjects 4 }
 
    stnLogServerEntry OBJECT-TYPE
        SYNTAX          StnLogServerEntry
        MAX-ACCESS      not-accessible
        STATUS          current
        DESCRIPTION     "Entry contains a particular log event."
        INDEX           { stnLogServerIndex }
        ::= { stnLogServerTable 1 }
 
    StnLogServerEntry ::= SEQUENCE {
                stnLogServerIndex               Integer32,
                stnLogServerType                INTEGER,
                stnLogServerIpAddress           IpAddress,
                stnLogServerFacility            DisplayString,
                stnLogServerFileSize            Integer32           
                }

    stnLogServerIndex OBJECT-TYPE
        SYNTAX          Integer32
        MAX-ACCESS      read-only
        STATUS          current
        DESCRIPTION     "A sequence number that identifies a flush server."
        ::= { stnLogServerEntry 1 }

    stnLogServerType OBJECT-TYPE
        SYNTAX          INTEGER { 
                                    flash(1), 
                                    syslog(2),
                                    nma(3),
                                    serial(4),
                                    debug-serial(5)
                                } 
        MAX-ACCESS      read-only
        STATUS          current
        DESCRIPTION     "The type of this log server."
        DEFVAL { flash }
        ::= { stnLogServerEntry 2 }

    stnLogServerIpAddress OBJECT-TYPE
        SYNTAX          IpAddress
        MAX-ACCESS      read-only
        STATUS          current
        DESCRIPTION     "The log server IP address if the type 
                         is Syslog or Network Management Application."
        ::= { stnLogServerEntry 3 }

    stnLogServerFacility OBJECT-TYPE
        SYNTAX          DisplayString
        MAX-ACCESS      read-only
        STATUS          current
        DESCRIPTION     "The log server facility if the type is Syslog."
        ::= { stnLogServerEntry 4 }

    stnLogServerFileSize OBJECT-TYPE
        SYNTAX          Integer32
        MAX-ACCESS      read-only
        STATUS          current
        DESCRIPTION     "The maximum file size when the log is written 
                         to flash, 0 when other types."
        ::= { stnLogServerEntry 5 }

    --
    -- Log Filter Table
    --
    stnLogFilterTable OBJECT-TYPE
        SYNTAX        SEQUENCE OF StnLogFilterEntry
        MAX-ACCESS    not-accessible
        STATUS        current
        DESCRIPTION   "Log filter per MC on each engine."
        ::= { stnLogObjects 5 }
 
    stnLogFilterEntry OBJECT-TYPE
        SYNTAX          StnLogFilterEntry
        MAX-ACCESS      not-accessible
        STATUS          current
        DESCRIPTION     "Each entry contains a particular log filter 
                         for a modular component on an engine."
        INDEX           { stnLogFilterEngineId, stnLogFilterMcId}
        ::= { stnLogFilterTable 1 }
 
    StnLogFilterEntry ::= SEQUENCE {
                stnLogFilterEngineId            Integer32,  
                stnLogFilterMcId                Integer32,        
                stnLogFilterPriority            INTEGER,
                stnLogFilterSeverityFatal       TruthValue,
                stnLogFilterSeverityError       TruthValue,
                stnLogFilterSeverityWarning     TruthValue,
                stnLogFilterSeverityInfo        TruthValue,
                stnLogFilterSeverityTrace       TruthValue,
                stnLogFilterSeverityDebug       TruthValue
                }

    stnLogFilterEngineId OBJECT-TYPE
        SYNTAX          Integer32
        MAX-ACCESS      read-only
        STATUS          current
        DESCRIPTION     "The engine ID."
        ::= { stnLogFilterEntry 1 }

    stnLogFilterMcId OBJECT-TYPE
        SYNTAX          Integer32
        MAX-ACCESS      read-only
        STATUS          current
        DESCRIPTION     "The modular component ID."
        ::= { stnLogFilterEntry 2}

    stnLogFilterPriority OBJECT-TYPE
        SYNTAX          INTEGER (0..10)
        MAX-ACCESS      read-only
        STATUS          current
        DESCRIPTION     "The priority filter level. 0 disable the log. This is now depricated"
        ::= { stnLogFilterEntry 3 }

    stnLogFilterSeverityFatal OBJECT-TYPE
        SYNTAX          TruthValue
        MAX-ACCESS      read-only
        STATUS          current
        DESCRIPTION     "Status of logging Fatal Events"
        ::= { stnLogFilterEntry 4 }

    stnLogFilterSeverityError OBJECT-TYPE
        SYNTAX          TruthValue
        MAX-ACCESS      read-only
        STATUS          current
        DESCRIPTION     "Status of logging Error Events"
        ::= { stnLogFilterEntry 5 }

    stnLogFilterSeverityWarning OBJECT-TYPE
        SYNTAX          TruthValue
        MAX-ACCESS      read-only
        STATUS          current
        DESCRIPTION     "Status of logging Warning Events"
        ::= { stnLogFilterEntry 6 }

    stnLogFilterSeverityInfo OBJECT-TYPE
        SYNTAX          TruthValue
        MAX-ACCESS      read-only
        STATUS          current
        DESCRIPTION     "Status of logging Info Events"
        ::= { stnLogFilterEntry 7 }

    stnLogFilterSeverityTrace OBJECT-TYPE
        SYNTAX          TruthValue
        MAX-ACCESS      read-only
        STATUS          current
        DESCRIPTION     "Status of logging Trace Events"
        ::= { stnLogFilterEntry 8 }

    stnLogFilterSeverityDebug OBJECT-TYPE
        SYNTAX          TruthValue
        MAX-ACCESS      read-only
        STATUS          current
        DESCRIPTION     "Status of logging Debug Events"
        ::= { stnLogFilterEntry 9 }


    --
    -- Log Event Table
    --
    stnLogEventTable OBJECT-TYPE
        SYNTAX        SEQUENCE OF StnLogEventEntry
        MAX-ACCESS    not-accessible
        STATUS        current
        DESCRIPTION   "A list of log entries."
        ::= { stnLogObjects 6 }
 
    stnLogEventEntry OBJECT-TYPE
        SYNTAX          StnLogEventEntry
        MAX-ACCESS      not-accessible
        STATUS          current
        DESCRIPTION     "Entry contains a particular log event."
        INDEX           { stnLogEventIndex }
        ::= { stnLogEventTable 1 }
 
    StnLogEventEntry ::= SEQUENCE {           
                stnLogEventIndex                Integer32,
                stnLogEventEngineId             Integer32,
                stnLogEventMcName               DisplayString,
                stnLogEventPriority             INTEGER,
                stnLogEventTimeStamp            DisplayString,
                stnLogEventMessage              DisplayString            
                }

    stnLogEventIndex OBJECT-TYPE
        SYNTAX          Integer32
        MAX-ACCESS      read-only
        STATUS          current
        DESCRIPTION     "A sequence number that identifies a log event."
        ::= { stnLogEventEntry 1 }

    stnLogEventEngineId OBJECT-TYPE
        SYNTAX          Integer32
        MAX-ACCESS      read-only
        STATUS          current
        DESCRIPTION     "The engine ID where this log event occured."
        ::= { stnLogEventEntry 2 }

    stnLogEventMcName OBJECT-TYPE
        SYNTAX          DisplayString (SIZE(4))
        MAX-ACCESS      read-only
        STATUS          current
        DESCRIPTION     "The name of moduler component this log event is from."
        ::= { stnLogEventEntry 3 }

    stnLogEventPriority OBJECT-TYPE
        SYNTAX          INTEGER (1..10)
        MAX-ACCESS      read-only
        STATUS          current
        DESCRIPTION     "The priority of this log event."
        ::= { stnLogEventEntry 4 }

    stnLogEventTimeStamp OBJECT-TYPE
        SYNTAX          DisplayString (SIZE(32))
        MAX-ACCESS      read-only
        STATUS          current
        DESCRIPTION     "The time stamp of this log event."
        ::= { stnLogEventEntry 5 }

    stnLogEventMessage OBJECT-TYPE
        SYNTAX          DisplayString
        MAX-ACCESS      read-only
        STATUS          current
        DESCRIPTION     "The log message."
        ::= { stnLogEventEntry 6 }


    --
    -- STN Traps & Notifications 
    --
    stnEventLogServerFailure NOTIFICATION-TYPE
        OBJECTS         { stnLogServerIndex, 
                          stnLogServerType, 
                          stnLogServerIpAddress }
        STATUS          current
        DESCRIPTION     "A stnEventLogServerFailure trap signifies that 
                        the agent entity has detected that the device
                        has lost contact to the external event log server.
                        The generation of this trap can be controlled by the
                        LogTraps configuration object."
        ::= { stnNotification 24 }

    stnEventLogInternalFailure NOTIFICATION-TYPE
        OBJECTS         { stnEngineIndex, 
                          stnEngineSlot, 
                          stnEngineCpu }
        STATUS          current
        DESCRIPTION     "A stnEventLogInternalFailure trap signifies that 
                        the agent entity has detected an internal
                        event log system failure. 
                        The generation of this trap can be controlled by the
                        LogTraps configuration object."
        ::= { stnNotification 25 }

END
