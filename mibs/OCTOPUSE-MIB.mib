--************************************************************************--
--  Name     : SNMP MIB for Octopus E LAN 10/20/30                        --
--                                                                        --
--  Date     : 24.11.2000                                                 --
--                                                                        --
--  Version  : 1.2.6                                                      --
--                                                                        --
--  Author   : Juergen Schwartze, ICN EN HO SE 86, Siemens, Witten        --
--                                                                        --
--  Purpose  : alarm forwarding, error history, statistics, cdr,          --
--             inventory                                                  --
--                                                                        --
--************************************************************************-- 

--*HOC********************************************************************--
--*                                                                      *--
--*    HISTORY OF CHANGE:                         VARIANTE: 2.2a         *--
--*                                                                      *--
--************************************************************************--
--*VERS| DATE | CHANGES                                      | KZ | VGNO *--
--*    |ttmmjj|                                              |    |      *--
--************************************************************************--
--* 01 |140199| first draft                                  |jsc |  N   *--
--* 02 |100299| trap community table, tftp config added      |jsc |  N   *--
--* 03 |180299| enhanced support for standard mibs           |jsc |  N   *--
--* 04 |030399| editorial update                             |jsc |  F   *--
--* 05 |300499| enumerations modified                        |jsc |  F   *--
--* 06 |100599| new mib objects                              |jsc |  N   *--
--* 07 |180599| new mib objects for octoExtensionTable       |jsc |  N   *--
--* 08 |170699| extended description for mib objects         |jsc |  N   *--
--* 09 |240699| description: delayed aps switchover          |jsc |  N   *--
--* 10 |300699| valid integer ranges                         |jsc |  F   *--
--************************************************************************--

--*HOC********************************************************************--
--*                                                                      *--
--*    HISTORY OF CHANGE:                         VARIANTE: 3.0          *--
--*                                                                      *--
--************************************************************************--
--*VERS| DATE | CHANGES                                      | KZ | VGNO *--
--*    |ttmmjj|                                              |    |      *--
--************************************************************************--
--* 01 |180200| extension for call charges               |jsc/hka |  N   *--
--* 02 |250500| new object IpAddress + editorial update      |hka |  N   *--
--* 03 |160800| CdrTftpClientTimer: range adapted to Database|hka |  F   *--
--* 04 |310800| update description                           |hka |  F   *--
--************************************************************************--

--*HOC********************************************************************--
--*                                                                      *--
--*    HISTORY OF CHANGE:                      VARIANTE: HiPath AllServe *--
--*                                                                      *--
--************************************************************************--
--*VERS| DATE | CHANGES                                      | KZ | VGNO *--
--*    |ttmmjj|                                              |    |      *--
--************************************************************************--
--* 01 |040500| editorial update                             |jsc |  F   *--
--* 02 |070700| new table LAN connection info                |jsc |  N   *--
--* 03 |230800| new object hiPathAllServeServer              |jsc |  N   *--
--* 04 |290900| new objects for HiPath FM (conn. control)    |jsc |  N   *--
--* 04 |021100| new objects for error histrory / agent vers. |jsc |  N   *--
--* 05 |241100| editorial update                             |jsc |  F   *--
--************************************************************************--


   OCTOPUSE-MIB DEFINITIONS ::= BEGIN
 
   IMPORTS
	TEXTUAL-CONVENTION FROM SNMPv2-TC
        IpAddress	
       	   FROM RFC1155-SMI
        MODULE-IDENTITY, OBJECT-TYPE, NOTIFICATION-TYPE, enterprises
           FROM SNMPv2-SMI;


-- Some MIB compilers require that the following 4 lines
-- which define the path to this MIB are added.

-- mgmt              OBJECT IDENTIFIER ::= { iso org(3) dod(6) internet(1)  mgmt(2) }
-- mib               OBJECT IDENTIFIER ::= { mgmt 1 }
-- private           OBJECT IDENTIFIER ::= { internet 4 }
-- enterprises       OBJECT IDENTIFIER ::= { private 1 }

   sni               OBJECT IDENTIFIER ::= {enterprises 231}
   siemensUnits      OBJECT IDENTIFIER ::= {sni 7}
   pn                OBJECT IDENTIFIER ::= {siemensUnits 2}
                     
   octopusE MODULE-IDENTITY
       LAST-UPDATED  "24.11.00"
       ORGANIZATION  "Siemens Information & Communication Networks"
       CONTACT-INFO  "            Technical Support               "
       DESCRIPTION
       "Octopus E MIB."
       ::= { pn 9 }

   octoControlGroup             OBJECT IDENTIFIER ::= {octopusE 1}
   octoErrorHistoryGroup        OBJECT IDENTIFIER ::= {octopusE 2}
   octoSystemInfoGroup          OBJECT IDENTIFIER ::= {octopusE 3}
   octoStatisticsGroup          OBJECT IDENTIFIER ::= {octopusE 4}
   octoCdrConfigGroup           OBJECT IDENTIFIER ::= {octopusE 5}
   octoTrapSpecifications       OBJECT IDENTIFIER ::= {octopusE 6}
   octoNetworkGroup             OBJECT IDENTIFIER ::= {octopusE 7}


--************************************************************************-- 
--******                     textual conventions                    ******--
--************************************************************************-- 

   DisplayString ::= OCTET STRING
       -- This data type is used to model textual information taken
       -- from the NVT ASCII character set.  By convention, objects
       -- with this syntax are declared as having SIZE (0..255)


   DateAndTime ::= TEXTUAL-CONVENTION
       DISPLAY-HINT "2d-1d-1d,1d:1d:1d.1d"
       STATUS       current
       DESCRIPTION
            "A date-time specification identical to rfc 1443 definition.

            field  octets  contents                  range
            -----  ------  --------                  -----
              1      1-2   year                      0..65536
              2       3    month                     1..12
              3       4    day                       1..31
              4       5    hour                      0..23
              5       6    minutes                   0..59
              6       7    seconds                   0..60
                           (use 60 for leap-second)
              7       8    deci-seconds              0..9

            For example, Tuesday May 26, 1992 at 1:30:15 PM EDT would be
            displayed as:
                             1992-5-26,13:30:15.0"
       SYNTAX      OCTET STRING (SIZE (8))


    ReadWrite ::= TEXTUAL-CONVENTION
       STATUS       current
       DESCRIPTION
            "A textual convention for describing objects that
             enable or disable some sort of write access."
       SYNTAX INTEGER {
            readWrite(1),
            readOnly(2)
            }


--********************************************************************--
--******                    Control Group                       ******--
--********************************************************************--

   octoSysState OBJECT-TYPE
       SYNTAX      INTEGER {
                     normal(1),
                     warning(2),
                     minor(3),
                     major(4),
                     critical(5)
                   }
       MAX-ACCESS  read-write
       STATUS      current
       DESCRIPTION
                   "The actual error state of the Octopus E PABX. Contains the
                    highest severity level of the recent error events. This object is
                    updated automatically, but it can also be modified manually."
       ::= { octoControlGroup 1 }

   tftpSwitchoverDateTime  OBJECT-TYPE
       SYNTAX      DateAndTime
       MAX-ACCESS  read-write
       STATUS      current
       DESCRIPTION
                   "Date and time for the switchover to the new system software. The configured
                    time will be ignored, if the upgrade is started with the
                    downloadAndImmediateSwitchover define of the tftpDownloadAction object.
                    octet format:
                    field  octets  contents                  range hex            (range dez)
                    -----  ------  --------                  ---------            ----------
                      1      1-2   year                      00 00 - FF FF        (0 - 65536)
                      2       3    month                     01    - 0C           (1 - 12)
                      3       4    day                       01    - 1F           (1 - 31)
                      4       5    hour                      00    - 17           (0 - 23)
                      5       6    minutes                   00    - 3B           (0 - 59)
                      6       7    seconds                   00    - 3B           (0 - 60)
                      7       8    deci-seconds              00    - 09           (0 - 9)

                      For example, to configure Wednesday June 16, 1999 at 8:30:15 AM
                      would be configured as 07 cf 06 10 08 1E 0F 00"
       ::= { octoControlGroup 2 }

   tftpDownloadAction  OBJECT-TYPE
    SYNTAX     INTEGER {
                 notDownloading(1),
                 downloadAndImmediateSwitchover(2),
                 downloadAndDelayedSwitchover(3),
                 downloadWithoutSwitchover(4)
               }
       MAX-ACCESS  read-write
       STATUS      current
       DESCRIPTION
                   "When this object is set to downloadAndImmediateSwitchover (2), the device
                    will download the new software from the configured host. After the
                    download is finished, the device will automatically restart with the new
                    software. If downloadAndDelayedSwitchover (3) is specified, the new image
                    is copied to the device. When the tftpDateTime value is matched, the device
                    discontinues its normal operation and does the software switchover. After
                    an automatic reset, it starts with the new system software. Setting
                    downloadWithoutSwitchover (4) initiates a download without switching over
                    to the new software. When the device is not downloading, this object will
                    have a value of notDownloading(1)."
    ::= { octoControlGroup 3 }

   octoResetControl  OBJECT-TYPE
    SYNTAX     INTEGER {
                    running(1),
                    warmBoot(2)
              }
    MAX-ACCESS read-write
    STATUS     current
    DESCRIPTION
        "Setting this object to warmBoot(2) causes the device to restart the application
         software with current configuration parameters saved in non-volatile memory. When
         the device is running normally, this variable has a value of running(1). The
         effect of configuring this object is identical to the configuration of the
         probeResetControl object of RFC 2021, except for the coldBoot option which is not
         supported."
    ::= { octoControlGroup 4 }

   octoSwitchoverState  OBJECT-TYPE
    SYNTAX     INTEGER {
                    readyForSwitchover(1),
                    notReadyForSwitchover(2),
                    initSwitchoverNow(3),
                    initSwitchoverDelayed(4)
              }
    MAX-ACCESS read-write
    STATUS     current
    DESCRIPTION
        "The values readyForSwitchover (1) and notReadyForSwitchover (2) indicate whether
         the system is ready to be switched over to the new software that was downloaded to
         the shadow flash area, or not. If it is not passible, octoShadowFlashState gives
         details on the reason.
         Setting this object to switchoverNow (3) causes the device to switchover immediately
         to the new software which was downloaded to the shadow flash area before and restart
         the system. initSwitchoverDelayed(4) causes a delayed switchover."
    ::= { octoControlGroup 5 }

   octoShadowFlashState  OBJECT-TYPE
    SYNTAX     INTEGER {
                    flashDeleted(1),
                    flashNotDeleted(2),
                    flashWriteProtected(3),
                    flashTooSmall(4),
                    deleteFlashNow(5)
              }
    MAX-ACCESS read-write
       STATUS      current
       DESCRIPTION
                   "This object informs about the state of the shadow flash memory area which
                    is used to buffer a new software image that is being downloaded to the
                    system. A download is only possible when the state is flashDeleted (1).
                    It is not possible to download if the state is flashNotDeleted(2), nor if
                    it's flashWriteProtected(3) (this means it is internally locked by software
                    because the system is not in the state of accepting new flash data). If the
                    flash memory is smaller than 8 MB ( flashTooSmall(4) ), no transfer is
                    possible, too. It is possible to delete an inactive software image from the
                    shadow flash area by setting deleteFlashNow (5)."
       ::= { octoControlGroup 6 }

   octoLoadLevel  OBJECT-TYPE
       SYNTAX      INTEGER (0..100)
       MAX-ACCESS  read-only
       STATUS      current
       DESCRIPTION
                   "The actual CPU load level (per cent)."
       ::= { octoControlGroup 7 }

   octoTrapRepetitions  OBJECT-TYPE
       SYNTAX      INTEGER (1..5)
       MAX-ACCESS  read-write
       STATUS      current
       DESCRIPTION
                   "The number of trap repetitions for error events marked as very important
                    (log-and-multiple-trap)."
       ::= { octoControlGroup 8 }

   octoCdrBufferState  OBJECT-TYPE
       SYNTAX     INTEGER {
                    accounting(1),
                    deleteBufferNow(2)
                  }
       MAX-ACCESS  read-write
       STATUS      current
       DESCRIPTION
                   "Use this object to delete the CDR buffer."
       ::= { octoControlGroup 9 }

   octoLogBufferState  OBJECT-TYPE
       SYNTAX     INTEGER {
                    logging(1),
                    deleteBufferNow(2)
                  }
       MAX-ACCESS  read-write
       STATUS      current
       DESCRIPTION
                   "Use this object to delete the log data."
       ::= { octoControlGroup 10 }

--********************************************************************--
--******                 Error History Group                    ******--
--********************************************************************--

   numberOfErrorHistoryEntries  OBJECT-TYPE
       SYNTAX      INTEGER (0..2147483187)
       MAX-ACCESS  read-write
       STATUS      current
       DESCRIPTION
                   "Contains the number of errors to be found in the error history table.
                    This value can be used to delete the last x entries (reduce value by x)
                    or to delete all entries (value = 0)."
       ::= { octoErrorHistoryGroup 1 }
  
   octoErrorHistoryTable  OBJECT-TYPE
       SYNTAX      SEQUENCE OF OctoErrorHistoryEntry
       MAX-ACCESS  not-accessible
       STATUS      current
       DESCRIPTION
                   "This table contains information about the errors that occured."
       ::= { octoErrorHistoryGroup 2 }

   octoErrorHistoryEntry  OBJECT-TYPE
       SYNTAX      OctoErrorHistoryEntry
       MAX-ACCESS  not-accessible
       STATUS      current
       DESCRIPTION
                   "The trap history table entries."
       INDEX { octoErrorIndex }
       ::= { octoErrorHistoryTable 1 }

   OctoErrorHistoryEntry ::= SEQUENCE {
       octoErrorIndex         INTEGER,
       octoErrorDateTime      DateAndTime,
       octoErrorClass         INTEGER,
       octoErrorCode          INTEGER,
       octoAccessSlot         INTEGER,
       octoAccessPort         INTEGER,
       octoErrorDescription   DisplayString,
       octoErrorSeverity      INTEGER
       }                 

   octoErrorIndex  OBJECT-TYPE
       SYNTAX      INTEGER (1..2147483187)
       MAX-ACCESS  read-only
       STATUS      current
       DESCRIPTION
                   "Identification of an table entry enabled by this index."
       ::= { octoErrorHistoryEntry 1 }

   octoErrorDateTime  OBJECT-TYPE
       SYNTAX      DateAndTime
       MAX-ACCESS  read-only
       STATUS      current
       DESCRIPTION
                   "Time, when the error occurred."
       ::= { octoErrorHistoryEntry 2 }

   octoErrorClass  OBJECT-TYPE
       SYNTAX      INTEGER (1..2147483187)
       MAX-ACCESS  read-only
       STATUS      current
       DESCRIPTION
                   "Contains the error class number (type of trap)."
       ::= { octoErrorHistoryEntry 3 }

   octoErrorCode  OBJECT-TYPE
       SYNTAX      INTEGER (1..2147483187)
       MAX-ACCESS  read-only
       STATUS      current
       DESCRIPTION
                   "Contains the error code."
       ::= { octoErrorHistoryEntry 4 }

   octoAccessSlot  OBJECT-TYPE
       SYNTAX      INTEGER (1..2147483187)
       MAX-ACCESS  read-only
       STATUS      current
       DESCRIPTION
                   "Contains the access slot for the error."
       ::= { octoErrorHistoryEntry 5 }
    
   octoAccessPort  OBJECT-TYPE
       SYNTAX      INTEGER (1..2147483187)
       MAX-ACCESS  read-only
       STATUS      current
       DESCRIPTION
                   "Contains the local access port of the error. Local means
                    that port numbering starts with 0 for each card."
       ::= { octoErrorHistoryEntry 6 }

   octoErrorDescription  OBJECT-TYPE
       SYNTAX      DisplayString (SIZE (1..255))
       MAX-ACCESS  read-only
       STATUS      current
       DESCRIPTION
                   "Detailed information about errors."
       ::= { octoErrorHistoryEntry 7 }

   octoErrorSeverity  OBJECT-TYPE
       SYNTAX      INTEGER {
                     normal(1),
                     warning(2),
                     minor(3),
                     major(4),
                     critical(5)
                   }
       MAX-ACCESS  read-only
       STATUS      current
       DESCRIPTION
                   "Contains the severity of the specific error."
       ::= { octoErrorHistoryEntry 8 }
       
       

--********************************************************************--
--******             Octopus E system info                      ******--
--********************************************************************--
 
   sysHardwareVersion  OBJECT-TYPE
       SYNTAX      DisplayString (SIZE (1..25))
       MAX-ACCESS  read-only
       STATUS      current
       DESCRIPTION
                   "Contains the version string of the system hardware."
       ::= { octoSystemInfoGroup 1 }

   sysSoftwareVersion  OBJECT-TYPE
       SYNTAX      DisplayString (SIZE (1..25))
       MAX-ACCESS  read-only
       STATUS      current
       DESCRIPTION
                   "Contains the version string of the system software."
       ::= { octoSystemInfoGroup 2 }
 
   sysCodeNumber  OBJECT-TYPE
       SYNTAX      DisplayString (SIZE (1..25))
       MAX-ACCESS  read-only
       STATUS      current
       DESCRIPTION
                   "Contains the code number of the system software."
       ::= { octoSystemInfoGroup 3 }

   sysSoftwareLocation  OBJECT-TYPE
       SYNTAX  INTEGER {
                    lower(1),
                    upper(2)
               }
       MAX-ACCESS  read-only
       STATUS      current
       DESCRIPTION
                   "Contains location (address space) where the system
                    software is currently running."
       ::= { octoSystemInfoGroup 4 }


--******      slot info      ******--

   numberOfSlotTableEntries  OBJECT-TYPE
       SYNTAX      INTEGER (0..2147483187)
       MAX-ACCESS  read-only
       STATUS      current
       DESCRIPTION
                   "Contains the number of entries in the slot table."
       ::= { octoSystemInfoGroup 5 }
   
   octoSlotTable  OBJECT-TYPE
       SYNTAX      SEQUENCE OF OctoSlotTableEntry
       MAX-ACCESS  not-accessible
       STATUS      current
       DESCRIPTION
                   "This table contains information about the system slots."
       ::= { octoSystemInfoGroup 6 }
 
   octoSlotTableEntry  OBJECT-TYPE
       SYNTAX      OctoSlotTableEntry
       MAX-ACCESS  not-accessible
       STATUS      current
       DESCRIPTION
                   "The slot table entries."
       INDEX { cardIndex }
       ::= { octoSlotTable 1 }

   OctoSlotTableEntry ::= SEQUENCE {
       cardIndex             INTEGER,
       cardBoxNum            INTEGER,
       cardSlotNum           INTEGER,
       cardType              DisplayString,
       cardDescription       DisplayString,
       cardCodeNumber        DisplayString,
       cardState             INTEGER
       }

   cardIndex  OBJECT-TYPE
       SYNTAX      INTEGER (1..2147483187)
       MAX-ACCESS  read-only
       STATUS      current
       DESCRIPTION
                   "Identification of an table entry enabled by this index."
       ::= { octoSlotTableEntry 1 }

   cardBoxNum  OBJECT-TYPE
       SYNTAX      INTEGER (1..2147483187)
       MAX-ACCESS  read-only
       STATUS      current
       DESCRIPTION
                   "Index of the box where the card is placed."
       ::= { octoSlotTableEntry 2 }

   cardSlotNum  OBJECT-TYPE
       SYNTAX      INTEGER (1..2147483187)
       MAX-ACCESS  read-only
       STATUS      current
       DESCRIPTION
                   "Index of the slot where the card is placed."
       ::= { octoSlotTableEntry 3 }
 
   cardType  OBJECT-TYPE
       SYNTAX      DisplayString (SIZE (1..40))
       MAX-ACCESS  read-only
       STATUS      current
       DESCRIPTION
                   "Code for the type of the card."
       ::= { octoSlotTableEntry 4 }
  
   cardDescription  OBJECT-TYPE
       SYNTAX      DisplayString (SIZE (1..255))
       MAX-ACCESS  read-only
       STATUS      current
       DESCRIPTION
                   "Textual card description."
       ::= { octoSlotTableEntry 5 }

   cardCodeNumber  OBJECT-TYPE
       SYNTAX      DisplayString (SIZE (1..25))
       MAX-ACCESS  read-only
       STATUS      current
       DESCRIPTION
                   "Contains the code number of the card software."
       ::= { octoSlotTableEntry 6 }

    cardState  OBJECT-TYPE
       SYNTAX      INTEGER {
                     normal(1),
                     warning(2),
                     minor(3),
                     major(4),
                     critical(5)
                   }
       MAX-ACCESS  read-only
       STATUS      current
       DESCRIPTION
                   "Contains the state of the card."
       ::= { octoSlotTableEntry 7 }


--******      port info      ******--

   numberOfPortTableEntries  OBJECT-TYPE
       SYNTAX      INTEGER (0..2147483187)
       MAX-ACCESS  read-only
       STATUS      current
       DESCRIPTION
                   "Contains the number of entries in the port table."
       ::= { octoSystemInfoGroup 7 }
   
   octoPortTable  OBJECT-TYPE
       SYNTAX      SEQUENCE OF OctoPortTableEntry
       MAX-ACCESS  not-accessible
       STATUS      current
       DESCRIPTION
                   "This table contains information about the system ports."
       ::= { octoSystemInfoGroup 8 }

   octoPortTableEntry  OBJECT-TYPE
       SYNTAX      OctoPortTableEntry
       MAX-ACCESS  not-accessible
       STATUS      current
       DESCRIPTION
                   "The port table entries."
       INDEX { portIndex }
       ::= { octoPortTable 1 }
  
   OctoPortTableEntry ::= SEQUENCE {
       portIndex       INTEGER,
       portCardIndex   INTEGER,
       portType        DisplayString,
       portState       INTEGER,
       portLock        INTEGER
       }

   portIndex  OBJECT-TYPE
       SYNTAX      INTEGER (1..2147483187)
       MAX-ACCESS  read-only
       STATUS      current
       DESCRIPTION
                   "Identification of an table entry enabled by this index."
       ::= { octoPortTableEntry 1 }

   portCardIndex  OBJECT-TYPE
       SYNTAX      INTEGER (1..2147483187)
       MAX-ACCESS  read-only
       STATUS      current
       DESCRIPTION
                   "Reference to the card the port is assigned to."
       ::= { octoPortTableEntry 2 }

   portType  OBJECT-TYPE
       SYNTAX      DisplayString (SIZE (1..40))
       MAX-ACCESS  read-only
       STATUS      current
       DESCRIPTION
                   "Contains the type of the port."
       ::= { octoPortTableEntry 3 }
 
   portState  OBJECT-TYPE
       SYNTAX      INTEGER { 
                     inactive(1),
                     active (2)
                   }
       MAX-ACCESS  read-only
       STATUS      current
       DESCRIPTION
                   "Contains the general state of the port."
       ::= { octoPortTableEntry 4 }

   portLock  OBJECT-TYPE
       SYNTAX      INTEGER {
                     unlocked(1),
                     lockedBySoftware(2),
                     lockedByHardware(3),
                     lockedBySoftAndHardware(4)
                   }
       MAX-ACCESS  read-write
       STATUS      current
       DESCRIPTION
                   "This object contains the lock state of the port. A software lock
                    can be enabled / disabled. Possible state transitions:
                        unlocked -> lockedBySoftware
                        lockedByHardware -> lockedBySoftAndHardware
                        lockedBySoftware -> unlocked
                        lockedBySoftAndHardware -> lockedByHardware"
       ::= { octoPortTableEntry 5 }


--******      hardware extension info      ******--

   numberOfExtensionTableEntries  OBJECT-TYPE
       SYNTAX      INTEGER (0..2147483187)
       MAX-ACCESS  read-only
       STATUS      current
       DESCRIPTION
                   "Contains the number of entries in the hardware extension table."
       ::= { octoSystemInfoGroup 9 }
   
   octoExtensionTable  OBJECT-TYPE
       SYNTAX      SEQUENCE OF OctoExtensionTableEntry
       MAX-ACCESS  not-accessible
       STATUS      current
       DESCRIPTION
                   "This table contains information about the hardware extensions."
       ::= { octoSystemInfoGroup 10 }

   octoExtensionTableEntry  OBJECT-TYPE
       SYNTAX      OctoExtensionTableEntry
       MAX-ACCESS  not-accessible
       STATUS      current
       DESCRIPTION
                   "The extension table entries."
       INDEX { extensionIndex }
       ::= { octoExtensionTable 1 }
  
   OctoExtensionTableEntry ::= SEQUENCE {
       extensionIndex       INTEGER,
       extensionDescription DisplayString,
       extensionCodeNumber  DisplayString
       }

   extensionIndex  OBJECT-TYPE
       SYNTAX      INTEGER (1..2147483187)
       MAX-ACCESS  read-only
       STATUS      current
       DESCRIPTION
                   "Identification of an table entry enabled by this index."
       ::= { octoExtensionTableEntry 1 }


    extensionDescription  OBJECT-TYPE
       SYNTAX      DisplayString (SIZE (1..40))
       MAX-ACCESS  read-only
       STATUS      current
       DESCRIPTION
                   "Contains a textual desription of the hardware extension."
       ::= { octoExtensionTableEntry 2 }


    extensionCodeNumber  OBJECT-TYPE
       SYNTAX      DisplayString (SIZE (1..40))
       MAX-ACCESS  read-only
       STATUS      current
       DESCRIPTION
                   "Contains the code number of the hardware extension."
       ::= { octoExtensionTableEntry 3 }


--******      LAN connection info      ******--

   numberOfLanConnTableEntries  OBJECT-TYPE
       SYNTAX      INTEGER (0..2147483187)
       MAX-ACCESS  read-only
       STATUS      current
       DESCRIPTION
                   "Contains the number of entries in the LAN connection table."
       ::= { octoSystemInfoGroup 11 }
   
   octoLanConnTable  OBJECT-TYPE
       SYNTAX      SEQUENCE OF OctoLanConnTableEntry
       MAX-ACCESS  not-accessible
       STATUS      current
       DESCRIPTION
                   "This table contains information about the interfaces available
                    for LAN access of the device or its cards."
       ::= { octoSystemInfoGroup 12 }
 
   octoLanConnTableEntry  OBJECT-TYPE
       SYNTAX      OctoLanConnTableEntry
       MAX-ACCESS  not-accessible
       STATUS      current
       DESCRIPTION
                   "The LAN connection table entries."
       INDEX { lanConnIndex }
       ::= { octoLanConnTable 1 }

   OctoLanConnTableEntry ::= SEQUENCE {
       lanConnIndex             INTEGER,
       lanConnDescription       DisplayString,
       lanConnIpAddress         IpAddress,
       lanConnSubnetMask        IpAddress,
       lanConnStatus            INTEGER
       }

   lanConnIndex  OBJECT-TYPE
       SYNTAX      INTEGER (1..2147483187)
       MAX-ACCESS  read-only
       STATUS      current
       DESCRIPTION
                   "Identification of an table entry enabled by this index."
       ::= { octoLanConnTableEntry 1 }

   lanConnDescription  OBJECT-TYPE
       SYNTAX  DisplayString (SIZE (0..255))
       MAX-ACCESS  read-only
       STATUS      current
       DESCRIPTION
                   "Textual desription on the LAN connection."
       ::= { octoLanConnTableEntry 2 }

   lanConnIpAddress  OBJECT-TYPE
       SYNTAX  IpAddress
       MAX-ACCESS  read-only
       STATUS      current
       DESCRIPTION
                   "IP address of the LAN connection."
       ::= { octoLanConnTableEntry 3 }

   lanConnSubnetMask  OBJECT-TYPE
       SYNTAX  IpAddress
       MAX-ACCESS  read-only
       STATUS      current
       DESCRIPTION
                   "Subnet mask of the LAN connection."
       ::= { octoLanConnTableEntry 4 }

   lanConnStatus  OBJECT-TYPE
       SYNTAX  INTEGER {
                 up(1),
                 down(2),
                 testing(3)
               }
       MAX-ACCESS  read-only
       STATUS      current
       DESCRIPTION
                   "Status of the LAN Connection."
       ::= { octoLanConnTableEntry 5 }
      
   hiPathAllServeServerIpAddress   OBJECT-TYPE
       SYNTAX      IpAddress
       MAX-ACCESS  read-only
       STATUS      current
       DESCRIPTION
                   "IP address of the HiPath AllServe (Venus) server."
       ::= { octoSystemInfoGroup 13 }
       


--*** index for port status notification trap ***--

   indexOfLastPortStatusNotificationTrap  OBJECT-TYPE
       SYNTAX      INTEGER (1..2147483187)
       MAX-ACCESS  read-write
       STATUS      current
       DESCRIPTION
		"Index of last 'port status change' notification trap sent by the device.
                 Note: only reset possible (0)"
       ::= { octoSystemInfoGroup 14 }


--***         additional system info       ***--

   sysSnmpAgentVersion  OBJECT-TYPE
       SYNTAX  DisplayString (SIZE (0..255))
       MAX-ACCESS  read-only
       STATUS      current
       DESCRIPTION
                   "Version number of the systems SNMP agent (formatting: x.y.z.)"
       ::= { octoSystemInfoGroup 15 }



--********************************************************************--
--******                   Statistics Group                     ******--
--********************************************************************--

   numberOfFeatureStatTableEntries  OBJECT-TYPE
       SYNTAX      INTEGER (1..2147483187)
       MAX-ACCESS  read-only
       STATUS      current
       DESCRIPTION
                   "Contains the number of feature counters to be found in the table."
       ::= { octoStatisticsGroup 1 }
    
   octoFeatureStatTable  OBJECT-TYPE
       SYNTAX      SEQUENCE OF OctoFeatureStatEntry
       MAX-ACCESS  not-accessible
       STATUS      current
       DESCRIPTION
                   "This table contains information about the usage of specific system
                    features. It is designed to monitor the use of these features for
                    a limited time only, because each counter is limited to one byte."
       ::= { octoStatisticsGroup 2 }

   octoFeatureStatEntry  OBJECT-TYPE
       SYNTAX      OctoFeatureStatEntry
       MAX-ACCESS  not-accessible
       STATUS      current
       DESCRIPTION
                   "The feature statistics table entries."
       INDEX { featureIndex }
       ::= { octoFeatureStatTable 1 }

   OctoFeatureStatEntry ::= SEQUENCE {
       featureIndex        INTEGER,
       featureDescription  DisplayString,
       featureCounter      INTEGER
       }

   featureIndex  OBJECT-TYPE
       SYNTAX      INTEGER (1..2147483187)
       MAX-ACCESS  read-only
       STATUS      current
       DESCRIPTION
                   "Identification of an table entry enabled by this index."
       ::= { octoFeatureStatEntry 1 }

   featureDescription  OBJECT-TYPE
       SYNTAX      DisplayString (SIZE (1..255))
       MAX-ACCESS  read-only
       STATUS      current
       DESCRIPTION
                   "Description of the feature."
       ::= { octoFeatureStatEntry 2 }

   featureCounter  OBJECT-TYPE
       SYNTAX      INTEGER (1..2147483187)
       MAX-ACCESS  read-only
       STATUS      current
       DESCRIPTION
                   "This Counter indicates how often the feature was used since
                    last system reload"
       ::= { octoFeatureStatEntry 3 }

   featureStatTableReset  OBJECT-TYPE
       SYNTAX      INTEGER {
                     counting(1),
                     reset(2)
                   }
       MAX-ACCESS  read-write
       STATUS      current
       DESCRIPTION
                   "Enables reset (2) of all counters of the featureStatTable."
       ::= { octoStatisticsGroup 3 }


--********************************************************************--
--******                        CDR Group                       ******--
--********************************************************************--

                  
--*** CDR output format only relevant over LAN ***--

   octoCdrSeparator  OBJECT-TYPE
       SYNTAX      INTEGER {
                     dosMode(1),
                     unixMode(2)
                   }
       MAX-ACCESS  read-write
       STATUS      current
       DESCRIPTION
                   "Separator between following CDRs:
                   DOS mode (1): CRLF
                   UNIX mode (2): LF"
       ::= { octoCdrConfigGroup 1 }

   octoCdrElementSeparator  OBJECT-TYPE
       SYNTAX      INTEGER {
                     pipe(124),
                     semicolon(59),
                     blank(32)
                   }
       MAX-ACCESS  read-write
       STATUS      current
       DESCRIPTION
                   "Separator between the different elements of one CDR:
                   pipe (0x7c): '|'
                   semicolon (0x3b): ';'
                   blank (0x20): ' ' NOTE: no write access for blank"
       ::= { octoCdrConfigGroup 2 }

--*** TFTP-Server in Octopus E ***--

   octoCdrThresholdValue  OBJECT-TYPE
       SYNTAX      INTEGER (1..2147483187)
       MAX-ACCESS  read-write
       STATUS      current
       DESCRIPTION
		"CDR buffer limit (only relevant for TFTP server mode):
                threshold value (in percent) for sending a CDR data notification trap
                recommended values: 0 to 80"
       ::= { octoCdrConfigGroup 3 }

--*** TFTP-Client in Octopus E ***--

   octoCdrTftpFileCounter  OBJECT-TYPE
       SYNTAX      INTEGER (1..2147483187)
       MAX-ACCESS  read-write
       STATUS      current
       DESCRIPTION
		" CDR <FileCounter> (only relevant for TFTP client mode):
                For each transferred CDR-file a new filename is necassary
		filename: 'GDS<IPAdr>.c<FileCounter>'"
       ::= { octoCdrConfigGroup 4 }

   octoCdrTftpServerDestAddress  OBJECT-TYPE
       SYNTAX      IpAddress
       MAX-ACCESS  read-write
       STATUS      current
       DESCRIPTION
		"Destination IP addresse of CDR TFTP server (only relevant for TFTP client mode)"
       ::= { octoCdrConfigGroup 5 }

   octoCdrTftpServerAlternateDestAddress  OBJECT-TYPE
       SYNTAX      IpAddress
       MAX-ACCESS  read-write
       STATUS      current
       DESCRIPTION
		"Alternate destination IP addresse of CDR TFTP server (only relevant for TFTP client mode):
		is the CDR TFTP Server not reachable the switch transfers CDR data to this
		alternative server"
       ::= { octoCdrConfigGroup 6 }  

   octoCdrTftpClientTimer  OBJECT-TYPE
       SYNTAX      INTEGER (1..2147483187)
       MAX-ACCESS  read-write
       STATUS      current
       DESCRIPTION
		"cycle time in minutes for initiating CDR output,
		max value 1439 minutes (23hours,59minutes)
		(only relevant for TFTP client mode)"
       ::= { octoCdrConfigGroup 7 }


--*** TCP-Client in Octopus E ***--

   octoCdrTcpServerDestAddress  OBJECT-TYPE
       SYNTAX     IpAddress
       MAX-ACCESS  read-write
       STATUS      current
       DESCRIPTION
		"Destination IP addresse of CDR TCP server (only relevant for TCP client mode)"
       ::= { octoCdrConfigGroup 8 }

   octoCdrTcpServerDestPort  OBJECT-TYPE
       SYNTAX      INTEGER (1..2147483187)
       MAX-ACCESS  read-write
       STATUS      current
       DESCRIPTION
		"Destination TCP port of CDR TCP server (only relevant for TCP client mode)"
       ::= { octoCdrConfigGroup 9 }


--*** CDR Output Mode ***--

   octoCdrOutputMode  OBJECT-TYPE
       SYNTAX      INTEGER {
                     v24port(1),
                     uPNport(2),
                     pCVPLport(3),
                     tftpClient(4),
                     tftpServer(5),
                     tcpClient(6),
                     noOutput(7)
                   }
       MAX-ACCESS  read-write
       STATUS      current
       DESCRIPTION
		"CDR (Call Detailed Record) output mode:
                V24-Port    (1): the device is permanently connected over a V.24 connection 
                                 to an extern application and sends each CDR immidiatly 
                                 NOTE: no write access
		UPN-Port    (2): the device is permanently connected over terminal adapter (PPM) connection 
                                 to an extern application and sends each CDR immidiatly 
                                 NOTE: no write access
		PCVPL-Port  (3): the device is permanently connected over a CorNet TS connection 
                                 to an extern application (PCVPL) and sends each CDR immidiatly 
                                 NOTE: no write access
                TFTP-Client (4): the device sends the collected CDRs to the administrated TFTP-Server
		TFTP-Server (5): an extern TFTP client can request the collected CDRs
		TCP-Client  (6): the device is permanently connected to an extern TCP server and sends
                                 each CDR immidiatly
		NoOutput    (7): no output for CDR"
       ::= { octoCdrConfigGroup 10 }

--*** CDR Notification Traps ***--

   octoIndexOfLastCdrNotificationTrap  OBJECT-TYPE
       SYNTAX      INTEGER (1..2147483187)
       MAX-ACCESS  read-write
       STATUS      current
       DESCRIPTION
		"Index of last CDR notification trap sent by the device
                 Note: only reset possible (0)"
       ::= { octoCdrConfigGroup 11 }

   octoTypeOfLastCdrNotificationTrap  OBJECT-TYPE
       SYNTAX      INTEGER (1..2147483187)
       MAX-ACCESS  read-only
       STATUS      current
       DESCRIPTION
		"Type of last CDR notification trap sent by the device:
                 (1) : error - CDR buffer overflow 
                 (2) : warning - CDR buffer is filled up over 80%
                 (3) : notification - administrateable CDR buffer threshold is reached
                       -> extern TFTP client has to get the collected CDRs
                 (4) : warning - TCP Client couldn´t reach administrated server
                 (5) : warning - TFTP Client couldn´t reach administrated server
                 (6) : warning - TFTP Client couldn´t reach administrated alternative server"
       ::= { octoCdrConfigGroup 12 }

   octoDescriptionOfLastCdrNotificationTrap  OBJECT-TYPE
       SYNTAX      DisplayString (SIZE (1..255))
       MAX-ACCESS  read-only
       STATUS      current
       DESCRIPTION
		"Textual description of last CDR notification trap sent
                 by the device"
       ::= { octoCdrConfigGroup 13 }


--********************************************************************--
--******                 trap specifications                    ******--
--********************************************************************--

   sendAlarm  NOTIFICATION-TYPE
       OBJECTS {
          octoErrorIndex,
          octoErrorDateTime,
          octoErrorClass,
          octoErrorCode,
          octoAccessSlot,
          octoAccessPort,
          octoErrorDescription,
          octoSysState,
          octoErrorSeverity
          }
       STATUS      current
       DESCRIPTION
                   "If an error occurs, there will be checked if the errorClass is configured
                    to trigger an immediate signalling. If so, a trap will be send to the
                    management station containing the information shown above."
       ::= { octoTrapSpecifications 1 }


   sendCdrNotification  NOTIFICATION-TYPE
       OBJECTS {
          octoIndexOfLastCdrNotificationTrap,
          octoTypeOfLastCdrNotificationTrap,
          octoDescriptionOfLastCdrNotificationTrap
          }
       STATUS      current
       DESCRIPTION
                   "The CDR notification trap is sent to trigger further actions by the management
                   station, for instance download of CDR data."
       ::= { octoTrapSpecifications 2 }


   sendPortStatusNotification  NOTIFICATION-TYPE
       OBJECTS {
          indexOfLastPortStatusNotificationTrap
          }
       STATUS      current
       DESCRIPTION
                   "The 'port status change' notification trap is sent to trigger a polling of the
                   port table by a management station. It indicates one or more changes in port
                   states."
       ::= { octoTrapSpecifications 3 }



--********************************************************************--
--******                  octoNetworkGroup                     ******--
--********************************************************************--

   numberOfIpConnControlTableEntries  OBJECT-TYPE
       SYNTAX      INTEGER (1..2147483187)
       MAX-ACCESS  read-write
       STATUS      current
       DESCRIPTION
                   "Contains the number of ip connection control entries to be found in the table.
                    Set this value to 0 to remove all connection control entries."
       ::= { octoNetworkGroup 1 }
    
   ipConnControlTable  OBJECT-TYPE
       SYNTAX      SEQUENCE OF IpConnControlEntry
       MAX-ACCESS  not-accessible
       STATUS      current
       DESCRIPTION
                   "This table can be used to control manual or automatic (periodical) checks 
                    of important ip connections from the device to a limited number of ip counterparts
                    using the feature 'local ping'. It also contains the result of this connection
                    control service."
       ::= { octoNetworkGroup 2 }

   ipConnControlEntry  OBJECT-TYPE
       SYNTAX      IpConnControlEntry
       MAX-ACCESS  not-accessible
       STATUS      current
       DESCRIPTION
                   "The ip connection control table entries."
       INDEX { connControlIndex }
       ::= { ipConnControlTable 1 }

   IpConnControlEntry ::= SEQUENCE {
       connControlIndex    INTEGER,
       connPartnerIpAddress IpAddress,
       connTimeout         INTEGER,
       connRetries         INTEGER,
       connRetryTimer      INTEGER,
       connResult          INTEGER,
       connControlState    INTEGER
       }

   connControlIndex  OBJECT-TYPE
       SYNTAX      INTEGER (1..2147483187)
       MAX-ACCESS  read-only
       STATUS      current
       DESCRIPTION
                   "Identification of an table entry enabled by this index."
       ::= { ipConnControlEntry 1 }

   connPartnerIpAddress  OBJECT-TYPE
       SYNTAX      IpAddress
       MAX-ACCESS  read-write
       STATUS      current
       DESCRIPTION
                   "This is a partner ip address of a ip connection to be
                    supervised."
       ::= { ipConnControlEntry 2 }

   connTimeout  OBJECT-TYPE
       SYNTAX      INTEGER (1..2147483187)
       MAX-ACCESS  read-write
       STATUS      current
       DESCRIPTION
                   "Timeout (in ms) for the 'local ping' mechanism which is used to
                    supervise ip connections."
       ::= { ipConnControlEntry 3 }

   connRetries  OBJECT-TYPE
       SYNTAX      INTEGER (1..2147483187)
       MAX-ACCESS  read-write
       STATUS      current
       DESCRIPTION
                   "Number of retries for the 'local ping' mechanism which
                    is used to supervise ip connections."
       ::= { ipConnControlEntry 4 }

   connRetryTimer  OBJECT-TYPE
       SYNTAX      INTEGER (1..2147483187)
       MAX-ACCESS  read-write
       STATUS      current
       DESCRIPTION
                   "Retry timer (in ms) for the 'local ping' mechanism which is used
                    to supervise ip connections."
       ::= { ipConnControlEntry 5 }

   connResult  OBJECT-TYPE
       SYNTAX      INTEGER {
                     disconnected(1),
                     connected(2),
                     notActivated(3),
                     activated(4)
                   }
       MAX-ACCESS  read-only
       STATUS      current
       DESCRIPTION
                   "The result of the supervision of the given ip connection.
                    disonnected vs. connected is the result of the last check,
                    if supervision has been started. not_activated means that
                    the supervision has not been started. The result is
                    activated, if the check has started, but there's no
                    result yet."
       ::= { ipConnControlEntry 6 }

   connControlState  OBJECT-TYPE
       SYNTAX      INTEGER {
                     singleTest(1),
                     periodicalTest(2),
                     noTest(3)
                   }
       MAX-ACCESS  read-write
       STATUS      current
       DESCRIPTION
                   "This object is used to start/stop the supervision of ip
                    connections."
       ::= { ipConnControlEntry 7 }

END
