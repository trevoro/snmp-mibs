LMS-COMPONENT-MIB DEFINITIONS ::= BEGIN

   IMPORTS
       enterprises, Counter, Gauge,TimeTicks
	FROM RFC1155-SMI
       DisplayString FROM SNMPv2-TC
	OBJECT-TYPE FROM RFC-1212;


-- OBJECT IDENTIFIERS
   lotus        	OBJECT IDENTIFIER ::= { enterprises 334 }
   notes       	OBJECT IDENTIFIER ::= { lotus 1 }
   lcs         	OBJECT IDENTIFIER ::= { lotus 2 }
   softswitch	OBJECT IDENTIFIER ::= { lotus 3 }
   common-mibs	OBJECT IDENTIFIER ::= { softswitch 1 }
   lms		OBJECT IDENTIFIER ::= { softswitch 2 }


  TimeInterval ::= INTEGER (0..2147483647)
  UInteger32 ::= INTEGER (0.. 4294967295)

-- MODULE IDENTIFICATION   use in V2 version only

--lmsComponent MODULE-IDENTITY
--       LAST-UPDATED "9511280000Z"
--       ORGANIZATION "Lotus Development Corporation"
--       CONTACT-INFO
--         " Bruce Ernst
--            Postal: 	Lotus Development Corporation
--                 	 640 Lee Road , Suite 200
--	   	Chesterbrook Corporate Center
--                  	Wayne, PA  19087
--                  	US
--
--            Tel: +1 610 251 3404
--            Fax: +1 610 251 3550
--            E-Mail: bge@softsw.ssw.com"
--       DESCRIPTION
--         "The MIB module describing LMS specific variables
--	  Version 1.0  - first cut - outline only. 8/30/95
--	  Version 1.1  - implemented switch and message store variables 9/11/95"
--       ::= {  lms 1 }
-- comment this out if using the MODULE-IDENTITY macro

lmsComponent OBJECT IDENTIFIER ::= { lms 1 } 

lmsSwitch	OBJECT IDENTIFIER ::= { lmsComponent 1 }
lmsSystem	OBJECT IDENTIFIER ::= { lmsComponent 2 }
lmsMsgStore	OBJECT IDENTIFIER ::= { lmsComponent 3 }
lmsTransports	OBJECT IDENTIFIER ::= { lmsComponent 4 }
lmsIPC		OBJECT IDENTIFIER ::= { lmsComponent 5 } 
lmsDatabase	OBJECT IDENTIFIER ::= { lmsComponent 6 }   



-- SWITCH LEVEL VARIABLES:

lmsSwitchID OBJECT-TYPE
	SYNTAX	   DisplayString
	ACCESS     read-only
	STATUS     mandatory
	DESCRIPTION
	   "The Lotus supplied Identifier, uniquely identifying this switch."
	::= { lmsSwitch 1 }

lmsSwitchName OBJECT-TYPE
	SYNTAX	   DisplayString
	ACCESS     read-write
	STATUS     mandatory
	DESCRIPTION
	   "A brief descriptive name or nickname for this switch."
	::= { lmsSwitch 2 }

lmsSwitchVersion OBJECT-TYPE
	SYNTAX	   DisplayString
	ACCESS     read-only
	STATUS     mandatory
	DESCRIPTION
	   "The version, including patch level, of this switch."
	::= { lmsSwitch 3 }

lmsSwitchUpTime OBJECT-TYPE
	SYNTAX	   TimeTicks
	ACCESS     read-only
	STATUS     mandatory
	DESCRIPTION
	   "The value of sysUpTime at the time this switch began 
execution."
	::= { lmsSwitch 4 }

lmsSwitchOperStatus OBJECT-TYPE
	SYNTAX	   INTEGER {
			unknown(1),
			stopped(2),
			starting(3),
			shutdown(4),
			configurable(5),
			running(6),
			stopping(7)
			}
	ACCESS     read-only
	STATUS     mandatory
	DESCRIPTION
	   "The current operational state of the switch."
	::= { lmsSwitch 5 }

lmsSwitchLastChange OBJECT-TYPE
	SYNTAX	   TimeTicks
	ACCESS     read-only
	STATUS     mandatory
	DESCRIPTION
	   "The value of sysUpTime at the time this switch entered its current
	     operational state. If the current state was entered prior to 
the last
	     initialization of the local network management subsystem then 
this
	     object contains a zero value."
	::= { lmsSwitch 6 }

lmsSwitchDesiredOperStatus OBJECT-TYPE
	SYNTAX	   INTEGER {
			stopped(1),
			shutdown(2),
			configurable(3),
			running(4)
			}
	ACCESS     read-write
	STATUS     mandatory
	DESCRIPTION
	   "The desired operational state for this switch."
	::= { lmsSwitch 7 }

lmsSwitchDescr OBJECT-TYPE
	SYNTAX	   DisplayString
	ACCESS     read-write
	STATUS     mandatory
	DESCRIPTION
	   "A textual description for the switch. This may contain any
	    pertinent details for the local or remote administrators."
	::= { lmsSwitch 8 }

lmsSwitchContact OBJECT-TYPE 
	SYNTAX	   DisplayString
	ACCESS     read-write
	STATUS     mandatory
	DESCRIPTION
	   "The textual information of the contact person for this switch, 
together
	    with information on how to contact that person."
	::= { lmsSwitch 9 }



-- SYSTEM LEVEL VARIABLES:


-- MESSAGE STORE VARIABLES:

lmsMsgStoreDatabaseUtilization OBJECT-TYPE
	SYNTAX	   INTEGER (0..100)
	ACCESS     read-only
	STATUS     mandatory
	DESCRIPTION
	   "The current utilization of the relational database portion of 
the
	    message store, expressed as a percentage."
	::= { lmsMsgStore 1 }

lmsMsgStoreFileSystemUtilization OBJECT-TYPE
	SYNTAX	   INTEGER (0..100)
	ACCESS     read-only
	STATUS     mandatory
	DESCRIPTION
	   "The current utilization of the native file system portion of 
the
	    message store, expressed as a percentage."
	::= { lmsMsgStore 2 }

-- TRANSPORT LEVEL VARIABLES:

snaState  OBJECT-TYPE
	SYNTAX     INTEGER {
			up(1),
			down(2),
			halted(3),
			congested(4),
			restarting(5),
			quiescing(6),
			unknown(7)
			}
	ACCESS    read-only
	STATUS     mandatory
	DESCRIPTION
	  "Indicates the operational status of the SNA transport subsystem. The 
values are:
		up	-     transport is operation and available
		down	-     transport is not available
		halted	-     transport is operational but not 
available
		congested -   transport is operationallly overloaded 
(optional)
		restarting -    transport is unavailable, but will be soon
		quiescing -    transport is unavailable, shutdown in 
progress
		unknown  -    transport status is unknown or cannot be 
determined"
	::= { lmsTransports 1 }

osiState  OBJECT-TYPE
	SYNTAX     INTEGER {
			up(1),
			down(2),
			halted(3),
			congested(4),
			restarting(5),
			quiescing(6),
			unknown(7)
			}
	ACCESS    read-only
	STATUS     mandatory
	DESCRIPTION
	  "Indicates the operational status of the OSI transport subsystem. The 
values are the
	   same as those for snaState and tcpIpState."
	::= { lmsTransports 2 }

tcpIpState  OBJECT-TYPE
	SYNTAX     INTEGER {
			up(1),
			down(2),
			halted(3),
			congested(4),
			restarting(5),
			quiescing(6),
			unknown(7)
			}
	ACCESS    read-only
	STATUS     mandatory
	DESCRIPTION
	  "Indicates the operational status of the TCP/IP transport subsystem. 
The values are the
	   same as those for snaState and osiState."
	::= { lmsTransports 3 }


transportLastUpdate OBJECT-TYPE
	SYNTAX	   TimeTicks
	ACCESS     read-only
	STATUS     mandatory
	DESCRIPTION
	   "The value of sysUpTime at the time the latest transport 
	     information was gathered."
	::= { lmsTransports 4 }

-- IPC LEVEL VARIABLES:

ipcOperStatus OBJECT-TYPE
	SYNTAX     INTEGER {
			up(1),
			down(2),
			halted(3),
			congested(4),
			restarting(5),
			quiescing(6),
			unknown(7)
			}
	ACCESS    read-only
	STATUS     mandatory
	DESCRIPTION
	   "Indicates the operational state of the IPC subsystem (XIPC)."
	::= { lmsIPC 1 }

semaphoreMaxUsers  OBJECT-TYPE
	SYNTAX	   UInteger32
	ACCESS     read-only
	STATUS     mandatory
	DESCRIPTION
	   "The configured maximum number of users of the semaphore 
subsystem."
	::= { lmsIPC 2 }

semaphoreCurrUsers  OBJECT-TYPE
	SYNTAX	    Gauge
	ACCESS    read-only
	STATUS     mandatory
	DESCRIPTION
	   "The current number of users of the semaphore subsystem."
	::= { lmsIPC 3 }

semaphoreMaxSemaphores  OBJECT-TYPE
	SYNTAX	    UInteger32
	ACCESS    read-only
	STATUS     mandatory
	DESCRIPTION
	   "The configured maximum number of semaphores in the semaphore 
subsystem."
	::= { lmsIPC 4 }

semaphoreCurrSemaphores  OBJECT-TYPE
	SYNTAX	    Gauge
	ACCESS    read-only
	STATUS     mandatory
	DESCRIPTION
	   "The current number of semaphores in use in the semaphore 
subsystem."
	::= { lmsIPC 5 }

semaphoreMaxNodes  OBJECT-TYPE
	SYNTAX	    UInteger32
	ACCESS    read-only
	STATUS     mandatory
	DESCRIPTION
	   "The configured maximum number of nodes in the semaphore 
subsystem."
	::= { lmsIPC 6 }

semaphoreCurrNodes  OBJECT-TYPE
	SYNTAX	    Gauge
	ACCESS    read-only
	STATUS     mandatory
	DESCRIPTION
	   "The current number of nodes in use in the semaphore subsystem."
	::= { lmsIPC 7 }

sharedmemMaxUsers  OBJECT-TYPE
	SYNTAX	   UInteger32
	ACCESS    read-only
	STATUS     mandatory
	DESCRIPTION
	   "The configured maximum number of users of the shared memory 
subsystem."
	::= { lmsIPC 8 }

sharedmemCurrUsers  OBJECT-TYPE
	SYNTAX	    Gauge
	ACCESS    read-only
	STATUS     mandatory
	DESCRIPTION
	   "The current number of users of the shared memory subsystem."
	::= { lmsIPC 9 }

sharedmemMaxSeqments  OBJECT-TYPE
	SYNTAX	   UInteger32
	ACCESS    read-only
	STATUS     mandatory
	DESCRIPTION
	   "The configured maximum number of seqments in the shared memory 
subsystem."
	::= { lmsIPC 10 }

sharedmemCurrSegments  OBJECT-TYPE
	SYNTAX	   Gauge
	ACCESS    read-only
	STATUS     mandatory
	DESCRIPTION
	   "The current number of segments in use by the shared memory 
subsystem."
	::= { lmsIPC 11 }

sharedmemMaxNodes  OBJECT-TYPE
	SYNTAX	   UInteger32
	ACCESS    read-only
	STATUS     mandatory
	DESCRIPTION
	   "The configured maximum number of nodes in the shared memory 
subsystem."
	::= { lmsIPC 12 }

sharedmemCurrNodes  OBJECT-TYPE
	SYNTAX	    Gauge
	ACCESS    read-only
	STATUS     mandatory
	DESCRIPTION
	   "The current number of nodes in use by the shared memory 
subsystem."
	::= { lmsIPC 13 }

sharedmemMaxMempool  OBJECT-TYPE
	SYNTAX	    UInteger32
	ACCESS    read-only
	STATUS     mandatory
	DESCRIPTION
	   "The configured maximum size of the mempool allowed for use by 
the
	     shared memory subsystem"
	::= { lmsIPC 14 }

sharedmemCurrMempool  OBJECT-TYPE
	SYNTAX	    Gauge
	ACCESS    read-only
	STATUS     mandatory
	DESCRIPTION
	   "The current size of the mempool in use by the shared memory 
subsystem."
	::= { lmsIPC 15 }

msgqueueMaxUsers  OBJECT-TYPE
	SYNTAX	   UInteger32
	ACCESS    read-only
	STATUS     mandatory
	DESCRIPTION
	   "The configured maximum number of users of the message queue 
subsystem."
	::= { lmsIPC 16 }

msgqueueCurrUsers  OBJECT-TYPE
	SYNTAX	   Gauge
	ACCESS    read-only
	STATUS     mandatory
	DESCRIPTION
	   "The current number of users of the message queue subsystem."
	::= { lmsIPC 17 }

msgqueueMaxQueues  OBJECT-TYPE
	SYNTAX	    UInteger32
	ACCESS    read-only
	STATUS     mandatory
	DESCRIPTION
	   "The configured maximum number of message queues to be used by 
the
	     message queue subsystem."
	::= { lmsIPC 18 }

msgqueueCurrQueues  OBJECT-TYPE
	SYNTAX	    Gauge
	ACCESS    read-only
	STATUS     mandatory
	DESCRIPTION
	   "The current number of message queues in use by the message 
queue subsystem."
	::= { lmsIPC 19 }

msgqueueMaxNodes  OBJECT-TYPE
	SYNTAX	   UInteger32
	ACCESS    read-only
	STATUS     mandatory
	DESCRIPTION
	   "The configured maximum number of nodes in the message queue 
subsystem."
	::= { lmsIPC 20 }

msgqueueCurrNodes  OBJECT-TYPE
	SYNTAX	    Gauge
	ACCESS    read-only
	STATUS     mandatory
	DESCRIPTION
	   "The current number of nodes in use by the message queue 
subsystem."
	::= { lmsIPC 21 }

msgqueueMaxMempool  OBJECT-TYPE
	SYNTAX	    UInteger32
	ACCESS    read-only
	STATUS     mandatory
	DESCRIPTION
	   "The configured maximum size of the mempool allowed for use by 
the
	     message queue subsystem."
	::= { lmsIPC 22 }

msgqueueCurrMempool  OBJECT-TYPE
	SYNTAX	    Gauge
	ACCESS    read-only
	STATUS     mandatory
	DESCRIPTION
	   "The current size of the mempool in use by the message queue 
subsystem."
	::= { lmsIPC 23 }


-- DATABASE LEVEL VARIABLES:

dbConfigSpaceUtilization  OBJECT-TYPE
	SYNTAX	   INTEGER (0..100)
	ACCESS    read-only
	STATUS     mandatory
	DESCRIPTION
	   "This is a percentage between 0 and 100 inclusive, representing 
the
	    current utilization of config table space in the database."
	::= { lmsDatabase 1 }

dbNameSpaceUtilization  OBJECT-TYPE
	SYNTAX	    INTEGER (0..100)
	ACCESS    read-only
	STATUS     mandatory
	DESCRIPTION
	   "This is a percentage between 0 and 100 inclusive, representing 
the
	    current utilization of names table space in the database."
	::= { lmsDatabase 2 }

dbDistribSpaceUtilization  OBJECT-TYPE
	SYNTAX	   INTEGER (0..100)
	ACCESS    read-only
	STATUS     mandatory
	DESCRIPTION
	   "This is a percentage between 0 and 100 inclusive, representing 
the
	    current utilization of distrib table space in the database."
	::= { lmsDatabase 3 }

dbSystemSpaceUtilization  OBJECT-TYPE
	SYNTAX	    INTEGER (0..100)
	ACCESS    read-only
	STATUS     mandatory
	DESCRIPTION
	   "This is a percentage between 0 and 100 inclusive, representing 
the
	    current utilization of system table space in the database."
	::= { lmsDatabase 4 }

dbLastUpdate OBJECT-TYPE
	SYNTAX	   TimeTicks
	ACCESS     read-only
	STATUS     mandatory
	DESCRIPTION
	   "The value of sysUpTime at the time the latest database 
	     information was gathered."
	::= { lmsDatabase 5 }


-- CONFORMANCE INFORMATION
	-- Used ONLY in V2 MIBs
-- COMPLIANCE STATEMENTS
	-- Used ONLY in V2 MIBs
-- UNITS OF CONFORMANCE
	-- Used ONLY in V2 MIBs


END
