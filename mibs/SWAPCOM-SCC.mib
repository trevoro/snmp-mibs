SWAPCOM-SCC	DEFINITIONS ::= BEGIN

	IMPORTS
		enterprises, MODULE-IDENTITY, OBJECT-TYPE, TimeTicks,
		Unsigned32, IpAddress, Gauge32, Counter32, Counter64
			FROM SNMPv2-SMI
		MacAddress, TimeInterval, TruthValue, TestAndIncr,
		RowStatus, DisplayString, StorageType, DateAndTime
			FROM SNMPv2-TC
		IpAddress
			FROM RFC1155-SMI
		DisplayString
			FROM RFC1213-MIB;

swapcom	MODULE-IDENTITY
LAST-UPDATED	"2007381648Z"
ORGANIZATION	"Organization name"
CONTACT-INFO	"Contact information"
DESCRIPTION	"Description"
REVISION	"2007381648Z"
DESCRIPTION	"Revision Description"
::=	{	enterprises	11308
	 }

org	OBJECT IDENTIFIER
::=	{	iso	3
	}

dod	OBJECT IDENTIFIER
::=	{	org	6
	}

internet	OBJECT IDENTIFIER
::=	{	dod	1
	}

private	OBJECT IDENTIFIER
::=	{	internet	4
	}

enterprises	OBJECT IDENTIFIER
::=	{	private	1
	}

scc	OBJECT IDENTIFIER
::=	{	swapcom	3
	}

platform	OBJECT IDENTIFIER
::=	{	scc	1
	}

platformPlatformId	OBJECT-TYPE
SYNTAX	OCTET STRING
MAX-ACCESS	read-only
STATUS	current
DESCRIPTION	 "Identifier of the local platform"
::=	{	platform	1
	}

platformPlatformStatus	OBJECT-TYPE
SYNTAX	INTEGER
MAX-ACCESS	read-only
STATUS	current
DESCRIPTION	 "Status of local platform (0=Initializing / 1=Platform initialized / 2=Domains initialized / 3=Platform started and ready"
::=	{	platform	2
	}

versionTable	OBJECT-TYPE
SYNTAX	SEQUENCE OF	VersionEntry
MAX-ACCESS	not-accessible
STATUS	current
DESCRIPTION	"Components version"
::=	{	scc	2
	}


versionEntry	OBJECT-TYPE
SYNTAX	VersionEntry
MAX-ACCESS	not-accessible
STATUS	current
DESCRIPTION	"The entry for versionTable"
INDEX {  versionProductName  }
::=	{	versionTable	1
	}

VersionEntry	::=  SEQUENCE	{ versionProductName OCTET STRING, versionProductVersion OCTET STRING, versionBuildNumber INTEGER, versionBuildDate DisplayString
}

versionProductName	OBJECT-TYPE
SYNTAX	OCTET STRING
MAX-ACCESS	read-only
STATUS	current
DESCRIPTION	 "Name of the component"
::=	{	versionEntry	1
	}

versionProductVersion	OBJECT-TYPE
SYNTAX	OCTET STRING
MAX-ACCESS	read-only
STATUS	current
DESCRIPTION	 "Version of the component, follows the standard SWAPCOM versioning"
::=	{	versionEntry	2
	}

versionBuildNumber	OBJECT-TYPE
SYNTAX	INTEGER
MAX-ACCESS	read-only
STATUS	current
DESCRIPTION	 "Component build number"
::=	{	versionEntry	3
	}

versionBuildDate	OBJECT-TYPE
SYNTAX	DisplayString
MAX-ACCESS	read-only
STATUS	current
DESCRIPTION	 "Component build date"
::=	{	versionEntry	4
	}

transactionManager	OBJECT IDENTIFIER
::=	{	scc	3
	}

transactionManagerLongTransactionThreshold	OBJECT-TYPE
SYNTAX	Unsigned32
MAX-ACCESS	read-only
STATUS	current
DESCRIPTION	 "Threshold duration for long transaction detection"
::=	{	transactionManager	1
	}

transactionManagerActiveTransactionCurrentCount	OBJECT-TYPE
SYNTAX	INTEGER
MAX-ACCESS	read-only
STATUS	current
DESCRIPTION	 "Number of current active transaction"
::=	{	transactionManager	2
	}

transactionManagerActiveTransactionMinCount	OBJECT-TYPE
SYNTAX	INTEGER
MAX-ACCESS	read-only
STATUS	current
DESCRIPTION	 "Minimum number of active transaction"
::=	{	transactionManager	3
	}

transactionManagerActiveTransactionMaxCount	OBJECT-TYPE
SYNTAX	INTEGER
MAX-ACCESS	read-only
STATUS	current
DESCRIPTION	 "Maximum number of active transaction"
::=	{	transactionManager	4
	}

transactionManagerCommittedTransactionCumulativeCount	OBJECT-TYPE
SYNTAX	INTEGER
MAX-ACCESS	read-only
STATUS	current
DESCRIPTION	 "Number of transaction committed"
::=	{	transactionManager	5
	}

transactionManagerRolledbackTransactionCumulativeCount	OBJECT-TYPE
SYNTAX	INTEGER
MAX-ACCESS	read-only
STATUS	current
DESCRIPTION	 "Number of transaction rollbacked"
::=	{	transactionManager	6
	}

transactionManagerTransactionCumulativeTime	OBJECT-TYPE
SYNTAX	Unsigned32
MAX-ACCESS	read-only
STATUS	current
DESCRIPTION	 "Cumulative transaction time"
::=	{	transactionManager	7
	}

transactionManagerTransactionMinTime	OBJECT-TYPE
SYNTAX	Unsigned32
MAX-ACCESS	read-only
STATUS	current
DESCRIPTION	 "Minimum transaction duration time"
::=	{	transactionManager	8
	}

transactionManagerTransactionMaxTime	OBJECT-TYPE
SYNTAX	Unsigned32
MAX-ACCESS	read-only
STATUS	current
DESCRIPTION	 "Maximum transaction duration time"
::=	{	transactionManager	9
	}

transactionManagerTransactionManagerLastError	OBJECT-TYPE
SYNTAX	DisplayString
MAX-ACCESS	read-only
STATUS	current
DESCRIPTION	 "Last error message that occured in the transaction manager"
::=	{	transactionManager	10
	}

lockManager	OBJECT IDENTIFIER
::=	{	scc	4
	}

lockManagerLockedItemCumulativeCount	OBJECT-TYPE
SYNTAX	INTEGER
MAX-ACCESS	read-only
STATUS	current
DESCRIPTION	 "Number of lock acquired"
::=	{	lockManager	1
	}

lockManagerLockedItemCurrentCount	OBJECT-TYPE
SYNTAX	INTEGER
MAX-ACCESS	read-only
STATUS	current
DESCRIPTION	 "Number of currenty locked objects"
::=	{	lockManager	2
	}

lockManagerLockedItemMinCount	OBJECT-TYPE
SYNTAX	INTEGER
MAX-ACCESS	read-only
STATUS	current
DESCRIPTION	 "Minimum number of locked objects"
::=	{	lockManager	3
	}

lockManagerLockedItemMaxCount	OBJECT-TYPE
SYNTAX	INTEGER
MAX-ACCESS	read-only
STATUS	current
DESCRIPTION	 "Maximum number of locked objects"
::=	{	lockManager	4
	}

lockManagerLockRejectedOnDeadlockCumulativeCount	OBJECT-TYPE
SYNTAX	INTEGER
MAX-ACCESS	read-only
STATUS	current
DESCRIPTION	 "Number of lock rejected on deadlock"
::=	{	lockManager	5
	}

lockManagerLockRejectedOnTimeoutCumulativeCount	OBJECT-TYPE
SYNTAX	INTEGER
MAX-ACCESS	read-only
STATUS	current
DESCRIPTION	 "Number of lock rejected on timeout"
::=	{	lockManager	6
	}

lockManagerBlockedTransactionCurrentCount	OBJECT-TYPE
SYNTAX	INTEGER
MAX-ACCESS	read-only
STATUS	current
DESCRIPTION	 "Number of currently blocked transaction in lockmanager"
::=	{	lockManager	7
	}

lockManagerBlockedTransactionMinCount	OBJECT-TYPE
SYNTAX	INTEGER
MAX-ACCESS	read-only
STATUS	current
DESCRIPTION	 "Minimum number of blocked transaction in lockmanager"
::=	{	lockManager	8
	}

lockManagerBlockedTransactionMaxCount	OBJECT-TYPE
SYNTAX	INTEGER
MAX-ACCESS	read-only
STATUS	current
DESCRIPTION	 "Maximum number of blocked transaction in lockmanager"
::=	{	lockManager	9
	}

schedulerTaskTable	OBJECT-TYPE
SYNTAX	SEQUENCE OF	SchedulerTaskEntry
MAX-ACCESS	not-accessible
STATUS	current
DESCRIPTION	"Status of tasks registered in the scheduler"
::=	{	scc	5
	}


schedulerTaskEntry	OBJECT-TYPE
SYNTAX	SchedulerTaskEntry
MAX-ACCESS	not-accessible
STATUS	current
DESCRIPTION	"The entry for schedulerTaskTable"
INDEX {  schedulerTaskName  }
::=	{	schedulerTaskTable	1
	}

SchedulerTaskEntry	::=  SEQUENCE	{ schedulerTaskName OCTET STRING, schedulerTaskRunning TruthValue, schedulerTaskExecutionCumulativeCount INTEGER, schedulerTaskExecutionCumulativeTime Unsigned32, schedulerTaskExecutionMinTime Unsigned32, schedulerTaskExecutionMaxTime Unsigned32, schedulerTaskExecutionRetryCurrentCount INTEGER, schedulerTaskExecutionLastError DisplayString
}

schedulerTaskName	OBJECT-TYPE
SYNTAX	OCTET STRING
MAX-ACCESS	read-only
STATUS	current
DESCRIPTION	 "Name of the task"
::=	{	schedulerTaskEntry	1
	}

schedulerTaskRunning	OBJECT-TYPE
SYNTAX	TruthValue
MAX-ACCESS	read-only
STATUS	current
DESCRIPTION	 "Indicate if the task is currenlty being executed"
::=	{	schedulerTaskEntry	2
	}

schedulerTaskExecutionCumulativeCount	OBJECT-TYPE
SYNTAX	INTEGER
MAX-ACCESS	read-only
STATUS	current
DESCRIPTION	 "Number of executions succesfully done"
::=	{	schedulerTaskEntry	3
	}

schedulerTaskExecutionCumulativeTime	OBJECT-TYPE
SYNTAX	Unsigned32
MAX-ACCESS	read-only
STATUS	current
DESCRIPTION	 "Cumulative processing time (success and failure)"
::=	{	schedulerTaskEntry	4
	}

schedulerTaskExecutionMinTime	OBJECT-TYPE
SYNTAX	Unsigned32
MAX-ACCESS	read-only
STATUS	current
DESCRIPTION	 "Minimum processing time of the task"
::=	{	schedulerTaskEntry	5
	}

schedulerTaskExecutionMaxTime	OBJECT-TYPE
SYNTAX	Unsigned32
MAX-ACCESS	read-only
STATUS	current
DESCRIPTION	 "Maximum processing time of the task"
::=	{	schedulerTaskEntry	6
	}

schedulerTaskExecutionRetryCurrentCount	OBJECT-TYPE
SYNTAX	INTEGER
MAX-ACCESS	read-only
STATUS	current
DESCRIPTION	 "Number of execution failure"
::=	{	schedulerTaskEntry	7
	}

schedulerTaskExecutionLastError	OBJECT-TYPE
SYNTAX	DisplayString
MAX-ACCESS	read-only
STATUS	current
DESCRIPTION	 "Message of the last execution failure"
::=	{	schedulerTaskEntry	8
	}

alarmProbeTable	OBJECT-TYPE
SYNTAX	SEQUENCE OF	AlarmProbeEntry
MAX-ACCESS	not-accessible
STATUS	current
DESCRIPTION	"Alarm probes status of the platform"
::=	{	scc	12
	}


alarmProbeEntry	OBJECT-TYPE
SYNTAX	AlarmProbeEntry
MAX-ACCESS	not-accessible
STATUS	current
DESCRIPTION	"The entry for alarmProbeTable"
INDEX {  alarmProbeAlertType, alarmProbeAlertSource  }
::=	{	alarmProbeTable	1
	}

AlarmProbeEntry	::=  SEQUENCE	{ alarmProbeAlertType OCTET STRING, alarmProbeAlertSource OCTET STRING, alarmProbeSeverity INTEGER, alarmProbeLastSeverityChange DisplayString
}

alarmProbeAlertType	OBJECT-TYPE
SYNTAX	OCTET STRING
MAX-ACCESS	read-only
STATUS	current
DESCRIPTION	 "Type of the probe alarm"
::=	{	alarmProbeEntry	1
	}

alarmProbeAlertSource	OBJECT-TYPE
SYNTAX	OCTET STRING
MAX-ACCESS	read-only
STATUS	current
DESCRIPTION	 "Source of the probe alarm"
::=	{	alarmProbeEntry	2
	}

alarmProbeSeverity	OBJECT-TYPE
SYNTAX	INTEGER
MAX-ACCESS	read-only
STATUS	current
DESCRIPTION	 "Current severity of the probe"
::=	{	alarmProbeEntry	3
	}

alarmProbeLastSeverityChange	OBJECT-TYPE
SYNTAX	DisplayString
MAX-ACCESS	read-only
STATUS	current
DESCRIPTION	 "Date of the last severity value change"
::=	{	alarmProbeEntry	4
	}

remotePlatformTable	OBJECT-TYPE
SYNTAX	SEQUENCE OF	RemotePlatformEntry
MAX-ACCESS	not-accessible
STATUS	current
DESCRIPTION	"Remote platform connected to this one"
::=	{	scc	21
	}


remotePlatformEntry	OBJECT-TYPE
SYNTAX	RemotePlatformEntry
MAX-ACCESS	not-accessible
STATUS	current
DESCRIPTION	"The entry for remotePlatformTable"
INDEX {  remotePlatformPlatformId  }
::=	{	remotePlatformTable	1
	}

RemotePlatformEntry	::=  SEQUENCE	{ remotePlatformPlatformId OCTET STRING, remotePlatformPlatformProtocol OCTET STRING, remotePlatformRemotePlatformStatus INTEGER
}

remotePlatformPlatformId	OBJECT-TYPE
SYNTAX	OCTET STRING
MAX-ACCESS	read-only
STATUS	current
DESCRIPTION	 "Identifier of the remote platform"
::=	{	remotePlatformEntry	1
	}

remotePlatformPlatformProtocol	OBJECT-TYPE
SYNTAX	OCTET STRING
MAX-ACCESS	read-only
STATUS	current
DESCRIPTION	 "Protocol used to communicate with the remote platform"
::=	{	remotePlatformEntry	2
	}

remotePlatformRemotePlatformStatus	OBJECT-TYPE
SYNTAX	INTEGER
MAX-ACCESS	read-only
STATUS	current
DESCRIPTION	 "Status of the remote platform connection (-2=unknown / -1=down / 3=up)"
::=	{	remotePlatformEntry	3
	}

asynchronousEventQueueTable	OBJECT-TYPE
SYNTAX	SEQUENCE OF	AsynchronousEventQueueEntry
MAX-ACCESS	not-accessible
STATUS	current
DESCRIPTION	"Asynchronous event queues status"
::=	{	scc	22
	}


asynchronousEventQueueEntry	OBJECT-TYPE
SYNTAX	AsynchronousEventQueueEntry
MAX-ACCESS	not-accessible
STATUS	current
DESCRIPTION	"The entry for asynchronousEventQueueTable"
INDEX {  asynchronousEventQueuePlatformId  }
::=	{	asynchronousEventQueueTable	1
	}

AsynchronousEventQueueEntry	::=  SEQUENCE	{ asynchronousEventQueuePlatformId OCTET STRING, asynchronousEventQueueInsertedEventCumulativeCount INTEGER, asynchronousEventQueueWaitingEventCurrentCount INTEGER, asynchronousEventQueueWaitingEventMinCount INTEGER, asynchronousEventQueueWaitingEventMaxCount INTEGER, asynchronousEventQueueProcessedEventCumulativeCount INTEGER, asynchronousEventQueueEventProcessingCumulativeTime Unsigned32, asynchronousEventQueueEventProcessingMinTime Unsigned32, asynchronousEventQueueEventProcessingMaxTime Unsigned32, asynchronousEventQueueFailedEventCumulativeCount INTEGER, asynchronousEventQueueFailedEventLastError DisplayString
}

asynchronousEventQueuePlatformId	OBJECT-TYPE
SYNTAX	OCTET STRING
MAX-ACCESS	read-only
STATUS	current
DESCRIPTION	 "Identifier of the platform events queue"
::=	{	asynchronousEventQueueEntry	1
	}

asynchronousEventQueueInsertedEventCumulativeCount	OBJECT-TYPE
SYNTAX	INTEGER
MAX-ACCESS	read-only
STATUS	current
DESCRIPTION	 "Number of generated asynchronous events"
::=	{	asynchronousEventQueueEntry	2
	}

asynchronousEventQueueWaitingEventCurrentCount	OBJECT-TYPE
SYNTAX	INTEGER
MAX-ACCESS	read-only
STATUS	current
DESCRIPTION	 "Number of events that are pending in the send queue"
::=	{	asynchronousEventQueueEntry	3
	}

asynchronousEventQueueWaitingEventMinCount	OBJECT-TYPE
SYNTAX	INTEGER
MAX-ACCESS	read-only
STATUS	current
DESCRIPTION	 "Minimum number of events pending in the send queue"
::=	{	asynchronousEventQueueEntry	4
	}

asynchronousEventQueueWaitingEventMaxCount	OBJECT-TYPE
SYNTAX	INTEGER
MAX-ACCESS	read-only
STATUS	current
DESCRIPTION	 "Maximum number of events pending in the send queue"
::=	{	asynchronousEventQueueEntry	5
	}

asynchronousEventQueueProcessedEventCumulativeCount	OBJECT-TYPE
SYNTAX	INTEGER
MAX-ACCESS	read-only
STATUS	current
DESCRIPTION	 "Number of successfully sent asynchronous events"
::=	{	asynchronousEventQueueEntry	6
	}

asynchronousEventQueueEventProcessingCumulativeTime	OBJECT-TYPE
SYNTAX	Unsigned32
MAX-ACCESS	read-only
STATUS	current
DESCRIPTION	 "Cumulated time of event processing"
::=	{	asynchronousEventQueueEntry	7
	}

asynchronousEventQueueEventProcessingMinTime	OBJECT-TYPE
SYNTAX	Unsigned32
MAX-ACCESS	read-only
STATUS	current
DESCRIPTION	 "Minimum event processing time"
::=	{	asynchronousEventQueueEntry	8
	}

asynchronousEventQueueEventProcessingMaxTime	OBJECT-TYPE
SYNTAX	Unsigned32
MAX-ACCESS	read-only
STATUS	current
DESCRIPTION	 "Maximum event processing time"
::=	{	asynchronousEventQueueEntry	9
	}

asynchronousEventQueueFailedEventCumulativeCount	OBJECT-TYPE
SYNTAX	INTEGER
MAX-ACCESS	read-only
STATUS	current
DESCRIPTION	 "Number of asynchronous events in the 'failed' queue"
::=	{	asynchronousEventQueueEntry	10
	}

asynchronousEventQueueFailedEventLastError	OBJECT-TYPE
SYNTAX	DisplayString
MAX-ACCESS	read-only
STATUS	current
DESCRIPTION	 "Last error message of events process failure"
::=	{	asynchronousEventQueueEntry	11
	}

slsConnection	OBJECT IDENTIFIER
::=	{	scc	23
	}

slsConnectionConnected	OBJECT-TYPE
SYNTAX	TruthValue
MAX-ACCESS	read-only
STATUS	current
DESCRIPTION	 "Indicate if the platform is connected to the SLS"
::=	{	slsConnection	1
	}

slsConnectionLicenseCheckSuccessCumulativeCount	OBJECT-TYPE
SYNTAX	INTEGER
MAX-ACCESS	read-only
STATUS	current
DESCRIPTION	 "Number of successfull license check"
::=	{	slsConnection	2
	}

slsConnectionLicenseCheckFailedCumulativeCount	OBJECT-TYPE
SYNTAX	INTEGER
MAX-ACCESS	read-only
STATUS	current
DESCRIPTION	 "Number of failed license check"
::=	{	slsConnection	3
	}

slsConnectionLicenseCheckLastError	OBJECT-TYPE
SYNTAX	DisplayString
MAX-ACCESS	read-only
STATUS	current
DESCRIPTION	 "Last error message that occured in the SLS connection"
::=	{	slsConnection	4
	}

sqlPoolXATable	OBJECT-TYPE
SYNTAX	SEQUENCE OF	SqlPoolXAEntry
MAX-ACCESS	not-accessible
STATUS	current
DESCRIPTION	"SQLPool status and properties"
::=	{	scc	24
	}


sqlPoolXAEntry	OBJECT-TYPE
SYNTAX	SqlPoolXAEntry
MAX-ACCESS	not-accessible
STATUS	current
DESCRIPTION	"The entry for sqlPoolXATable"
INDEX {  sqlPoolXAName  }
::=	{	sqlPoolXATable	1
	}

SqlPoolXAEntry	::=  SEQUENCE	{ sqlPoolXAName OCTET STRING, sqlPoolXASqlPlatformName OCTET STRING, sqlPoolXADatabaseName OCTET STRING, sqlPoolXADriverName OCTET STRING, sqlPoolXADriverClassName OCTET STRING, sqlPoolXAMaximumSize INTEGER, sqlPoolXAMaximumIdleTime Unsigned32, sqlPoolXAMaximumWaitTime Unsigned32, sqlPoolXACheckIsClosedInterval Unsigned32, sqlPoolXACreateConnectionSuccessCumulativeCount INTEGER, sqlPoolXACreateConnectionFailureCumulativeCount INTEGER, sqlPoolXACreateConnectionLastError DisplayString, sqlPoolXAConnectionCurrentCount INTEGER, sqlPoolXAConnectionMinCount INTEGER, sqlPoolXAConnectionMaxCount INTEGER, sqlPoolXACheckedOutConnectionCurrentCount INTEGER, sqlPoolXACheckedOutConnectionMinCount INTEGER, sqlPoolXACheckedOutConnectionMaxCount INTEGER, sqlPoolXACheckedOutConnectionCumulativeCount INTEGER, sqlPoolXACheckedOutConnectionCumulativeTime Unsigned32, sqlPoolXACheckedOutConnectionMinTime Unsigned32, sqlPoolXACheckedOutConnectionMaxTime Unsigned32, sqlPoolXACheckedOutConnectionAverageTime DisplayString
}

sqlPoolXAName	OBJECT-TYPE
SYNTAX	OCTET STRING
MAX-ACCESS	read-only
STATUS	current
DESCRIPTION	 "Name of the connection pool"
::=	{	sqlPoolXAEntry	1
	}

sqlPoolXASqlPlatformName	OBJECT-TYPE
SYNTAX	OCTET STRING
MAX-ACCESS	read-only
STATUS	current
DESCRIPTION	 "Detected database type"
::=	{	sqlPoolXAEntry	2
	}

sqlPoolXADatabaseName	OBJECT-TYPE
SYNTAX	OCTET STRING
MAX-ACCESS	read-only
STATUS	current
DESCRIPTION	 "Raw database name"
::=	{	sqlPoolXAEntry	3
	}

sqlPoolXADriverName	OBJECT-TYPE
SYNTAX	OCTET STRING
MAX-ACCESS	read-only
STATUS	current
DESCRIPTION	 "Name of the JDBC driver"
::=	{	sqlPoolXAEntry	4
	}

sqlPoolXADriverClassName	OBJECT-TYPE
SYNTAX	OCTET STRING
MAX-ACCESS	read-only
STATUS	current
DESCRIPTION	 "Name of the JDBC driver class"
::=	{	sqlPoolXAEntry	5
	}

sqlPoolXAMaximumSize	OBJECT-TYPE
SYNTAX	INTEGER
MAX-ACCESS	read-only
STATUS	current
DESCRIPTION	 "Maximum size of connection pool"
::=	{	sqlPoolXAEntry	6
	}

sqlPoolXAMaximumIdleTime	OBJECT-TYPE
SYNTAX	Unsigned32
MAX-ACCESS	read-only
STATUS	current
DESCRIPTION	 "Maximum life duration of a connection in the pool"
::=	{	sqlPoolXAEntry	7
	}

sqlPoolXAMaximumWaitTime	OBJECT-TYPE
SYNTAX	Unsigned32
MAX-ACCESS	read-only
STATUS	current
DESCRIPTION	 "Maximum waiting time for getting a connection when the pool is exhausted"
::=	{	sqlPoolXAEntry	8
	}

sqlPoolXACheckIsClosedInterval	OBJECT-TYPE
SYNTAX	Unsigned32
MAX-ACCESS	read-only
STATUS	current
DESCRIPTION	 "Minimum time between two connection checking"
::=	{	sqlPoolXAEntry	9
	}

sqlPoolXACreateConnectionSuccessCumulativeCount	OBJECT-TYPE
SYNTAX	INTEGER
MAX-ACCESS	read-only
STATUS	current
DESCRIPTION	 "Number of connections succesfully created"
::=	{	sqlPoolXAEntry	10
	}

sqlPoolXACreateConnectionFailureCumulativeCount	OBJECT-TYPE
SYNTAX	INTEGER
MAX-ACCESS	read-only
STATUS	current
DESCRIPTION	 "Number of connection creation failure"
::=	{	sqlPoolXAEntry	11
	}

sqlPoolXACreateConnectionLastError	OBJECT-TYPE
SYNTAX	DisplayString
MAX-ACCESS	read-only
STATUS	current
DESCRIPTION	 "Last exception message during checkout failure"
::=	{	sqlPoolXAEntry	12
	}

sqlPoolXAConnectionCurrentCount	OBJECT-TYPE
SYNTAX	INTEGER
MAX-ACCESS	read-only
STATUS	current
DESCRIPTION	 "Current size of the connection pool"
::=	{	sqlPoolXAEntry	13
	}

sqlPoolXAConnectionMinCount	OBJECT-TYPE
SYNTAX	INTEGER
MAX-ACCESS	read-only
STATUS	current
DESCRIPTION	 "Minimum size reached by the connection pool"
::=	{	sqlPoolXAEntry	14
	}

sqlPoolXAConnectionMaxCount	OBJECT-TYPE
SYNTAX	INTEGER
MAX-ACCESS	read-only
STATUS	current
DESCRIPTION	 "Maximum size reached by the connection pool"
::=	{	sqlPoolXAEntry	15
	}

sqlPoolXACheckedOutConnectionCurrentCount	OBJECT-TYPE
SYNTAX	INTEGER
MAX-ACCESS	read-only
STATUS	current
DESCRIPTION	 "Current number of connection that are checked out from the pool"
::=	{	sqlPoolXAEntry	16
	}

sqlPoolXACheckedOutConnectionMinCount	OBJECT-TYPE
SYNTAX	INTEGER
MAX-ACCESS	read-only
STATUS	current
DESCRIPTION	 "Minimum number of simultaneous checked out connections reached by the pool"
::=	{	sqlPoolXAEntry	17
	}

sqlPoolXACheckedOutConnectionMaxCount	OBJECT-TYPE
SYNTAX	INTEGER
MAX-ACCESS	read-only
STATUS	current
DESCRIPTION	 "Maximum number of simultaneous checked out connections reached by the pool"
::=	{	sqlPoolXAEntry	18
	}

sqlPoolXACheckedOutConnectionCumulativeCount	OBJECT-TYPE
SYNTAX	INTEGER
MAX-ACCESS	read-only
STATUS	current
DESCRIPTION	 "Number of checkout performed from pool"
::=	{	sqlPoolXAEntry	19
	}

sqlPoolXACheckedOutConnectionCumulativeTime	OBJECT-TYPE
SYNTAX	Unsigned32
MAX-ACCESS	read-only
STATUS	current
DESCRIPTION	 "Cumulation of time that the connections are checked out from the pool"
::=	{	sqlPoolXAEntry	20
	}

sqlPoolXACheckedOutConnectionMinTime	OBJECT-TYPE
SYNTAX	Unsigned32
MAX-ACCESS	read-only
STATUS	current
DESCRIPTION	 "Minimum time that a connection has been checked out from the pool"
::=	{	sqlPoolXAEntry	21
	}

sqlPoolXACheckedOutConnectionMaxTime	OBJECT-TYPE
SYNTAX	Unsigned32
MAX-ACCESS	read-only
STATUS	current
DESCRIPTION	 "Maximum time that a connection has been checked out from the pool"
::=	{	sqlPoolXAEntry	22
	}

sqlPoolXACheckedOutConnectionAverageTime	OBJECT-TYPE
SYNTAX	DisplayString
MAX-ACCESS	read-only
STATUS	current
DESCRIPTION	 "Connection checkedout average time (equals to CheckedOutConnectionCumulativeTime divided by CheckedOutConnectionCumulativeCount"
::=	{	sqlPoolXAEntry	23
	}


END
