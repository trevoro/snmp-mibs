Wellfleet-FRSW-MIB DEFINITIONS ::= BEGIN

-- Created by mdl2asn version 3.1
-- Creation date: Wed Aug 30 16:41:23 EDT 1995


    IMPORTS

      IpAddress, Counter, TimeTicks, Gauge
        FROM RFC1155-SMI
      OBJECT-TYPE
        FROM RFC-1212
      DisplayString
        FROM RFC1213-MIB
      wfFrswGroup
        FROM Wellfleet-COMMON-MIB;


    wfFrSwDlcmiTable OBJECT-TYPE
        SYNTAX	SEQUENCE OF WfFrSwDlcmiEntry
        ACCESS	not-accessible
        STATUS	mandatory
        DESCRIPTION
                "The Parameters for the Data Link Connection
                Management Interface corresponding to any
                interface.  Incorporates the Error table."
        ::= { wfFrswGroup 1 }

    wfFrSwDlcmiEntry OBJECT-TYPE
        SYNTAX	WfFrSwDlcmiEntry
        ACCESS	not-accessible
        STATUS	mandatory
        DESCRIPTION
                "The parameters for a particular Data Link Connection
                Management Interface."
        INDEX	{ wfFrSwDlcmiCircuit }
        ::= { wfFrSwDlcmiTable 1 }

    WfFrSwDlcmiEntry ::= SEQUENCE {
    	    wfFrSwDlcmiDelete
    		INTEGER,
    	    wfFrSwDlcmiState
    		INTEGER,
    	    wfFrSwDlcmiNniEnable
    		INTEGER,
    	    wfFrSwDlcmiCircuit
    		INTEGER,
    	    wfFrSwDlcmiManagementType
    		INTEGER,
    	    wfFrSwL3NetAddress
    		IpAddress,
    	    wfFrSwDlcmiAddressLen
    		INTEGER,
    	    wfFrSwDlcmiControlByteDisable
    		INTEGER,
    	    wfFrSwDlcmiPollingInterval
    		INTEGER,
    	    wfFrSwDlcmiFullEnquiryInterval
    		INTEGER,
    	    wfFrSwDlcmiErrorThreshold
    		INTEGER,
    	    wfFrSwDlcmiMonitoredEvents
    		INTEGER,
    	    wfFrSwDlcmiRecoveryCounts
    		INTEGER,
    	    wfFrSwDlcmiMaxSupportedVCs
    		INTEGER,
    	    wfFrSwDlcmiVCsInUse
    		INTEGER,
    	    wfFrSwSwitchHdrErrors
    		Counter,
    	    wfFrSwDlcmiSequenceCount
    		INTEGER,
    	    wfFrSwDlcmiLastReceived
    		INTEGER,
    	    wfFrSwDlcmiActiveSeqCount
    		INTEGER,
    	    wfFrSwDlcmiActiveReceived
    		INTEGER,
    	    wfFrSwDlcmiPolls
    		Counter,
    	    wfFrSwDlcmiAlarmTimer
    		INTEGER,
    	    wfFrSwErrType
    		INTEGER,
    	    wfFrSwErrData
    		OCTET STRING,
    	    wfFrSwErrTime
    		TimeTicks,
    	    wfFrSwBcMeasurementInterval
    		INTEGER,
    	    wfFrSwDlcmiMcastNoBufferErrors
    		Counter,
    	    wfFrSwDlcmiFrameTooShortErrors
    		Counter,
    	    wfFrSwDlcmiFrameTooLongErrors
    		Counter,
    	    wfFrSwDlcmiIllegalDlciErrors
    		Counter,
    	    wfFrSwDlcmiUnknownDlciErrors
    		Counter,
    	    wfFrSwDlcmiProtocolErrors
    		Counter,
    	    wfFrSwDlcmiUnknownIEErrors
    		Counter,
    	    wfFrSwDlcmiSequenceErrors
    		Counter,
    	    wfFrSwDlcmiUnknownRPTErrors
    		Counter,
    	    wfFrSwDlcmiControlByteErrors
    		Counter,
    	    wfFrSwDlcmiFormatErrors
    		Counter,
    	    wfFrSwDlcmiOtherErrors
    		Counter,
    	    wfFrSwDlcmiStatus
    		INTEGER,
    	    wfFrSwDlcmiNewVCs
    		Counter,
    	    wfFrSwDlcmiDeletedVCs
    		Counter,
    	    wfFrSwDlcmiFullStatusSeq
    		Counter,
    	    wfFrSwDlcmiBidirect
    		INTEGER,
    	    wfFrSwDlcmiDteStatus
    		INTEGER,
    	    wfFrSwDlcmiDteSeqCount
    		INTEGER,
    	    wfFrSwDlcmiDteReceived
    		INTEGER,
    	    wfFrSwDlcmiDteLastReceived
    		INTEGER,
    	    wfFrSwDlcmiDtePolls
    		Counter,
    	    wfFrSwDlcmiDtePollingInterval
    		INTEGER,
    	    wfFrSwDlcmiDteFullEnquiryInterval
    		INTEGER,
    	    wfFrSwDlcmiDteErrorThreshold
    		INTEGER,
    	    wfFrSwDlcmiCrossNetEnable
    		INTEGER,
    	    wfFrSwDlcmiCrossNetPollingInterval
    		INTEGER,
    	    wfFrSwDlcmiCrossNetErrorThreshold
    		INTEGER,
    	    wfFrSwDlcmiCrossNetAsyncUpdateEnable
    		INTEGER,
    	    wfFrSwDlcmiBcMeasurementEnable
    		INTEGER,
    	    wfFrSwDlcmiAsyncUpdateEnable
    		INTEGER,
            wfFrSwDlcmiCrossNetListenEnable
		INTEGER,
    	    wfFrSwDlcmiSvcDisable
    		INTEGER,
    	    wfFrSwDlcmiL2AddrType
    		INTEGER,
	    wfFrSwDlcmiEscapeMode
		INTEGER,
    	    wfFrSwDlcmiEscapeCircuit
    		INTEGER,
    	    wfFrSwDlcmiEscapeVcCount
    		INTEGER,
    	    wfFrSwDlcmiIwfMode
    		INTEGER,
    	    wfFrSwDlcmiSvcBillingEnable
    		INTEGER,
	    wfFrSwDlcmiSpvcAgent
		INTEGER,
	    wfFrSwDlcmiCallAccDlciSelectionType
		INTEGER
        }

    wfFrSwDlcmiDelete OBJECT-TYPE
        SYNTAX	INTEGER {
    		    created(1),
    		    deleted(2)
    		}
        ACCESS	read-write
        STATUS	mandatory
        DESCRIPTION
                "Indication to delete this frame relay interface."
        DEFVAL	{ created }
        ::= { wfFrSwDlcmiEntry 1 }
 
   wfFrSwDlcmiState OBJECT-TYPE
        SYNTAX	INTEGER {
    		    up(1),
    		    down(2),
    		    init(3)
    		}
        ACCESS	read-only
        STATUS	mandatory
        DESCRIPTION
                "Indicates which state of DLCMI the interface is in"
        DEFVAL	{ init }
        ::= { wfFrSwDlcmiEntry 2 }

    wfFrSwDlcmiNniEnable OBJECT-TYPE
        SYNTAX	INTEGER {
    		    enabled(1),
    		    disabled(2)
    		}
        ACCESS	read-write
        STATUS	mandatory
        DESCRIPTION
                "Indicates whether a NNI is enabled for this entry."
        DEFVAL	{ disabled }
        ::= { wfFrSwDlcmiEntry 3 }

    wfFrSwDlcmiCircuit OBJECT-TYPE
        SYNTAX	INTEGER
        ACCESS	read-only
        STATUS	mandatory
        DESCRIPTION
                "Instance identifier; the circuit number of this entry."
        ::= { wfFrSwDlcmiEntry 4 }

    wfFrSwDlcmiManagementType OBJECT-TYPE
        SYNTAX	INTEGER {
    		    none(1),
    		    lmi(2),
    		    t1617d(3),
    		    t1617b(4),
    		    annexa(5),
    		    lmiswitch(6),
    		    annexdswitch(7),
    		    annexaswitch(8),
    		    iwfoamenabled(9),
    		    iwfoamdisabled(10)
    		}
        ACCESS	read-write
        STATUS	mandatory
        DESCRIPTION
                "Indicates the Data Link Connection Management scheme
                that is active."
        DEFVAL	{ t1617d }
        ::= { wfFrSwDlcmiEntry 5 }

    wfFrSwL3NetAddress OBJECT-TYPE
        SYNTAX	IpAddress
        ACCESS	read-write
        STATUS	mandatory
        DESCRIPTION
                "Indicates level 3 (IP) address of this frame relay interface"
        ::= { wfFrSwDlcmiEntry 6 }

    wfFrSwDlcmiAddressLen OBJECT-TYPE
        SYNTAX	INTEGER {
    		    twobyte(2),
    		    threebyte(3),
    		    fourbyte(4)
    		}
        ACCESS	read-write
        STATUS	mandatory
        DESCRIPTION
                "Indicates the address length, including the
                control portion."
        DEFVAL	{ twobyte }
        ::= { wfFrSwDlcmiEntry 7 }

    wfFrSwDlcmiControlByteDisable OBJECT-TYPE
        SYNTAX	INTEGER {
    		    enabled(1),
    		    disabled(2)
    		}
        ACCESS	read-write
        STATUS	mandatory
        DESCRIPTION
                "Indicates inclusion of control byte in q922 format."
        DEFVAL	{ disabled }
        ::= { wfFrSwDlcmiEntry 8 }

    wfFrSwDlcmiPollingInterval OBJECT-TYPE
        SYNTAX	INTEGER(5..30)
        ACCESS	read-write
        STATUS	mandatory
        DESCRIPTION
                "The number of seconds between successive status enquiry
                messages."
        DEFVAL	{ 15 }
        ::= { wfFrSwDlcmiEntry 9 }

    wfFrSwDlcmiFullEnquiryInterval OBJECT-TYPE
        SYNTAX	INTEGER(1..255)
        ACCESS	read-write
        STATUS	mandatory
        DESCRIPTION
                "Indicates the number of status enquiries before a full
                status enquiry. (For bidirectional procedures.)"
        DEFVAL	{ 6 }
        ::= { wfFrSwDlcmiEntry 10 }

    wfFrSwDlcmiErrorThreshold OBJECT-TYPE
        SYNTAX	INTEGER
        ACCESS	read-write
        STATUS	mandatory
        DESCRIPTION
                "Indicates the number errors monitored before declaring
                the interface down."
        DEFVAL	{ 3 }
        ::= { wfFrSwDlcmiEntry 11 }

    wfFrSwDlcmiMonitoredEvents OBJECT-TYPE
        SYNTAX	INTEGER
        ACCESS	read-write
        STATUS	mandatory
        DESCRIPTION
                "Indicates the events over which error threshold is kept."
        DEFVAL	{ 4 }
        ::= { wfFrSwDlcmiEntry 12 }

    wfFrSwDlcmiRecoveryCounts OBJECT-TYPE
        SYNTAX	INTEGER
        ACCESS	read-only
        STATUS	mandatory
        DESCRIPTION
                "Indicates the number of correct polling
                cycles during recovery."
        ::= { wfFrSwDlcmiEntry 13 }

    wfFrSwDlcmiMaxSupportedVCs OBJECT-TYPE
        SYNTAX	INTEGER(1..1024)
        ACCESS	read-write
        STATUS	mandatory
        DESCRIPTION
                "Indicates the maximum number of VCs allowed."
        DEFVAL	{ 100 }
        ::= { wfFrSwDlcmiEntry 14 }

    wfFrSwDlcmiVCsInUse OBJECT-TYPE
        SYNTAX	INTEGER
        ACCESS	read-only
        STATUS	mandatory
        DESCRIPTION
                "Indicates the number of VCs that are currently
                configured on this interface."
        ::= { wfFrSwDlcmiEntry 15 }

    wfFrSwSwitchHdrErrors OBJECT-TYPE
        SYNTAX	Counter
        ACCESS	read-only
        STATUS	mandatory
        DESCRIPTION
                "Indicates the number of frames dropped because they were
                received on the remote side with an invalid switch header."
        ::= { wfFrSwDlcmiEntry 16 }

    wfFrSwDlcmiSequenceCount OBJECT-TYPE
        SYNTAX	INTEGER(1..255)
        ACCESS	read-only
        STATUS	mandatory
        DESCRIPTION
                "Indicates this switch's sequence counter; value of
                next to send."
        DEFVAL	{ 1 }
        ::= { wfFrSwDlcmiEntry 17 }

    wfFrSwDlcmiLastReceived OBJECT-TYPE
        SYNTAX	INTEGER(1..255)
        ACCESS	read-only
        STATUS	mandatory
        DESCRIPTION
                "Indicates the sequence number just received from
                the end station."
        DEFVAL	{ 1 }
        ::= { wfFrSwDlcmiEntry 18 }

    wfFrSwDlcmiActiveSeqCount OBJECT-TYPE
        SYNTAX	INTEGER(1..255)
        ACCESS	read-only
        STATUS	mandatory
        DESCRIPTION
                "Indicates the switch's sequence counter for sending
                status enquiry. (For bidirectional procedures.)"
        DEFVAL	{ 1 }
        ::= { wfFrSwDlcmiEntry 19 }

    wfFrSwDlcmiActiveReceived OBJECT-TYPE
        SYNTAX	INTEGER(1..255)
        ACCESS	read-only
        STATUS	mandatory
        DESCRIPTION
                "Indicates the sequence number just received from the
                enquiring station. (For bidirectional procedures.)"
        DEFVAL	{ 1 }
        ::= { wfFrSwDlcmiEntry 20 }

    wfFrSwDlcmiPolls OBJECT-TYPE
        SYNTAX	Counter
        ACCESS	read-only
        STATUS	mandatory
        DESCRIPTION
                "This is the counter of where we are in the polling cycle."
        ::= { wfFrSwDlcmiEntry 21 }

    wfFrSwDlcmiAlarmTimer OBJECT-TYPE
        SYNTAX	INTEGER
        ACCESS	read-only
        STATUS	mandatory
        DESCRIPTION
                "Counter of 1/2 second timeouts. Indicates
                when to expect poll."
        ::= { wfFrSwDlcmiEntry 22 }

    wfFrSwErrType OBJECT-TYPE
        SYNTAX	INTEGER {
    		    reset(1),
    		    other(2),
    		    short(3),
    		    long(4),
    		    illegaldlci(5),
    		    unknowndlci(6),
    		    protoerr(7),
    		    unknownie(8),
    		    sequenceerr(9),
    		    unknownrpt(10),
    		    byteerr(11),
    		    hdrerr(12),
    		    formaterr(13)
    		}
        ACCESS	read-only
        STATUS	mandatory
        DESCRIPTION
                "Indicates the type of the last specific monitored error."
        DEFVAL	{ reset }
        ::= { wfFrSwDlcmiEntry 23 }

    wfFrSwErrData OBJECT-TYPE
        SYNTAX	OCTET STRING
        ACCESS	read-only
        STATUS	mandatory
        DESCRIPTION
                "Contains as much of the error packet as possible."
        ::= { wfFrSwDlcmiEntry 24 }

    wfFrSwErrTime OBJECT-TYPE
        SYNTAX	TimeTicks
        ACCESS	read-only
        STATUS	mandatory
        DESCRIPTION
                "Indicates the time the last error occurred."
        ::= { wfFrSwDlcmiEntry 25 }

    wfFrSwBcMeasurementInterval OBJECT-TYPE
        SYNTAX	INTEGER(100..2000)
        ACCESS	read-write
        STATUS	mandatory
        DESCRIPTION
                "Indicates the Committed Burst sample window interval in msec"
        DEFVAL	{ 500 }
        ::= { wfFrSwDlcmiEntry 26 }

    wfFrSwDlcmiMcastNoBufferErrors OBJECT-TYPE
        SYNTAX	Counter
        ACCESS	read-only
        STATUS	mandatory
        DESCRIPTION
                "Indicates the number of times a multicast failed partially
                or wholly because there are insufficient buffers available
                to create multiple copies of a multicast frame"
        ::= { wfFrSwDlcmiEntry 27 }

    wfFrSwDlcmiFrameTooShortErrors OBJECT-TYPE
        SYNTAX	Counter
        ACCESS	read-only
        STATUS	mandatory
        DESCRIPTION
                "Indicates the number of frames dropped that
                are too short to be accepted."
        ::= { wfFrSwDlcmiEntry 28 }

    wfFrSwDlcmiFrameTooLongErrors OBJECT-TYPE
        SYNTAX	Counter
        ACCESS	read-only
        STATUS	mandatory
        DESCRIPTION
                "Indicates the number of frames dropped that
                are too long to be accepted."
        ::= { wfFrSwDlcmiEntry 29 }

    wfFrSwDlcmiIllegalDlciErrors OBJECT-TYPE
        SYNTAX	Counter
        ACCESS	read-only
        STATUS	mandatory
        DESCRIPTION
                "Indicates the number of frames dropped that
                had an invalid DLCI value."
        ::= { wfFrSwDlcmiEntry 30 }

    wfFrSwDlcmiUnknownDlciErrors OBJECT-TYPE
        SYNTAX	Counter
        ACCESS	read-only
        STATUS	mandatory
        DESCRIPTION
                "Indicates the number of frames dropped which
                had an unknown DLCI value."
        ::= { wfFrSwDlcmiEntry 31 }

    wfFrSwDlcmiProtocolErrors OBJECT-TYPE
        SYNTAX	Counter
        ACCESS	read-only
        STATUS	mandatory
        DESCRIPTION
                "Indicates the number of frames dropped because
                of a DLCMI protocol violation."
        ::= { wfFrSwDlcmiEntry 32 }

    wfFrSwDlcmiUnknownIEErrors OBJECT-TYPE
        SYNTAX	Counter
        ACCESS	read-only
        STATUS	mandatory
        DESCRIPTION
                "Indicates the number of frames dropped that
                had an unknown information element."
        ::= { wfFrSwDlcmiEntry 33 }

    wfFrSwDlcmiSequenceErrors OBJECT-TYPE
        SYNTAX	Counter
        ACCESS	read-only
        STATUS	mandatory
        DESCRIPTION
                "Indicates the number of frames dropped because
                of a DLCMI sequence error."
        ::= { wfFrSwDlcmiEntry 34 }

    wfFrSwDlcmiUnknownRPTErrors OBJECT-TYPE
        SYNTAX	Counter
        ACCESS	read-only
        STATUS	mandatory
        DESCRIPTION
                "Indicates the number of frames dropped which
                had an unknown report type."
        ::= { wfFrSwDlcmiEntry 35 }

    wfFrSwDlcmiControlByteErrors OBJECT-TYPE
        SYNTAX	Counter
        ACCESS	read-only
        STATUS	mandatory
        DESCRIPTION
                "Indicates the number of frames dropped that
                had an unsupported control byte."
        ::= { wfFrSwDlcmiEntry 36 }

    wfFrSwDlcmiFormatErrors OBJECT-TYPE
        SYNTAX	Counter
        ACCESS	read-only
        STATUS	mandatory
        DESCRIPTION
                "Indicates the number of frames dropped due to
                a frame format error."
        ::= { wfFrSwDlcmiEntry 37 }

    wfFrSwDlcmiOtherErrors OBJECT-TYPE
        SYNTAX	Counter
        ACCESS	read-only
        STATUS	mandatory
        DESCRIPTION
                "Indicates the number of frames dropped due to unknown
                or other errors not counted by any error counter."
        ::= { wfFrSwDlcmiEntry 38 }

    wfFrSwDlcmiStatus OBJECT-TYPE
        SYNTAX	INTEGER {
    		    running(1),
    		    recovered(2),
    		    fault(3),
    		    start(4)
    		}
        ACCESS	read-only
        STATUS	mandatory
        DESCRIPTION
                "Indicates which state of execution the DLCMI gate is in"
        DEFVAL	{ start }
        ::= { wfFrSwDlcmiEntry 39 }

    wfFrSwDlcmiNewVCs OBJECT-TYPE
        SYNTAX	Counter
        ACCESS	read-only
        STATUS	mandatory
        DESCRIPTION
                "Indicates the number of newly added PVCs that we have not yet told the
                CPE about, by means of a full-status message."
        ::= { wfFrSwDlcmiEntry 40 }

    wfFrSwDlcmiDeletedVCs OBJECT-TYPE
        SYNTAX	Counter
        ACCESS	read-only
        STATUS	mandatory
        DESCRIPTION
                "Indicates the number of deletedly added PVCs that we have not yet told the
                CPE about, by means of a full-status message."
        ::= { wfFrSwDlcmiEntry 41 }

    wfFrSwDlcmiFullStatusSeq OBJECT-TYPE
        SYNTAX	Counter
        ACCESS	read-only
        STATUS	mandatory
        DESCRIPTION
                "Indicates the expected sequence number for the next Status Enquiry
                message that will prove that the CPE received our last Full Status
                Message and knows about the deleted PVCs."
        ::= { wfFrSwDlcmiEntry 42 }

    wfFrSwDlcmiBidirect OBJECT-TYPE
        SYNTAX	INTEGER {
    		    enable(1),
    		    disable(2)
    		}
        ACCESS	read-write
        STATUS	mandatory
        DESCRIPTION
                "Indication to delete this frame relay interface."
        DEFVAL	{ disable }
        ::= { wfFrSwDlcmiEntry 43 }

    wfFrSwDlcmiDteStatus OBJECT-TYPE
        SYNTAX	INTEGER {
    		    running(1),
    		    recovered(2),
    		    fault(3),
    		    start(4)
    		}
        ACCESS	read-only
        STATUS	mandatory
        DESCRIPTION
                "Indicates which state of execution the DLCMI gate is in for
                bidirectional procedures."
        DEFVAL	{ start }
        ::= { wfFrSwDlcmiEntry 44 }

    wfFrSwDlcmiDteSeqCount OBJECT-TYPE
        SYNTAX	INTEGER(1..255)
        ACCESS	read-only
        STATUS	mandatory
        DESCRIPTION
                "Indicates the switch's sequence counter for sending
                status enquiry. (For bidirectional procedures.)"
        DEFVAL	{ 1 }
        ::= { wfFrSwDlcmiEntry 45 }

    wfFrSwDlcmiDteReceived OBJECT-TYPE
        SYNTAX	INTEGER(1..255)
        ACCESS	read-only
        STATUS	mandatory
        DESCRIPTION
                "Indicates the sequence number just received from the
                enquiring station. (For bidirectional procedures.)"
        DEFVAL	{ 1 }
        ::= { wfFrSwDlcmiEntry 46 }

    wfFrSwDlcmiDteLastReceived OBJECT-TYPE
        SYNTAX	INTEGER(1..255)
        ACCESS	read-only
        STATUS	mandatory
        DESCRIPTION
                "Indicates the sequence number just received from
                the end station."
        DEFVAL	{ 1 }
        ::= { wfFrSwDlcmiEntry 47 }

    wfFrSwDlcmiDtePolls OBJECT-TYPE
        SYNTAX	Counter
        ACCESS	read-only
        STATUS	mandatory
        DESCRIPTION
                "This is the counter of where we are in the polling cycle."
        ::= { wfFrSwDlcmiEntry 48 }

    wfFrSwDlcmiDtePollingInterval OBJECT-TYPE
        SYNTAX	INTEGER(5..30)
        ACCESS	read-write
        STATUS	mandatory
        DESCRIPTION
                "The number of seconds between successive status enquiry
                messages."
        DEFVAL	{ 10 }
        ::= { wfFrSwDlcmiEntry 49 }

    wfFrSwDlcmiDteFullEnquiryInterval OBJECT-TYPE
        SYNTAX	INTEGER(1..255)
        ACCESS	read-write
        STATUS	mandatory
        DESCRIPTION
                "Indicates the number of status enquiries before a full
                status enquiry. (For bidirectional procedures.)"
        DEFVAL	{ 6 }
        ::= { wfFrSwDlcmiEntry 50 }

    wfFrSwDlcmiDteErrorThreshold OBJECT-TYPE
        SYNTAX	INTEGER
        ACCESS	read-write
        STATUS	mandatory
        DESCRIPTION
                "Indicates the number errors monitored before declaring
                the interface down."
        DEFVAL	{ 3 }
        ::= { wfFrSwDlcmiEntry 51 }

    wfFrSwDlcmiCrossNetEnable OBJECT-TYPE
        SYNTAX	INTEGER {
    		    enable(1),
    		    disable(2)
    		}
        ACCESS	read-write
        STATUS	mandatory
        DESCRIPTION
                "Indication to delete this frame relay interface."
        DEFVAL	{ enable }
        ::= { wfFrSwDlcmiEntry 52 }

    wfFrSwDlcmiCrossNetPollingInterval OBJECT-TYPE
        SYNTAX	INTEGER(5..86400)
        ACCESS	read-write
        STATUS	mandatory
        DESCRIPTION
                "The number of seconds between successive status enquiry
                messages."
        DEFVAL	{ 120 }
        ::= { wfFrSwDlcmiEntry 53 }

    wfFrSwDlcmiCrossNetErrorThreshold OBJECT-TYPE
        SYNTAX	INTEGER
        ACCESS	read-write
        STATUS	mandatory
        DESCRIPTION
                "Indicates the number missed heartbeat polls before
                declaring the cross-net PVC inactive."
        DEFVAL	{ 3 }
        ::= { wfFrSwDlcmiEntry 54 }

    wfFrSwDlcmiCrossNetAsyncUpdateEnable OBJECT-TYPE
        SYNTAX	INTEGER {
    		    enabled(1),
    		    disabled(2)
    		}
        ACCESS	read-write
        STATUS	mandatory
        DESCRIPTION
                "Indicates whether we are to send to the other end
                of the network, status updates for dlcis as soon as
                there is a change of status for the dlci."
        DEFVAL	{ enabled }
        ::= { wfFrSwDlcmiEntry 55 }

    wfFrSwDlcmiBcMeasurementEnable OBJECT-TYPE
        SYNTAX	INTEGER {
    		    enable(1),
    		    disable(2)
    		}
        ACCESS	read-write
        STATUS	mandatory
        DESCRIPTION
                "Indicates whether Committed Burst Measurement is enabled
                for this interface. If this attribute is set to DISABLE then
                DE bit setting in Frame Relay frames at this interface is disabled."
        DEFVAL	{ enable }
        ::= { wfFrSwDlcmiEntry 56 }

    wfFrSwDlcmiAsyncUpdateEnable OBJECT-TYPE
        SYNTAX	INTEGER {
    		    enabled(1),
    		    disabled(2)
    		}
        ACCESS	read-write
        STATUS	mandatory
        DESCRIPTION
                "Indicates whether the link management entity should
                send an asynchronous single PVC update message
                when the state of a PVC is changed by a technician
                or by cross-net polling procedures. "
        DEFVAL	{ enabled }
        ::= { wfFrSwDlcmiEntry 57 }

    wfFrSwDlcmiCrossNetListenEnable
	OBJECT-TYPE
        SYNTAX	INTEGER {
    		    enabled(1),
    		    disabled(2)
    		}
        ACCESS	read-write
        STATUS	mandatory
        DESCRIPTION
                "Indicates whether the link management entity should
		 make a judgement of the PVC's status based on Cross
		 Net updates."
        DEFVAL	{ disabled }
        ::= { wfFrSwDlcmiEntry 58 }

    wfFrSwDlcmiSvcDisable OBJECT-TYPE
	SYNTAX	INTEGER {
		enabled(1),
		disabled(2)
	}
	ACCESS	read-write
	STATUS	mandatory
	DESCRIPTION
		" Indicates whether SVC is enabled or disabled for this access
		   channel. "
	DEFVAL	{ disabled }
	::= { wfFrSwDlcmiEntry 59 }

    wfFrSwDlcmiL2AddrType OBJECT-TYPE
	SYNTAX	INTEGER {
		e164(1),
		x121(2)
	}
	ACCESS	read-write
	STATUS	mandatory
	DESCRIPTION
		" Indicates the address type supported on this access
		   channel.  This information is needed when wFrSwDlcmiSVCDisable
		   is enabled. "
	DEFVAL	{ e164 }
	::= { wfFrSwDlcmiEntry 60 }

    wfFrSwDlcmiEscapeMode OBJECT-TYPE
	SYNTAX  INTEGER {
		    disabled(1),
		    ingress(2),
		    egress(3)
		    }
	ACCESS	read-write
	STATUS	mandatory
	DESCRIPTION
		" Identifies the Escape mode (none, ingress or egress) to be used for 
		  PVCs with wfFrSwVcEscapeMode set to enabled."
	DEFVAL { disabled }
	::= { wfFrSwDlcmiEntry 61 }
	
    wfFrSwDlcmiEscapeCircuit OBJECT-TYPE
	SYNTAX  INTEGER
	ACCESS	read-write
	STATUS	mandatory
	DESCRIPTION
		"Identifies the FR-DTE circuit number corresponding to an Escape PVC.
		Applies only to PVCs with wfFrSwVcEscapeEnable set to enabled."
	::= { wfFrSwDlcmiEntry 62 }
	
    wfFrSwDlcmiEscapeVcCount OBJECT-TYPE
	SYNTAX	INTEGER 
	ACCESS	read-write
	STATUS	mandatory
	DESCRIPTION
		" The number of PVCs on this DLCMI that are configured as 
                  Escape VCs"
        DEFVAL	{ 0 }
	::= { wfFrSwDlcmiEntry 63 }

    wfFrSwDlcmiIwfMode OBJECT-TYPE
	SYNTAX  INTEGER {
		    none(1),
		    sdlc2frsw(2)
		    }
	ACCESS	read-write
	STATUS	mandatory
	DESCRIPTION
		" Identifies the interworking mode (none, SDLC-to-FRSW) to be used for 
		  PVCs with wfFrSwVcEscapeMode set to enabled."
        DEFVAL	{ none }
	::= { wfFrSwDlcmiEntry 64 }

    wfFrSwDlcmiSvcBillingEnable
	OBJECT-TYPE
        SYNTAX	INTEGER {
    		    enabled(1),
    		    disabled(2)
    		}	
        ACCESS	read-write
        STATUS	mandatory
        DESCRIPTION
                "Indicates whether the SVC Billing on this access 
		 channel set to enable."
        DEFVAL	{ enabled }
        ::= { wfFrSwDlcmiEntry 65 }

    wfFrSwDlcmiSpvcAgent OBJECT-TYPE
	SYNTAX  INTEGER {
		    none(1),
		    cra(2),
		    caa(3),
		    craandcaa(4)
		    }
	ACCESS	read-write
	STATUS	mandatory
	DESCRIPTION
		" Indicates if an SPVC Call Request Agent, Call Accept
		  Agent, or both are enabled on this FRSW circuit."
	DEFVAL { none }
	::= { wfFrSwDlcmiEntry 66 }

    wfFrSwDlcmiCallAccDlciSelectionType OBJECT-TYPE
	SYNTAX	INTEGER {
			any(1),
			specific(2)
			}
	ACCESS	read-write
	STATUS	mandatory
	DESCRIPTION
		"Indicates to the Call Accept Agent to accept SPVC Call Setup 
		 requests for any available DLCI or for a specific DLCI. Call 
		 Setup requests with the wrong selection type will be rejected."
	DEFVAL { any }
	::= { wfFrSwDlcmiEntry 67 }

    wfFrSwCctTable OBJECT-TYPE
        SYNTAX	SEQUENCE OF WfFrSwCctEntry
        ACCESS	not-accessible
        STATUS	obsolete
        DESCRIPTION
                "Frame Relay Circuit table gives information
                about a virtual circuit."
        ::= { wfFrswGroup 2 }

    wfFrSwCctEntry OBJECT-TYPE
        SYNTAX	WfFrSwCctEntry
        ACCESS	not-accessible
        STATUS	obsolete
        DESCRIPTION
                "An entry in the Frame Relay (Virtual) Circuit table."
        INDEX	{ wfFrSwCctNumber,
    		  wfFrSwCctDlci }
        ::= { wfFrSwCctTable 1 }

    WfFrSwCctEntry ::= SEQUENCE {
    	    wfFrSwCctDelete
    		INTEGER,
    	    wfFrSwCctNumber
    		INTEGER,
    	    wfFrSwCctDlci
    		INTEGER,
    	    wfFrSwCctState
    		INTEGER,
    	    wfFrSwCctMulticast
    		INTEGER,
    	    wfFrSwCctInBc
    		INTEGER,
    	    wfFrSwCctOutBc
    		INTEGER,
    	    wfFrSwCctInBe
    		INTEGER,
    	    wfFrSwCctOutBe
    		INTEGER,
    	    wfFrSwCctInThroughput
    		INTEGER,
    	    wfFrSwCctOutThroughput
    		INTEGER,
    	    wfFrSwCctCreationTime
    		TimeTicks,
    	    wfFrSwCctLastTimeChange
    		TimeTicks,
    	    wfFrSwCctLocalSentNonDEFrames
    		Counter,
    	    wfFrSwCctLocalSentNonDEOctets
    		Counter,
    	    wfFrSwCctLocalSentDEFrames
    		Counter,
    	    wfFrSwCctLocalSentDEOctets
    		Counter,
    	    wfFrSwCctLocalSetFECNFrames
    		Counter,
    	    wfFrSwCctLocalSetFECNOctets
    		Counter,
    	    wfFrSwCctLocalSetBECNFrames
    		Counter,
    	    wfFrSwCctLocalSetBECNOctets
    		Counter,
    	    wfFrSwCctLocalSetDEFrames
    		Counter,
    	    wfFrSwCctLocalSetDEOctets
    		Counter,
    	    wfFrSwCctLocalDropNonDEFrames
    		Counter,
    	    wfFrSwCctLocalDropNonDEOctets
    		Counter,
    	    wfFrSwCctLocalDropDEFrames
    		Counter,
    	    wfFrSwCctLocalDropDEOctets
    		Counter,
    	    wfFrSwCctInactiveVCDropFrames
    		Counter,
    	    wfFrSwCctInactiveVCDropOctets
    		Counter,
    	    wfFrSwCctLocalRecvNonDEFrames
    		Counter,
    	    wfFrSwCctLocalRecvNonDEOctets
    		Counter,
    	    wfFrSwCctLocalRecvDEFrames
    		Counter,
    	    wfFrSwCctLocalRecvDEOctets
    		Counter,
    	    wfFrSwCctLocalRecvFECNFrames
    		Counter,
    	    wfFrSwCctLocalRecvFECNOctets
    		Counter,
    	    wfFrSwCctLocalRecvBECNFrames
    		Counter,
    	    wfFrSwCctLocalRecvBECNOctets
    		Counter,
    	    wfFrSwCctLocalRecentNonDEOctets
    		Counter,
    	    wfFrSwCctRemoteSentNonDEFrames
    		Counter,
    	    wfFrSwCctRemoteSentNonDEOctets
    		Counter,
    	    wfFrSwCctRemoteSentDEFrames
    		Counter,
    	    wfFrSwCctRemoteSentDEOctets
    		Counter,
    	    wfFrSwCctRemoteSetFECNFrames
    		Counter,
    	    wfFrSwCctRemoteSetFECNOctets
    		Counter,
    	    wfFrSwCctRemoteSetBECNFrames
    		Counter,
    	    wfFrSwCctRemoteSetBECNOctets
    		Counter,
    	    wfFrSwCctRemoteDropNonDEFrames
    		Counter,
    	    wfFrSwCctRemoteDropNonDEOctets
    		Counter,
    	    wfFrSwCctRemoteDropDEFrames
    		Counter,
    	    wfFrSwCctRemoteDropDEOctets
    		Counter,
    	    wfFrSwCctRemoteRecvNonDEFrames
    		Counter,
    	    wfFrSwCctRemoteRecvNonDEOctets
    		Counter,
    	    wfFrSwCctRemoteRecvDEFrames
    		Counter,
    	    wfFrSwCctRemoteRecvDEOctets
    		Counter,
    	    wfFrSwCctRemoteRecvFECNFrames
    		Counter,
    	    wfFrSwCctRemoteRecvFECNOctets
    		Counter,
    	    wfFrSwCctRemoteRecvBECNFrames
    		Counter,
    	    wfFrSwCctRemoteRecvBECNOctets
    		Counter,
    	    wfFrSwCctLocalBecnState
    		INTEGER,
    	    wfFrSwCctRemoteBecnState
    		INTEGER,
    	    wfFrSwCctLocalOrRemoteConnection
    		INTEGER,
    	    wfFrSwCctInBcOctets
    		INTEGER,
    	    wfFrSwCctStateSet
    		INTEGER,
    	    wfFrSwCctReportedStatus
    		INTEGER,
    	    wfFrSwCctReceivedStatus
    		INTEGER,
    	    wfFrSwCctCrossNetStatus
    		INTEGER,
    	    wfFrSwCctXNetSent
    		INTEGER,
    	    wfFrSwCctXNetReceived
    		INTEGER,
    	    wfFrSwCctXNetErrors
    		Counter
        }

    wfFrSwCctDelete OBJECT-TYPE
        SYNTAX	INTEGER {
    		    created(1),
    		    deleted(2),
    		    system(3)
    		}
        ACCESS	read-write
        STATUS	obsolete
        DESCRIPTION
                "Indication to delete this frame relay interface."
        DEFVAL	{ created }
        ::= { wfFrSwCctEntry 1 }

    wfFrSwCctNumber OBJECT-TYPE
        SYNTAX	INTEGER
        ACCESS	read-only
        STATUS	obsolete
        DESCRIPTION
                "Instance identifier; the circuit number of this interface."
        ::= { wfFrSwCctEntry 2 }

    wfFrSwCctDlci OBJECT-TYPE
        SYNTAX	INTEGER {
    		    twobyteminimum(16),
    		    twobytemaximum(1007),
    		    threebyteminimum(1024),
    		    threebytemaximum(64511),
    		    fourbyteminimum(131072),
    		    fourbytemaximum(8257535)
    		}
        ACCESS	read-only
        STATUS	obsolete
        DESCRIPTION
                "Instance identifier; this indicates the virtual
                circuit identifier"
        ::= { wfFrSwCctEntry 3 }

    wfFrSwCctState OBJECT-TYPE
        SYNTAX	INTEGER {
    		    invalid(1),
    		    active(2),
    		    inactive(3),
    		    control(4),
    		    user(5)
    		}
        ACCESS	read-only
        STATUS	obsolete
        DESCRIPTION
                "Indicates whether the particular virtual circuit is
                operational."
        DEFVAL	{ invalid }
        ::= { wfFrSwCctEntry 4 }

    wfFrSwCctMulticast OBJECT-TYPE
        SYNTAX	INTEGER {
    		    multicast(1),
    		    unicast(2)
    		}
        ACCESS	read-write
        STATUS	obsolete
        DESCRIPTION
                "Indicates whether this dlci is used for multicast
                or single destination."
        DEFVAL	{ unicast }
        ::= { wfFrSwCctEntry 5 }

    wfFrSwCctInBc OBJECT-TYPE
        SYNTAX	INTEGER
        ACCESS	read-only
        STATUS	obsolete
        DESCRIPTION
                "Indicates the Incoming Committed Burst bits
                for this virtual circuit."
        ::= { wfFrSwCctEntry 6 }

    wfFrSwCctOutBc OBJECT-TYPE
        SYNTAX	INTEGER
        ACCESS	read-only
        STATUS	obsolete
        DESCRIPTION
                "Indicates the Outgoing Committed Burst bits
                for this virtual circuit."
        ::= { wfFrSwCctEntry 7 }

    wfFrSwCctInBe OBJECT-TYPE
        SYNTAX	INTEGER
        ACCESS	read-write
        STATUS	obsolete
        DESCRIPTION
                "Indicates the Incoming Excess Burst bits
                for this virtual circuit."
        ::= { wfFrSwCctEntry 8 }

    wfFrSwCctOutBe OBJECT-TYPE
        SYNTAX	INTEGER
        ACCESS	read-write
        STATUS	obsolete
        DESCRIPTION
                "Indicates the Outgoing Excess Burst bits
                for this virtual circuit."
        ::= { wfFrSwCctEntry 9 }

    wfFrSwCctInThroughput OBJECT-TYPE
        SYNTAX	INTEGER
        ACCESS	read-write
        STATUS	obsolete
        DESCRIPTION
                "Indicates the incoming throughput in bits/sec for this virtual circuit."
        ::= { wfFrSwCctEntry 10 }

    wfFrSwCctOutThroughput OBJECT-TYPE
        SYNTAX	INTEGER
        ACCESS	read-write
        STATUS	obsolete
        DESCRIPTION
                "Indicates the outgoing throughput in bits/sec for this virtual circuit."
        ::= { wfFrSwCctEntry 11 }

    wfFrSwCctCreationTime OBJECT-TYPE
        SYNTAX	TimeTicks
        ACCESS	read-only
        STATUS	obsolete
        DESCRIPTION
                "Indicates the value of sysUpTime when the VC
                was created."
        ::= { wfFrSwCctEntry 12 }

    wfFrSwCctLastTimeChange OBJECT-TYPE
        SYNTAX	TimeTicks
        ACCESS	read-only
        STATUS	obsolete
        DESCRIPTION
                "Indicates the value of sysUpTime when last there was a
                change in VC state."
        ::= { wfFrSwCctEntry 13 }

    wfFrSwCctLocalSentNonDEFrames OBJECT-TYPE
        SYNTAX	Counter
        ACCESS	read-only
        STATUS	obsolete
        DESCRIPTION
                "Indicates the number of frames without the DE bit sent on this
                virtual circuit  over the local interface."
        ::= { wfFrSwCctEntry 14 }

    wfFrSwCctLocalSentNonDEOctets OBJECT-TYPE
        SYNTAX	Counter
        ACCESS	read-only
        STATUS	obsolete
        DESCRIPTION
                "Indicates the number of octets without DE bit sent on this
                virtual circuit over the local interface."
        ::= { wfFrSwCctEntry 15 }

    wfFrSwCctLocalSentDEFrames OBJECT-TYPE
        SYNTAX	Counter
        ACCESS	read-only
        STATUS	obsolete
        DESCRIPTION
                "Indicates the number of frames with DE bit set sent on this virtual
                circuit over the local interface."
        ::= { wfFrSwCctEntry 16 }

    wfFrSwCctLocalSentDEOctets OBJECT-TYPE
        SYNTAX	Counter
        ACCESS	read-only
        STATUS	obsolete
        DESCRIPTION
                "Indicates the number of octets with DE bit set sent on this
                virtual circuit over the local interface."
        ::= { wfFrSwCctEntry 17 }

    wfFrSwCctLocalSetFECNFrames OBJECT-TYPE
        SYNTAX	Counter
        ACCESS	read-only
        STATUS	obsolete
        DESCRIPTION
                "Indicates the number of frames sent to the local
                interface on which this switch set the FECN bit ."
        ::= { wfFrSwCctEntry 18 }

    wfFrSwCctLocalSetFECNOctets OBJECT-TYPE
        SYNTAX	Counter
        ACCESS	read-only
        STATUS	obsolete
        DESCRIPTION
                "Indicates the number of octets in frames sent to the
                local interface on which this switch set the FECN bit."
        ::= { wfFrSwCctEntry 19 }

    wfFrSwCctLocalSetBECNFrames OBJECT-TYPE
        SYNTAX	Counter
        ACCESS	read-only
        STATUS	obsolete
        DESCRIPTION
                "Indicates the number of frames sent to the local
                interface on which this switch set the BECN bit."
        ::= { wfFrSwCctEntry 20 }

    wfFrSwCctLocalSetBECNOctets OBJECT-TYPE
        SYNTAX	Counter
        ACCESS	read-only
        STATUS	obsolete
        DESCRIPTION
                "Indicates the number of octets in frames sent to the
                local interface on which this switch set the BECN bit."
        ::= { wfFrSwCctEntry 21 }

    wfFrSwCctLocalSetDEFrames OBJECT-TYPE
        SYNTAX	Counter
        ACCESS	read-only
        STATUS	obsolete
        DESCRIPTION
                "Indicates the number of frames sent to the local
                interface on which this switch set the DE bit."
        ::= { wfFrSwCctEntry 22 }

    wfFrSwCctLocalSetDEOctets OBJECT-TYPE
        SYNTAX	Counter
        ACCESS	read-only
        STATUS	obsolete
        DESCRIPTION
                "Indicates the number of octets in frames sent to the
                local interface on which this switch set the DE bit."
        ::= { wfFrSwCctEntry 23 }

    wfFrSwCctLocalDropNonDEFrames OBJECT-TYPE
        SYNTAX	Counter
        ACCESS	read-only
        STATUS	obsolete
        DESCRIPTION
                "Indicates the number of frames received over the local
                interface which were discarded, excluding any frames
                with the DE bit set."
        ::= { wfFrSwCctEntry 24 }

    wfFrSwCctLocalDropNonDEOctets OBJECT-TYPE
        SYNTAX	Counter
        ACCESS	read-only
        STATUS	obsolete
        DESCRIPTION
                "Indicates the number of octets in frames received over
                the local interface which were discarded, excluding any
                frames with the DE bit set."
        ::= { wfFrSwCctEntry 25 }

    wfFrSwCctLocalDropDEFrames OBJECT-TYPE
        SYNTAX	Counter
        ACCESS	read-only
        STATUS	obsolete
        DESCRIPTION
                "Indicates the number of frames received over the local
                interface, having the DE bit set, which were discarded."
        ::= { wfFrSwCctEntry 26 }

    wfFrSwCctLocalDropDEOctets OBJECT-TYPE
        SYNTAX	Counter
        ACCESS	read-only
        STATUS	obsolete
        DESCRIPTION
                "Indicates the number of octets in frames received over
                the local interface, having the DE bit set, which
                were discarded."
        ::= { wfFrSwCctEntry 27 }

    wfFrSwCctInactiveVCDropFrames OBJECT-TYPE
        SYNTAX	Counter
        ACCESS	read-only
        STATUS	obsolete
        DESCRIPTION
                "Indicates how many frames were discarded because the
                virtual circuit was inactive."
        ::= { wfFrSwCctEntry 28 }

    wfFrSwCctInactiveVCDropOctets OBJECT-TYPE
        SYNTAX	Counter
        ACCESS	read-only
        STATUS	obsolete
        DESCRIPTION
                "Indicates how many Octets were discarded because the
                virtual circuit was inactive."
        ::= { wfFrSwCctEntry 29 }

    wfFrSwCctLocalRecvNonDEFrames OBJECT-TYPE
        SYNTAX	Counter
        ACCESS	read-only
        STATUS	obsolete
        DESCRIPTION
                "Indicates the number of frames received on this
                virtual circuit over the local interface."
        ::= { wfFrSwCctEntry 30 }

    wfFrSwCctLocalRecvNonDEOctets OBJECT-TYPE
        SYNTAX	Counter
        ACCESS	read-only
        STATUS	obsolete
        DESCRIPTION
                "Indicates the number of octets received on
                this virtual circuit over the local interface."
        ::= { wfFrSwCctEntry 31 }

    wfFrSwCctLocalRecvDEFrames OBJECT-TYPE
        SYNTAX	Counter
        ACCESS	read-only
        STATUS	obsolete
        DESCRIPTION
                "Indicates the number of frames received over the
                local interface with the DE bit set."
        ::= { wfFrSwCctEntry 32 }

    wfFrSwCctLocalRecvDEOctets OBJECT-TYPE
        SYNTAX	Counter
        ACCESS	read-only
        STATUS	obsolete
        DESCRIPTION
                "Indicates the number of octets in frames received
                over the local interface with the DE bit set."
        ::= { wfFrSwCctEntry 33 }

    wfFrSwCctLocalRecvFECNFrames OBJECT-TYPE
        SYNTAX	Counter
        ACCESS	read-only
        STATUS	obsolete
        DESCRIPTION
                "Indicates the number of frames received over the
                local interface with the FECN bit set."
        ::= { wfFrSwCctEntry 34 }

    wfFrSwCctLocalRecvFECNOctets OBJECT-TYPE
        SYNTAX	Counter
        ACCESS	read-only
        STATUS	obsolete
        DESCRIPTION
                "Indicates the number of octets in frames received
                over the local interface with the FECN bit set."
        ::= { wfFrSwCctEntry 35 }

    wfFrSwCctLocalRecvBECNFrames OBJECT-TYPE
        SYNTAX	Counter
        ACCESS	read-only
        STATUS	obsolete
        DESCRIPTION
                "Indicates the number of frames received over the
                local interface with the BECN bit set."
        ::= { wfFrSwCctEntry 36 }

    wfFrSwCctLocalRecvBECNOctets OBJECT-TYPE
        SYNTAX	Counter
        ACCESS	read-only
        STATUS	obsolete
        DESCRIPTION
                "Indicates the number of octets in frames received
                over the local interface with the BECN bit set."
        ::= { wfFrSwCctEntry 37 }

    wfFrSwCctLocalRecentNonDEOctets OBJECT-TYPE
        SYNTAX	Counter
        ACCESS	read-only
        STATUS	obsolete
        DESCRIPTION
                "Indicates the number of octets received over the local
                interface during the most recent sampling period."
        ::= { wfFrSwCctEntry 38 }

    wfFrSwCctRemoteSentNonDEFrames OBJECT-TYPE
        SYNTAX	Counter
        ACCESS	read-only
        STATUS	obsolete
        DESCRIPTION
                "Indicates the number of Non DE set frames sent over the remote interface."
        ::= { wfFrSwCctEntry 39 }

    wfFrSwCctRemoteSentNonDEOctets OBJECT-TYPE
        SYNTAX	Counter
        ACCESS	read-only
        STATUS	obsolete
        DESCRIPTION
                "Indicates the number of Non DE set octets sent over the remote interface."
        ::= { wfFrSwCctEntry 40 }

    wfFrSwCctRemoteSentDEFrames OBJECT-TYPE
        SYNTAX	Counter
        ACCESS	read-only
        STATUS	obsolete
        DESCRIPTION
                "Indicates the number of DE set frames sent over the remote interface."
        ::= { wfFrSwCctEntry 41 }

    wfFrSwCctRemoteSentDEOctets OBJECT-TYPE
        SYNTAX	Counter
        ACCESS	read-only
        STATUS	obsolete
        DESCRIPTION
                "Indicates the number of DE set octets sent over the remote interface."
        ::= { wfFrSwCctEntry 42 }

    wfFrSwCctRemoteSetFECNFrames OBJECT-TYPE
        SYNTAX	Counter
        ACCESS	read-only
        STATUS	obsolete
        DESCRIPTION
                "Indicates the number of frames sent to the remote
                interface on which this switch set the FECN bit."
        ::= { wfFrSwCctEntry 43 }

    wfFrSwCctRemoteSetFECNOctets OBJECT-TYPE
        SYNTAX	Counter
        ACCESS	read-only
        STATUS	obsolete
        DESCRIPTION
                "Indicates the number of octets in frames sent to the remote
                interface that on which this switch set the FECN bit."
        ::= { wfFrSwCctEntry 44 }

    wfFrSwCctRemoteSetBECNFrames OBJECT-TYPE
        SYNTAX	Counter
        ACCESS	read-only
        STATUS	obsolete
        DESCRIPTION
                "Indicates the number of frames sent to the remote
                interface on which this switch set the BECN bit."
        ::= { wfFrSwCctEntry 45 }

    wfFrSwCctRemoteSetBECNOctets OBJECT-TYPE
        SYNTAX	Counter
        ACCESS	read-only
        STATUS	obsolete
        DESCRIPTION
                "Indicates the number of octets in frames sent to the
                remote interface on which this switch set the BECN bit."
        ::= { wfFrSwCctEntry 46 }

    wfFrSwCctRemoteDropNonDEFrames OBJECT-TYPE
        SYNTAX	Counter
        ACCESS	read-only
        STATUS	obsolete
        DESCRIPTION
                "Indicates the number of frames received over the
                remote interface which were discarded, excluding
                any frames with the DE bit set."
        ::= { wfFrSwCctEntry 47 }

    wfFrSwCctRemoteDropNonDEOctets OBJECT-TYPE
        SYNTAX	Counter
        ACCESS	read-only
        STATUS	obsolete
        DESCRIPTION
                "Indicates the number of octets in frames received
                over the remote interface which were discarded,
                excluding any frames with the DE bit set."
        ::= { wfFrSwCctEntry 48 }

    wfFrSwCctRemoteDropDEFrames OBJECT-TYPE
        SYNTAX	Counter
        ACCESS	read-only
        STATUS	obsolete
        DESCRIPTION
                "Indicates the number of frames received over
                the remote interface, having the DE bit set,
                which were discarded."
        ::= { wfFrSwCctEntry 49 }

    wfFrSwCctRemoteDropDEOctets OBJECT-TYPE
        SYNTAX	Counter
        ACCESS	read-only
        STATUS	obsolete
        DESCRIPTION
                "Indicates the number of octets in frames received over
                the remote interface, having the DE bit set,
                which were discarded."
        ::= { wfFrSwCctEntry 50 }

    wfFrSwCctRemoteRecvNonDEFrames OBJECT-TYPE
        SYNTAX	Counter
        ACCESS	read-only
        STATUS	obsolete
        DESCRIPTION
                "Indicates the number of frames received on this virtual
                circuit over the remote interface."
        ::= { wfFrSwCctEntry 51 }

    wfFrSwCctRemoteRecvNonDEOctets OBJECT-TYPE
        SYNTAX	Counter
        ACCESS	read-only
        STATUS	obsolete
        DESCRIPTION
                "Indicates the number of octets received on this
                virtual circuit over the remote interface."
        ::= { wfFrSwCctEntry 52 }

    wfFrSwCctRemoteRecvDEFrames OBJECT-TYPE
        SYNTAX	Counter
        ACCESS	read-only
        STATUS	obsolete
        DESCRIPTION
                "Indicates the number of frames received over the
                remote interface with the DE bit set."
        ::= { wfFrSwCctEntry 53 }

    wfFrSwCctRemoteRecvDEOctets OBJECT-TYPE
        SYNTAX	Counter
        ACCESS	read-only
        STATUS	obsolete
        DESCRIPTION
                "Indicates the number of octets in frames received over
                the remote interface with the DE bit set."
        ::= { wfFrSwCctEntry 54 }

    wfFrSwCctRemoteRecvFECNFrames OBJECT-TYPE
        SYNTAX	Counter
        ACCESS	read-only
        STATUS	obsolete
        DESCRIPTION
                "Indicates the number of frames received over the
                remote interface with the FECN bit set."
        ::= { wfFrSwCctEntry 55 }

    wfFrSwCctRemoteRecvFECNOctets OBJECT-TYPE
        SYNTAX	Counter
        ACCESS	read-only
        STATUS	obsolete
        DESCRIPTION
                "Indicates the number of octets in frames received over
                the remote interface with the FECN bit set."
        ::= { wfFrSwCctEntry 56 }

    wfFrSwCctRemoteRecvBECNFrames OBJECT-TYPE
        SYNTAX	Counter
        ACCESS	read-only
        STATUS	obsolete
        DESCRIPTION
                "Indicates the number of frames received over the
                remote interface with the BECN bit set."
        ::= { wfFrSwCctEntry 57 }

    wfFrSwCctRemoteRecvBECNOctets OBJECT-TYPE
        SYNTAX	Counter
        ACCESS	read-only
        STATUS	obsolete
        DESCRIPTION
                "Indicates the number of octets in frames received over
                the remote interface with the BECN bit set."
        ::= { wfFrSwCctEntry 58 }

    wfFrSwCctLocalBecnState OBJECT-TYPE
        SYNTAX	INTEGER
        ACCESS	read-only
        STATUS	obsolete
        DESCRIPTION
                "Indicates the local BECN state"
        ::= { wfFrSwCctEntry 59 }

    wfFrSwCctRemoteBecnState OBJECT-TYPE
        SYNTAX	INTEGER
        ACCESS	read-only
        STATUS	obsolete
        DESCRIPTION
                "Indicates the remote BECN state"
        ::= { wfFrSwCctEntry 60 }

    wfFrSwCctLocalOrRemoteConnection OBJECT-TYPE
        SYNTAX	INTEGER {
    		    local(1),
    		    remote(2)
    		}
        ACCESS	read-only
        STATUS	obsolete
        DESCRIPTION
                "Indicates whether this connection is Local to Local Connection
                or Local to Remote connection."
        DEFVAL	{ remote }
        ::= { wfFrSwCctEntry 61 }

    wfFrSwCctInBcOctets OBJECT-TYPE
        SYNTAX	INTEGER
        ACCESS	read-only
        STATUS	obsolete
        DESCRIPTION
                "Indicates the Incoming Committed Burst in octets
                for this virtual circuit."
        ::= { wfFrSwCctEntry 62 }

    wfFrSwCctStateSet OBJECT-TYPE
        SYNTAX	INTEGER {
    		    inactive(1),
    		    active(2)
    		}
        ACCESS	read-write
        STATUS	obsolete
        DESCRIPTION
                "User access for setting the state of a virtual circuit"
        DEFVAL	{ active }
        ::= { wfFrSwCctEntry 63 }

    wfFrSwCctReportedStatus OBJECT-TYPE
        SYNTAX	INTEGER {
    		    acked(1),
    		    unacked(2),
    		    unreported(3)
    		}
        ACCESS	read-only
        STATUS	obsolete
        DESCRIPTION
                "Record keeping for circuit status"
        DEFVAL	{ unreported }
        ::= { wfFrSwCctEntry 64 }

    wfFrSwCctReceivedStatus OBJECT-TYPE
        SYNTAX	INTEGER {
    		    inactive(1),
    		    active(2)
    		}
        ACCESS	read-only
        STATUS	obsolete
        DESCRIPTION
                "State of a virtual circuit as reported by the network at an NNI"
        DEFVAL	{ active }
        ::= { wfFrSwCctEntry 65 }

    wfFrSwCctCrossNetStatus OBJECT-TYPE
        SYNTAX	INTEGER {
    		    inactive(1),
    		    active(2)
    		}
        ACCESS	read-only
        STATUS	obsolete
        DESCRIPTION
                "State of a virtual circuit as reported by the other end of the network
                under bidirectional signalling."
        DEFVAL	{ active }
        ::= { wfFrSwCctEntry 66 }

    wfFrSwCctXNetSent OBJECT-TYPE
        SYNTAX	INTEGER {
    		    unsent(1),
    		    sent(2)
    		}
        ACCESS	read-only
        STATUS	obsolete
        DESCRIPTION
                "Whether we have sent a cross net status message for this VC yet."
        DEFVAL	{ unsent }
        ::= { wfFrSwCctEntry 67 }

    wfFrSwCctXNetReceived OBJECT-TYPE
        SYNTAX	INTEGER {
    		    recv(1),
    		    unrecv(2)
    		}
        ACCESS	read-only
        STATUS	obsolete
        DESCRIPTION
                "Whether we have received a cross net status message for this VC during
                the current polling interval. "
        DEFVAL	{ unrecv }
        ::= { wfFrSwCctEntry 68 }

    wfFrSwCctXNetErrors OBJECT-TYPE
        SYNTAX	Counter
        ACCESS	read-only
        STATUS	obsolete
        DESCRIPTION
                "This is the count of the consecutive errors (usually timeouts) against
                this VC in cross-network heartbeat polling  "
        ::= { wfFrSwCctEntry 69 }

    wfFrSwTupleTable OBJECT-TYPE
        SYNTAX	SEQUENCE OF WfFrSwTupleEntry
        ACCESS	not-accessible
        STATUS	obsolete
        DESCRIPTION
                "The Parameters for the Tuple table, identifying
                the endpoints of virtual circuits as pairs of IP
                addresses and DLCI."
        ::= { wfFrswGroup 3 }

    wfFrSwTupleEntry OBJECT-TYPE
        SYNTAX	WfFrSwTupleEntry
        ACCESS	not-accessible
        STATUS	obsolete
        DESCRIPTION
                "The parameters for a particular Tuple."
        INDEX	{ wfFrSwTupleIpAddrA,
    		  wfFrSwTupleDlciA,
    		  wfFrSwTupleIpAddrB,
    		  wfFrSwTupleDlciB }
        ::= { wfFrSwTupleTable 1 }

    WfFrSwTupleEntry ::= SEQUENCE {
    	    wfFrSwTupleDelete
    		INTEGER,
    	    wfFrSwTupleIpAddrA
    		IpAddress,
    	    wfFrSwTupleDlciA
    		INTEGER,
    	    wfFrSwTupleIpAddrB
    		IpAddress,
    	    wfFrSwTupleDlciB
    		INTEGER
        }

    wfFrSwTupleDelete OBJECT-TYPE
        SYNTAX	INTEGER {
    		    created(1),
    		    deleted(2)
    		}
        ACCESS	read-write
        STATUS	obsolete
        DESCRIPTION
                "Indication to delete this tuple."
        DEFVAL	{ created }
        ::= { wfFrSwTupleEntry 1 }

    wfFrSwTupleIpAddrA OBJECT-TYPE
        SYNTAX	IpAddress
        ACCESS	read-only
        STATUS	obsolete
        DESCRIPTION
                "Instance indentifier; indicates the IP address
                associated with endpoint 'A' of a virtual circuit."
        ::= { wfFrSwTupleEntry 2 }

    wfFrSwTupleDlciA OBJECT-TYPE
        SYNTAX	INTEGER
        ACCESS	read-only
        STATUS	obsolete
        DESCRIPTION
                "Instance identfier; indicates the DLCI associated
                with endpoint 'A' of a virtual circuit."
        ::= { wfFrSwTupleEntry 3 }

    wfFrSwTupleIpAddrB OBJECT-TYPE
        SYNTAX	IpAddress
        ACCESS	read-only
        STATUS	obsolete
        DESCRIPTION
                "Instance identfier; indicates the IP address
                associated with endpoint 'B' of a virtual circuit."
        ::= { wfFrSwTupleEntry 4 }

    wfFrSwTupleDlciB OBJECT-TYPE
        SYNTAX	INTEGER
        ACCESS	read-only
        STATUS	obsolete
        DESCRIPTION
                "Instance identifier; Indicates the DLCI associated
                with endpoint 'B' of a virtual circuit."
        ::= { wfFrSwTupleEntry 5 }

    wfFrSwMcastTable OBJECT-TYPE
        SYNTAX	SEQUENCE OF WfFrSwMcastEntry
        ACCESS	not-accessible
        STATUS	mandatory
        DESCRIPTION
                "The list of multicast addresses"
        ::= { wfFrswGroup 4 }

    wfFrSwMcastEntry OBJECT-TYPE
        SYNTAX	WfFrSwMcastEntry
        ACCESS	not-accessible
        STATUS	mandatory
        DESCRIPTION
                "The parameters for a particular Multicast address."
        INDEX	{ wfFrSwMcastIndex }
        ::= { wfFrSwMcastTable 1 }

    WfFrSwMcastEntry ::= SEQUENCE {
    	    wfFrSwMcastDelete
    		INTEGER,
    	    wfFrSwMcastIndex
    		INTEGER,
    	    wfFrSwMcastIpAddr
    		IpAddress,
    	    wfFrSwMcastDlci
    		INTEGER,
    	    wfFrSwMcastIndividualDlci
    		INTEGER
        }

    wfFrSwMcastDelete OBJECT-TYPE
        SYNTAX	INTEGER {
    		    created(1),
    		    deleted(2)
    		}
        ACCESS	read-write
        STATUS	mandatory
        DESCRIPTION
                "Indication to delete this multicast instance."
        DEFVAL	{ created }
        ::= { wfFrSwMcastEntry 1 }

    wfFrSwMcastIndex OBJECT-TYPE
        SYNTAX	INTEGER
        ACCESS	read-only
        STATUS	mandatory
        DESCRIPTION
                "Index of this multicast DLCI instance"
        ::= { wfFrSwMcastEntry 2 }

    wfFrSwMcastIpAddr OBJECT-TYPE
        SYNTAX	IpAddress
        ACCESS	read-write
        STATUS	mandatory
        DESCRIPTION
                "IP address of the interface in which this multicast DLCI is defined."
        ::= { wfFrSwMcastEntry 3 }

    wfFrSwMcastDlci OBJECT-TYPE
        SYNTAX	INTEGER
        ACCESS	read-write
        STATUS	mandatory
        DESCRIPTION
                "Identifies the multicast DLCI with which the IndividualDlci is associated."
        ::= { wfFrSwMcastEntry 4 }

    wfFrSwMcastIndividualDlci OBJECT-TYPE
        SYNTAX	INTEGER
        ACCESS	read-write
        STATUS	mandatory
        DESCRIPTION
                "Indicates the DLCI associated with the above multicast DLCI."
        ::= { wfFrSwMcastEntry 5 }

    wfFrSwUsage	OBJECT IDENTIFIER ::= { wfFrswGroup 5 }

    wfFrSwUsageEnable OBJECT-TYPE
        SYNTAX	INTEGER {
    		    enabled(1),
    		    disabled(2)
    		}
        ACCESS	read-write
        STATUS	mandatory
        DESCRIPTION
                "Enable/Disable FRSW billing."
        DEFVAL	{ enabled }
        ::= { wfFrSwUsage 1 }

    wfFrSwUsageVolume OBJECT-TYPE
        SYNTAX	INTEGER(0..14)
        ACCESS	read-write
        STATUS	mandatory
        DESCRIPTION
                "Indicates the file system volume number to which the
                billing usage data files will be written.  The volume
                number corresponds to the slot number on which the
                volume resides.
                Note: Value 0 has the special meaning that no
                      'Store' and 'Flush' operations will take
                      place.  This translates to no Billing data
                      will be written to the local file system.
                      'Update' operations will still be performed on
                      each local slot.  Full Billing statistics
                      will still be available in the wfFrSwUsageTable
                      MIB."
        ::= { wfFrSwUsage 2 }

    wfFrSwUsageVolumeBackup OBJECT-TYPE
        SYNTAX	INTEGER(0..14)
        ACCESS	read-write
        STATUS	mandatory
        DESCRIPTION
                "Indicates the backup volume if wfFrSwUsageVolume
                becomes inoperative.
                Note: This feature is not implemented in this release."
        ::= { wfFrSwUsage 3 }

    wfFrSwUsageDirectory OBJECT-TYPE
        SYNTAX	DisplayString
        ACCESS	read-write
        STATUS	mandatory
        DESCRIPTION
                "The name of the directory where the billing usage data
                files are stored. "
        ::= { wfFrSwUsage 4 }

    wfFrSwUsageFilePrefix OBJECT-TYPE
        SYNTAX	DisplayString
        ACCESS	read-write
        STATUS	mandatory
        DESCRIPTION
                "The base name of billing usage data files."
        ::= { wfFrSwUsage 5 }

    wfFrSwUsageTimerInterval OBJECT-TYPE
        SYNTAX	INTEGER(1..60)
        ACCESS	read-write
        STATUS	mandatory
        DESCRIPTION
                "This number determines the timer interval (number
                of seconds) unit for the Billing process to perform
                its various timer driven tasks. i.e. updating billing
                usage data, writing billing usage data to file system
                and file system management activities."
        DEFVAL	{ 20 }
        ::= { wfFrSwUsage 6 }

    wfFrSwUsageUpdateInterval OBJECT-TYPE
        SYNTAX	INTEGER(1..2147483647)
        ACCESS	read-write
        STATUS	mandatory
        DESCRIPTION
                "This number specifies the interval (number of minutes)
                for the Billing process to collect and update billing
                usage data in the wfFrSwUsage MIB.   Note: When converted to seconds, this must be a multiple
                of wfFrSwUsageTimerInterval."
        DEFVAL	{ 10 }
        ::= { wfFrSwUsage 7 }

    wfFrSwUsageStoreInterval OBJECT-TYPE
        SYNTAX	INTEGER(1..2147483647)
        ACCESS	read-write
        STATUS	mandatory
        DESCRIPTION
                "This number specifies the interval (number of minutes)
                for the Billing process to write billing usage data on
                to the file system from the wfFrSwUsage MIB.
                Note: When converted to seconds, this must be a multiple
                of wfFrSwUsageTimerInterval."
        DEFVAL	{ 10 }
        ::= { wfFrSwUsage 8 }

    wfFrSwUsageFlushInterval OBJECT-TYPE
        SYNTAX	INTEGER(1..2147483647)
        ACCESS	read-write
        STATUS	mandatory
        DESCRIPTION
                "This number specifies the interval (number of minutes)
                for the Billing process to write billing usage data on
                to the file system from the wfFrSwUsage MIB follow
                by zeroing the wfFrSwUsage MIB.
                Note: When converted to seconds, this must be a multiple of
                wfFrSwUsageTimerInterval."
        DEFVAL	{ 60 }
        ::= { wfFrSwUsage 9 }

    wfFrSwUsageCleanupInterval OBJECT-TYPE
        SYNTAX	INTEGER(1..2147483647)
        ACCESS	read-write
        STATUS	mandatory
        DESCRIPTION
                "This is the interval (number of minutes) for the Billing
                process to check and delete old billing usage data files.
                Note: When converted to seconds, this must be a multilple
                of wfFrSwUsageTimerInterval."
        DEFVAL	{ 60 }
        ::= { wfFrSwUsage 10 }

    wfFrSwUsageLocalTimeZone OBJECT-TYPE
        SYNTAX	INTEGER
        ACCESS	read-only
        STATUS	mandatory
        DESCRIPTION
                "Indicates local time zone of the switch"
        ::= { wfFrSwUsage 11 }

    wfFrSwUsageUpdateTimeStamp OBJECT-TYPE
        SYNTAX	TimeTicks
        ACCESS	read-only
        STATUS	mandatory
        DESCRIPTION
                "Time stamp of last wfFrSwUsageUpdateInterval timer
                expiration or the starting time of the current
                wfFrSwUsageUpdateInterval.  This value is number
                of seconds since midnight Jan 1, 1976 (GMT)."
        ::= { wfFrSwUsage 12 }

    wfFrSwUsageStoreTimeStamp OBJECT-TYPE
        SYNTAX	TimeTicks
        ACCESS	read-only
        STATUS	mandatory
        DESCRIPTION
                "Time stamp of last wfFrSwUsageStoreInterval
                timer expiration or the starting time of the current
                wfFrSwUsageStoreInterval.  This value is number
                of seconds since midnight Jan. 1, 1976 (GMT).   "
        ::= { wfFrSwUsage 13 }

    wfFrSwUsageFlushTimeStamp OBJECT-TYPE
        SYNTAX	TimeTicks
        ACCESS	read-only
        STATUS	mandatory
        DESCRIPTION
                "Time stamp of last wfFrSwUsageFlushInterval
                timer expiration or the starting time of the current
                wfFrSwUsageFlushInterval.  This value is
                number of seconds since midnight Jan. 1, 1976 (GMT)."
        ::= { wfFrSwUsage 14 }

    wfFrSwUsageCleanupTimeStamp OBJECT-TYPE
        SYNTAX	TimeTicks
        ACCESS	read-only
        STATUS	mandatory
        DESCRIPTION
                "Time stamp of last wfFrSwUsageCleanupInterval
                timer expiration or the starting time of the current
                wfFrSwUsageCleanupInterval.  This value is number
                of seconds since midnight Jan. 1, 1976 (GMT)."
        ::= { wfFrSwUsage 15 }

    wfFrSwUsageUpdateData OBJECT-TYPE
        SYNTAX	INTEGER
        ACCESS	read-write
        STATUS	mandatory
        DESCRIPTION
                "Setting this attribute to a non-zero value will cause
                an immediate updating of the billing usage data.
                Once activated, this attribute should be reset to zero
                to allow subsequent activations.  "
        ::= { wfFrSwUsage 16 }

    wfFrSwUsageStoreData OBJECT-TYPE
        SYNTAX	INTEGER
        ACCESS	read-write
        STATUS	mandatory
        DESCRIPTION
                "Setting this attribute to a non-zero value will cause
                an immediate updating and writing of the billing
                usage data. Once activated, this attribute should
                be reset to zero to allow subsequent activations. "
        ::= { wfFrSwUsage 17 }

    wfFrSwUsageFlushData OBJECT-TYPE
        SYNTAX	INTEGER
        ACCESS	read-write
        STATUS	mandatory
        DESCRIPTION
                "Setting this attribute to a non-zero value will cause
                an immediate updating and writing of the billing usage
                data and followed by zeroing the wfFrSwBillingUsage
                MIB. Once activated, this attribute should be reset
                to zero to allow subsequent activations. "
        ::= { wfFrSwUsage 18 }

    wfFrSwUsageFileCleanup OBJECT-TYPE
        SYNTAX	INTEGER
        ACCESS	read-write
        STATUS	mandatory
        DESCRIPTION
                "Setting this attribute to a non-zero value will cause
                an immediate checking and deleting old billing usage
                data files. Once activated, this attribute should
                be reset to zero to allow subsequent activations. "
        ::= { wfFrSwUsage 19 }

    wfFrSwUsageState OBJECT-TYPE
        SYNTAX	INTEGER {
    		    up(1),
    		    down(2),
    		    init(3),
    		    notpresent(4)
    		}
        ACCESS	read-only
        STATUS	mandatory
        DESCRIPTION
                "current state FRSW billing."
        DEFVAL	{ notpresent }
        ::= { wfFrSwUsage 20 }

    wfFrSwUsageCurVolume OBJECT-TYPE
        SYNTAX	INTEGER(0..14)
        ACCESS	read-only
        STATUS	mandatory
        DESCRIPTION
                "current file system volume number used. This
                number is the same as wfFrSwUsageVolume except
                when the user sets wfFrSwUsageVolume to an
                invalid number."
        ::= { wfFrSwUsage 21 }

    wfFrSwUsageCurVolumeBackup OBJECT-TYPE
        SYNTAX	INTEGER(0..14)
        ACCESS	read-only
        STATUS	mandatory
        DESCRIPTION
                "curent backup file system volume number used. This
                number is the same as wfFrSwUsageVolumeBackUp except
                when the user sets wfFrSwUsageVolume to an
                invalid number.
                Note: This feature is not implemented in this release."
        ::= { wfFrSwUsage 22 }

    wfFrSwUsageCurDirectory OBJECT-TYPE
        SYNTAX	DisplayString
        ACCESS	read-only
        STATUS	mandatory
        DESCRIPTION
                "current directory name used. This number is the
                same as wfFrSwUsageDirectory except when the user
                sets wfFrSwUsageDirectory to an invalid name."
        ::= { wfFrSwUsage 23 }

    wfFrSwUsageCurFilePrefix OBJECT-TYPE
        SYNTAX	DisplayString
        ACCESS	read-only
        STATUS	mandatory
        DESCRIPTION
                "current base file name used. This number is the
                same as wfFrSwUsageFilePrefix except when the user
                sets wfFrSwUsageFilePrefix to an invalid name."
        ::= { wfFrSwUsage 24 }

    wfFrSwUsageCurTimerInterval OBJECT-TYPE
        SYNTAX	INTEGER (1..60)
        ACCESS	read-only
        STATUS	mandatory
        DESCRIPTION
                "current timer interval number used. This number is
                the same as wfFrSwUsageTimerInterval except when the
                user sets wfFrSwUsageTimerInterval to an invalid value."
        DEFVAL	{ 20 }
        ::= { wfFrSwUsage 25 }

    wfFrSwUsageCurUpdateInterval OBJECT-TYPE
        SYNTAX	INTEGER(1..2147483647)
        ACCESS	read-only
        STATUS	mandatory
        DESCRIPTION
                "current update interval number used. This number is
                the same as wfFrSwUsageUpdateInterval except when the
                user sets wfFrSwUsageUpdateInterval to an invalid value."
        DEFVAL	{ 10 }
        ::= { wfFrSwUsage 26 }

    wfFrSwUsageCurStoreInterval OBJECT-TYPE
        SYNTAX	INTEGER(1..2147483647)
        ACCESS	read-only
        STATUS	mandatory
        DESCRIPTION
                "current store timer interval number used. This
                number is the same as wfFrSwUsageStoreInterval
                except when the user sets wfFrSwUsageStoreInterval
                to an invalid value."
        DEFVAL	{ 10 }
        ::= { wfFrSwUsage 27 }

    wfFrSwUsageCurFlushInterval OBJECT-TYPE
        SYNTAX	INTEGER(1..2147483647)
        ACCESS	read-only
        STATUS	mandatory
        DESCRIPTION
                "current flush timer interval number used. This
                number is the same as wfFrSwUsageFlushInterval
                except when the user sets wfFrSwUsageFlushInterval
                to an invalid value."
        DEFVAL	{ 60 }
        ::= { wfFrSwUsage 28 }

    wfFrSwUsageCurCleanupInterval OBJECT-TYPE
        SYNTAX	INTEGER(1..2147483647)
        ACCESS	read-only
        STATUS	mandatory
        DESCRIPTION
                "current file cleanup timer interval number used. This
                number is the same as wfFrSwUsageCleanupInterval
                except when the user sets wfFrSwUsageCleanupInterval
                to an invalid value."
        DEFVAL	{ 60 }
        ::= { wfFrSwUsage 29 }

    wfFrSwUsageDebug OBJECT-TYPE
        SYNTAX	INTEGER {
    		    enabled(1),
    		    disabled(2)
    		}
        ACCESS	read-write
        STATUS	mandatory
        DESCRIPTION
                "Enable/Disable printing of debug edl (trap)
                messages.
                NOTE:  Do not enable this attribute in operational enviornment
                       as it will likely flood the logging facility.  This
                       attribute is reserved for specialized debugging in a
                       controlled lab enviornment."
        DEFVAL	{ disabled }
        ::= { wfFrSwUsage 30 }

    wfFrSwUsageCurDebug OBJECT-TYPE
        SYNTAX	INTEGER {
    		    enabled(1),
    		    disabled(2)
    		}
        ACCESS	read-only
        STATUS	mandatory
        DESCRIPTION
                "current debug value used. This value is the
                same as wfFrSwUsageDebug except when the user
                sets wfFrSwUsageDeubg to an invalid value."
        DEFVAL	{ disabled }
        ::= { wfFrSwUsage 31 }

    wfFrSwUsageSwitchId OBJECT-TYPE
        SYNTAX	INTEGER
        ACCESS	read-only
        STATUS	mandatory
        DESCRIPTION
                "switch id used in the billing usage data file."
        ::= { wfFrSwUsage 32 }

    wfFrSwUsageNumEntries OBJECT-TYPE
        SYNTAX	INTEGER
        ACCESS	read-only
        STATUS	mandatory
        DESCRIPTION
                "number of entries in wfFrSwUsageTable"
        ::= { wfFrSwUsage 33 }

    wfFrSwSvcUsageEnable OBJECT-TYPE
        SYNTAX	INTEGER {
    		    enabled(1),
    		    disabled(2)
    		}
        ACCESS	read-write
        STATUS	mandatory
        DESCRIPTION
                "Enable/Disable FRSW SVC billing."
        DEFVAL	{ enabled }
        ::= { wfFrSwUsage 34 }

    wfFrSwSvcUsageInterimRecordEnable OBJECT-TYPE
        SYNTAX	INTEGER {
    		    enabled(1),
    		    disabled(2)
    		}
        ACCESS	read-write
        STATUS	mandatory
        DESCRIPTION
                "Enable/Disable Writing FRSW SVC billing record 
		 while SVC connection is still up."
        DEFVAL	{ enabled }
        ::= { wfFrSwUsage 35 }

    wfFrSwSvcUsageVolume OBJECT-TYPE
        SYNTAX	INTEGER(0..14)
        ACCESS	read-write
        STATUS	mandatory
        DESCRIPTION
                "Indicates the file system volume number to which the
                SVC billing usage data files will be written.  The volume
                number corresponds to the slot number on which the
                volume resides.
                Note: Value 0 has the special meaning that no
                      'Store' and 'Flush' operations will take
                      place.  This translates to no Billing data
                      will be written to the local file system.
                      'Update' operations will still be performed on
                      each local slot.  Full Billing statistics
                      will still be available in the wfFrSwUsageTable
                      MIB."
        ::= { wfFrSwUsage 36 }

    wfFrSwSvcUsageDirectory OBJECT-TYPE
        SYNTAX	DisplayString
        ACCESS	read-write
        STATUS	mandatory
        DESCRIPTION
                "The name of the directory where the SVC billing usage data
                files are stored. "
        ::= { wfFrSwUsage 37 }

    wfFrSwSvcUsageFilePrefix OBJECT-TYPE
        SYNTAX	DisplayString
        ACCESS	read-write
        STATUS	mandatory
        DESCRIPTION
                "The base name of SVC billing usage data files."
        ::= { wfFrSwUsage 38 }

    wfFrSwSvcUsageUpdateInterval OBJECT-TYPE
        SYNTAX	INTEGER(1..2147483647)
        ACCESS	read-write
        STATUS	mandatory
        DESCRIPTION
                "This number specifies the interval (number of minutes)
                for the SVC Billing process to collect and update billing
                usage data in the wfFrSwUsage MIB.   Note: When converted 
		to seconds, this must be a multiple of 
		wfFrSwUsageTimerInterval."
        DEFVAL	{ 10 }
        ::= { wfFrSwUsage 39 }

    wfFrSwSvcUsageStoreInterval OBJECT-TYPE
        SYNTAX	INTEGER(1..2147483647)
        ACCESS	read-write
        STATUS	mandatory
        DESCRIPTION
                "This number specifies the interval (number of minutes)
                for the SVC Billing process to write billing usage data on
                to the file system from the wfFrSwUsage MIB.
                Note: When converted to seconds, this must be a multiple
                of wfFrSwUsageTimerInterval."
        DEFVAL	{ 10 }
        ::= { wfFrSwUsage 40 }

    wfFrSwSvcUsageFlushInterval OBJECT-TYPE
        SYNTAX	INTEGER(1..2147483647)
        ACCESS	read-write
        STATUS	mandatory
        DESCRIPTION
                "This number specifies the interval (number of minutes)
                for the SVC Billing process to write billing usage data on
                to the file system from the wfFrSwUsage MIB follow
                by zeroing the wfFrSwUsage MIB.
                Note: When converted to seconds, this must be a multiple of
                wfFrSwUsageTimerInterval."
        DEFVAL	{ 60 }
        ::= { wfFrSwUsage 41 }

    wfFrSwSvcUsageCleanupInterval OBJECT-TYPE
        SYNTAX	INTEGER(1..2147483647)
        ACCESS	read-write
        STATUS	mandatory
        DESCRIPTION
                "This is the interval (number of minutes) for the SVC Billing
                process to check and delete old billing usage data files.
                Note: When converted to seconds, this must be a multilple
                of wfFrSwUsageTimerInterval."
        DEFVAL	{ 60 }
        ::= { wfFrSwUsage 42 }

    wfFrSwSvcUsageUpdateTimeStamp OBJECT-TYPE
        SYNTAX	TimeTicks
        ACCESS	read-only
        STATUS	mandatory
        DESCRIPTION
                "Time stamp of last wfFrSwSvcUsageUpdateInterval timer
                expiration or the starting time of the current
                wfFrSwSvcUsageUpdateInterval.  This value is number
                of seconds since midnight Jan 1, 1976 (GMT)."
        ::= { wfFrSwUsage 43 }

    wfFrSwSvcUsageStoreTimeStamp OBJECT-TYPE
        SYNTAX	TimeTicks
        ACCESS	read-only
        STATUS	mandatory
        DESCRIPTION
                "Time stamp of last wfFrSwSvcUsageStoreInterval
                timer expiration or the starting time of the current
                wfFrSwSvcUsageStoreInterval.  This value is number
                of seconds since midnight Jan. 1, 1976 (GMT).   "
        ::= { wfFrSwUsage 44 }

    wfFrSwSvcUsageFlushTimeStamp OBJECT-TYPE
        SYNTAX	TimeTicks
        ACCESS	read-only
        STATUS	mandatory
        DESCRIPTION
                "Time stamp of last wfFrSwSvcUsageFlushInterval
                timer expiration or the starting time of the current
                wfFrSwSvcUsageFlushInterval.  This value is
                number of seconds since midnight Jan. 1, 1976 (GMT)."
        ::= { wfFrSwUsage 45 }

    wfFrSwSvcUsageCleanupTimeStamp OBJECT-TYPE
        SYNTAX	TimeTicks
        ACCESS	read-only
        STATUS	mandatory
        DESCRIPTION
                "Time stamp of last wfFrSwSvcUsageCleanupInterval
                timer expiration or the starting time of the current
                wfFrSwSvcUsageCleanupInterval.  This value is number
                of seconds since midnight Jan. 1, 1976 (GMT)."
        ::= { wfFrSwUsage 46 }

    wfFrSwSvcUsageUpdateData OBJECT-TYPE
        SYNTAX	INTEGER
        ACCESS	read-write
        STATUS	mandatory
        DESCRIPTION
                "Setting this attribute to a non-zero value will cause
                an immediate updating of the SVC billing usage data.
                Once activated, this attribute should be reset to zero
                to allow subsequent activations.  "
        ::= { wfFrSwUsage 47 }

    wfFrSwSvcUsageStoreData OBJECT-TYPE
        SYNTAX	INTEGER
        ACCESS	read-write
        STATUS	mandatory
        DESCRIPTION
                "Setting this attribute to a non-zero value will cause
                an immediate updating and writing of the SVC billing
                usage data. Once activated, this attribute should
                be reset to zero to allow subsequent activations. "
        ::= { wfFrSwUsage 48 }

    wfFrSwSvcUsageFlushData OBJECT-TYPE
        SYNTAX	INTEGER
        ACCESS	read-write
        STATUS	mandatory
        DESCRIPTION
                "Setting this attribute to a non-zero value will cause
                an immediate updating and writing of the SVC billing usage
                data and followed by zeroing the wfFrSwBillingUsage
                MIB. Once activated, this attribute should be reset
                to zero to allow subsequent activations. "
        ::= { wfFrSwUsage 49 }

    wfFrSwSvcUsageFileCleanup OBJECT-TYPE
        SYNTAX	INTEGER
        ACCESS	read-write
        STATUS	mandatory
        DESCRIPTION
                "Setting this attribute to a non-zero value will cause
                an immediate checking and deleting old SVC billing usage
                data files. Once activated, this attribute should
                be reset to zero to allow subsequent activations. "
        ::= { wfFrSwUsage 50 }

    wfFrSwSvcUsageState OBJECT-TYPE
        SYNTAX	INTEGER {
    		    up(1),
    		    down(2),
    		    init(3),
    		    notpresent(4)
    		}
        ACCESS	read-only
        STATUS	mandatory
        DESCRIPTION
                "current state FRSW SVC billing."
        DEFVAL	{ notpresent }
        ::= { wfFrSwUsage 51 }

    wfFrSwSvcUsageCurVolume OBJECT-TYPE
        SYNTAX	INTEGER(0..14)
        ACCESS	read-only
        STATUS	mandatory
        DESCRIPTION
                "current file system volume number used for SVC Billing. 
	        This number is the same as wfFrSwSvcUsageVolume except
                when the user sets wfFrSwSvcUsageVolume to an
                invalid number."
        ::= { wfFrSwUsage 52 }

    wfFrSwSvcUsageCurDirectory OBJECT-TYPE
        SYNTAX	DisplayString
        ACCESS	read-only
        STATUS	mandatory
        DESCRIPTION
                "current directory name used for SVC Billing. This number 
		is the same as wfFrSwSvcUsageDirectory except when the user
                sets wfFrSwSvcUsageDirectory to an invalid name."
        ::= { wfFrSwUsage 53 }

    wfFrSwSvcUsageCurFilePrefix  OBJECT-TYPE
        SYNTAX	DisplayString
        ACCESS	read-only
        STATUS	mandatory
        DESCRIPTION
                "current base file name used for SVC Billing. This name
		is the same as wfFrSwSvcUsageFilePrefix except when the user
                sets wfFrSwSvcUsageFilePrefix to an invalid name."
        ::= { wfFrSwUsage 54 }

    wfFrSwSvcUsageCurUpdateInterval OBJECT-TYPE
        SYNTAX	INTEGER(1..2147483647)
        ACCESS	read-only
        STATUS	mandatory
        DESCRIPTION
                "current update interval number used. This number is
                the same as wfFrSwSvcUsageUpdateInterval except when the
                user sets wfFrSwSvcUsageUpdateInterval to an invalid value."
        DEFVAL	{ 10 }
        ::= { wfFrSwUsage 55 }

    wfFrSwSvcUsageCurStoreInterval OBJECT-TYPE
        SYNTAX	INTEGER(1..2147483647)
        ACCESS	read-only
        STATUS	mandatory
        DESCRIPTION
                "current store timer interval number used. This
                number is the same as wfFrSwSvcUsageStoreInterval
                except when the user sets wfFrSwSvcUsageStoreInterval
                to an invalid value."
        DEFVAL	{ 10 }
        ::= { wfFrSwUsage 56 }

    wfFrSwSvcUsageCurFlushInterval OBJECT-TYPE
        SYNTAX	INTEGER(1..2147483647)
        ACCESS	read-only
        STATUS	mandatory
        DESCRIPTION
                "current flush timer interval number used. This
                number is the same as wfFrSwSvcUsageFlushInterval
                except when the user sets wfFrSwSvcUsageFlushInterval
                to an invalid value."
        DEFVAL	{ 60 }
        ::= { wfFrSwUsage 57 }

    wfFrSwSvcUsageCurCleanupInterval OBJECT-TYPE
        SYNTAX	INTEGER(1..2147483647)
        ACCESS	read-only
        STATUS	mandatory
        DESCRIPTION
                "current file cleanup timer interval number used. This
                number is the same as wfFrSwSvcUsageCleanupInterval
                except when the user sets wfFrSwSvcUsageCleanupInterval
                to an invalid value."
        DEFVAL	{ 60 }
        ::= { wfFrSwUsage 58 }

    wfFrSwSvcUsageNumEntries OBJECT-TYPE
        SYNTAX	INTEGER
        ACCESS	read-only
        STATUS	mandatory
        DESCRIPTION
                "number of entries in wfFrSwSvcUsageTable"
        ::= { wfFrSwUsage 59 }

    wfFrSwSvcUsageVersionId OBJECT-TYPE
        SYNTAX	INTEGER
        ACCESS	read-only
        STATUS	mandatory
        DESCRIPTION
                "The Software Version ID field is a two byte, right justified, 
		binary formated value that identifies the particular version 
		number of the software release. High nibble of byte 1 represents
		the major version number. Low nibble of byte 1 represents the 
		release number. Byte 2 represents the integration number."
        ::= { wfFrSwUsage 60 }

    wfFrSwUsageSwitchName OBJECT-TYPE
        SYNTAX	DisplayString
        ACCESS	read-write
        STATUS	mandatory
        DESCRIPTION
                "The Switch name is a 6-bytes, right justified with leading 
		blanks as necessary. It can be combination of letters, numbers
	 	and blanks. This ID identifies the particular networks 
		equipment for SVC billing usage data process."
        ::= { wfFrSwUsage 61 }

    wfFrSwPvcUsageFileLayout OBJECT-TYPE
        SYNTAX	INTEGER
        ACCESS	read-only
        STATUS	mandatory
        DESCRIPTION
                "PVC usage file layout version"
        ::= { wfFrSwUsage 62 }

    wfFrSwSvcUsageFileLayout OBJECT-TYPE
        SYNTAX	INTEGER
        ACCESS	read-only
        STATUS	mandatory
        DESCRIPTION
                "SVC usage file layout version"
        ::= { wfFrSwUsage 63 }

    wfFrSwUsageTable OBJECT-TYPE
        SYNTAX	SEQUENCE OF WfFrSwUsageEntry
        ACCESS	not-accessible
        STATUS	obsolete
        DESCRIPTION
                "The Billing usage table."
        ::= { wfFrswGroup 6 }

    wfFrSwUsageEntry OBJECT-TYPE
        SYNTAX	WfFrSwUsageEntry
        ACCESS	not-accessible
        STATUS	obsolete
        DESCRIPTION
                "The parameters for Billing Usage."
        INDEX	{ wfFrSwUsageCircuitNumber,
    		  wfFrSwUsageDlci }
        ::= { wfFrSwUsageTable 1 }

    WfFrSwUsageEntry ::= SEQUENCE {
    	    wfFrSwUsageDelete
    		INTEGER,
    	    wfFrSwUsageCircuitNumber
    		INTEGER,
    	    wfFrSwUsageDlci
    		INTEGER,
    	    wfFrSwUsageIPAddress
    		IpAddress,
    	    wfFrSwUsageStartTimeStampHigh
    		INTEGER,
    	    wfFrSwUsageStartTimeStampLow
    		INTEGER,
    	    wfFrSwUsageEndTimeStampHigh
    		INTEGER,
    	    wfFrSwUsageEndTimeStampLow
    		INTEGER,
    	    wfFrSwUsageSentNonDEFramesHigh
    		INTEGER,
    	    wfFrSwUsageSentNonDEFramesLow
    		INTEGER,
    	    wfFrSwUsageSentNonDEOctetsHigh
    		INTEGER,
    	    wfFrSwUsageSentNonDEOctetsLow
    		INTEGER,
    	    wfFrSwUsageSentDEFramesHigh
    		INTEGER,
    	    wfFrSwUsageSentDEFramesLow
    		INTEGER,
    	    wfFrSwUsageSentDEOctetsHigh
    		INTEGER,
    	    wfFrSwUsageSentDEOctetsLow
    		INTEGER,
    	    wfFrSwUsageLastNonDEFramesHigh
    		INTEGER,
    	    wfFrSwUsageLastNonDEFramesLow
    		INTEGER,
    	    wfFrSwUsageLastNonDEOctetsHigh
    		INTEGER,
    	    wfFrSwUsageLastNonDEOctetsLow
    		INTEGER,
    	    wfFrSwUsageLastDEFramesHigh
    		INTEGER,
    	    wfFrSwUsageLastDEFramesLow
    		INTEGER,
    	    wfFrSwUsageLastDEOctetsHigh
    		INTEGER,
    	    wfFrSwUsageLastDEOctetsLow
    		INTEGER,
    	    wfFrSwUsageRemoteIPAddress
    		IpAddress,
    	    wfFrSwUsageRemoteDlci
    		INTEGER
        }

    wfFrSwUsageDelete OBJECT-TYPE
        SYNTAX	INTEGER {
    		    created(1),
    		    deleted(2)
    		}
        ACCESS	read-only
        STATUS	obsolete
        DESCRIPTION
                "Indicates status of this entry. FRSW_USAGE_CREATED
                is the normal case.  FRSW_USAGE_DELETED means the
                corresponding tuple and vc instances were deleted
                some time during this collection interval.  This
                billing instance will be deleted at the end of
                the next wfFrSwUsageFlush period after this
                billing record is written out to the file system."
        DEFVAL	{ created }
        ::= { wfFrSwUsageEntry 1 }

    wfFrSwUsageCircuitNumber OBJECT-TYPE
        SYNTAX	INTEGER
        ACCESS	read-only
        STATUS	obsolete
        DESCRIPTION
                "Instance identifier; the circuit number of this
                interface. "
        ::= { wfFrSwUsageEntry 2 }

    wfFrSwUsageDlci OBJECT-TYPE
        SYNTAX	INTEGER {
    		    twobyteminimum(16),
    		    twobytemaximum(1007),
    		    threebyteminimum(1024),
    		    threebytemaximum(64511),
    		    fourbyteminimum(131072),
    		    fourbytemaximum(8257535)
    		}
        ACCESS	read-only
        STATUS	obsolete
        DESCRIPTION
                "Instance identifier; this indicates which virtual
                circuit. "
        ::= { wfFrSwUsageEntry 3 }

    wfFrSwUsageIPAddress OBJECT-TYPE
        SYNTAX	IpAddress
        ACCESS	read-only
        STATUS	obsolete
        DESCRIPTION
                "(Local) IP address corresponding to
                wfFrSwUsageCircuitNumber of this virtual circuit. "
        ::= { wfFrSwUsageEntry 4 }

    wfFrSwUsageStartTimeStampHigh OBJECT-TYPE
        SYNTAX	INTEGER
        ACCESS	read-only
        STATUS	obsolete
        DESCRIPTION
                "Time stamp of the starting time (the high 32 bits)
                of last billing usage interval.  This value is the
                number of 1/100th seconds since midnight Jan 1, 1976 (GMT)."
        ::= { wfFrSwUsageEntry 5 }

    wfFrSwUsageStartTimeStampLow OBJECT-TYPE
        SYNTAX	INTEGER
        ACCESS	read-only
        STATUS	obsolete
        DESCRIPTION
                "Time stamp of the starting time (the low 32 bits)
                of last billing usage interval.  This value is the
                number of 1/100th seconds since midnight Jan 1, 1976 (GMT)."
        ::= { wfFrSwUsageEntry 6 }

    wfFrSwUsageEndTimeStampHigh OBJECT-TYPE
        SYNTAX	INTEGER
        ACCESS	read-only
        STATUS	obsolete
        DESCRIPTION
                "Time stamp of the ending time (the high 32 bits)
                of last billing usage interval.  This value is the
                number of 1/100th seconds since midnight Jan 1, 1976 (GMT)."
        ::= { wfFrSwUsageEntry 7 }

    wfFrSwUsageEndTimeStampLow OBJECT-TYPE
        SYNTAX	INTEGER
        ACCESS	read-only
        STATUS	obsolete
        DESCRIPTION
                "Time stamp of the ending time (the low 32 bits)
                of last billing usage interval.  This value is the
                number of 1/100th seconds since midnight Jan 1, 1976 (GMT)."
        ::= { wfFrSwUsageEntry 8 }

    wfFrSwUsageSentNonDEFramesHigh OBJECT-TYPE
        SYNTAX	INTEGER
        ACCESS	read-only
        STATUS	obsolete
        DESCRIPTION
                "Number (the high 32 bits) of local frames sent
                from this virtual circuit between
                wfFrSwUsageStartTimeStamp and
                wfFrSwUsageEndTimeStamp."
        ::= { wfFrSwUsageEntry 9 }

    wfFrSwUsageSentNonDEFramesLow OBJECT-TYPE
        SYNTAX	INTEGER
        ACCESS	read-only
        STATUS	obsolete
        DESCRIPTION
                "Number (the low 32 bits) of local frames sent
                from this virtual circuit between
                wfFrSwUsageStartTimeStamp
                and wfFrSwUsageEndTimeStamp."
        ::= { wfFrSwUsageEntry 10 }

    wfFrSwUsageSentNonDEOctetsHigh OBJECT-TYPE
        SYNTAX	INTEGER
        ACCESS	read-only
        STATUS	obsolete
        DESCRIPTION
                "Number (the high 32 bits) of local octets sent from
                this virtual circuit between
                wfFrSwUsageStartTimeStamp and
                wfFrSwUsageEndTimeStamp."
        ::= { wfFrSwUsageEntry 11 }

    wfFrSwUsageSentNonDEOctetsLow OBJECT-TYPE
        SYNTAX	INTEGER
        ACCESS	read-only
        STATUS	obsolete
        DESCRIPTION
                "Number (the low 32 bits) of local octets sent from
                this virtual circuit between
                wfFrSwUsageStartTimeStamp and
                wfFrSwUsageEndTimeStamp."
        ::= { wfFrSwUsageEntry 12 }

    wfFrSwUsageSentDEFramesHigh OBJECT-TYPE
        SYNTAX	INTEGER
        ACCESS	read-only
        STATUS	obsolete
        DESCRIPTION
                "Number (the high 32 bits) of local frames with DE
                bit sent from this virtual circuit between
                wfFrSwUsageStartTimeStamp and
                wfFrSwUsageEndTimeStamp."
        ::= { wfFrSwUsageEntry 13 }

    wfFrSwUsageSentDEFramesLow OBJECT-TYPE
        SYNTAX	INTEGER
        ACCESS	read-only
        STATUS	obsolete
        DESCRIPTION
                "Number (the low 32 bits) of local frames with DE
                bit sent from this virtual circuit between
                wfFrSwUsageStartTimeStamp
                and wfFrSwUsageEndTimeStamp."
        ::= { wfFrSwUsageEntry 14 }

    wfFrSwUsageSentDEOctetsHigh OBJECT-TYPE
        SYNTAX	INTEGER
        ACCESS	read-only
        STATUS	obsolete
        DESCRIPTION
                "Number (the high 32 bits) of local octets with
                DE bit sent from this virtual circuit between
                wfFrSwUsageStartTimeStamp and
                wfFrSwUsageEndTimeStamp."
        ::= { wfFrSwUsageEntry 15 }

    wfFrSwUsageSentDEOctetsLow OBJECT-TYPE
        SYNTAX	INTEGER
        ACCESS	read-only
        STATUS	obsolete
        DESCRIPTION
                "Number (the low 32 bits) of local octets with
                DE bit sent from this virtual circuit between
                wfFrSwUsageStartTimeStamp and
                wfFrSwUsageEndTimeStamp."
        ::= { wfFrSwUsageEntry 16 }

    wfFrSwUsageLastNonDEFramesHigh OBJECT-TYPE
        SYNTAX	INTEGER
        ACCESS	read-only
        STATUS	obsolete
        DESCRIPTION
                "The (high 32 bits) value of
                wfFrSwCctLocalSentNonDEFrames value at
                wfFrSwUsageEndTimeStamp.
                Note:  Since wfFrSwCctLocalSentNonDEFrames
                is a 32-bit COUNTER, this is really a counter
                keeping track of number of times
                wfFrSwCctLocalSentNonDEFrames has wrapped
                around."
        ::= { wfFrSwUsageEntry 17 }

    wfFrSwUsageLastNonDEFramesLow OBJECT-TYPE
        SYNTAX	INTEGER
        ACCESS	read-only
        STATUS	obsolete
        DESCRIPTION
                "The (low 32 bits) value of
                wfFrSwCctLocalSentNonDEFrames value at
                wfFrSwUsageEndTimeStamp.  "
        ::= { wfFrSwUsageEntry 18 }

    wfFrSwUsageLastNonDEOctetsHigh OBJECT-TYPE
        SYNTAX	INTEGER
        ACCESS	read-only
        STATUS	obsolete
        DESCRIPTION
                "The (high 32 bits) value of
                wfFrSwCctLocalSentNonDEOctets value at
                wfFrSwUsageEndTimeStamp.
                Note:  Since wfFrSwCctLocalSentNonDEOctets
                is a 32-bit COUNTER, this is really a counter
                keeping track of number of times
                wfFrSwCctLocalSentNonDEOctets has wrapped around."
        ::= { wfFrSwUsageEntry 19 }

    wfFrSwUsageLastNonDEOctetsLow OBJECT-TYPE
        SYNTAX	INTEGER
        ACCESS	read-only
        STATUS	obsolete
        DESCRIPTION
                "The (low 32 bits) value of
                wfFrSwCctLocalSentNonDEOctets value at
                wfFrSwUsageEndTimeStamp.  "
        ::= { wfFrSwUsageEntry 20 }

    wfFrSwUsageLastDEFramesHigh OBJECT-TYPE
        SYNTAX	INTEGER
        ACCESS	read-only
        STATUS	obsolete
        DESCRIPTION
                "The (high 32 bits) value of
                wfFrSwCctLocalSentDEFrames value at
                wfFrSwUsageEndTimeStamp.
                Note:  Since wfFrSwCctLocalSentNonDEFrames
                is a 32-bit COUNTER, this is really a counter
                keeping track of number of times
                wfFrSwCctLocalSentDEFrames has wrapped
                around."
        ::= { wfFrSwUsageEntry 21 }

    wfFrSwUsageLastDEFramesLow OBJECT-TYPE
        SYNTAX	INTEGER
        ACCESS	read-only
        STATUS	obsolete
        DESCRIPTION
                "The (low 32 bits) value of
                wfFrSwCctLocalSentDEFrames value at
                wfFrSwUsageEndTimeStamp.  "
        ::= { wfFrSwUsageEntry 22 }

    wfFrSwUsageLastDEOctetsHigh OBJECT-TYPE
        SYNTAX	INTEGER
        ACCESS	read-only
        STATUS	obsolete
        DESCRIPTION
                "The (high 32 bits) value of
                wfFrSwCctLocalSentDEOctets value
                at wfFrSwUsageEndTimeStamp.
                Note:  Since wfFrSwCctLocalSentDEOctets
                is a 32-bit COUNTER, this is really a counter
                keeping track of number of times
                wfFrSwCctLocalSentDEOctets has wrapped around."
        ::= { wfFrSwUsageEntry 23 }

    wfFrSwUsageLastDEOctetsLow OBJECT-TYPE
        SYNTAX	INTEGER
        ACCESS	read-only
        STATUS	obsolete
        DESCRIPTION
                "The (low 32 bits) value of
                wfFrSwCctLocalSentDEOctets value
                at wfFrSwUsageEndTimeStamp.  "
        ::= { wfFrSwUsageEntry 24 }

    wfFrSwUsageRemoteIPAddress OBJECT-TYPE
        SYNTAX	IpAddress
        ACCESS	read-only
        STATUS	obsolete
        DESCRIPTION
                "IP address of the other side (remote) of this PVC endpoint."
        ::= { wfFrSwUsageEntry 25 }

    wfFrSwUsageRemoteDlci OBJECT-TYPE
        SYNTAX	INTEGER {
    		    twobyteminimum(16),
    		    twobytemaximum(1007),
    		    threebyteminimum(1024),
    		    threebytemaximum(64511),
    		    fourbyteminimum(131072),
    		    fourbytemaximum(8257535)
    		}
        ACCESS	read-only
        STATUS	obsolete
        DESCRIPTION
                "DLCI number of the other side (remote) of this PVC endpoint."
        ::= { wfFrSwUsageEntry 26 }

    wfFrSwVcTable OBJECT-TYPE
        SYNTAX	SEQUENCE OF WfFrSwVcEntry
        ACCESS	not-accessible
        STATUS	mandatory
        DESCRIPTION
                "Frame Relay Virtual Circuit table gives information
                about a virtual circuit."
        ::= { wfFrswGroup 7 }

    wfFrSwVcEntry OBJECT-TYPE
        SYNTAX	WfFrSwVcEntry
        ACCESS	not-accessible
        STATUS	mandatory
        DESCRIPTION
                "An entry in the Frame Relay (Virtual) Circuit table."
        INDEX	{ wfFrSwVcCircuit,
    		  wfFrSwVcDlci }
        ::= { wfFrSwVcTable 1 }

    WfFrSwVcEntry ::= SEQUENCE {
    	    wfFrSwVcDelete
    		INTEGER,
    	    wfFrSwVcCircuit
    		INTEGER,
    	    wfFrSwVcDlci
    		INTEGER,
    	    wfFrSwVcState
    		INTEGER,
    	    wfFrSwVcStateSet
    		INTEGER,
    	    wfFrSwVcMulticast
    		INTEGER,
    	    wfFrSwVcInBe
    		INTEGER,
    	    wfFrSwVcOutBe
    		INTEGER,
    	    wfFrSwVcInThroughput
    		INTEGER,
    	    wfFrSwVcOutThroughput
    		INTEGER,
    	    wfFrSwVcOutBc
    		INTEGER,
    	    wfFrSwVcInBc
    		INTEGER,
    	    wfFrSwVcInBcOctets
    		INTEGER,
    	    wfFrSwVcBecnState
    		INTEGER,
    	    wfFrSwVcReportedStatus
    		INTEGER,
    	    wfFrSwVcReceivedStatus
    		INTEGER,
    	    wfFrSwVcCrossNetStatus
    		INTEGER,
    	    wfFrSwVcXNetSent
    		INTEGER,
    	    wfFrSwVcXNetReceived
    		INTEGER,
    	    wfFrSwVcCalledIpAddr
    		IpAddress,
    	    wfFrSwVcCalledDlci
    		INTEGER,
    	    wfFrSwVcTrfPriority
    		INTEGER,
    	    wfFrSwVcCreationTime
    		TimeTicks,
    	    wfFrSwVcLastTimeChange
    		TimeTicks,
    	    wfFrSwVcTxNonDeFrames
    		Counter,
    	    wfFrSwVcTxNonDeOctets
    		Counter,
    	    wfFrSwVcTxDeFrames
    		Counter,
    	    wfFrSwVcTxDeOctets
    		Counter,
    	    wfFrSwVcSetFecnFrames
    		Counter,
    	    wfFrSwVcSetFecnOctets
    		Counter,
    	    wfFrSwVcSetBecnFrames
    		Counter,
    	    wfFrSwVcSetBecnOctets
    		Counter,
    	    wfFrSwVcSetDeFrames
    		Counter,
    	    wfFrSwVcSetDeOctets
    		Counter,
    	    wfFrSwVcDropNonDeFrames
    		Counter,
    	    wfFrSwVcDropNonDeOctets
    		Counter,
    	    wfFrSwVcDropDeFrames
    		Counter,
    	    wfFrSwVcDropDeOctets
    		Counter,
    	    wfFrSwVcInactiveVcDropFrames
    		Counter,
    	    wfFrSwVcInactiveVcDropOctets
    		Counter,
    	    wfFrSwVcRecvNonDeFrames
    		Counter,
    	    wfFrSwVcRecvNonDeOctets
    		Counter,
    	    wfFrSwVcRecvDeFrames
    		Counter,
    	    wfFrSwVcRecvDeOctets
    		Counter,
    	    wfFrSwVcRecvFecnFrames
    		Counter,
    	    wfFrSwVcRecvFecnOctets
    		Counter,
    	    wfFrSwVcRecvBecnFrames
    		Counter,
    	    wfFrSwVcRecvBecnOctets
    		Counter,
    	    wfFrSwVcRecentNonDeOctets
    		Counter,
    	    wfFrSwVcXNetErrors
    		Counter,
    	    wfFrSwVcDropExcessBurstFrames
    		Counter,
    	    wfFrSwVcDropExcessBurstOctets
    		Counter,
    	    wfFrSwVcInBeOctets
    		INTEGER,
    	    wfFrSwVcCfgInBe
    		INTEGER,
	    wfFrSwVcRedirectAction
    		INTEGER,
	    wfFrSwVcRedirectType
    		INTEGER,
	    wfFrSwVcRedirectState
    		INTEGER,
	    wfFrSwVcBackupCalledIpAddr
    		IpAddress,
	    wfFrSwVcBackupCalledDlci
    		INTEGER,
	    wfFrSwVcBackupCrossNetStatus
    		INTEGER,
	    wfFrSwVcBackupCrossNetErrors
    		INTEGER,
	    wfFrSwVcAtmIwfMode
                INTEGER,
	    wfFrSwVcAtmIwfVPI
		INTEGER,
	    wfFrSwVcAtmIwfVCI
                INTEGER,
	    wfFrSwVcAtmIwfLossPriorityPolicy
                INTEGER,
	    wfFrSwVcAtmIwfDePolicy
                INTEGER,
	    wfFrSwVcAtmIwfEfciPolicy
                INTEGER,
	    wfFrSwVcEscapeEnable
		INTEGER,
	    wfFrSwVcSpvcCallState
		INTEGER,
	    wfFrSwVcCallReqCalledAddr
		DisplayString,
	    wfFrSwVcCallReqDlciSelectionType
		INTEGER,
	    wfFrSwVcCallReqCalledDlci
		INTEGER,
	    wfFrSwVcCallReqRetryTimer
		INTEGER,
	    wfFrSwVcCallReqMaxRetries
		INTEGER
        }


    wfFrSwVcDelete OBJECT-TYPE
        SYNTAX	INTEGER {
    		    created(1),
    		    deleted(2),
    		    system(3),
    		    svc(4),
		    spvccra(5),
		    spvccaa(6)
    		}
        ACCESS	read-write
        STATUS	mandatory
        DESCRIPTION
                "Indication to delete this virtual circuit."
        DEFVAL	{ created }
        ::= { wfFrSwVcEntry 1 }

    wfFrSwVcCircuit OBJECT-TYPE
        SYNTAX	INTEGER
        ACCESS	read-only
        STATUS	mandatory
        DESCRIPTION
                "Instance identifier; the circuit number of this interface
                (logical port)."
        ::= { wfFrSwVcEntry 2 }

    wfFrSwVcDlci OBJECT-TYPE
        SYNTAX	INTEGER
        ACCESS	read-only
        STATUS	mandatory
        DESCRIPTION
                "Instance identifier; this indicates the virtual
                circuit identifier"
        ::= { wfFrSwVcEntry 3 }

    wfFrSwVcState OBJECT-TYPE
        SYNTAX	INTEGER {
    		    invalid(1),
    		    active(2),
    		    inactive(3),
    		    control(4),
    		    user(5)
    		}
        ACCESS	read-only
        STATUS	mandatory
        DESCRIPTION
                "Indicates whether the particular virtual circuit is
                operational."
        DEFVAL	{ invalid }
        ::= { wfFrSwVcEntry 4 }

    wfFrSwVcStateSet OBJECT-TYPE
        SYNTAX	INTEGER {
    		    inactive(1),
    		    active(2)
    		}
        ACCESS	read-write
        STATUS	mandatory
        DESCRIPTION
                "User access for setting the state of a virtual circuit"
        DEFVAL	{ active }
        ::= { wfFrSwVcEntry 5 }

    wfFrSwVcMulticast OBJECT-TYPE
        SYNTAX	INTEGER {
    		    multicast(1),
    		    unicast(2)
    		}
        ACCESS	read-write
        STATUS	mandatory
        DESCRIPTION
                "Indicates whether this dlci is used for multicast
                or a single destination."
        DEFVAL	{ unicast }
        ::= { wfFrSwVcEntry 6 }

    wfFrSwVcInBe OBJECT-TYPE
        SYNTAX	INTEGER
        ACCESS	read-only
        STATUS	mandatory
        DESCRIPTION
                "Indicates the maximum number Incoming Excess Burst bits
                that are allowed in a configured time interval (T)."
        DEFVAL	{ 2147483647 }
        ::= { wfFrSwVcEntry 7 }

    wfFrSwVcOutBe OBJECT-TYPE
        SYNTAX	INTEGER
        ACCESS	read-only
        STATUS	mandatory
        DESCRIPTION
                "Indicates the Outgoing Excess Burst bits
                for this virtual circuit."
        ::= { wfFrSwVcEntry 8 }

    wfFrSwVcInThroughput OBJECT-TYPE
        SYNTAX	INTEGER
        ACCESS	read-write
        STATUS	mandatory
        DESCRIPTION
                "Indicates the incoming throughput in bits/sec
                for this virtual circuit."
        ::= { wfFrSwVcEntry 9 }

    wfFrSwVcOutThroughput OBJECT-TYPE
        SYNTAX	INTEGER
        ACCESS	read-write
        STATUS	mandatory
        DESCRIPTION
                "Indicates the outgoing throughput in bits/sec
                for this virtual circuit."
        ::= { wfFrSwVcEntry 10 }

    wfFrSwVcOutBc OBJECT-TYPE
        SYNTAX	INTEGER
        ACCESS	read-only
        STATUS	mandatory
        DESCRIPTION
                "Indicates the Outgoing Committed Burst bits
                for this virtual circuit."
        ::= { wfFrSwVcEntry 11 }

    wfFrSwVcInBc OBJECT-TYPE
        SYNTAX	INTEGER
        ACCESS	read-only
        STATUS	mandatory
        DESCRIPTION
                "Indicates the Incoming Committed Burst bits
                for this virtual circuit."
        ::= { wfFrSwVcEntry 12 }

    wfFrSwVcInBcOctets OBJECT-TYPE
        SYNTAX	INTEGER
        ACCESS	read-only
        STATUS	mandatory
        DESCRIPTION
                "Indicates the Incoming Committed Burst in octets
                for this virtual circuit."
        ::= { wfFrSwVcEntry 13 }

    wfFrSwVcBecnState OBJECT-TYPE
        SYNTAX	INTEGER
        ACCESS	read-only
        STATUS	mandatory
        DESCRIPTION
                "Indicates the BECN state"
        ::= { wfFrSwVcEntry 14 }

    wfFrSwVcReportedStatus OBJECT-TYPE
        SYNTAX	INTEGER {
    		    acked(1),
    		    unacked(2),
    		    unreported(3)
    		}
        ACCESS	read-only
        STATUS	mandatory
        DESCRIPTION
                "Record keeping for circuit status"
        DEFVAL	{ unreported }
        ::= { wfFrSwVcEntry 15 }

    wfFrSwVcReceivedStatus OBJECT-TYPE
        SYNTAX	INTEGER {
    		    inactive(1),
    		    active(2)
    		}
        ACCESS	read-only
        STATUS	mandatory
        DESCRIPTION
                "State of a virtual circuit as reported by the network at an NNI"
        DEFVAL	{ active }
        ::= { wfFrSwVcEntry 16 }

    wfFrSwVcCrossNetStatus OBJECT-TYPE
        SYNTAX	INTEGER {
    		    inactive(1),
    		    active(2)
    		}
        ACCESS	read-only
        STATUS	mandatory
        DESCRIPTION
                "State of a virtual circuit as reported by
                the other end of the network under
                bidirectional signalling."
        DEFVAL	{ active }
        ::= { wfFrSwVcEntry 17 }

    wfFrSwVcXNetSent OBJECT-TYPE
        SYNTAX	INTEGER {
    		    unsent(1),
    		    sent(2)
    		}
        ACCESS	read-only
        STATUS	mandatory
        DESCRIPTION
                "Whether we have sent a cross net status
                message for this VC yet."
        DEFVAL	{ unsent }
        ::= { wfFrSwVcEntry 18 }

    wfFrSwVcXNetReceived OBJECT-TYPE
        SYNTAX	INTEGER {
    		    recv(1),
    		    unrecv(2)
    		}
        ACCESS	read-only
        STATUS	mandatory
        DESCRIPTION
                "Whether we have received a cross net status
                message for this VC during the current
                polling interval."
        DEFVAL	{ unrecv }
        ::= { wfFrSwVcEntry 19 }

    wfFrSwVcCalledIpAddr OBJECT-TYPE
        SYNTAX	IpAddress
        ACCESS	read-write
        STATUS	mandatory
        DESCRIPTION
                "Indicates the IP address associated with
                destination of a virtual circuit."
        ::= { wfFrSwVcEntry 20 }

    wfFrSwVcCalledDlci OBJECT-TYPE
        SYNTAX	INTEGER  (16..8257535)
        ACCESS	read-write
        STATUS	mandatory
        DESCRIPTION
                "Indicates the DLCI associated with
                destination of a virtual circuit."
        ::= { wfFrSwVcEntry 21 }

    wfFrSwVcTrfPriority OBJECT-TYPE
        SYNTAX	INTEGER {
    		    one(1),
    		    two(2),
    		    three(3),
    		    default(999)
    		}
        ACCESS	read-write
        STATUS	mandatory
        DESCRIPTION
                "Defines the traffic priority level of all the
                incoming packets on this VC.
                FRSW_VCPRIORITY_DEFAULT - Set all incoming user
                traffic packets to the default priority used by the port.
                FRSW_VCPRIORITY_ONE - Set all incoming packets to priority 1.
                FRSW_VCPRIORITY_TWO - Set all incoming packets to priority 2.
                FRSW_VCPRIORITY_THREE - Set all incoming packets to priority 3.
                Priority 0 is reserved for network critical packets like
                OSPF, FR LMI and SMDS heartbeat and is not available for
                user traffic."
        DEFVAL	{ default }
        ::= { wfFrSwVcEntry 22 }

    wfFrSwVcCreationTime OBJECT-TYPE
        SYNTAX	TimeTicks
        ACCESS	read-only
        STATUS	mandatory
        DESCRIPTION
                "Indicates the value of sysUpTime when the VC
                was created."
        ::= { wfFrSwVcEntry 23 }

    wfFrSwVcLastTimeChange OBJECT-TYPE
        SYNTAX	TimeTicks
        ACCESS	read-only
        STATUS	mandatory
        DESCRIPTION
                "Indicates the value of sysUpTime when last
                there was a change in VC state."
        ::= { wfFrSwVcEntry 24 }

    wfFrSwVcTxNonDeFrames OBJECT-TYPE
        SYNTAX	Counter
        ACCESS	read-only
        STATUS	mandatory
        DESCRIPTION
                "Indicates the number of frames without the
                DE bit sent on this virtual circuit over
                the interface."
        ::= { wfFrSwVcEntry 25 }

    wfFrSwVcTxNonDeOctets OBJECT-TYPE
        SYNTAX	Counter
        ACCESS	read-only
        STATUS	mandatory
        DESCRIPTION
                "Indicates the number of octets without DE bit
                sent on this virtual circuit over the interface."
        ::= { wfFrSwVcEntry 26 }

    wfFrSwVcTxDeFrames OBJECT-TYPE
        SYNTAX	Counter
        ACCESS	read-only
        STATUS	mandatory
        DESCRIPTION
                "Indicates the number of frames with DE bit
                set sent on this virtual circuit over the interface."
        ::= { wfFrSwVcEntry 27 }

    wfFrSwVcTxDeOctets OBJECT-TYPE
        SYNTAX	Counter
        ACCESS	read-only
        STATUS	mandatory
        DESCRIPTION
                "Indicates the number of octets with DE bit set
                sent on this virtual circuit over the interface."
        ::= { wfFrSwVcEntry 28 }

    wfFrSwVcSetFecnFrames OBJECT-TYPE
        SYNTAX	Counter
        ACCESS	read-only
        STATUS	mandatory
        DESCRIPTION
                "Indicates the number of frames sent to the
                interface on which this switch set the FECN bit."
        ::= { wfFrSwVcEntry 29 }

    wfFrSwVcSetFecnOctets OBJECT-TYPE
        SYNTAX	Counter
        ACCESS	read-only
        STATUS	mandatory
        DESCRIPTION
                "Indicates the number of octets in frames sent
                to the interface on which this switch set the
                FECN bit."
        ::= { wfFrSwVcEntry 30 }

    wfFrSwVcSetBecnFrames OBJECT-TYPE
        SYNTAX	Counter
        ACCESS	read-only
        STATUS	mandatory
        DESCRIPTION
                "Indicates the number of frames sent to the
                interface on which this switch set the BECN bit."
        ::= { wfFrSwVcEntry 31 }

    wfFrSwVcSetBecnOctets OBJECT-TYPE
        SYNTAX	Counter
        ACCESS	read-only
        STATUS	mandatory
        DESCRIPTION
                "Indicates the number of octets in frames sent to the
                interface on which this switch set the BECN bit."
        ::= { wfFrSwVcEntry 32 }

    wfFrSwVcSetDeFrames OBJECT-TYPE
        SYNTAX	Counter
        ACCESS	read-only
        STATUS	mandatory
        DESCRIPTION
                "Indicates the number of frames sent to the
                interface on which this switch set the DE bit."
        ::= { wfFrSwVcEntry 33 }

    wfFrSwVcSetDeOctets OBJECT-TYPE
        SYNTAX	Counter
        ACCESS	read-only
        STATUS	mandatory
        DESCRIPTION
                "Indicates the number of octets in frames sent to the
                interface on which this switch set the DE bit."
        ::= { wfFrSwVcEntry 34 }

    wfFrSwVcDropNonDeFrames OBJECT-TYPE
        SYNTAX	Counter
        ACCESS	read-only
        STATUS	mandatory
        DESCRIPTION
                "Indicates the number of frames received over the
                interface which were discarded, excluding any frames
                with the DE bit set."
        ::= { wfFrSwVcEntry 35 }

    wfFrSwVcDropNonDeOctets OBJECT-TYPE
        SYNTAX	Counter
        ACCESS	read-only
        STATUS	mandatory
        DESCRIPTION
                "Indicates the number of octets in frames received over
                the interface which were discarded, excluding any
                frames with the DE bit set."
        ::= { wfFrSwVcEntry 36 }

    wfFrSwVcDropDeFrames OBJECT-TYPE
        SYNTAX	Counter
        ACCESS	read-only
        STATUS	mandatory
        DESCRIPTION
                "Indicates the number of frames received over the
                interface, having the DE bit set, which were discarded."
        ::= { wfFrSwVcEntry 37 }

    wfFrSwVcDropDeOctets OBJECT-TYPE
        SYNTAX	Counter
        ACCESS	read-only
        STATUS	mandatory
        DESCRIPTION
                "Indicates the number of octets in frames received over
                the interface, having the DE bit set, which
                were discarded."
        ::= { wfFrSwVcEntry 38 }

    wfFrSwVcInactiveVcDropFrames OBJECT-TYPE
        SYNTAX	Counter
        ACCESS	read-only
        STATUS	mandatory
        DESCRIPTION
                "Indicates how many frames were discarded because the
                virtual circuit was inactive."
        ::= { wfFrSwVcEntry 39 }

    wfFrSwVcInactiveVcDropOctets OBJECT-TYPE
        SYNTAX	Counter
        ACCESS	read-only
        STATUS	mandatory
        DESCRIPTION
                "Indicates how many Octets were discarded because the
                virtual circuit was inactive."
        ::= { wfFrSwVcEntry 40 }

    wfFrSwVcRecvNonDeFrames OBJECT-TYPE
        SYNTAX	Counter
        ACCESS	read-only
        STATUS	mandatory
        DESCRIPTION
                "Indicates the number of frames received on this
                virtual circuit over the interface."
        ::= { wfFrSwVcEntry 41 }

    wfFrSwVcRecvNonDeOctets OBJECT-TYPE
        SYNTAX	Counter
        ACCESS	read-only
        STATUS	mandatory
        DESCRIPTION
                "Indicates the number of octets received on
                this virtual circuit over the interface."
        ::= { wfFrSwVcEntry 42 }

    wfFrSwVcRecvDeFrames OBJECT-TYPE
        SYNTAX	Counter
        ACCESS	read-only
        STATUS	mandatory
        DESCRIPTION
                "Indicates the number of frames received over the
                interface with the DE bit set."
        ::= { wfFrSwVcEntry 43 }

    wfFrSwVcRecvDeOctets OBJECT-TYPE
        SYNTAX	Counter
        ACCESS	read-only
        STATUS	mandatory
        DESCRIPTION
                "Indicates the number of octets in frames received
                over the interface with the DE bit set."
        ::= { wfFrSwVcEntry 44 }

    wfFrSwVcRecvFecnFrames OBJECT-TYPE
        SYNTAX	Counter
        ACCESS	read-only
        STATUS	mandatory
        DESCRIPTION
                "Indicates the number of frames received over the
                interface with the FECN bit set."
        ::= { wfFrSwVcEntry 45 }

    wfFrSwVcRecvFecnOctets OBJECT-TYPE
        SYNTAX	Counter
        ACCESS	read-only
        STATUS	mandatory
        DESCRIPTION
                "Indicates the number of octets in frames received
                over the interface with the FECN bit set."
        ::= { wfFrSwVcEntry 46 }

    wfFrSwVcRecvBecnFrames OBJECT-TYPE
        SYNTAX	Counter
        ACCESS	read-only
        STATUS	mandatory
        DESCRIPTION
                "Indicates the number of frames received over the
                interface with the BECN bit set."
        ::= { wfFrSwVcEntry 47 }

    wfFrSwVcRecvBecnOctets OBJECT-TYPE
        SYNTAX	Counter
        ACCESS	read-only
        STATUS	mandatory
        DESCRIPTION
                "Indicates the number of octets in frames received
                over the interface with the BECN bit set."
        ::= { wfFrSwVcEntry 48 }

    wfFrSwVcRecentNonDeOctets OBJECT-TYPE
        SYNTAX	Counter
        ACCESS	read-only
        STATUS	mandatory
        DESCRIPTION
                "Indicates the number of octets received over the
                interface during the most recent sampling period."
        ::= { wfFrSwVcEntry 49 }

    wfFrSwVcXNetErrors OBJECT-TYPE
        SYNTAX	Counter
        ACCESS	read-only
        STATUS	mandatory
        DESCRIPTION
                "This is the count of the consecutive errors
                (usually timeouts) against this VC in cross-network
                heartbeat polling."
        ::= { wfFrSwVcEntry 50 }

    wfFrSwVcDropExcessBurstFrames OBJECT-TYPE
        SYNTAX	Counter
        ACCESS	read-only
        STATUS	mandatory
        DESCRIPTION
                "Indicates the number of Excess Burst Frames dropped
                on this virtual circuit."
        ::= { wfFrSwVcEntry 51 }

    wfFrSwVcDropExcessBurstOctets OBJECT-TYPE
        SYNTAX	Counter
        ACCESS	read-only
        STATUS	mandatory
        DESCRIPTION
                "Indicates the number of Excess Burst Octets dropped
                on this virtual circuit."
        ::= { wfFrSwVcEntry 52 }

    wfFrSwVcInBeOctets OBJECT-TYPE
        SYNTAX	INTEGER
        ACCESS	read-only
        STATUS	mandatory
        DESCRIPTION
                "Indicates the maximum number Incoming Excess Burst bytes
                that are allowed in a configured time interval (T)."
        ::= { wfFrSwVcEntry 53 }

    wfFrSwVcCfgInBe OBJECT-TYPE
        SYNTAX	INTEGER
        ACCESS	read-write
        STATUS	mandatory
        DESCRIPTION
                "The number of Excess Burst in bits"
        DEFVAL	{ 2147483647 }
        ::= { wfFrSwVcEntry 54 }

    wfFrSwVcRedirectAction OBJECT-TYPE
        SYNTAX	INTEGER {
		redirecttoprimary(2),
		redirecttobackup(3),
                switchondemand(4),
                swondemandtoprimary(5),
                swondemandtobackup(6)
		}
        ACCESS	read-write
        STATUS	mandatory
	DESCRIPTION
		"Perform pvc source redirect manually or based on
		cross-net updates:
		'redirecttoprimary(2)' will force to switch to primary;
		'redirecttobackup(3)'  will force to switch to backup;
                'switchondemand(4)'    will switch based on cross-net
                status of the primary to and from primary;
                'swondemandtoprimary(5)' will switch to primary from
                backup iff cross-net of primary became active;
                'swondemandtobackup(6)'  will switch to backup from
                primary iff cross-net of primary became inactive."
        DEFVAL	{ redirecttoprimary }
	::= { wfFrSwVcEntry 55 }

    wfFrSwVcRedirectType OBJECT-TYPE
        SYNTAX INTEGER {
		transparent(1),
		intrusiven(2),
		intrusivea(3)
		}
        ACCESS	read-write
        STATUS	mandatory
	DESCRIPTION
		"Type of dte notification at switching time:
		'transparent(1)' will not send notification to dte;
		'intrusiven(2)' will send async update with NEW bit;
		'intrusivea(3)' will send async update with A bit not set."
	DEFVAL	{ intrusivea }
	::= { wfFrSwVcEntry 56 }

    wfFrSwVcRedirectState OBJECT-TYPE
        SYNTAX INTEGER {
		backupinactive(1),
		primaryactive(2),
		switchtobackup(3),
		backupactive(12),
		switchtoprimary(13),
		holddown(21)
		}
        ACCESS	read-only
        STATUS	mandatory
	DESCRIPTION
		"PVC Source Redirect State:
		'backupinactive(1)' - backup is not configured and/or cross-net status
				is inactive; will allow traffic only through primary.
		'primaryactive(2)' - both primary and backup rx'ed 'active' cross-net
				status, currently primary is active and traffic only 
				through primary.
		'switchtobackup(3)' - primary cross-net status is inactive, but can
				not switch to backup due to manual (or semi-manual)
				operation of the redirect; will allow traffic only 
				through primary.
		'backupactive(12)' - cross-net status is 'inactive' for primary;  
				will allow traffic only through backup.
		'switchtoprimary(13)'  - cross-net status is 'active' for primary, 
				should by can not switch to primary due to  manual 
				(or semi-manual) operation of the redirect; will 
				allow traffic only through backup.
		'holddown(21)' - down state used as intermediate state at switching time
 				(for not more then a second); all traffic is dropped."

	DEFVAL	{ backupinactive }
	::= { wfFrSwVcEntry 57 }

    wfFrSwVcBackupCalledIpAddr OBJECT-TYPE
        SYNTAX  IpAddress
        ACCESS	read-write
        STATUS	mandatory
	DESCRIPTION
		" Backup Called Ip Address of the remote end of the PVC."
	::= { wfFrSwVcEntry 58 }

    wfFrSwVcBackupCalledDlci  OBJECT-TYPE
        SYNTAX INTEGER  (16..8257535)
        ACCESS	read-write
        STATUS	mandatory
	DESCRIPTION
		" Backup Called Dlci of the remote end of the PVC."
	::= { wfFrSwVcEntry 59 }

    wfFrSwVcBackupCrossNetStatus OBJECT-TYPE
        SYNTAX INTEGER {
    		    inactive(1),
    		    active(2)
    		}
        ACCESS	read-only
        STATUS	mandatory
	DESCRIPTION
		" Cross net status of the backup remote end of the PVC."
	DEFVAL	{ inactive }
	::= { wfFrSwVcEntry 60 }

    wfFrSwVcBackupCrossNetErrors OBJECT-TYPE
        SYNTAX INTEGER
        ACCESS	read-only
        STATUS	mandatory
	DESCRIPTION
		" Support counter of missed cross net update from backup 
		remote end of the PVC, range: [0, wfFrSwDlcmiCrossNetErrorThreshold]."
	::= { wfFrSwVcEntry 61 }



    wfFrSwVcAtmIwfMode OBJECT-TYPE
        SYNTAX	INTEGER {
		    atmDisableIwfMode(1),
		    atmServiceIwfTransparentMode(2),
		    atmServiceIwfTranslationMode(3),
                    atmNetworkIwfMode(4)
    		}   
        ACCESS	read-write
        STATUS	mandatory
        DESCRIPTION
                "This attribute indicates the mode of FR-ATM interworking over
                 this FR PVC or that FR-ATM interworking is not enabled on it."
        DEFVAL	{ atmDisableIwfMode }
        ::= { wfFrSwVcEntry 62 }

    wfFrSwVcAtmIwfVPI OBJECT-TYPE
        SYNTAX	INTEGER (0..255)
        ACCESS	read-write
        STATUS	mandatory
        DESCRIPTION
                "This is relevant only when the ATM/FR interworking is enabled
                 for this PVC. This indicates the ATM virtual path identifier 
                 associated with the Frame Relay PVC described by this record
                 virtual circuit identifier."
        DEFVAL	{ 0 }
        ::= { wfFrSwVcEntry 63 }

    wfFrSwVcAtmIwfVCI OBJECT-TYPE
        SYNTAX	INTEGER (32..65535) 
        ACCESS	read-write
        STATUS	mandatory
        DESCRIPTION
                "This is relevant only when FR/ATM interworking is enabled
                 for this PVC. This indicates the ATM virtual circuit 
                 identifier associated with the Frame Relay PVC described by 
                 this record."
        DEFVAL	{ 32 }
        ::= { wfFrSwVcEntry 64 }

    wfFrSwVcAtmIwfLossPriorityPolicy OBJECT-TYPE
        SYNTAX	INTEGER {
		    atmiwfmapDe(1),
		    atmiwfsetDe1(2),
		    atmiwfsetDe0(3)
    		}   
        ACCESS	read-write
        STATUS	mandatory
        DESCRIPTION
                "This is relevant only when FR/ATM interworking is enabled 
                 for this FR PVC. This indicates the policy for translating 
                 ATM CLP to FR DE on this PVC or simply setting FR DE to a 
                 constant value for all frames."
        DEFVAL	{ atmiwfmapDe }
        ::= { wfFrSwVcEntry 65 }

    wfFrSwVcAtmIwfDePolicy OBJECT-TYPE
        SYNTAX	INTEGER {
		    atmiwfmapClp(1),
		    atmiwfsetClp1(2),
		    atmiwfsetClp0(3)
    		}   
        ACCESS	read-write
        STATUS	mandatory
        DESCRIPTION
                "This is relevant only when FR/ATM interworking is enabled 
                 for this FR PVC. This indicates the policy on this PVC for 
                 translating FR DE to ATM CLP or simply setting CLP to a 
                 constant value for all frames."
        DEFVAL	{ atmiwfmapClp }
        ::= { wfFrSwVcEntry 66 }

    wfFrSwVcAtmIwfEfciPolicy OBJECT-TYPE
        SYNTAX	INTEGER {
		    atmiwfmapFecn(1),
		    atmiwfsetFecn1(2),
		    atmiwfsetFecn0(3)
    		}   
        ACCESS	read-write
        STATUS	mandatory
        DESCRIPTION
                "This is relevant only when FR/ATM interworking is enabled 
                 for this FR PVC. This indicates the policy on this PVC for 
                 translating FR FECN to ATM EFCI or simply setting ATM EFCI 
                 to a constant value for all frames."
        DEFVAL	{ atmiwfmapFecn }
        ::= { wfFrSwVcEntry 67 }

    wfFrSwVcEscapeEnable OBJECT-TYPE
	SYNTAX  INTEGER {
		    enabled(1),
		    disabled(2)
		    }
	ACCESS	read-write
	STATUS	mandatory
	DESCRIPTION
		" Identifies this PVC as either a standard FRSW PVC (escape 
		  disabled) or an Escape PVC (escape enabled).  The type of
		  Escape PVC (ingress node or egress node) is specified in the
		  wfFrSwDlcmiEntry Object."
	DEFVAL {disabled }
	::= { wfFrSwVcEntry 68 }

    wfFrSwVcSpvcCallState OBJECT-TYPE
	SYNTAX	INTEGER {
			inactive(1),
			inprogress(2),
			active(3)
		}
	ACCESS	read-only
	STATUS	mandatory
	DESCRIPTION
		"Indicates to the state of the SPVC call for this DLCI."
	DEFVAL 	{inactive }
	::= { wfFrSwVcEntry 69 }

    wfFrSwVcCallReqCalledAddr OBJECT-TYPE
	SYNTAX	DisplayString
	ACCESS	read-write
	STATUS	mandatory  
	DESCRIPTION
		"Called E.164/X.121 Address for an SPVC Call Request
		 Agent.  The address type is determined by the
		 wfFrSwDlcmiL2AddrType attribute in wfFrSwDlcmiEntry."
	::= { wfFrSwVcEntry 70 }

    wfFrSwVcCallReqDlciSelectionType OBJECT-TYPE
	SYNTAX	INTEGER {
		any(1),
		specific(2)
		}
	ACCESS	read-write
	STATUS	mandatory
	DESCRIPTION
		"Indicates to the Calling End of an SPVC Call Request whether
                 to use any available DLCI, or a specific DLCI. If 'specific'
                 is chosen, the called DLCI value is specified in
                 wfFrSwVcCallReqCalledDlci."
	DEFVAL 	{ any }
	::= { wfFrSwVcEntry 71 }

    wfFrSwVcCallReqCalledDlci OBJECT-TYPE
        SYNTAX	INTEGER  (16..8257535)
        ACCESS	read-write
        STATUS	mandatory
        DESCRIPTION
                "Indicates to the Calling End of an SPVC Call Request the
                DLCI to be used at the destination of a virtual circuit.
                This value should be specified when 'specific'
                wfFrSwVcCallReqDlciSelectionType is chosen."
        ::= { wfFrSwVcEntry 72 }

    wfFrSwVcCallReqRetryTimer OBJECT-TYPE
	SYNTAX	INTEGER (1..60)
	ACCESS	read-write
	STATUS	mandatory
	DESCRIPTION
		"Indicates the number of minutes the Call Request Agent should
                 wait for an SPVC CONNECT message before declaring a Call Setup
                 request REJECTED."
	DEFVAL	{ 3 }
	::= { wfFrSwVcEntry 73 }

    wfFrSwVcCallReqMaxRetries OBJECT-TYPE
	SYNTAX	INTEGER
	ACCESS	read-write
	STATUS	mandatory
	DESCRIPTION
		"Indicates the number of times the Call Request Agent should
                 retry failed Call Setup requests before declaring the SPVC
                 invalid."
	DEFVAL	{ 2147483647 }
	::= { wfFrSwVcEntry 74 }


    wfFrSwIsdnBaseTable OBJECT-TYPE
	SYNTAX	SEQUENCE OF WfFrSwIsdnBaseEntry
	ACCESS	not-accessible
	STATUS	mandatory
	DESCRIPTION
		"This is a FRSW over ISDN configuration table.  This
		 table specifies whether the Calling Party (ANI) or Called
		 Party (DNIS) ISDN Phone Number should be used to map
		 the ISDN call to a particular FRSW UNI.  The table is
		 indexed by the Slot Number where the PRI(s) exist."
	::= { wfFrswGroup 8 }

    wfFrSwIsdnBaseEntry OBJECT-TYPE
	SYNTAX	WfFrSwIsdnBaseEntry
	ACCESS	not-accessible
	STATUS	mandatory
	DESCRIPTION
		"Instance Id for this table."
	INDEX	{ wfFrSwIsdnBaseSlotNum }
	::= { wfFrSwIsdnBaseTable 1 }

    WfFrSwIsdnBaseEntry ::= SEQUENCE {
	wfFrSwIsdnBaseDelete
		INTEGER,
	wfFrSwIsdnBaseSlotNum
		INTEGER,
	wfFrSwIsdnBaseAssocType
		INTEGER
      }

    wfFrSwIsdnBaseDelete OBJECT-TYPE
	SYNTAX	INTEGER {
		created(1),
		deleted(2)
	}
	ACCESS	read-write
	STATUS	mandatory
	DESCRIPTION
		"Indication to delete this FRSW ISDN interface. "
	DEFVAL	{ created }
	::= { wfFrSwIsdnBaseEntry 1 }

    wfFrSwIsdnBaseSlotNum OBJECT-TYPE
	SYNTAX	INTEGER
	ACCESS	read-only
	STATUS	mandatory
	DESCRIPTION
		"This number is the Slot Number for the PRI interface(s)
		 that are being configured for FRSW ISDN.  There will be
		 one of these tables for every slot where an FRSW ISDN 
		 PRI Interface exists."
	::= { wfFrSwIsdnBaseEntry 2 }

    wfFrSwIsdnBaseAssocType OBJECT-TYPE
	SYNTAX	INTEGER {
		dnis(1),
		ani(2)
	}
	ACCESS	read-write
	STATUS	mandatory
	DESCRIPTION
		"Indicates which ISDN Phone Number (ANI or DNIS) 
		 to use to do the ISDN call to FRSW UNI mapping."
	DEFVAL	{ dnis }
	::= { wfFrSwIsdnBaseEntry 3 }

    wfFrSwIsdnAssocTable OBJECT-TYPE
	SYNTAX	SEQUENCE OF WfFrSwIsdnAssocEntry
	ACCESS	not-accessible
	STATUS	mandatory
	DESCRIPTION
		"This table defines the Association Table
		 to be used for the FRSW over ISDN application.
		 The table contains a list of ISDN Phone
		 Numbers and the associated FRSW UNI Index Number.  
		 The table is indexed by the Slot Number and the 
		 ISDN Phone Number."
	::= { wfFrswGroup 9 }

    wfFrSwIsdnAssocEntry OBJECT-TYPE
	SYNTAX	WfFrSwIsdnAssocEntry
	ACCESS	not-accessible
	STATUS	mandatory
	DESCRIPTION
		"Instance Id for this table."
	INDEX	{ wfFrSwIsdnAssocSlotNum,
		wfFrSwIsdnAssocNum }
	::= { wfFrSwIsdnAssocTable 1 }

    WfFrSwIsdnAssocEntry ::= SEQUENCE {
	wfFrSwIsdnAssocDelete
		INTEGER,
	wfFrSwIsdnAssocSlotNum
		INTEGER,
	wfFrSwIsdnAssocNum
		OCTET STRING,
	wfFrSwIsdnAssocScrnEnable
		INTEGER,
	wfFrSwIsdnAssocIndex
		INTEGER
      }

    wfFrSwIsdnAssocDelete OBJECT-TYPE
	SYNTAX	INTEGER {
		created(1),
		deleted(2)
	}
	ACCESS	read-write
	STATUS	mandatory
	DESCRIPTION
		"Indication to delete this Association Instance."
	DEFVAL	{ created }
	::= { wfFrSwIsdnAssocEntry 1 }

    wfFrSwIsdnAssocSlotNum OBJECT-TYPE
	SYNTAX	INTEGER
	ACCESS	read-only
	STATUS	mandatory
	DESCRIPTION
		"Slot with which this ISDN Phone Number is associated."
	::= { wfFrSwIsdnAssocEntry 2 }

    wfFrSwIsdnAssocNum OBJECT-TYPE
	SYNTAX	OCTET STRING
	ACCESS	read-only
	STATUS	mandatory
	DESCRIPTION
		"ISDN Phone Number that is used to look up the
		 appropriate FRSW UNI Index.  This number is
		 compared with either the Calling Party Number (ANI)
		 Information Element or the Called Party Number (DNIS)
		 Information Element contained in the ISDN Call 
		 Setup Message."
	::= { wfFrSwIsdnAssocEntry 3 }

    wfFrSwIsdnAssocScrnEnable OBJECT-TYPE
	SYNTAX	INTEGER {
		enabled(1),
		disabled(2)
	}
	ACCESS	read-write
	STATUS	mandatory
	DESCRIPTION
		"Indicate whether allowed screening should be
		 enabled or disabled for all of the UNIs 
		 contained in the FRSW UNI Index."
	DEFVAL	{ disabled }
	::= { wfFrSwIsdnAssocEntry 4 }

    wfFrSwIsdnAssocIndex OBJECT-TYPE
	SYNTAX	INTEGER
	ACCESS	read-write
	STATUS	mandatory
	DESCRIPTION
		"A number that indicates the FRSW UNI Index that is
		 is associated with the ISDN Phone Number.  This
		 FRSW UNI Index is used as a key to obtain the UNIs and
		 the Screening information from the wfFrSwIsdnScrnEntry and
		 wfFrSwIsdnUniEntry mibs.  The default for the index is 
		 2**31 - 1 = 2147483647 = 0x7FFFFFFF, which represents
		 an unconfigured index number."
        DEFVAL { 2147483647 }
	::= { wfFrSwIsdnAssocEntry 5 }

    wfFrSwIsdnUniTable OBJECT-TYPE
	SYNTAX	SEQUENCE OF WfFrSwIsdnUniEntry
	ACCESS	not-accessible
	STATUS	mandatory
	DESCRIPTION
		"This table is used by the FRSW over ISDN
		 application.  The table defines a list
		 of FRSW UNIs that are to be collected into
		 a hunt group identifiable by an Index Number."
	::= { wfFrswGroup 10 }

    wfFrSwIsdnUniEntry OBJECT-TYPE
	SYNTAX	WfFrSwIsdnUniEntry
	ACCESS	not-accessible
	STATUS	mandatory
	DESCRIPTION
		"Instance Id for this table."
	INDEX	{ wfFrSwIsdnUniIndex,
		wfFrSwIsdnUniNum }
	::= { wfFrSwIsdnUniTable 1 }

    WfFrSwIsdnUniEntry ::= SEQUENCE {
	wfFrSwIsdnUniDelete
		INTEGER,
	wfFrSwIsdnUniIndex
		INTEGER,
	wfFrSwIsdnUniNum
		INTEGER,
        wfFrSwIsdnUniState
                INTEGER		
      }

    wfFrSwIsdnUniDelete OBJECT-TYPE
	SYNTAX	INTEGER {
		created(1),
		deleted(2)
	}
	ACCESS	read-write
	STATUS	mandatory
	DESCRIPTION
		"Indication to delete this FRSW UNI Index 
		 Instance."
	DEFVAL	{ created }
	::= { wfFrSwIsdnUniEntry 1 }

    wfFrSwIsdnUniIndex OBJECT-TYPE
	SYNTAX	INTEGER
	ACCESS	read-only
	STATUS	mandatory
	DESCRIPTION
		"FRSW UNI Index -- a number that identifies 
		 a group of related FRSW UNIs that are 
		 collected together as a hunt group.  This number
		 ties this entry to an entry in
		 wfFrSwIsdnAssocEntry."
	::= { wfFrSwIsdnUniEntry 2 }

    wfFrSwIsdnUniNum OBJECT-TYPE
	SYNTAX	INTEGER
	ACCESS	read-only
	STATUS	mandatory
	DESCRIPTION
		"A FRSW UNI/Circuit."
	::= { wfFrSwIsdnUniEntry 3 }

    wfFrSwIsdnUniState OBJECT-TYPE
	SYNTAX	INTEGER {
	        available(1),
	        inuse(2)
	}
	ACCESS	read-only
	STATUS	mandatory
	DESCRIPTION
		"State of this UNI (available or in-use)."
        DEFVAL	{ available }
	::= { wfFrSwIsdnUniEntry 4 }

    wfFrSwIsdnScrnTable OBJECT-TYPE
	SYNTAX	SEQUENCE OF WfFrSwIsdnScrnEntry
	ACCESS	not-accessible
	STATUS	mandatory
	DESCRIPTION
		"This is the incoming call screening table
		 for the FRSW over ISDN application.  The table
		 consists of a FRSW UNI Index and a list of allowable
		 ISDN Phone numbers for that FRSW UNI Index.
		 The table is indexed by both the FRSW UNI Index
		 and the ISDN Phone Number.
                 This table is referenced only when the
		 wfFrSwIsdnAssocScrnEnable is set to
		 Enabled for this FRSW UNI Index."
	::= { wfFrswGroup 11 }

    wfFrSwIsdnScrnEntry OBJECT-TYPE
	SYNTAX	WfFrSwIsdnScrnEntry
	ACCESS	not-accessible
	STATUS	mandatory
	DESCRIPTION
		" Instance Id for this table. "
	INDEX	{ wfFrSwIsdnScrnIndex,
		wfFrSwIsdnScrnNum }
	::= { wfFrSwIsdnScrnTable 1 }

    WfFrSwIsdnScrnEntry ::= SEQUENCE {
	wfFrSwIsdnScrnDelete
		INTEGER,
	wfFrSwIsdnScrnIndex
		INTEGER,
	wfFrSwIsdnScrnNum
		OCTET STRING
    }

    wfFrSwIsdnScrnDelete OBJECT-TYPE
	SYNTAX	INTEGER {
		created(1),
		deleted(2)
	}
	ACCESS	read-write
	STATUS	mandatory
	DESCRIPTION
		" Indication to delete this Scrn Instance. "
	DEFVAL	{ created }
	::= { wfFrSwIsdnScrnEntry 1 }

    wfFrSwIsdnScrnIndex OBJECT-TYPE
	SYNTAX	INTEGER
	ACCESS	read-only
	STATUS	mandatory
	DESCRIPTION
		"FRSW UNI Index - A number that ties this 
		 entry to an entry in wfFrSwIsdnAssocEntry."
	::= { wfFrSwIsdnScrnEntry 2 }

    wfFrSwIsdnScrnNum OBJECT-TYPE
	SYNTAX	OCTET STRING
	ACCESS	read-only
	STATUS	mandatory
	DESCRIPTION
		"ISDN Phone Number of a user authorized to
		 access the UNIs contained in the FRSW
		 UNI Index. "
	::= { wfFrSwIsdnScrnEntry 3 }

wfFrSwSigTable OBJECT-TYPE
	SYNTAX	SEQUENCE OF WfFrSwSigEntry
	ACCESS	not-accessible
	STATUS	mandatory
	DESCRIPTION
		" The Frame relay signalling table contains frame relay
		  signalling entries indexed by the frame relay access
		  channel circuit number. An instance of wfFrSwSigEntry
		  is required for each frame relay access channel with
		  frame relay signalling enabled.  The absence of
		  wfFrSwSigEntry for a given frame relay access channel
		  implies that frame relay signalling is disabled for the
		  circuit.  Note that the terms 'incoming' and 'outgoing'
		  refer to the frame mode call with respect to the network
		  side of the interface.  The terminology used by CCITT
		  Q.933/Q.931 is different. "
	::= { wfFrswGroup 12 }

wfFrSwSigEntry OBJECT-TYPE
	SYNTAX	WfFrSwSigEntry
	ACCESS	not-accessible
	STATUS	mandatory
	DESCRIPTION
		" An entry in the Frame Relay signalling port
		  information table. "
	INDEX	{ wfFrSwSigCircuit }
	::= { wfFrSwSigTable 1 }

WfFrSwSigEntry ::= SEQUENCE {
	wfFrSwSigDelete
		INTEGER,
	wfFrSwSigCircuit
		INTEGER,
	wfFrSwSigSvcDlciLow
		INTEGER,
	wfFrSwSigSvcDlciHigh
		INTEGER,
	wfFrSwSigDlciAssign
		INTEGER,
	wfFrSwSigMaxNumOfSvcs
		INTEGER,
	wfFrSwSigNumOfSvcsInUse
		INTEGER,
	wfFrSwSigDefaultThroughput
		INTEGER,
	wfFrSwSigDefaultMinAcceptThroughput
		INTEGER,
	wfFrSwSigDefaultBc
		INTEGER,
	wfFrSwSigDefaultBe
		INTEGER,
	wfFrSwSigMaxInThroughputPerSvc
		INTEGER,
	wfFrSwSigMaxOutThroughputPerSvc
		INTEGER,
	wfFrSwSigTotalInNegotiableThroughput
		INTEGER,
	wfFrSwSigTotalInCurrentThroughput
		INTEGER,
	wfFrSwSigTotalOutNegotiableThroughput
		INTEGER,
	wfFrSwSigTotalOutCurrentThroughput
		INTEGER,
	wfFrSwSigXNetClearingDisable
		INTEGER,
	wfFrSwSigCallingPartyIEMandatory
		INTEGER,
	wfFrSwSigT301
		INTEGER,
	wfFrSwSigT303
		INTEGER,
	wfFrSwSigT305
		INTEGER,
	wfFrSwSigT308
		INTEGER,
	wfFrSwSigT310
		INTEGER,
	wfFrSwSigT322
		INTEGER,
	wfFrSwSigInSetupPkts
		Counter,
	wfFrSwSigInCallProceedingPkts
		Counter,
	wfFrSwSigInConnectPkts
		Counter,
	wfFrSwSigInDisconnectPkts
		Counter,
	wfFrSwSigInReleasePkts
		Counter,
	wfFrSwSigInReleaseCompletePkts
		Counter,
	wfFrSwSigInStatusEnquiryPkts
		Counter,
	wfFrSwSigInStatusPkts
		Counter,
	wfFrSwSigInUnknownPkts
		Counter,
	wfFrSwSigOutSetupPkts
		Counter,
	wfFrSwSigOutCallProceedingPkts
		Counter,
	wfFrSwSigOutConnectPkts
		Counter,
	wfFrSwSigOutDisconnectPkts
		Counter,
	wfFrSwSigOutReleasePkts
		Counter,
	wfFrSwSigOutReleaseCompletePkts
		Counter,
	wfFrSwSigOutStatusEnquiryPkts
		Counter,
	wfFrSwSigOutStatusPkts
		Counter,
	wfFrSwSigRejectedConnRequests
		Counter,
	wfFrSwSigNwrkAbortedConnections
		Counter,
	wfFrSwSigL2Resets
		Counter,
	wfFrSwSigDlciIEAllowed
		INTEGER,
	wfFrSwSigX213PriorityIEAllowed
		INTEGER,
	wfFrSwSigMaximumBe
		INTEGER
}

wfFrSwSigDelete OBJECT-TYPE
	SYNTAX	INTEGER {
		created(1),
		deleted(2)
	}
	ACCESS	read-write
	STATUS	mandatory
	DESCRIPTION
		" Indication to delete this instance "
	DEFVAL	{ created }
	::= { wfFrSwSigEntry 1 }

wfFrSwSigCircuit OBJECT-TYPE
	SYNTAX	INTEGER
	ACCESS	read-only
	STATUS	mandatory
	DESCRIPTION
		" The circuit number for this frame relay access channel "
	::= { wfFrSwSigEntry 2 }

wfFrSwSigSvcDlciLow OBJECT-TYPE
	SYNTAX	INTEGER (0..2147483647)
	ACCESS	read-write
	STATUS	mandatory
	DESCRIPTION
		" Lowest DLCI to be used for SVC, the default value
		  is for 2 octet frame header "
	DEFVAL	{ 16 }
	::= { wfFrSwSigEntry 3 }

wfFrSwSigSvcDlciHigh OBJECT-TYPE
	SYNTAX	INTEGER (0..2147483647)
	ACCESS	read-write
	STATUS	mandatory
	DESCRIPTION
		" Highest DLCI to be used for SVC, the default value
		  is for 2 octet frame header. "
	DEFVAL	{ 991 }
	::= { wfFrSwSigEntry 4 }

wfFrSwSigDlciAssign OBJECT-TYPE
	SYNTAX	INTEGER {
		increment(1),
		decrement(2)
	}
	ACCESS	read-write
	STATUS	mandatory
	DESCRIPTION
		" Determines if DLCI's are assigned starting
		  at wfFrSwSigSvcDlciHigh and working towards
		  wfFrSwSigSvcDlciLow or vice versa. "
	DEFVAL	{ decrement }
	::= { wfFrSwSigEntry 5 }

wfFrSwSigMaxNumOfSvcs OBJECT-TYPE
	SYNTAX	INTEGER (1..65535)
	ACCESS	read-write
	STATUS	mandatory
	DESCRIPTION
		" Indicates the maximum number of simultaneous switched
		  virtual circuits allowed on the logical line. "
	DEFVAL	{ 100 }
	::= { wfFrSwSigEntry 6 }

wfFrSwSigNumOfSvcsInUse OBJECT-TYPE
	SYNTAX	INTEGER
	ACCESS	read-only
	STATUS	mandatory
	DESCRIPTION
		" Indicates the number of switched virtual circuits
		  in use on the logical line. "
	::= { wfFrSwSigEntry 7 }

wfFrSwSigDefaultThroughput OBJECT-TYPE
	SYNTAX	INTEGER (0..2147483647)
	ACCESS	read-write
	STATUS	mandatory
	DESCRIPTION
		" This value is used by the network in the Link Layer
		  Core Parameters IE incoming & outgoing throughput
		  fields when they are not included in the setup message
		  by the user. "
	DEFVAL	{ 0 }
	::= { wfFrSwSigEntry 8 }

wfFrSwSigDefaultMinAcceptThroughput OBJECT-TYPE
	SYNTAX	INTEGER (0..2147483647)
	ACCESS	read-write
	STATUS	mandatory
	DESCRIPTION
		" This value is used by the network in the Link Layer
		  Core Parameters IE incoming & outgoing minimum acceptable
		  throughput fields when they are not included in the
		  setup message by the user. "
	DEFVAL	{ 0 }
	::= { wfFrSwSigEntry 9 }

wfFrSwSigDefaultBc OBJECT-TYPE
	SYNTAX	INTEGER (0..2147483647)
	ACCESS	read-only
	STATUS	mandatory
	DESCRIPTION
		" This value is used by the network in the Link Layer
		  Core Parameters IE incoming & outgoing Bc fields when
		  they are not included in the setup message by the user. "
	::= { wfFrSwSigEntry 10 }

wfFrSwSigDefaultBe OBJECT-TYPE
	SYNTAX	INTEGER (0..2147483647)
	ACCESS	read-write
	STATUS	mandatory
	DESCRIPTION
		" This value is used by the network in the Link Layer
		  Core Parameters IE incoming & outgoing Be fields when
		  they are not included in the setup message by the user. "
	DEFVAL	{ 2147483647 }
	::= { wfFrSwSigEntry 11 }

wfFrSwSigMaxInThroughputPerSvc OBJECT-TYPE
	SYNTAX	INTEGER (0..2147483647)
	ACCESS	read-write
	STATUS	mandatory
	DESCRIPTION
		" This is the maximum incoming throughput that any
		  single SVC may negotiate for a call.  Calls requesting
		  in excess of this attribute are rejected. "
	DEFVAL	{ 2147483647 }
	::= { wfFrSwSigEntry 12 }

wfFrSwSigMaxOutThroughputPerSvc OBJECT-TYPE
	SYNTAX	INTEGER (0..2147483647)
	ACCESS	read-write
	STATUS	mandatory
	DESCRIPTION
		" This is the maximum outgoing throughput that any
		  single SVC may negotiate for a call.  Calls requesting
		  in excess of this attribute are rejected. "
	DEFVAL	{ 2147483647 }
	::= { wfFrSwSigEntry 13 }

wfFrSwSigTotalInNegotiableThroughput OBJECT-TYPE
	SYNTAX	INTEGER (0..2147483647)
	ACCESS	read-write
	STATUS	mandatory
	DESCRIPTION
		" This is the total maximum incoming throughput that is
		  available for all frame mode calls on the port.  If the
		  sum of the incoming throughput requested by a call
		  and wfFrSwSigTotalInCurrentThroughput is in excess of
		  this value, the call is rejected. "
	DEFVAL	{ 2147483647 }
	::= { wfFrSwSigEntry 14 }

wfFrSwSigTotalInCurrentThroughput OBJECT-TYPE
	SYNTAX	INTEGER
	ACCESS	read-only
	STATUS	mandatory
	DESCRIPTION
		" This is the total incoming throughput that has been
		  negotiated for use by all SVC's on the port. "
	::= { wfFrSwSigEntry 15 }

wfFrSwSigTotalOutNegotiableThroughput OBJECT-TYPE
	SYNTAX	INTEGER (0..2147483647)
	ACCESS	read-write
	STATUS	mandatory
	DESCRIPTION
		" This is the total maximum outgoing throughput that is
		  available for all frame mode calls on the port.  If the
		  sum of the outgoing throughput requested by a call
		  and wfFrSwSigTotalOutCurrentThroughput is in excess of
		  this value, the call is rejected. "
	DEFVAL	{ 2147483647 }
	::= { wfFrSwSigEntry 16 }

wfFrSwSigTotalOutCurrentThroughput OBJECT-TYPE
	SYNTAX	INTEGER
	ACCESS	read-only
	STATUS	mandatory
	DESCRIPTION
		" This is the total incoming throughput that has been
		  negotiated for use by all SVC's on the port. "
	::= { wfFrSwSigEntry 17 }

wfFrSwSigXNetClearingDisable OBJECT-TYPE
	SYNTAX	INTEGER {
		enable(1),
		disable(2)
	}
	ACCESS	read-write
	STATUS	mandatory
	DESCRIPTION
		" If cross-net polling (wfFrSwDlcmiCrossNetEnable) is
		  enabled on this interface, and the error threshold
		  (wfFrSwDlcmiCrossNetErrorThreshold) is exceeded, the
		  network can clear the call. "
	DEFVAL	{ enable }
	::= { wfFrSwSigEntry 18 }

wfFrSwSigCallingPartyIEMandatory OBJECT-TYPE
        SYNTAX	INTEGER {
    		    enabled(1),
    		    disabled(2)
    		}
	ACCESS	read-write
	STATUS	mandatory
	DESCRIPTION
		" Reject the call if the Calling Party IE is absent in the
                  setup message or if the provided Calling Party IE fails
                  address authentication tests againt the configured 
                  address(es) on the ingress logical line."
	DEFVAL	{ disabled }
	::= { wfFrSwSigEntry 19 }

wfFrSwSigT301 OBJECT-TYPE
	SYNTAX	INTEGER (1..10)
	ACCESS	read-write
	STATUS	mandatory
	DESCRIPTION
		"  Timer number:         T301
		   default time-out:     3 min
		   state of call:        call initiated
		   cause for start:      incoming setup
		   normal stop:          outgoing connect
		   at the first expiry:  clear call
		   at the second expiry: timer not restarted "
	DEFVAL	{ 3 }
	::= { wfFrSwSigEntry 20 }

wfFrSwSigT303 OBJECT-TYPE
	SYNTAX	INTEGER (2..90)
	ACCESS	read-write
	STATUS	mandatory
	DESCRIPTION
		"  Timer number:         T303
		   default time-out:     4 s
		   state of call:        call present
		   cause for start:      outgoing setup
		   normal stop:          incoming connect/call-proceeding/
		                         release-complete
		   at the first expiry:  retransmit setup, restart T303
		   at the second expiry: clear call "
	DEFVAL	{ 4 }
	::= { wfFrSwSigEntry 21 }

wfFrSwSigT305 OBJECT-TYPE
	SYNTAX	INTEGER (20..90)
	ACCESS	read-write
	STATUS	mandatory
	DESCRIPTION
		"  Timer number:         T305
		   default time-out:     30 s
		   state of call:        disconnect ind
		   cause for start:      outgoing disconnect
		   normal stop:          incoming release/disconnect
		   at the first expiry:  outgoing release
		   at the second expiry: timer not restarted "
	DEFVAL	{ 30 }
	::= { wfFrSwSigEntry 22 }

wfFrSwSigT308 OBJECT-TYPE
	SYNTAX	INTEGER (2..90)
	ACCESS	read-write
	STATUS	mandatory
	DESCRIPTION
		"  Timer number:         T308
		   default time-out:     4 s
		   state of call:        release req
		   cause for start:      outgoing release
		   normal stop:          incoming release/release-complete
		   at the first expiry:  retransmit release, restart T308
		   at the second expiry: place access channel in maintenance "
	DEFVAL	{ 4 }
	::= { wfFrSwSigEntry 23 }

wfFrSwSigT310 OBJECT-TYPE
	SYNTAX	INTEGER (2..90)
	ACCESS	read-write
	STATUS	mandatory
	DESCRIPTION
		"  Timer number:         T310
		   default time-out:     10 s
		   state of call:        incoming call proceeding
		   cause for start:      incoming call proceeding
		   normal stop:          incoming connect/disconnect
		   at the first expiry:  clear call
		   at the second expiry: timer not restarted "
	DEFVAL	{ 10 }
	::= { wfFrSwSigEntry 24 }

wfFrSwSigT322 OBJECT-TYPE
	SYNTAX	INTEGER (2..90)
	ACCESS	read-write
	STATUS	mandatory
	DESCRIPTION
		"  Timer number:         T322
		   default time-out:     4 s
		   state of call:        any call state
		   cause for start:      outgoing status enquiry
		   normal stop:          incoming status/disconnect/
		                         release/release-complete
		   at the first expiry:  retransmit status-enq, restart T322
		   at the second expiry: resend status enq and restart T322 "
	DEFVAL	{ 4 }
	::= { wfFrSwSigEntry 25 }

wfFrSwSigInSetupPkts OBJECT-TYPE
	SYNTAX	Counter
	ACCESS	read-only
	STATUS	mandatory
	DESCRIPTION
		" number of incoming setup packets "
	::= { wfFrSwSigEntry 26 }

wfFrSwSigInCallProceedingPkts OBJECT-TYPE
	SYNTAX	Counter
	ACCESS	read-only
	STATUS	mandatory
	DESCRIPTION
		" number of incoming call proceeding packets "
	::= { wfFrSwSigEntry 27 }

wfFrSwSigInConnectPkts OBJECT-TYPE
	SYNTAX	Counter
	ACCESS	read-only
	STATUS	mandatory
	DESCRIPTION
		" number of incoming connect packets "
	::= { wfFrSwSigEntry 28 }

wfFrSwSigInDisconnectPkts OBJECT-TYPE
	SYNTAX	Counter
	ACCESS	read-only
	STATUS	mandatory
	DESCRIPTION
		" number of incoming disconnect packets "
	::= { wfFrSwSigEntry 29 }

wfFrSwSigInReleasePkts OBJECT-TYPE
	SYNTAX	Counter
	ACCESS	read-only
	STATUS	mandatory
	DESCRIPTION
		" number of incoming release packets "
	::= { wfFrSwSigEntry 30 }

wfFrSwSigInReleaseCompletePkts OBJECT-TYPE
	SYNTAX	Counter
	ACCESS	read-only
	STATUS	mandatory
	DESCRIPTION
		" number of incoming release complete packets "
	::= { wfFrSwSigEntry 31 }

wfFrSwSigInStatusEnquiryPkts OBJECT-TYPE
	SYNTAX	Counter
	ACCESS	read-only
	STATUS	mandatory
	DESCRIPTION
		" number of incoming status enquiry packets "
	::= { wfFrSwSigEntry 32 }

wfFrSwSigInStatusPkts OBJECT-TYPE
	SYNTAX	Counter
	ACCESS	read-only
	STATUS	mandatory
	DESCRIPTION
		" number of incoming status packets "
	::= { wfFrSwSigEntry 33 }

wfFrSwSigInUnknownPkts OBJECT-TYPE
	SYNTAX	Counter
	ACCESS	read-only
	STATUS	mandatory
	DESCRIPTION
		" number of incoming unknown packets "
	::= { wfFrSwSigEntry 34 }

wfFrSwSigOutSetupPkts OBJECT-TYPE
	SYNTAX	Counter
	ACCESS	read-only
	STATUS	mandatory
	DESCRIPTION
		" number of outgoing setup packets "
	::= { wfFrSwSigEntry 35 }

wfFrSwSigOutCallProceedingPkts OBJECT-TYPE
	SYNTAX	Counter
	ACCESS	read-only
	STATUS	mandatory
	DESCRIPTION
		" number of outgoing call proceeding packets "
	::= { wfFrSwSigEntry 36 }

wfFrSwSigOutConnectPkts OBJECT-TYPE
	SYNTAX	Counter
	ACCESS	read-only
	STATUS	mandatory
	DESCRIPTION
		" number of outgoing connect packets "
	::= { wfFrSwSigEntry 37 }

wfFrSwSigOutDisconnectPkts OBJECT-TYPE
	SYNTAX	Counter
	ACCESS	read-only
	STATUS	mandatory
	DESCRIPTION
		" number of outgoing disconnect packets "
	::= { wfFrSwSigEntry 38 }

wfFrSwSigOutReleasePkts OBJECT-TYPE
	SYNTAX	Counter
	ACCESS	read-only
	STATUS	mandatory
	DESCRIPTION
		" number of outgoing release packets "
	::= { wfFrSwSigEntry 39 }

wfFrSwSigOutReleaseCompletePkts OBJECT-TYPE
	SYNTAX	Counter
	ACCESS	read-only
	STATUS	mandatory
	DESCRIPTION
		" number of outgoing release packest "
	::= { wfFrSwSigEntry 40 }

wfFrSwSigOutStatusEnquiryPkts OBJECT-TYPE
	SYNTAX	Counter
	ACCESS	read-only
	STATUS	mandatory
	DESCRIPTION
		" number of outgoing status enquiry packets "
	::= { wfFrSwSigEntry 41 }

wfFrSwSigOutStatusPkts OBJECT-TYPE
	SYNTAX	Counter
	ACCESS	read-only
	STATUS	mandatory
	DESCRIPTION
		" number of outgoing status packets "
	::= { wfFrSwSigEntry 42 }

wfFrSwSigRejectedConnRequests OBJECT-TYPE
	SYNTAX	Counter
	ACCESS	read-only
	STATUS	mandatory
	DESCRIPTION
		" number of connections rejected "
	::= { wfFrSwSigEntry 43 }

wfFrSwSigNwrkAbortedConnections OBJECT-TYPE
	SYNTAX	Counter
	ACCESS	read-only
	STATUS	mandatory
	DESCRIPTION
		" number of connections aborted by network "
	::= { wfFrSwSigEntry 44 }

wfFrSwSigL2Resets OBJECT-TYPE
	SYNTAX	Counter
	ACCESS	read-only
	STATUS	mandatory
	DESCRIPTION
		" number of L2 resets "
	::= { wfFrSwSigEntry 45 }

wfFrSwSigDlciIEAllowed OBJECT-TYPE
        SYNTAX	INTEGER {
    		    enabled(1),
    		    disabled(2)
    		}
	ACCESS	read-write
	STATUS	mandatory
	DESCRIPTION
		" Reject the call if the Dlci IE is present in the setup
                  message and wfFrSwSigDlciIEAllowed is set to disabled."
	DEFVAL	{ enabled }
	::= { wfFrSwSigEntry 46 }

wfFrSwSigX213PriorityIEAllowed OBJECT-TYPE
        SYNTAX	INTEGER {
    		    enabled(1),
    		    disabled(2)
    		}
	ACCESS	read-write
	STATUS	mandatory
	DESCRIPTION
		" Reject the call if the X213 Priority IE is present in 
                  setup message and wfFrSwSigX213PriorityIEAllowed is set
                  to disabled."
	DEFVAL	{ enabled }
	::= { wfFrSwSigEntry 47 }

wfFrSwSigMaximumBe OBJECT-TYPE
	SYNTAX	INTEGER (0..2147483647)
	ACCESS	read-write
	STATUS	mandatory
	DESCRIPTION
		"This value is the maximum allowed Be for a SVC connection"
	DEFVAL	{2147483647}
	::= { wfFrSwSigEntry 48 }

wfFrSwGlobalE164AddrTable OBJECT-TYPE
	SYNTAX	SEQUENCE OF WfFrSwGlobalE164AddrEntry
	ACCESS	not-accessible
	STATUS	mandatory
	DESCRIPTION
		" wfFrSwGlobalE164AddrTable is used by Directory Services
    	    	  to translate a range of E.164 addresses into an
    	    	  internal IP network address.  E.164 ranges must not ever overlap. "
	::= { wfFrswGroup 13 }

wfFrSwGlobalE164AddrEntry OBJECT-TYPE
	SYNTAX	WfFrSwGlobalE164AddrEntry
	ACCESS	not-accessible
	STATUS	mandatory
	DESCRIPTION
		" An entry in the Frame Relay Global E.164 Address Table. "
	INDEX	{ wfFrSwGlobalE164AddrLow,
		wfFrSwGlobalE164AddrHigh }
	::= { wfFrSwGlobalE164AddrTable 1 }

WfFrSwGlobalE164AddrEntry ::= SEQUENCE {
	wfFrSwGlobalE164AddrDelete
		INTEGER,
	wfFrSwGlobalE164AddrLow
		OCTET STRING,
	wfFrSwGlobalE164AddrHigh
		OCTET STRING,
	wfFrSwGlobalE164AddrIPAddr
		IpAddress
}

wfFrSwGlobalE164AddrDelete OBJECT-TYPE
	SYNTAX	INTEGER {
		created(1),
		deleted(2)
	}
	ACCESS	read-write
	STATUS	mandatory
	DESCRIPTION
		" Indication to delete/create this entry. "
	DEFVAL	{ created }
	::= { wfFrSwGlobalE164AddrEntry 1 }

wfFrSwGlobalE164AddrLow OBJECT-TYPE
	SYNTAX	OCTET STRING
	ACCESS	read-only
	STATUS	mandatory
	DESCRIPTION
		" Instance identifier; the low end of the E.164
		   address range. This is an 8-byte fixed length octet
		   string format, right justified with padded leading zeros
		   as necessary. "
	::= { wfFrSwGlobalE164AddrEntry 2 }

wfFrSwGlobalE164AddrHigh OBJECT-TYPE
	SYNTAX	OCTET STRING
	ACCESS	read-only
	STATUS	mandatory
	DESCRIPTION
		" Instance identifier; the high end of the E.164
		   address range. This is an 8-byte fixed length octet
		   string format, right justified with padded leading zeros
		   as necessary. "
	::= { wfFrSwGlobalE164AddrEntry 3 }

wfFrSwGlobalE164AddrIPAddr OBJECT-TYPE
	SYNTAX	IpAddress
	ACCESS	read-write
	STATUS	mandatory
	DESCRIPTION
		" This is the internal IP network address associated with
		   this range of E.164 addresses. "
	::= { wfFrSwGlobalE164AddrEntry 4 }

wfFrSwGlobalX121AddrTable OBJECT-TYPE
	SYNTAX	SEQUENCE OF WfFrSwGlobalX121AddrEntry
	ACCESS	not-accessible
	STATUS	mandatory
	DESCRIPTION
		" wfFrSwGlobalX121AddrTable is used by Directory Services
    	    	  to translate a range of X.121 addresses into an
    	    	  internal IP network address. X.121 ranges must not ever overlap. "
	::= { wfFrswGroup 14 }

wfFrSwGlobalX121AddrEntry OBJECT-TYPE
	SYNTAX	WfFrSwGlobalX121AddrEntry
	ACCESS	not-accessible
	STATUS	mandatory
	DESCRIPTION
		" An entry in the Frame Relay Global X.121 Address Table. "
	INDEX	{ wfFrSwGlobalX121AddrLow,
		wfFrSwGlobalX121AddrHigh }
	::= { wfFrSwGlobalX121AddrTable 1 }

WfFrSwGlobalX121AddrEntry ::= SEQUENCE {
	wfFrSwGlobalX121AddrDelete
		INTEGER,
	wfFrSwGlobalX121AddrLow
		OCTET STRING,
	wfFrSwGlobalX121AddrHigh
		OCTET STRING,
	wfFrSwGlobalX121AddrIPAddr
		IpAddress
}

wfFrSwGlobalX121AddrDelete OBJECT-TYPE
	SYNTAX	INTEGER {
		created(1),
		deleted(2)
	}
	ACCESS	read-write
	STATUS	mandatory
	DESCRIPTION
		" Indication to delete/create this entry. "
	DEFVAL	{ created }
	::= { wfFrSwGlobalX121AddrEntry 1 }

wfFrSwGlobalX121AddrLow OBJECT-TYPE
	SYNTAX	OCTET STRING
	ACCESS	read-only
	STATUS	mandatory
	DESCRIPTION
		" Instance identifier; the low end of the X.121
		   address range. This is an 8-byte fixed length octet
		   string format, right justified with padded leading zeros
		   as necessary. "
	::= { wfFrSwGlobalX121AddrEntry 2 }

wfFrSwGlobalX121AddrHigh OBJECT-TYPE
	SYNTAX	OCTET STRING
	ACCESS	read-only
	STATUS	mandatory
	DESCRIPTION
		" Instance identifier; the high end of the X.121
		   address range. This is an 8-byte fixed length octet
		   string format, right justified with padded leading zeros
		   as necessary. "
	::= { wfFrSwGlobalX121AddrEntry 3 }

wfFrSwGlobalX121AddrIPAddr OBJECT-TYPE
	SYNTAX	IpAddress
	ACCESS	read-write
	STATUS	mandatory
	DESCRIPTION
		" This is the internal IP network address associated with
		   this range of X.121 addresses. "
	::= { wfFrSwGlobalX121AddrEntry 4 }

wfFrSwLocalE164AddrTable OBJECT-TYPE
	SYNTAX	SEQUENCE OF WfFrSwLocalE164AddrEntry
	ACCESS	not-accessible
	STATUS	mandatory
	DESCRIPTION
		" wfFrSwLocalE164AddrTable contains E.164 addresses on the
		   local BNX and CUG (Closed User Group) related information. "
	::= { wfFrswGroup 15 }

wfFrSwLocalE164AddrEntry OBJECT-TYPE
	SYNTAX	WfFrSwLocalE164AddrEntry
	ACCESS	not-accessible
	STATUS	mandatory
	DESCRIPTION
		" An entry in the Frame Relay Local E.164 Address Table. "
	INDEX	{ wfFrSwLocalE164AddrCct,
		wfFrSwLocalE164Address }
	::= { wfFrSwLocalE164AddrTable 1 }

WfFrSwLocalE164AddrEntry ::= SEQUENCE {
	wfFrSwLocalE164AddrDelete
		INTEGER,
	wfFrSwLocalE164AddrCct
		INTEGER,
	wfFrSwLocalE164Address
		OCTET STRING,
	wfFrSwLocalE164AddrCUG
		OCTET STRING,
        wfFrSwLocalE164AddrLocalFlag
		INTEGER
}

wfFrSwLocalE164AddrDelete OBJECT-TYPE
	SYNTAX	INTEGER {
		created(1),
		deleted(2)
	}
	ACCESS	read-write
	STATUS	mandatory
	DESCRIPTION
		" Indication to delete/create this entry. "
	DEFVAL	{ created }
	::= { wfFrSwLocalE164AddrEntry 1 }

wfFrSwLocalE164AddrCct OBJECT-TYPE
	SYNTAX	INTEGER
	ACCESS	read-only
	STATUS	mandatory
	DESCRIPTION
		" Instance identifier; internal CCT number associated
		   with this E.164 address. "
	::= { wfFrSwLocalE164AddrEntry 2 }

wfFrSwLocalE164Address OBJECT-TYPE
	SYNTAX	OCTET STRING
	ACCESS	read-only
	STATUS	mandatory
	DESCRIPTION
		" Instance identifier; an E.164 address.
		   This is an 8-byte fixed length octet string format,
		   right justified with padded leading zeros as necessary. "
	::= { wfFrSwLocalE164AddrEntry 3 }

wfFrSwLocalE164AddrCUG OBJECT-TYPE
	SYNTAX	OCTET STRING
	ACCESS	read-write
	STATUS	mandatory
	DESCRIPTION
		" CUG (Closed User Group) information.
		   The structure of the CUG information consists zero or 
		   more groups (number of groups can be derived from the 
		   OCTET STRING data type of this MIB attribute) of COI
		   structure information. Each COI structure consists of 
		   a COI group number (4-byte integer) and a COI list. 
		   Each COI list consists of a length field (4-byte integer)
		   which specifies the number of bytes of COI bit-encoded 
		   information belonging to this group and the COI information
		   structure.  COI information structure is a bit mask field 
		   where each bit from left to right represents whether this 
		   E.164 address belongs to a particular COI number within this
		   COI group number.
		   Please note that COI group numbers can not be repeated and 
		   that the COI group numbers must be in increasing order in the
		   CUG configuration MIB
		   wfFrSwLocalE164AddrCUG defaults to zero COI groups which
		   means no CUG related information and hence this local
		   wfFrSwLocalE164Address is allowed to communicate with
		   all users. "
	::= { wfFrSwLocalE164AddrEntry 4 }

wfFrSwLocalE164AddrLocalFlag OBJECT-TYPE
	SYNTAX	INTEGER {
		local(1),
		nonlocal(2)
	}
	ACCESS	read-write
	STATUS	mandatory
	DESCRIPTION
		" Local/Non-Local Identifier Flag.  Used for SPVCs."
	DEFVAL	{ local }
	::= { wfFrSwLocalE164AddrEntry 5 }

wfFrSwLocalX121AddrTable OBJECT-TYPE
	SYNTAX	SEQUENCE OF WfFrSwLocalX121AddrEntry
	ACCESS	not-accessible
	STATUS	mandatory
	DESCRIPTION
		" wfFrSwLocalX121AddrTable contains X.121 addresses on the
		   local BNX and CUG (Closed User Group) related information. "
	::= { wfFrswGroup 16 }

wfFrSwLocalX121AddrEntry OBJECT-TYPE
	SYNTAX	WfFrSwLocalX121AddrEntry
	ACCESS	not-accessible
	STATUS	mandatory
	DESCRIPTION
		" An entry in the Frame Relay Local X.121 Address Table. "
	INDEX	{ wfFrSwLocalX121AddrCct,
		wfFrSwLocalX121Address }
	::= { wfFrSwLocalX121AddrTable 1 }

WfFrSwLocalX121AddrEntry ::= SEQUENCE {
	wfFrSwLocalX121AddrDelete
		INTEGER,
	wfFrSwLocalX121AddrCct
		INTEGER,
	wfFrSwLocalX121Address
		OCTET STRING,
	wfFrSwLocalX121AddrCUG
		OCTET STRING,
	wfFrSwLocalX121AddrLocalFlag
		INTEGER
}

wfFrSwLocalX121AddrDelete OBJECT-TYPE
	SYNTAX	INTEGER {
		created(1),
		deleted(2)
	}
	ACCESS	read-write
	STATUS	mandatory
	DESCRIPTION
		" Indication to delete/create this entry. "
	DEFVAL	{ created }
	::= { wfFrSwLocalX121AddrEntry 1 }

wfFrSwLocalX121AddrCct OBJECT-TYPE
	SYNTAX	INTEGER
	ACCESS	read-only
	STATUS	mandatory
	DESCRIPTION
		" Instance identifier; internal CCT number associated
		   with this X.121 address. "
	::= { wfFrSwLocalX121AddrEntry 2 }

wfFrSwLocalX121Address OBJECT-TYPE
	SYNTAX	OCTET STRING
	ACCESS	read-only
	STATUS	mandatory
	DESCRIPTION
		" Instance identifier; a X.121 address.
		   This is an 8-byte fixed length octet string format,
		   right justified with padded leading zeros as necessary. "
	::= { wfFrSwLocalX121AddrEntry 3 }

wfFrSwLocalX121AddrCUG OBJECT-TYPE
	SYNTAX	OCTET STRING
	ACCESS	read-write
	STATUS	mandatory
	DESCRIPTION
		" CUG (Closed User Group) information.
		   The structure of the CUG information consists zero or 
		   more groups (number of groups can be derived from the 
		   OCTET STRING data type of this MIB attribute) of COI
		   structure information. Each COI structure consists of 
		   a COI group number (4-byte integer) and a COI list. 
		   Each COI list consists of a length field (4-byte integer)
		   which specifies the number of bytes of COI bit-encoded 
		   information belonging to this group and the COI information
		   structure.  COI information structure is a bit mask field 
		   where each bit from left to right represents whether this 
		   X.121 address belongs to a particular COI number within this
		   COI group number.
		   wfFrSwLocalX121AddrCUG defaults to zero COI groups which
		   means no CUG related information and hence this local
		   wfFrSwLocalX121Address is allowed to communicate with
		   all users. "
	::= { wfFrSwLocalX121AddrEntry 4 }

wfFrSwLocalX121AddrLocalFlag OBJECT-TYPE
	SYNTAX	INTEGER {
		local(1),
		nonlocal(2)
	}
	ACCESS	read-write
	STATUS	mandatory
	DESCRIPTION
		" Local/Non-Local Identifier Flag.  Used for SPVCs."
	DEFVAL	{ local }
	::= { wfFrSwLocalX121AddrEntry 5 }

wfFrSwBase	OBJECT IDENTIFIER ::= { wfFrswGroup 17 }

wfFrSwBaseDelete OBJECT-TYPE
	SYNTAX	INTEGER {
		created(1),
		deleted(2)
	}
	ACCESS	read-write
	STATUS	mandatory
	DESCRIPTION
		" Indication to delete/create this base group "
	DEFVAL	{ created }
	::= { wfFrSwBase 1 }

wfFrSwBaseIpAddr OBJECT-TYPE
	SYNTAX	IpAddress
	ACCESS	read-write
	STATUS	mandatory
	DESCRIPTION
		" Indicates this BNX's (circuit-less) IP address "
	::= { wfFrSwBase 2 }


wfFrSwBaseShutDown OBJECT-TYPE
	SYNTAX	Counter
	ACCESS	read-write
	STATUS	mandatory
	DESCRIPTION
		"Bit mask for slots to shutdown, slots 1-14. The MSBit 
		 represents slot 1, the next most significant bit represents
		 slot 2, and so forth." 
	::= { wfFrSwBase 3 }

wfFrSwCngcMonTable OBJECT-TYPE
	SYNTAX	SEQUENCE OF WfFrSwCngcMonEntry
	ACCESS	not-accessible
	STATUS	mandatory
	DESCRIPTION
		"This table is used by FRSW Congestion Control application.
                 The table is used to Monitor the congestion level of a
                 particular circuit."
	::= { wfFrswGroup 18 }

wfFrSwCngcMonEntry OBJECT-TYPE
	SYNTAX	WfFrSwCngcMonEntry
	ACCESS	not-accessible
	STATUS	mandatory
	DESCRIPTION
		"Instance Id for this table."
	INDEX	{ wfFrSwCngcMonCct }
	::= { wfFrSwCngcMonTable 1 }

WfFrSwCngcMonEntry ::= SEQUENCE {
	wfFrSwCngcMonReset
		INTEGER,
	wfFrSwCngcMonCct
		INTEGER,
	wfFrSwCngcMonP0Level1Percent
		Gauge,
	wfFrSwCngcMonP0Level2Percent
		Gauge,
	wfFrSwCngcMonP0Level3Percent
		Gauge,
	wfFrSwCngcMonP0Level4Percent
		Gauge,
	wfFrSwCngcMonP1Level1Percent
		Gauge,
	wfFrSwCngcMonP1Level2Percent
		Gauge,
	wfFrSwCngcMonP1Level3Percent
		Gauge,
	wfFrSwCngcMonP1Level4Percent
		Gauge,
	wfFrSwCngcMonP2Level1Percent
		Gauge,
	wfFrSwCngcMonP2Level2Percent
		Gauge,
	wfFrSwCngcMonP2Level3Percent
		Gauge,
	wfFrSwCngcMonP2Level4Percent
		Gauge,
	wfFrSwCngcMonP3Level1Percent
		Gauge,
	wfFrSwCngcMonP3Level2Percent
		Gauge,
	wfFrSwCngcMonP3Level3Percent
		Gauge,
	wfFrSwCngcMonP3Level4Percent
		Gauge
      }

wfFrSwCngcMonReset OBJECT-TYPE
	SYNTAX	INTEGER
	ACCESS	read-write
	STATUS	mandatory
	DESCRIPTION
		"Indication to reset Cngc Monitor Counters."
	::= { wfFrSwCngcMonEntry 1 }

wfFrSwCngcMonCct OBJECT-TYPE
	SYNTAX	INTEGER
	ACCESS	read-only
	STATUS	mandatory
	DESCRIPTION
		"Circuit to be monitored. "
	::= { wfFrSwCngcMonEntry 2 }

wfFrSwCngcMonP0Level1Percent OBJECT-TYPE
	SYNTAX	Gauge
	ACCESS	read-only
	STATUS	mandatory
	DESCRIPTION
		"Percentage of time congestion is at level 1.
	 	 for Priority 0 Traffic."
	::= { wfFrSwCngcMonEntry 3 }

wfFrSwCngcMonP0Level2Percent OBJECT-TYPE
	SYNTAX	Gauge
	ACCESS	read-only
	STATUS	mandatory
	DESCRIPTION
		"Percentage of time congestion is at level 2.
	 	 for Priority 0 Traffic."
	::= { wfFrSwCngcMonEntry 4 }

wfFrSwCngcMonP0Level3Percent OBJECT-TYPE
	SYNTAX	Gauge
	ACCESS	read-only
	STATUS	mandatory
	DESCRIPTION
		"Percentage of time congestion is at level 3.
	 	 for Priority 0 Traffic."
	::= { wfFrSwCngcMonEntry 5 }

wfFrSwCngcMonP0Level4Percent OBJECT-TYPE
	SYNTAX	Gauge
	ACCESS	read-only
	STATUS	mandatory
	DESCRIPTION
		"Percentage of time congestion is at level 4.
	 	 for Priority 0 Traffic."
	::= { wfFrSwCngcMonEntry 6 }

wfFrSwCngcMonP1Level1Percent OBJECT-TYPE
	SYNTAX	Gauge
	ACCESS	read-only
	STATUS	mandatory
	DESCRIPTION
		"Percentage of time congestion is at level 1.
	 	 for Priority 1 Traffic."
	::= { wfFrSwCngcMonEntry 7 }

wfFrSwCngcMonP1Level2Percent OBJECT-TYPE
	SYNTAX	Gauge
	ACCESS	read-only
	STATUS	mandatory
	DESCRIPTION
		"Percentage of time congestion is at level 2.
	 	 for Priority 1 Traffic."
	::= { wfFrSwCngcMonEntry 8 }

wfFrSwCngcMonP1Level3Percent OBJECT-TYPE
	SYNTAX	Gauge
	ACCESS	read-only
	STATUS	mandatory
	DESCRIPTION
		"Percentage of time congestion is at level 3.
	 	 for Priority 1 Traffic."
	::= { wfFrSwCngcMonEntry 9 }

wfFrSwCngcMonP1Level4Percent OBJECT-TYPE
	SYNTAX	Gauge
	ACCESS	read-only
	STATUS	mandatory
	DESCRIPTION
		"Percentage of time congestion is at level 4.
	 	 for Priority 1 Traffic."
	::= { wfFrSwCngcMonEntry 10 }

wfFrSwCngcMonP2Level1Percent OBJECT-TYPE
	SYNTAX	Gauge
	ACCESS	read-only
	STATUS	mandatory
	DESCRIPTION
		"Percentage of time congestion is at level 1.
	 	 for Priority 2 Traffic."
	::= { wfFrSwCngcMonEntry 11 }

wfFrSwCngcMonP2Level2Percent OBJECT-TYPE
	SYNTAX	Gauge
	ACCESS	read-only
	STATUS	mandatory
	DESCRIPTION
		"Percentage of time congestion is at level 2.
	 	 for Priority 2 Traffic."
	::= { wfFrSwCngcMonEntry 12 }

wfFrSwCngcMonP2Level3Percent OBJECT-TYPE
	SYNTAX	Gauge
	ACCESS	read-only
	STATUS	mandatory
	DESCRIPTION
		"Percentage of time congestion is at level 3.
	 	 for Priority 2 Traffic."
	::= { wfFrSwCngcMonEntry 13 }

wfFrSwCngcMonP2Level4Percent OBJECT-TYPE
	SYNTAX	Gauge
	ACCESS	read-only
	STATUS	mandatory
	DESCRIPTION
		"Percentage of time congestion is at level 4.
	 	 for Priority 2 Traffic."
	::= { wfFrSwCngcMonEntry 14 }

wfFrSwCngcMonP3Level1Percent OBJECT-TYPE
	SYNTAX	Gauge
	ACCESS	read-only
	STATUS	mandatory
	DESCRIPTION
		"Percentage of time congestion is at level 1.
	 	 for Priority 3 Traffic."
	::= { wfFrSwCngcMonEntry 15 }

wfFrSwCngcMonP3Level2Percent OBJECT-TYPE
	SYNTAX	Gauge
	ACCESS	read-only
	STATUS	mandatory
	DESCRIPTION
		"Percentage of time congestion is at level 2.
	 	 for Priority 3 Traffic."
	::= { wfFrSwCngcMonEntry 16 }

wfFrSwCngcMonP3Level3Percent OBJECT-TYPE
	SYNTAX	Gauge
	ACCESS	read-only
	STATUS	mandatory
	DESCRIPTION
		"Percentage of time congestion is at level 3.
	 	 for Priority 3 Traffic."
	::= { wfFrSwCngcMonEntry 17 }

wfFrSwCngcMonP3Level4Percent OBJECT-TYPE
	SYNTAX	Gauge
	ACCESS	read-only
	STATUS	mandatory
	DESCRIPTION
		"Percentage of time congestion is at level 4.
	 	 for Priority 3 Traffic."
	::= { wfFrSwCngcMonEntry 18 }

wfFrSwVirtualIntfTable OBJECT-TYPE
	SYNTAX	SEQUENCE OF WfFrSwVirtualIntfEntry
	ACCESS	not-accessible
	STATUS	mandatory
	DESCRIPTION
                 "The table is used to create 'virtual' FRSW access lines."
	::= { wfFrswGroup 19 }

wfFrSwVirtualIntfEntry OBJECT-TYPE
	SYNTAX	WfFrSwVirtualIntfEntry
	ACCESS	not-accessible
	STATUS	mandatory
	DESCRIPTION
		"Instance Id for this table."
	INDEX	{ wfFrSwVirtualIntfSlot,
                  wfFrSwVirtualIntfCct }
	::= { wfFrSwVirtualIntfTable 1 }

WfFrSwVirtualIntfEntry ::= SEQUENCE {
    	    wfFrSwVirtualIntfDelete
    		INTEGER,
    	    wfFrSwVirtualIntfSlot
    		INTEGER,
    	    wfFrSwVirtualIntfCct
    		INTEGER,
    	    wfFrSwVirtualIntfLineNum
    		INTEGER
        }

    wfFrSwVirtualIntfDelete OBJECT-TYPE
        SYNTAX	INTEGER {
    		    created(1),
    		    deleted(2)
    		}
        ACCESS	read-write
        STATUS	mandatory
        DESCRIPTION
                "Indication to delete this virtual interface."
        DEFVAL	{ created }
        ::= { wfFrSwVirtualIntfEntry 1 }

    wfFrSwVirtualIntfSlot OBJECT-TYPE
        SYNTAX	INTEGER
        ACCESS	read-only
        STATUS	mandatory
        DESCRIPTION
                "Instance identifier; the slot number of this interface."
        ::= { wfFrSwVirtualIntfEntry 2 }

    wfFrSwVirtualIntfCct OBJECT-TYPE
        SYNTAX	INTEGER
        ACCESS	read-only
        STATUS	mandatory
        DESCRIPTION
                "Instance identifier; the circuit number of this interface."
        ::= { wfFrSwVirtualIntfEntry 3 }

    wfFrSwVirtualIntfLineNum OBJECT-TYPE
        SYNTAX	INTEGER
        ACCESS	read-only
        STATUS	mandatory
        DESCRIPTION
                "Line number for this virtual interface."
        ::= { wfFrSwVirtualIntfEntry 4 }

wfFrSwExtFileSysTable OBJECT-TYPE
	SYNTAX	SEQUENCE OF WfFrSwExtFileSysEntry
	ACCESS	not-accessible
	STATUS	mandatory
	DESCRIPTION
		"This table is used by FRSW to extend the file system
                 to DRAM device."
	::= { wfFrswGroup 20 }

wfFrSwExtFileSysEntry OBJECT-TYPE
	SYNTAX	WfFrSwExtFileSysEntry
	ACCESS	not-accessible
	STATUS	mandatory
	DESCRIPTION
		"Instance Id for this table."
	INDEX	{ wfFrSwExtFileSysSlot }
	::= { wfFrSwExtFileSysTable 1 }

WfFrSwExtFileSysEntry ::= SEQUENCE {
	wfFrSwExtFileSysDelete
		INTEGER,
	wfFrSwExtFileSysSlot
		INTEGER,
	wfFrSwExtFileSysSize
		INTEGER,
	wfFrSwExtFileSysActualSize
		INTEGER,
	wfFrSwExtFileSysState
		INTEGER
      }

    wfFrSwExtFileSysDelete OBJECT-TYPE
	SYNTAX	INTEGER {
		created(1),
		deleted(2)
	}
	ACCESS	read-write
	STATUS	mandatory
	DESCRIPTION
		" Indication to delete/create this entry. "
	DEFVAL	{ created }
	::= { wfFrSwExtFileSysEntry 1 }

    wfFrSwExtFileSysSlot OBJECT-TYPE
	SYNTAX	INTEGER
	ACCESS	read-only
	STATUS	mandatory
	DESCRIPTION
		"A unique value for each slot.
                 Its value ranges between 1 and 14."
	::= { wfFrSwExtFileSysEntry 2 }

    wfFrSwExtFileSysSize OBJECT-TYPE
	SYNTAX	INTEGER
	ACCESS	read-write
	STATUS	mandatory
	DESCRIPTION
		"The memory size of the extended file system in
		 byte unit.  The value zero also means that extended
                 file system is disabled.  Non-zero value
                 means enabled.  Its suggested that the size
                 is in multiple of 128k bytes.

                 Some of the well-known memory sizes and their correspond
                 decimal values are as followed:

                  Mem size     Decimal Value
                  ^^^^^^^^     ^^^^^^^^^^^^^
	            128K         131072
	            256K         262144
	            512K         524288
	            1M          1048576
	            2M          2097152
	            4M          4194304
	            8M          8388608
	         "
        DEFVAL  { 0 }
	::= { wfFrSwExtFileSysEntry 3 }

    wfFrSwExtFileSysActualSize OBJECT-TYPE
	SYNTAX	INTEGER
	ACCESS	read-only
	STATUS	mandatory
	DESCRIPTION
		"The actual memory size the system allocated."
        DEFVAL  { 0 }
	::= { wfFrSwExtFileSysEntry 4 }
	
    wfFrSwExtFileSysState OBJECT-TYPE
	SYNTAX	INTEGER {
	            up(1),
	            fault(2),
	            init(3),
	            notpresent(4)
        	}
	ACCESS	read-only
	STATUS	mandatory
	DESCRIPTION
		"The status of the extended file system.

		 State up indicates that the requested memory size
		 for the extended file system has been allocated
		 successfully and the extended file system is in
		 operational state.

		 State fault indicates that the requested memory size
		 for the extended file system has NOT been allocated
		 successfully and the extended file system is NOT
		 in operational state.  One reason for entering the
		 fault state is insufficient available memory.

		 State init indicates that the system is in the
		 initialization cycle.  The extended file system
		 is not operational.

		 State notpresent reflects the size of zero."

        DEFVAL	{ notpresent }
	::= { wfFrSwExtFileSysEntry 5 }

    END  -- Wellfleet-FRSW-MIB
