CPQ-TRAPS-MIB DEFINITIONS ::= BEGIN

IMPORTS mgmt, enterprises FROM SNMPv2-SMI;

DisplayString ::=
	OCTET STRING

PhysAddress ::=
	OCTET STRING

mib-2 OBJECT IDENTIFIER ::= { mgmt 1 }
compaq OBJECT IDENTIFIER ::= { enterprises 232 }
compaq OBJECT IDENTIFIER ::= { enterprises 232 }
compaq-proLiantBLeClassCG-proLiantBLpClassGbE OBJECT IDENTIFIER ::= { compaq 161 }
compaq-common-mgmt OBJECT IDENTIFIER ::= { compaq-proLiantBLeClassCG-proLiantBLpClassGbE 3 }
cpqRackInfo OBJECT IDENTIFIER ::= { compaq 22 }
cpqRackComponent OBJECT IDENTIFIER ::= { cpqRackInfo 2 }
cpqRackAsset OBJECT IDENTIFIER ::= { cpqRackComponent 2 }
cpqRackAssetTable OBJECT IDENTIFIER ::= { cpqRackAsset 1 }
cpqRackAssetEntry OBJECT IDENTIFIER ::= { cpqRackAssetTable 1 }
cpqRackUid OBJECT IDENTIFIER ::= { cpqRackAssetEntry 3 }
cpqRackEnclosure OBJECT IDENTIFIER ::= { cpqRackComponent 3 }
cpqRackCommonEnclosure OBJECT IDENTIFIER ::= { cpqRackEnclosure 1 }
cpqRackCommonEnclosureTable OBJECT IDENTIFIER ::= { cpqRackCommonEnclosure 1 }
cpqRackCommonEnclosureEntry OBJECT IDENTIFIER ::= { cpqRackCommonEnclosureTable 1 }
cpqRackCommonEnclosureSerialNum OBJECT IDENTIFIER ::= { cpqRackCommonEnclosureEntry 7 }
cpqRackNetwork OBJECT IDENTIFIER ::= { cpqRackComponent 6 }
cpqRackNetConnector OBJECT IDENTIFIER ::= { cpqRackNetwork 1 }
cpqRackNetConnectorTable OBJECT IDENTIFIER ::= { cpqRackNetConnector 1 }
cpqRackNetConnectorEntry OBJECT IDENTIFIER ::= { cpqRackNetConnectorTable 1 }
cpqRackNetConnectorSerialNum OBJECT IDENTIFIER ::= { cpqRackNetConnectorEntry 7 }
cpqRackName OBJECT IDENTIFIER ::= { cpqRackAssetEntry 2 }
cpqRackCommonEnclosureName OBJECT IDENTIFIER ::= { cpqRackCommonEnclosureEntry 9 }
cpqRackNetConnectorName OBJECT IDENTIFIER ::= { cpqRackNetConnectorEntry 5 }
cpqRackNetConnectorLocation OBJECT IDENTIFIER ::= { cpqRackNetConnectorEntry 12 }
cpqRackNetConnectorFWRev OBJECT IDENTIFIER ::= { cpqRackNetConnectorEntry 10 }
cpqRackNetConnectorSparePartNumber OBJECT IDENTIFIER ::= { cpqRackNetConnectorEntry 9 }
agentGeneralMgmt OBJECT IDENTIFIER ::= { compaq-common-mgmt 1 }
agentBasicConfig OBJECT IDENTIFIER ::= { agentGeneralMgmt 2 }
agentBscSwFileTable OBJECT IDENTIFIER ::= { agentBasicConfig 1 }
agentBscSwFileEntry OBJECT IDENTIFIER ::= { agentBscSwFileTable 1 }
agentBscSwFileAddr OBJECT IDENTIFIER ::= { agentBscSwFileEntry 3 }
agentBscSwFile OBJECT IDENTIFIER ::= { agentBscSwFileEntry 5 }
agentBscSwFileLoadType OBJECT IDENTIFIER ::= { agentBscSwFileEntry 7 }
agentBscSwFileStatus OBJECT IDENTIFIER ::= { agentBscSwFileEntry 11 }
agentSNTP OBJECT IDENTIFIER ::= { agentGeneralMgmt 7 }
agentSNTPServer1IPAddr OBJECT IDENTIFIER ::= { agentSNTP 3 }
agentSNTPServer2IPAddr OBJECT IDENTIFIER ::= { agentSNTP 4 }
agentSwitchCommonMgmt OBJECT IDENTIFIER ::= { compaq-common-mgmt 3 }
agentSwitchFan OBJECT IDENTIFIER ::= { agentSwitchCommonMgmt 3 }
agentSwitchFanTable OBJECT IDENTIFIER ::= { agentSwitchFan 1 }
agentSwitchFanEntry OBJECT IDENTIFIER ::= { agentSwitchFanTable 1 }
agentSwitchFanIndex OBJECT IDENTIFIER ::= { agentSwitchFanEntry 1 }
agentSwitchFanCondition OBJECT IDENTIFIER ::= { agentSwitchFanEntry 2 }
agentSwitchTempSensor OBJECT IDENTIFIER ::= { agentSwitchCommonMgmt 4 }
agentSwitchTempSensorTable OBJECT IDENTIFIER ::= { agentSwitchTempSensor 1 }
agentSwitchTempSensorEntry OBJECT IDENTIFIER ::= { agentSwitchTempSensorTable 1 }
agentSwitchTempSensorIndex OBJECT IDENTIFIER ::= { agentSwitchTempSensorEntry 1 }
agentSwitchTempSensorCurrent OBJECT IDENTIFIER ::= { agentSwitchTempSensorEntry 2 }
agentSwitchTempSensorThreshold OBJECT IDENTIFIER ::= { agentSwitchTempSensorEntry 3 }
agentSwitchTempSensorCondition OBJECT IDENTIFIER ::= { agentSwitchTempSensorEntry 4 }
agentSwitchTempSensorTempType OBJECT IDENTIFIER ::= { agentSwitchTempSensorEntry 5 }
agentSwitchPowerSupply OBJECT IDENTIFIER ::= { agentSwitchCommonMgmt 2 }
agentSwitchPowerSupplyTable OBJECT IDENTIFIER ::= { agentSwitchPowerSupply 1 }
agentSwitchPowerSupplyEntry OBJECT IDENTIFIER ::= { agentSwitchPowerSupplyTable 1 }
agentSwitchPowerSupplyMaxPwrOutput OBJECT IDENTIFIER ::= { agentSwitchPowerSupplyEntry 2 }
agentSwitchPowerSupplyCurPwrOutput OBJECT IDENTIFIER ::= { agentSwitchPowerSupplyEntry 3 }
agentSwitchPowerSupplyIntakeTemp OBJECT IDENTIFIER ::= { agentSwitchPowerSupplyEntry 4 }
agentSwitchPowerSupplyExhaustTemp OBJECT IDENTIFIER ::= { agentSwitchPowerSupplyEntry 5 }
agentSwitchPowerSupplyStatus OBJECT IDENTIFIER ::= { agentSwitchPowerSupplyEntry 6 }
agentSwitchPowerSupplyInputLineStatus OBJECT IDENTIFIER ::= { agentSwitchPowerSupplyEntry 7 }
agentSwitchPowerSupplyCondition OBJECT IDENTIFIER ::= { agentSwitchPowerSupplyEntry 8 }
agentSwitchCube OBJECT IDENTIFIER ::= { agentSwitchCommonMgmt 1 }
agentSwitchCubeTable OBJECT IDENTIFIER ::= { agentSwitchCube 1 }
agentSwitchCubeEntry OBJECT IDENTIFIER ::= { agentSwitchCubeTable 1 }
agentSwitchCubeType OBJECT IDENTIFIER ::= { agentSwitchCubeEntry 1 }
agentSwitchCubeSpareName OBJECT IDENTIFIER ::= { agentSwitchCubeEntry 2 }
agentSwitchCubeSparePartNumber OBJECT IDENTIFIER ::= { agentSwitchCubeEntry 3 }
entityMIB OBJECT IDENTIFIER ::= { mib-2 47 }

entityMIBTraps OBJECT IDENTIFIER ::= { entityMIB 2 }

entityMIBTrapPrefix OBJECT IDENTIFIER ::= { entityMIBTraps 0 }

switchFanFailed TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, cpqRackNetConnectorSparePartNumber, agentSwitchFanIndex, agentSwitchFanCondition }
      --#SEVERITY CRITICAL
      --#TYPE "The switch fan has failed"
      --#CATEGORY "ProLiant BL p-Class GbE Interconnect Switch Events"
DESCRIPTION "The switch fan has failed."
      ::= 161006


switchPostSuccess TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, cpqRackNetConnectorSparePartNumber }
      --#SEVERITY MINOR
      --#TYPE "Successfully completed POST"
      --#CATEGORY "ProLiant BL p-Class GbE Interconnect Switch Events"
DESCRIPTION "The switch has successfully completed POST."
      ::= 161011


switchTFTPTransferFailed TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, agentBscSwFileAddr, agentBscSwFile, agentBscSwFileLoadType }
      --#SEVERITY MINOR
      --#TYPE "Failed a TFTP transfer"
      --#CATEGORY "ProLiant BL p-Class GbE Interconnect Switch Events"
DESCRIPTION "The switch has failed a TFTP transfer."
      ::= 161004


switchSNTPServiceUnavailable TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, agentSNTPServer1IPAddr, agentSNTPServer2IPAddr }
      --#SEVERITY MINOR
      --#TYPE "SNTP service unavailable"
      --#CATEGORY "ProLiant BL p-Class GbE Interconnect Switch Events"
DESCRIPTION "A SNTP Server was configured, but no SNTP servers were found.  This trap is sent once if SNTP is enabled,	 a SNTP server  is configured, and a SNTP server could not be contacted for  10minutes from the start time.  The start time will be defined  as when both SNTP was enabled and a SNTP server was configured  or when a SNTP server was contacted successfully."
      ::= 161015


switchFanOk TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, cpqRackNetConnectorSparePartNumber, agentSwitchFanIndex, agentSwitchFanCondition }
      --#SEVERITY INFORMATIONAL
      --#TYPE "The switch fan has returned to normal operation"
      --#CATEGORY "ProLiant BL p-Class GbE Interconnect Switch Events"
DESCRIPTION "The switch fan has returned to normal operation."
      ::= 161007


entConfigChange TRAP-TYPE
      ENTERPRISE entityMIBTrapPrefix
      --#SEVERITY INFORMATIONAL
      --#TYPE "Configuration Change Event"
      --#CATEGORY "ProLiant BL p-Class GbE Interconnect Switch Events"
DESCRIPTION "An entConfigChange notification is generated when the value of entLastChangeTime changes. It can be utilized by an NMS to trigger logical/physical entity table maintenance polls.  An agent should not generate more than one entConfigChange 'notification-event' in a given time interval (five seconds is the suggested default).  A 'notification-event' is the transmission of a single trap or inform PDU to a list of notification destinations.  If additional configuration changes occur within the throttling period, then notification-events for these changes should be suppressed by the agent until the current throttling period expires.  At the end of a throttling period, one notification-event should be generated if any configuration changes occurred since the start of the throttling period. In such a case, another throttling period is started right away.  An NMS should periodically check the value of entLastChangeTime to detect any missed entConfigChange notification-events, e.g., due to throttling or transmission loss."
      ::= 1


switchLoginFailure TRAP-TYPE
      ENTERPRISE compaq
      VARIABLES { cpqRackUid, cpqRackCommonEnclosureSerialNum, cpqRackNetConnectorSerialNum, cpqRackName, cpqRackCommonEnclosureName, cpqRackNetConnectorName, cpqRackNetConnectorLocation }
      --#SEVERITY MINOR
      --#TYPE "Rejected a login attempt"
      --#CATEGORY "ProLiant BL p-Class GbE Interconnect Switch Events"
DESCRIPTION "The switch has rejected a login attempt."
      ::= 161012


switchTempSensorFailed TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, cpqRackNetConnectorSparePartNumber, agentSwitchTempSensorIndex, agentSwitchTempSensorCurrent, agentSwitchTempSensorThreshold, agentSwitchTempSensorCondition, agentSwitchTempSensorTempType }
      --#SEVERITY CRITICAL
      --#TYPE "Over-temperature condition"
      --#CATEGORY "ProLiant BL p-Class GbE Interconnect Switch Events"
DESCRIPTION "The switch temperature sensor indicates an over-temperature condition."
      ::= 161009


switchTempSensorDegraded TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, cpqRackNetConnectorSparePartNumber, agentSwitchTempSensorIndex, agentSwitchTempSensorCurrent, agentSwitchTempSensorThreshold, agentSwitchTempSensorCondition, agentSwitchTempSensorTempType }
      --#SEVERITY MAJOR
      --#TYPE "High temperature condidtion"
      --#CATEGORY "ProLiant BL p-Class GbE Interconnect Switch Events"
DESCRIPTION "The switch temperature sensor indicates a high temperature condidtion."
      ::= 161008


switchTFTPTransferSucceeded TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, agentBscSwFileAddr, agentBscSwFile, agentBscSwFileLoadType }
      --#SEVERITY INFORMATIONAL
      --#TYPE "Successfully completed a TFTP transfer"
      --#CATEGORY "ProLiant BL p-Class GbE Interconnect Switch Events"
DESCRIPTION "The switch has successfully completed a TFTP transfer."
      ::= 161003


switchCubeTypeChange TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, cpqRackNetConnectorSparePartNumber, agentSwitchCubeType, agentSwitchCubeSpareName, agentSwitchCubeSparePartNumber }
      --#SEVERITY INFORMATIONAL
      --#TYPE "Switch cube type changed"
      --#CATEGORY "ProLiant BL p-Class GbE Interconnect Switch Events"
DESCRIPTION "Trap for connection different cube type.  Customer has changed the cube type since  the last boot. "
      ::= 161014


switchFirmwareTransferred TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, agentBscSwFileAddr, agentBscSwFile, agentBscSwFileLoadType, cpqRackNetConnectorFWRev }
      --#SEVERITY INFORMATIONAL
      --#TYPE "Successfully transferred a firmware image"
      --#CATEGORY "ProLiant BL p-Class GbE Interconnect Switch Events"
DESCRIPTION "The switch has successfully transferred a firmware image."
      ::= 161001


switchLocationChange TRAP-TYPE
      ENTERPRISE compaq
      VARIABLES { cpqRackUid, cpqRackCommonEnclosureSerialNum, cpqRackNetConnectorSerialNum, cpqRackName, cpqRackCommonEnclosureName, cpqRackNetConnectorName, cpqRackNetConnectorLocation }
      --#SEVERITY INFORMATIONAL
      --#TYPE "Switch location change"
      --#CATEGORY "ProLiant BL p-Class GbE Interconnect Switch Events"
DESCRIPTION "The switch location has changed.  The new location is defined in the variables. The  trap will be sent out on the next boot"
      ::= 161013


switchFileInvalid TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, agentBscSwFileAddr, agentBscSwFile, agentBscSwFileLoadType, agentBscSwFileStatus }
      --#SEVERITY MINOR
      --#TYPE "Invalid firmware or configuration image downloaded"
      --#CATEGORY "ProLiant BL p-Class GbE Interconnect Switch Events"
DESCRIPTION "Invalid firmware or configuration image downloaded."
      ::= 161005


switchConfigFileTransferred TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, agentBscSwFileAddr, agentBscSwFile, agentBscSwFileLoadType }
      --#SEVERITY INFORMATIONAL
      --#TYPE "Successfully transferred a configuration file"
      --#CATEGORY "ProLiant BL p-Class GbE Interconnect Switch Events"
DESCRIPTION "The switch has successfully transferred a configuration file."
      ::= 161002


switchTempSensorOk TRAP-TYPE
      ENTERPRISE compaq
      VARIABLES { cpqRackUid, cpqRackCommonEnclosureSerialNum, cpqRackNetConnectorSerialNum, cpqRackName, cpqRackCommonEnclosureName, cpqRackNetConnectorName, cpqRackNetConnectorLocation, cpqRackNetConnectorSparePartNumber, agentSwitchTempSensorIndex, agentSwitchTempSensorCurrent, agentSwitchTempSensorThreshold, agentSwitchTempSensorCondition, agentSwitchTempSensorTempType }
      --#SEVERITY INFORMATIONAL
      --#TYPE "Returned to Normal Temperature"
      --#CATEGORY "ProLiant BL p-Class GbE Interconnect Switch Events"
DESCRIPTION "The switch temperature sensor indicates temperature has returned to normal."
      ::= 161010


END
