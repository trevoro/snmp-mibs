XEDIA-PIM-MIB DEFINITIONS ::= BEGIN

IMPORTS
    MODULE-IDENTITY, OBJECT-TYPE
	  FROM SNMPv2-SMI
    xediaMibs
	FROM XEDIA-REG
    ;

xpimMIB MODULE-IDENTITY
    LAST-UPDATED "9904151600Z" -- April 15, 1999
    ORGANIZATION "Xedia Corp."
    CONTACT-INFO
          "support@xedia.com"
    DESCRIPTION
            "The Xedia extention MIB module for management of PIM routers."
    ::= { xediaMibs 31 }

xpimMIBObjects OBJECT IDENTIFIER ::= { xpimMIB 1 }

xpim           OBJECT IDENTIFIER ::= { xpimMIBObjects 1 }

xpimVersion OBJECT-TYPE
    SYNTAX	INTEGER (1..2)
    MAX-ACCESS  read-write
    STATUS	current
    DESCRIPTION
		"Select PIM protocol version."
    DEFVAL { 2 }
    ::= { xpim 1 }

xpimInterfaceTable OBJECT-TYPE
    SYNTAX     SEQUENCE OF XpimInterfaceEntry
    MAX-ACCESS not-accessible
    STATUS     current
    DESCRIPTION
            "The (conceptual) table listing the router's multicast-
            capable interfaces."
    ::= { xpim 2 }

xpimInterfaceEntry OBJECT-TYPE
    SYNTAX     XpimInterfaceEntry
    MAX-ACCESS not-accessible
    STATUS     current
    DESCRIPTION
            "An entry (conceptual row) in the pimInterfaceTable.  This
            row augments ipMRouteInterfaceEntry in the IP Multicast MIB,
            where the threshold object resides."

    INDEX      { xpimInterfaceIfIndex }
    ::= { xpimInterfaceTable 1 }

XpimInterfaceEntry ::= SEQUENCE {
    xpimInterfaceIfIndex      INTEGER,
    xpimInterfaceAdminStatus	INTEGER
}

xpimInterfaceIfIndex OBJECT-TYPE
    SYNTAX     INTEGER
    MAX-ACCESS not-accessible
    STATUS     current
    DESCRIPTION
            "The ifIndex value of the interface for which PIM is
            enabled."
    ::= { xpimInterfaceEntry 1 }

xpimInterfaceAdminStatus OBJECT-TYPE
    SYNTAX     INTEGER { enable(1), disable(2) }
    MAX-ACCESS read-create
    STATUS     current
    DESCRIPTION
            "The current adminstrative status of this PIM interface."
    ::= { xpimInterfaceEntry 2 }

END
