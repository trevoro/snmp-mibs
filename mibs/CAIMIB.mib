-- ********************************************************************
-- ********************************************************************
-- **      Copyright (c) 1994 Computer Associates International.     **
-- **                                                                **
-- **                                                                **
-- **                                                                **
-- ** Computer Associates Intl. retains the right to change this MIB **
-- ** without notification.                                          **
-- **                                                                **
-- **                                                                **
-- ** Author: Ven Subbarao                                           **
-- **                                                                **
-- ********************************************************************
-- ********************************************************************
-- ** Modification Log:                                              **
-- **                                                                **
-- ** MM/DD/YYYY USERID  :                                           **
-- **                                                                **
-- **                                                                **
-- ********************************************************************
-- ********************************************************************
--
-- --------------------------------------------------------------------
--  SCCS Module Control Stamp
-- --------------------------------------------------------------------
--
-- "@(#)cai.mib	1.1  12/27/94 09:49:01"
-- "Copyright (C) 1994 Computer Associates International, Inc.  All rights reserved."
--
-- --------------------------------------------------------------------

CAIMIB DEFINITIONS ::= BEGIN

--
-- The below statements import basic types from the relevant
-- definitions.
--


IMPORTS
	enterprises
		FROM RFC1155-SMI
 DisplayString
		FROM RFC1213-MIB
 TRAP-TYPE
  FROM RFC-1215
	OBJECT-TYPE
		FROM RFC-1212;

-- *******************************************************************
-- *******************************************************************
-- **                                                               **
-- ** Start the definition of CAI enterprise MIB.                   **
-- **                                                               **
-- *******************************************************************
-- *******************************************************************

cai         	OBJECT IDENTIFIER ::= { enterprises 791 }


-- *******************************************************************
-- *******************************************************************
-- **                                                               **
-- ** This is not a complete list and entries                       **
-- ** will be added on an as per need basis.                        **
-- **                                                               **
-- *******************************************************************
-- *******************************************************************

caiSysMgt    	  OBJECT IDENTIFIER ::= { cai           2 }
caiDbMgt     	  OBJECT IDENTIFIER ::= { cai           3 }
caiAppSft    	  OBJECT IDENTIFIER ::= { cai           4 }


-- *******************************************************************
-- *******************************************************************
-- **                                                               **
-- ** This level expands 'caiSysMgt' branch.                        **
-- **                                                               **
-- *******************************************************************
-- *******************************************************************

caiUnicenter OBJECT IDENTIFIER ::= { caiSysMgt   2 }


caiUniGenlvl OBJECT-TYPE
 SYNTAX DisplayString (SIZE(0..30))
 ACCESS read-only
 STATUS mandatory
 DESCRIPTION "This string displays the genlevel of the product."
 ::= { caiUnicenter   2 }


caiUniConfig OBJECT-TYPE
 SYNTAX DisplayString (SIZE(0..30))
 ACCESS read-only
 STATUS mandatory
 DESCRIPTION "This string displays under what configuration
              CA-Unicenter is running, i.e., Client/Server or
              just standalone
             "
 ::= { caiUnicenter   3 }


caiUniLicExp OBJECT-TYPE
 SYNTAX DisplayString (SIZE(0..30))
 ACCESS read-only
 STATUS mandatory
 DESCRIPTION "This string displays the license expiry date for
              the product.
             "
 ::= { caiUnicenter   4 }


caiUniLstMsg OBJECT-TYPE
 SYNTAX DisplayString (SIZE(0..256))
 ACCESS read-only
 STATUS mandatory
 DESCRIPTION "This string displays the last Event/Message which was
              received by the Event Manager. This object type is
              also used when defining TRAPs to send CA-Unicenter
              messages in a trap.
             "
 ::= { caiUnicenter   5 }


caiUniCltSrv OBJECT-TYPE
 SYNTAX INTEGER {
                 client(1),
                 server(2),
                 standalone(3)
                }
 ACCESS read-only
 STATUS mandatory
 DESCRIPTION "This integer value will tell the user if CA-Unicenter
              in the queried node is a client, server, or just a
              standalone.
             "
 ::= { caiUnicenter   6 }


caiUniStatTable OBJECT-TYPE
 SYNTAX SEQUENCE OF CaiUniStatEntry
 ACCESS not-accessible
 STATUS mandatory
 DESCRIPTION "This table will provide information about what
              components are active in CA-Unicenter.
             "
 ::= { caiUnicenter   7 }


caiUniStatEntry OBJECT-TYPE
SYNTAX CaiUniStatEntry
ACCESS not-accessible
STATUS mandatory
DESCRIPTION "This provides the list of entries for the above table."
INDEX { caiUniStatEntIdx }
::= { caiUniStatTable 2 }


CaiUniStatEntry ::=
 SEQUENCE {
           caiUniStatEntIdx INTEGER,
           caiUniStatComp   DisplayString
          }


caiUniStatEntIdx OBJECT-TYPE
SYNTAX INTEGER
ACCESS read-only
STATUS mandatory
DESCRIPTION "This provides the sequence/index number of a
             component being checked for status.
            "
::= { caiUniStatEntry 2 }

caiUniStatComp   OBJECT-TYPE
SYNTAX DisplayString  (SIZE(0..80))
ACCESS read-only
STATUS mandatory
DESCRIPTION "This provides the string that displays the status
             of a component being checked.
            "
::= { caiUniStatEntry 3 }


-- *******************************************************************
-- *******************************************************************
-- **                                                               **
-- ** Following defines the traps used by CA products.              **
-- ** Traps are defined using the conventions in RFC 1215.          **
-- ** Trap numbers are allocated as follows. If need be, they       **
-- ** can be expanded on an as per need basis.                      **
-- **                                                               **
-- ** 1-999  - Reserved for CA-Unicenter for Unix                   **
-- ** xxxxx  -                                                      **
-- ** xxxxx  -                                                      **
-- ** xxxxx  -                                                      **
-- **                                                               **
-- *******************************************************************
-- *******************************************************************

-- **************************************************************
-- * 1 thru 99 is reserved for Security related traps.          *
-- **************************************************************

caiUniSecuT1  TRAP-TYPE
	ENTERPRISE 	cai
 VARIABLES { caiUniLstMsg }
	DESCRIPTION "Reason: CAISSF resource check could not be evaluated
                      because the security daemon is not running.

              Action: Start the security daemon.

              Msgref: CASF_E_461
             "
	::= 1


caiUniSecuT2  TRAP-TYPE
	ENTERPRISE 	cai
 VARIABLES { caiUniLstMsg }
	DESCRIPTION "Reason: Access violation to an asset has occurred.

              Action: Appropriate permissions need to be granted.

              Msgref: CASF_E_465
             "
	::= 2

caiUniSecuT3  TRAP-TYPE
	ENTERPRISE 	cai
 VARIABLES { caiUniLstMsg }
	DESCRIPTION "Reason: Userid suspended for password violations.

              Action: Contact system administrator.

              Msgref: CASF_E_480
             "
	::= 3

caiUniSecuT4  TRAP-TYPE
	ENTERPRISE 	cai
 VARIABLES { caiUniLstMsg }
	DESCRIPTION "Reason: Userid suspended for rule violations.

              Action: Contact system administrator.

              Msgref: CASF_E_481
             "
	::= 4

caiUniSecuT5  TRAP-TYPE
	ENTERPRISE 	cai
 VARIABLES { caiUniLstMsg }
	DESCRIPTION "Reason: Password violation by user.

              Action: Enter another password.

              Msgref: CASF_E_482
             "
	::= 5

caiUniSecuT6  TRAP-TYPE
	ENTERPRISE 	cai
 VARIABLES { caiUniLstMsg }
	DESCRIPTION "Reason: The communications path between the security
                      engine's master daemon and one of its rule
                      evaluators has failed.

              Action: Verify the status of IPC facilities on your
                      system.

              Msgref: CA_SCTY_E_001
             "
	::= 6

caiUniSecuT7  TRAP-TYPE
	ENTERPRISE 	cai
 VARIABLES { caiUniLstMsg }
	DESCRIPTION "Reason: A communications error occurred when a rule
                      evaluator attempted to send a request back
                      to the security engine master daemon.

              Action: Verify the status of IPC facilities on your
                      system.

              Msgref: CA_SCTY_E_004
             "
	::= 7

caiUniSecuT8  TRAP-TYPE
	ENTERPRISE 	cai
 VARIABLES { caiUniLstMsg }
	DESCRIPTION "Reason: The security daemon has lost IPC with CAIENF
                      system.

              Action: Verify the status of IPC facilities on your
                      system.

              Msgref: CA_SCTY_E_034
             "
	::= 8


-- **************************************************************
-- * 100 thru 199 is reserved for Workload related traps.       *
-- **************************************************************


caiUniScheT1  TRAP-TYPE
	ENTERPRISE 	cai
 VARIABLES { caiUniLstMsg }
	DESCRIPTION "Reason: A Main Monitor function has encountered more
                      than ten consecutive CAICCI failures. This
                      message is a warning of possible network
                      problems.

              Action: Investigate CAICCI and network status.

              Msgref: CASH_W_0132
             "
	::= 100

caiUniScheT2  TRAP-TYPE
	ENTERPRISE 	cai
 VARIABLES { caiUniLstMsg }
	DESCRIPTION "Reason: Workload monitor attempted to submit a job,
                      but found that a required resource is not
                      defined in any global or station resource
                      table.

              Action: Either add the resource to a global or
                      station table, or remove the resource
                      requirement for the job.

              Msgref: CASH_E_0470
             "
	::= 101

caiUniScheT3  TRAP-TYPE
	ENTERPRISE 	cai
 VARIABLES { caiUniLstMsg }
	DESCRIPTION "Reason: Workload monitor received a failure record
                      from the CAIENF tracking function on a
                      specified node.

              Action: Review the logs SCHDEN2.nnnn and SCHDEN4.nnnn
                      to determine the cause of failure.

              Msgref: CASH_E_0471
             "
	::= 102

caiUniScheT4  TRAP-TYPE
	ENTERPRISE 	cai
 VARIABLES { caiUniLstMsg }
	DESCRIPTION "Reason: Workload remote tracking task discovered that
                      CAIENF is not active on the specified node.
                      This means that no tracking data is being
                      recorded on that node.

              Action: Start the CAIENF tracking task on this node.

              Msgref: CASH_W_0479
             "
	::= 103

caiUniScheT5  TRAP-TYPE
	ENTERPRISE 	cai
 VARIABLES { caiUniLstMsg }
	DESCRIPTION "Reason: An unauthorized user attempted to update either
                      the assigned user (SUBUser) or the submitted
                      file (SUBFile) field.

              Action: Contact your security administrator.

              Msgref: CASH_E_0492
             "
	::= 104

caiUniScheT6  TRAP-TYPE
	ENTERPRISE 	cai
 VARIABLES { caiUniLstMsg }
	DESCRIPTION "Reason: The main monitor tracking task has marked job
                      and its qualifier to have aborted at a specified
                      time and code.

              Action: Informational Message.

              Msgref: CASH_I_0062
             "
	::= 105

caiUniScheT7  TRAP-TYPE
	ENTERPRISE 	cai
 VARIABLES { caiUniLstMsg }
	DESCRIPTION "Reason: The main monitor tracking task has marked job
                      and its qualifier to have interrupted at a
                      specified time.

              Action: Informational Message.

              Msgref: CASH_I_0063
             "
	::= 106

caiUniScheT8  TRAP-TYPE
	ENTERPRISE 	cai
 VARIABLES { caiUniLstMsg }
	DESCRIPTION "Reason: The main monitor tracking task has marked job
                      and its qualifier to have purged at a
                      specified time.

              Action: Informational Message.

              Msgref: CASH_I_0065
             "
	::= 107

-- **************************************************************
-- * 200 thru 299 is reserved for GUI related traps.            *
-- **************************************************************

caiUniGuiT1  TRAP-TYPE
	ENTERPRISE 	cai
 VARIABLES { caiUniLstMsg }
	DESCRIPTION "Reason: The GUI main message router (CaMRouter) has
                      abnormally ended.

              Action: Use the uniclean command and then restart
                      the GUI main message router with the command
                      unistart gui.

              Msgref: CAMR_F_MAINROUTER
             "
	::= 200

-- **************************************************************
-- * 300 thru 399 is reserved for Tape related traps.           *
-- **************************************************************

caiUniTapeT1  TRAP-TYPE
	ENTERPRISE 	cai
 VARIABLES { caiUniLstMsg }
	DESCRIPTION "Reason: The volume serial number of the mounted tape
                      volume does not match the volume serial
                      number requested.

              Action: Mount the requested tape volume.

              Msgref: CAI_E_TMS011
             "
	::= 300

caiUniTapeT2  TRAP-TYPE
	ENTERPRISE 	cai
 VARIABLES { caiUniLstMsg }
	DESCRIPTION "Reason: A resident tape volume, whose volume serial
                      number matches the volume serial number requested,
                      was mounted in response to a request for a
                      nonresident tape.

              Action: Mount the nonresident tape volume.

              Msgref: CAI_E_TMS012
             "
	::= 301

caiUniTapeT3  TRAP-TYPE
	ENTERPRISE 	cai
 VARIABLES { caiUniLstMsg }
	DESCRIPTION "Reason: A nonresident tape volume was mounted in
                      response to a request for scratch tape.

              Action: Mount a resident scratch tape.

              Msgref: CAI_E_TMS013
             "
	::= 302

caiUniTapeT4  TRAP-TYPE
	ENTERPRISE 	cai
 VARIABLES { caiUniLstMsg }
	DESCRIPTION "Reason: The tape volume that was mounted in response
                      for a scratch tape has a nonblank LOCATION
                      in the corresponding volume definition in DB.

              Action: Mount a different scratch tape.

              Msgref: CAI_E_TMS014
             "
	::= 303

caiUniTapeT5  TRAP-TYPE
	ENTERPRISE 	cai
 VARIABLES { caiUniLstMsg }
	DESCRIPTION "Reason: The first 17 chars of the file name stored on
                      the tape's header HDR1 label do not match
                      those in the FILE17 field in the corresponding
                      volume definition.

              Action: Verify the labels.

              Msgref: CAI_E_TMS015
             "
	::= 304

caiUniTapeT6  TRAP-TYPE
	ENTERPRISE 	cai
 VARIABLES { caiUniLstMsg }
	DESCRIPTION "Reason: Either the tape volume mounted has a future
                      expiry date or it is not in scratch status.

              Action: Mount a valid scratch tape.

              Msgref: CAI_E_TMS016
             "
	::= 305

caiUniTapeT7  TRAP-TYPE
	ENTERPRISE 	cai
 VARIABLES { caiUniLstMsg }
	DESCRIPTION "Reason: Either the age threshold or error threshold
                      has been exceeded for the tape volume mounted,
                      causing the volume to be flagged as a bad tape
                      in the DB.

              Action: Mount a valid scratch tape.

              Msgref: CAI_E_TMS024
             "
	::= 306

caiUniTapeT8  TRAP-TYPE
	ENTERPRISE 	cai
 VARIABLES { caiUniLstMsg }
	DESCRIPTION "Reason: This user is not authorized to relabel tapes.

              Action: Contact CA-Unicenter security administrator.

              Msgref: CAI_E_TMS025
             "
	::= 307

caiUniTapeT9  TRAP-TYPE
	ENTERPRISE 	cai
 VARIABLES { caiUniLstMsg }
	DESCRIPTION "Reason: An attempt was made to initialize or mount a
                      tape volume that is defined to the Tape Mgmt
                      DB but is not in active service.

              Action: Use the CATAPE ACTIVE VOLUME control statement
                      to place the tape volume in active service.

              Msgref: CAI_E_TMS026
             "
	::= 308

-- **************************************************************
-- * 400 thru 499 is reserved for ASM related traps.            *
-- **************************************************************

caiUniAsmT1  TRAP-TYPE
	ENTERPRISE 	cai
 VARIABLES { caiUniLstMsg }
	DESCRIPTION "Reason: This message is issued when a medium does not
                      exist in the specified device for an MNTREQ
                      or SCRREQ.

              Action: Load the medium or specify another device which
                      has a medium.

              Msgref: CASM_E_NOTAPE
             "
	::= 400


caiUniAsmT2  TRAP-TYPE
	ENTERPRISE 	cai
 VARIABLES { caiUniLstMsg }
	DESCRIPTION "Reason: This message is issued when a medium is not
                      at loadpoint for an MNTREQ or SCRREQ.

              Action: Rewind or specify another device.

              Msgref: CASM_E_NOTATLP
             "
	::= 401


-- **************************************************************
-- * 500 thru 599 is reserved for CA90s related traps.          *
-- **************************************************************

caiUniCciT1  TRAP-TYPE
	ENTERPRISE 	cai
 VARIABLES { caiUniLstMsg }
	DESCRIPTION "Reason: CCI CA90s service has shut down.

              Action: Informational.

              Msgref: CAICCI_I_1003
             "
	::= 500

caiUniEnfT1  TRAP-TYPE
	ENTERPRISE 	cai
 VARIABLES { caiUniLstMsg }
	DESCRIPTION "Reason: ENF CA90s service has shut down.

              Action: Informational.

              Msgref: CAIENF_S_0036
             "
	::= 501


-- **************************************************************
--
-- Trap numbers in the range 30000 to 30999 are reserved for
-- user defined trap numbers.
--
-- **************************************************************

END
