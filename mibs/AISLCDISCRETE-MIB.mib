AISLCDISCRETE-MIB DEFINITIONS ::= BEGIN

IMPORTS
        MODULE-IDENTITY, OBJECT-TYPE, enterprises
                        FROM SNMPv2-SMI
        TruthValue, DisplayString
                        FROM SNMPv2-TC;

        PositiveInteger    ::= INTEGER (1..2147483647)

        aii OBJECT IDENTIFIER ::= {enterprises 539}

aiSLCDiscrete MODULE-IDENTITY
        LAST-UPDATED "0002181700Z"
        ORGANIZATION "Applied Innovation Inc."
        CONTACT-INFO "Engineering MIB Administrator
                      Postal: Applied Innovation Inc.
                              5800 Innovation Drive
                              Dublin, Ohio 43017-3271

                      Tel:    614-798-2000
                      Fax:    614-798-1770
                      Email:  snmp@aiinet.com"
        DESCRIPTION
                "MIB module for SLCs with discrete input and output points."
        ::= {aii 24}

--=========================================================================

aiSLCDiscreteInputTable OBJECT-TYPE
        SYNTAX          SEQUENCE OF AISLCDiscreteInputEntry
        MAX-ACCESS      not-accessible
        STATUS          current
        DESCRIPTION
                "Table of discrete input points indexed by point number.
                Includes description, configuration, and status information."
        ::= {aiSLCDiscrete 1}

aiSLCDiscreteInputEntry OBJECT-TYPE
        SYNTAX          AISLCDiscreteInputEntry
        MAX-ACCESS      not-accessible
        STATUS          current
        DESCRIPTION     "Entry of aiSLCDiscreteInputTable."
        INDEX           {aislcdinPointNumber}
        ::= {aiSLCDiscreteInputTable 1}

AISLCDiscreteInputEntry ::= SEQUENCE {
        aislcdinPointNumber             PositiveInteger,
        aislcdinDescription             DisplayString,
        aislcdinTrapEnable              INTEGER,
        aislcdinNormalInput             INTEGER,
        aislcdinAlarmSeverity           INTEGER,
        aislcdinNormalStateText         DisplayString,
        aislcdinAlarmStateText          DisplayString,
        aislcdinCurrentInput            INTEGER,
        aislcdinLastChangeTime          DisplayString,
        aislcdinCurrentState            INTEGER,
        aislcdinCurrentStateText        DisplayString,
        aislcdintl1AccessID             DisplayString,
        aislcdintl1Provisioned          TruthValue,
        aislcdintl1AccessIDType         INTEGER,
        aislcdintl1NotificationCode     INTEGER,
        aislcdintl1ServiceAffecting     INTEGER,
        aislcdintl1ConditionType        DisplayString,
        aislcdintl1ConditionDescription DisplayString,
        aislcdintl1AlarmType            DisplayString,
        aislcdintl1AlarmMessage         DisplayString,
        aislcdinDebounceValue           INTEGER
}

aislcdinPointNumber OBJECT-TYPE
        SYNTAX          PositiveInteger
        MAX-ACCESS      read-only
        STATUS          current
        DESCRIPTION     "Input point number to which this table row applies."
        ::= {aiSLCDiscreteInputEntry 1}

aislcdinDescription OBJECT-TYPE
        SYNTAX          DisplayString (SIZE (0..80))
        MAX-ACCESS      read-write
        STATUS          current
        DESCRIPTION
                "Textual description of the point.
                Maximum length is 80 characters."
        ::= {aiSLCDiscreteInputEntry 2}

aislcdinTrapEnable OBJECT-TYPE
        SYNTAX          INTEGER {enabled(1), disabled(2)}
        MAX-ACCESS      read-write
        STATUS          current
        DESCRIPTION     "Enable or disable alarm traps."
        ::= {aiSLCDiscreteInputEntry 3}

aislcdinNormalInput OBJECT-TYPE
        SYNTAX          INTEGER {open(1), closed(2)}
        MAX-ACCESS      read-write
        STATUS          current
        DESCRIPTION     "Input that corresponds to the point's normal state."
        ::= {aiSLCDiscreteInputEntry 4}

aislcdinAlarmSeverity OBJECT-TYPE
        SYNTAX          INTEGER {
                        critical(1),
                        major(2),
                        minor(3),
                        info(4),
                        notReported(5)
                        }
        MAX-ACCESS      read-write
        STATUS          current
        DESCRIPTION
                "Severity of the point's alarm state, or notReported(5)
                if the point does not generate an alarm."
        ::= {aiSLCDiscreteInputEntry 5}

aislcdinNormalStateText OBJECT-TYPE
        SYNTAX          DisplayString (SIZE (0..80))
        MAX-ACCESS      read-write
        STATUS          current
        DESCRIPTION
                "Textual description of the point's normal state.
                Maximum length is 80 characters."
        ::= {aiSLCDiscreteInputEntry 6}

aislcdinAlarmStateText OBJECT-TYPE
        SYNTAX          DisplayString (SIZE (0..80))
        MAX-ACCESS      read-write
        STATUS          current
        DESCRIPTION
                "Textual description of the point's alarm state.
                Maximum length is 80 characters."
        ::= {aiSLCDiscreteInputEntry 7}

aislcdinCurrentInput OBJECT-TYPE
        SYNTAX          INTEGER {open(1), closed(2)}
        MAX-ACCESS      read-only
        STATUS          current
        DESCRIPTION     "The current input to the point."
        ::= {aiSLCDiscreteInputEntry 8}

aislcdinLastChangeTime OBJECT-TYPE
        SYNTAX          DisplayString (SIZE (19..23))
        MAX-ACCESS      read-only
        STATUS          current
        DESCRIPTION
                "Textual representation of the time of the most recent
                input change.  24-hour format: YYYY-MM-DD HH:MM:SS."
        ::= {aiSLCDiscreteInputEntry 9}

aislcdinCurrentState OBJECT-TYPE
        SYNTAX          INTEGER {
                        critical(1),
                        major(2),
                        minor(3),
                        info(4),
                        normal(5)
                        }
        MAX-ACCESS      read-only
        STATUS          current
        DESCRIPTION     "The point's current alarm state, or normal(5)."
        ::= {aiSLCDiscreteInputEntry 10}

aislcdinCurrentStateText OBJECT-TYPE
        SYNTAX          DisplayString (SIZE (0..80))
        MAX-ACCESS      read-only
        STATUS          current
        DESCRIPTION
                "Textual description of the point's current state.
                This is either aislcdinNormalStateText or
                aislcdinAlarmStateText."
        ::= {aiSLCDiscreteInputEntry 11}

--====== TL1 Parameters for Discrete Input

aislcdintl1AccessID OBJECT-TYPE
        SYNTAX          DisplayString (SIZE (0..22))
        MAX-ACCESS      read-write
        STATUS          current
        DESCRIPTION
                "Unique TL1 access identifier for this point.
                Maximum length is 22 characters."
        ::= {aiSLCDiscreteInputEntry 12}

aislcdintl1Provisioned OBJECT-TYPE
        SYNTAX          TruthValue
        MAX-ACCESS      read-write
        STATUS          current
        DESCRIPTION     "Enable TL1 management of this point."
        ::= {aiSLCDiscreteInputEntry 13}

aislcdintl1AccessIDType OBJECT-TYPE
        SYNTAX          INTEGER {equipment(1), environmental(2)}
        MAX-ACCESS      read-write
        STATUS          current
        DESCRIPTION
                "Identifies the point as either an equipment(1) alarm condition
                or an environmental(2) alarm."
        ::= {aiSLCDiscreteInputEntry 14}

aislcdintl1NotificationCode OBJECT-TYPE
        SYNTAX          INTEGER {critical(1), major(2), minor(3)}
        MAX-ACCESS      read-write
        STATUS          current
        DESCRIPTION
                "Severity of the point's alarm state."
        ::= {aiSLCDiscreteInputEntry 15}

aislcdintl1ServiceAffecting OBJECT-TYPE
        SYNTAX          INTEGER {serviceAffecting(1), notServiceAffecting(2)}
        MAX-ACCESS      read-write
        STATUS          current
        DESCRIPTION
                "Indicates whether or not the alarm affects the functioning
                of the equipment.  This is only meaningful when
                aislcdintl1AccessIDType is equipment(1)."
        ::= {aiSLCDiscreteInputEntry 16}

aislcdintl1ConditionType OBJECT-TYPE
        SYNTAX          DisplayString (SIZE (0..20))
        MAX-ACCESS      read-write
        STATUS          current
        DESCRIPTION
                "String indicating the type of alarm condition, used
                only when aislcdintl1AccessIDType is equipment(1).
                Maximum length is 20 characters."
        ::= {aiSLCDiscreteInputEntry 17}

aislcdintl1ConditionDescription OBJECT-TYPE
        SYNTAX          DisplayString (SIZE (0..64))
        MAX-ACCESS      read-write
        STATUS          current
        DESCRIPTION
                "Textual description of the alarm condition, used only
                when aislcdintl1AccessIDType is equipment(1).
                Maximum length is 64 characters."
        ::= {aiSLCDiscreteInputEntry 18}

aislcdintl1AlarmType OBJECT-TYPE
        SYNTAX          DisplayString (SIZE (0..10))
        MAX-ACCESS      read-write
        STATUS          current
        DESCRIPTION
                "String indicating the type of alarm, used only
                when aislcdintl1AccessIDType is environmental(2).
                Maximum length is 10 characters."
        ::= {aiSLCDiscreteInputEntry 19}

aislcdintl1AlarmMessage OBJECT-TYPE
        SYNTAX          DisplayString (SIZE (0..40))
        MAX-ACCESS      read-write
        STATUS          current
        DESCRIPTION
                "Textual description of the alarm, used only when
                aislcdintl1AccessIDType is environmental(2).
                Maximum length is 40 characters."
        ::= {aiSLCDiscreteInputEntry 20}


--====== Debounce Value 

aislcdinDebounceValue OBJECT-TYPE
        SYNTAX          INTEGER (0..99)
        MAX-ACCESS      read-write
        STATUS          current
        DESCRIPTION     "Number of 100 msec intervals to wait
			for the input to stop bouncing."
        ::= {aiSLCDiscreteInputEntry 21}

--=========================================================================

aiSLCDiscreteOutputTable OBJECT-TYPE
        SYNTAX          SEQUENCE OF AISLCDiscreteOutputEntry
        MAX-ACCESS      not-accessible
        STATUS          current
        DESCRIPTION
                "Table of discrete input points indexed by point number.
                Includes description, configuration, and status information."
        ::= {aiSLCDiscrete 2}

aiSLCDiscreteOutputEntry OBJECT-TYPE
        SYNTAX          AISLCDiscreteOutputEntry
        MAX-ACCESS      not-accessible
        STATUS          current
        DESCRIPTION     "Entry of aiSLCDiscreteOutputTable."
        INDEX           {aislcdoutPointNumber}
        ::= {aiSLCDiscreteOutputTable 1}

AISLCDiscreteOutputEntry ::= SEQUENCE {
        aislcdoutPointNumber             PositiveInteger,
        aislcdoutDescription             DisplayString,
        aislcdoutOutputEnable            INTEGER,
        aislcdoutNormalOutput            INTEGER,
        aislcdoutMomentaryTimeout        INTEGER,
        aislcdoutCurrentOutput           INTEGER,
        aislcdouttl1AccessID             DisplayString,
        aislcdoutTrapEnable              INTEGER,
        aislcdoutAlarmStateOutput        INTEGER,
        aislcdoutAlarmSeverity           INTEGER,
        aislcdoutNonAlarmStateText       DisplayString,
        aislcdoutAlarmStateText          DisplayString,
        aislcdoutOutput                  INTEGER,
        aislcdoutLastChangeTime          DisplayString,
        aislcdoutCurrentState            INTEGER,
        aislcdoutCurrentStateText        DisplayString,
        aislcdoutEnergizeExpression      DisplayString
}

aislcdoutPointNumber OBJECT-TYPE
        SYNTAX          PositiveInteger
        MAX-ACCESS      read-only
        STATUS          current
        DESCRIPTION     "Output point number to which this table row applies."
        ::= {aiSLCDiscreteOutputEntry 1}

aislcdoutDescription OBJECT-TYPE
        SYNTAX          DisplayString (SIZE (0..80))
        MAX-ACCESS      read-write
        STATUS          current
        DESCRIPTION
                "Textual description of the point.
                Maximum length is 80 characters."
        ::= {aiSLCDiscreteOutputEntry 2}

aislcdoutOutputEnable OBJECT-TYPE
        SYNTAX          INTEGER {enabled(1), disabled(2)}
        MAX-ACCESS      read-write
        STATUS          current
        DESCRIPTION     "Enable or disable this point.  When the
                        point is disabled, the output is immediately
                        de-energized and remains so regardless of the
      values of other objects in this row.
      When the point is enabled, output is immediately
      set to its non-alarm state and operates according
      to the values of the other objects in this row."
        ::= {aiSLCDiscreteOutputEntry 3}

aislcdoutNormalOutput OBJECT-TYPE
        SYNTAX          INTEGER {relayOn(1), relayOff(2)}
        MAX-ACCESS      not-accessible
        STATUS          deprecated
        DESCRIPTION     "DEPRECATED: use aislcdoutAlarmStateOutput."
        ::= {aiSLCDiscreteOutputEntry 4}

aislcdoutMomentaryTimeout OBJECT-TYPE
        SYNTAX          INTEGER (0..999)
        UNITS           "0.1 second"
        MAX-ACCESS      read-write
        STATUS          current
        DESCRIPTION
                "If zero, the output will stay in the alarm state until
    it is returned to the normal state by some other event.
                If nonzero, this defines the time interval for
    momentary operation described in aislcdoutOutput.
                Maximum is 99.9 seconds."
        ::= {aiSLCDiscreteOutputEntry 5}

aislcdoutCurrentOutput OBJECT-TYPE
        SYNTAX          INTEGER {relayOn(1), relayOff(2)}
        MAX-ACCESS      not-accessible
        STATUS          deprecated
        DESCRIPTION     "DEPRECATED: use aislcdoutOutput."
        ::= {aiSLCDiscreteOutputEntry 6}

--====== TL1 Parameter for Discrete Output

aislcdouttl1AccessID OBJECT-TYPE
        SYNTAX          DisplayString (SIZE (0..22))
        MAX-ACCESS      read-write
        STATUS          current
        DESCRIPTION
                "Unique TL1 access identifier for this point.
                Maximum length is 22 characters."
        ::= {aiSLCDiscreteOutputEntry 7}

--====== end TL1 Parameter for Discrete Output

aislcdoutTrapEnable OBJECT-TYPE
        SYNTAX          INTEGER {enabled(1), disabled(2)}
        MAX-ACCESS      read-write
        STATUS          current
        DESCRIPTION     "Enable or disable traps.  If enabled, a trap
                        is sent whenever the point changes state."
        ::= {aiSLCDiscreteOutputEntry 8}

aislcdoutAlarmStateOutput OBJECT-TYPE
        SYNTAX          INTEGER {energized(1), de-energized(2)}
        MAX-ACCESS      read-write
        STATUS          current
        DESCRIPTION     "Output that corresponds to the point's alarm state."
        ::= {aiSLCDiscreteOutputEntry 9}

aislcdoutAlarmSeverity OBJECT-TYPE
        SYNTAX          INTEGER {
                        critical(1),
                        major(2),
                        minor(3),
                        info(4),
                        notReported(5)
                        }
        MAX-ACCESS      read-write
        STATUS          current
        DESCRIPTION
                "Severity of the point's alarm state, or notReported(5)
                if the point does not generate an alarm."
        ::= {aiSLCDiscreteOutputEntry 10}

aislcdoutNonAlarmStateText OBJECT-TYPE
        SYNTAX          DisplayString (SIZE (0..80))
        MAX-ACCESS      read-write
        STATUS          current
        DESCRIPTION
                "Textual description of the point's non-alarm state.
                Maximum length is 80 characters."
        ::= {aiSLCDiscreteOutputEntry 11}

aislcdoutAlarmStateText OBJECT-TYPE
        SYNTAX          DisplayString (SIZE (0..80))
        MAX-ACCESS      read-write
        STATUS          current
        DESCRIPTION
                "Textual description of the point's alarm state.
                Maximum length is 80 characters."
        ::= {aiSLCDiscreteOutputEntry 12}

aislcdoutOutput OBJECT-TYPE
        SYNTAX          INTEGER {energized(1), de-energized(2)}
        MAX-ACCESS      read-write
        STATUS          current
        DESCRIPTION     
      
      "On a read operation, this is the current output of the point.

      On a write operation when the output is controlled
      by aislcdoutEnergizeExpression, the write is rejected.

      Otherwise on a write operation, when set to
      de-energized, the output immediately assumes this
      state.  When set to energized, the state of the
      output goes to the energized state, unless the
      output is already waiting for its
      aislcdoutMomentaryTimeout interval to elapse."
        ::= {aiSLCDiscreteOutputEntry 13}

aislcdoutLastChangeTime OBJECT-TYPE
        SYNTAX          DisplayString (SIZE (19..23))
        MAX-ACCESS      read-only
        STATUS          current
        DESCRIPTION
                "Textual representation of the time of the most recent
                output change.  24-hour format: YYYY-MM-DD HH:MM:SS."
        ::= {aiSLCDiscreteOutputEntry 14}

aislcdoutCurrentState OBJECT-TYPE
        SYNTAX          INTEGER {
                        critical(1),
                        major(2),
                        minor(3),
                        info(4),
                        normal(5)
                        }
        MAX-ACCESS      read-only
        STATUS          current
        DESCRIPTION     "The point's current alarm state, or normal(5)."
        ::= {aiSLCDiscreteOutputEntry 15}

aislcdoutCurrentStateText OBJECT-TYPE
        SYNTAX          DisplayString (SIZE (0..80))
        MAX-ACCESS      read-only
        STATUS          current
        DESCRIPTION
                "Textual description of the point's current state.
                This is either aislcdoutNonAlarmStateText or
                aislcdoutAlarmStateText."
        ::= {aiSLCDiscreteOutputEntry 16}

aislcdoutEnergizeExpression OBJECT-TYPE
  SYNTAX    DisplayString (SIZE (0..128))
  MAX-ACCESS  read-write
  STATUS    current
  DESCRIPTION
    "String that describes when this output goes into the
    energized state, as a function of a discrete input (or
    analog input for AIscout2).

    For AIscout, an integer >= 1 represents a discrete 
    input, and '~' complements the input state.  

    For AIscout2, this expression is a combination of analog
    and discrete inputs.  Analog inputs are preceded by an 'A'
    and discrete inputs by a 'D'.  The complement '~' works
    on a group of inputs.  Also, multiple inputs may be specified 
    as a comma separated list (1,3,5) or a hyphenated range (1-5).
    The expression is a combination of up to three ORs and as many
    ANDs as desired (i.e. a sum of 3 products).

    An empty string indicates manual control of the output point. 

    AIscout examples:
        '15' -- energize the output when input 15 is alarmed
                (and deenergize when the input is normal).
        '~8' -- energize the output when input 8 is normal
                (and deenergize when the input is alarmed).

    AIscout2 examples:
    'AH1,3,5'    -- energize if the high alarm is active on analog
                    inputs 1, 3 and 5.
    '~AH1-2&AL3' -- energize if analog inputs 1 and 2 are normal
                    (not in the alarm state) AND analog input 3 is
                    in the low alarm state.
    'AH*|AL*|D*' -- energize if ANY analog is alarmed OR any 
                    discrete input is alarmed."
  ::= {aiSLCDiscreteOutputEntry 17}

--=========================================================================

aislcdiscPowerSupplyStatus OBJECT-TYPE
        SYNTAX          INTEGER {okay(1), trouble(2)}
        MAX-ACCESS      read-only
        STATUS          current
        DESCRIPTION
                "Status of the power supply.  okay(1) or trouble(2).
                When the SLC is booted, this indicates okay(1) until
                the software determines the correct status."
        ::= {aiSLCDiscrete 3}

--
-- This was 'aislcdisc48VSupplyAStatus', changed for Scout II
-- There is little or no risk in doing this since most folks use
-- the NUMBER not the NAME.
--
aislcdiscPowerSupplyAStatus OBJECT-TYPE
        SYNTAX          INTEGER {okay(1), underVoltage(2), overVoltage(3)}
        MAX-ACCESS      read-only
        STATUS          current
        DESCRIPTION
                "Status of the 'A' power supply."
        ::= {aiSLCDiscrete 4}

--
-- This was 'aislcdisc48VSupplyBStatus', changed for Scout II
-- There is little or no risk in doing this since most folks use
-- the NUMBER not the NAME.
--
aislcdiscPowerSupplyBStatus OBJECT-TYPE
        SYNTAX          INTEGER {okay(1), underVoltage(2), overVoltage(3)}
        MAX-ACCESS      read-only
        STATUS          current
        DESCRIPTION
                "Status of the 'B' power supply."
        ::= {aiSLCDiscrete 5}

aislcdiscFanStatus OBJECT-TYPE
        SYNTAX          INTEGER {okay(1), fail(2)}
        MAX-ACCESS      read-only
        STATUS          current
        DESCRIPTION
                "Status of the fan unit."
        ::= {aiSLCDiscrete 6}

aislcdisc5VPowerSupplyAStatus OBJECT-TYPE
        SYNTAX          INTEGER {okay(1), fail(2)}
        MAX-ACCESS      read-only
        STATUS          current
        DESCRIPTION
                "Status of the 'A' 5V power supply."
        ::= {aiSLCDiscrete 7}

aislcdisc5VPowerSupplyBStatus OBJECT-TYPE
        SYNTAX          INTEGER {okay(1), fail(2), notPresent(3)}
        MAX-ACCESS      read-only
        STATUS          current
        DESCRIPTION
                "Status of the 'B' 5V power supply."
        ::= {aiSLCDiscrete 8}

aislcdiscFiber1TransmitterStatus OBJECT-TYPE
        SYNTAX          INTEGER {okay(1), fail(2), notPresent(3)}
        MAX-ACCESS      read-only
        STATUS          current
        DESCRIPTION
                "Status of the first fiber port's transmitter."
        ::= {aiSLCDiscrete 9}

aislcdiscFiber2TransmitterStatus OBJECT-TYPE
        SYNTAX          INTEGER {okay(1), fail(2), notPresent(3)}
        MAX-ACCESS      read-only
        STATUS          current
        DESCRIPTION
                "Status of the second fiber port's transmitter."
        ::= {aiSLCDiscrete 10}

aislcdiscAnalogInputPowerSupplyStatus OBJECT-TYPE
        SYNTAX          INTEGER {okay(1), fail(2), notPresent(3)}
        MAX-ACCESS      read-only
        STATUS          current
        DESCRIPTION
                "Status of the analog input power supply fuse."
        ::= {aiSLCDiscrete 11}
--=========================================================================
END
