ENDRUNTECHNOLOGIES-MIB DEFINITIONS ::= BEGIN

IMPORTS
   MODULE-IDENTITY, OBJECT-TYPE, NOTIFICATION-TYPE,
   Counter32, enterprises                           FROM SNMPv2-SMI
   DisplayString                                    FROM SNMPv2-TC;

endRunTechnologiesMIB OBJECT IDENTIFIER ::= { enterprises 13827 }

endRunTechnologies MODULE-IDENTITY
   LAST-UPDATED
      "0208190000Z"
   ORGANIZATION
      "EndRun Technologies LLC"
   CONTACT-INFO
      "Technical Support 1-877-749-3878 snmpsupport@endruntechnologies.com"
   DESCRIPTION
      "EndRun Technologies Enterprise MIB"
                                  ::= { endRunTechnologiesMIB 0 }

-- Praecis Cntp Product Group

praecisCntp     OBJECT IDENTIFIER ::= { endRunTechnologiesMIB 1 }

cntp            OBJECT IDENTIFIER ::= { praecisCntp 0 }

cntptrap        OBJECT IDENTIFIER ::= { cntp 0 }

cdma            OBJECT IDENTIFIER ::= { praecisCntp 1 }

cdmatrap        OBJECT IDENTIFIER ::= { cdma 0 }

-- cntp branch of the Praecis Cntp subtree

cntpTrapLeapIndBitsChange NOTIFICATION-TYPE
   OBJECTS { cntpLeapIndBits }
   STATUS current
   DESCRIPTION
   "A cntpTrapNTPLeapIndBitsChange trap signifies that the value of the leap
   indicator bits contained in the NTP reply packets sent by the time server
   has changed.  The current value of these bits is contained in the included
   cntpLeapIndBits.  The decimal value of these bits ranges from 0 to 3:

   0   is the no fault, no leap warning condition
   1   is the no fault, leap second insertion warning condition
   2   is the no fault, leap second deletion warning condition
   3   is the unsynchronized, alarm condition"
   ::= { cntptrap 1 }

cntpTrapStratumChange NOTIFICATION-TYPE
   OBJECTS { cntpStratum }
   STATUS current
   DESCRIPTION
   "A cntpTrapStratumChange trap signifies that the value of the stratum
   field contained in the NTP reply packets sent by the time server
   has changed.  The current value is contained in the included
   variable, cntpStratum.  The decimal value of this field ranges from 1 to 16:

   1   is the synchronized, actively locked to the reference UTC source stratum
   11  is the synchronized, but flywheeling on the local real time clock stratum
   16  is the unsynchronized stratum level"
   ::= { cntptrap 2 }

cntpRxPkts OBJECT-TYPE
   SYNTAX Counter32
   MAX-ACCESS read-only
   STATUS current
   DESCRIPTION
   "Total number of NTP request packets received by the NTP daemon."
   ::= { cntp 1 }

cntpTxPkts OBJECT-TYPE
   SYNTAX Counter32
   MAX-ACCESS read-only
   STATUS current
   DESCRIPTION
   "Total number of NTP reply packets transmitted by the NTP daemon."
   ::= { cntp 2 }

cntpIgnoredPkts OBJECT-TYPE
   SYNTAX Counter32
   MAX-ACCESS read-only
   STATUS current
   DESCRIPTION
   "Total number of NTP request packets ignored by the NTP daemon."
   ::= { cntp 3 }

cntpDroppedPkts OBJECT-TYPE
   SYNTAX Counter32
   MAX-ACCESS read-only
   STATUS current
   DESCRIPTION
   "Total number of NTP request packets dropped by the NTP daemon."
   ::= { cntp 4 }

cntpAuthFail OBJECT-TYPE
   SYNTAX Counter32
   MAX-ACCESS read-only
   STATUS current
   DESCRIPTION
   "Total number of authentication failures detected by the NTP daemon."
   ::= { cntp 5 }

cntpTimeFigureOfMerit OBJECT-TYPE
   SYNTAX INTEGER
   {
      lessthan100us       (6),
      lessthan1ms         (7),
      lessthan10ms        (8),
      greaterthan10ms     (9)
   }
   MAX-ACCESS read-only
   STATUS current
   DESCRIPTION
   "The Time Figure of Merit (TFOM) value ranges from 4 to 9 and indicates the
   current estimate of the worst case time error.  It is a logarithmic scale,
   with each increment indicating a tenfold increase in the worst case time
   error boundaries.

   The scale is referenced to a worst case time error of 100 picoseconds,
   equivalent to a TFOM of zero.  During normal locked operation with CDMA
   the TFOM is 6 and implies a worst case time error of 100 microseconds.

   During periods of signal loss, the CDMA sub-system will compute an
   extrapolated worst case time error.  One hour after the worst case time error
   has reached the value equivalent to a TFOM of 9, the NTP server will cease
   to send stratum 1 reply packets and an Alarm LED will be energized."
   ::= { cntp 6 }

cntpLeapIndBits OBJECT-TYPE
   SYNTAX INTEGER
   {
      noFaultorLeap   (0),
      leapInsWarning  (1),
      leapDelWarning  (2),
      unSynchronized  (3)
   }
   MAX-ACCESS read-only
   STATUS current
   DESCRIPTION
   "This is a status code indicating:  normal operation, a leap second to
   be inserted in the last minute of the current day, a leap second to be
   deleted in the last second of the day or an alarm condition indicating
   loss of timing synchronization.  The leap indicator field of NTP reply
   packets sent from this server is set to cntpLeapIndBits."
   ::= { cntp 7 }

cntpSyncSource OBJECT-TYPE
   SYNTAX DisplayString (SIZE (0..4))
   MAX-ACCESS read-only
   STATUS current
   DESCRIPTION
   "This is an ASCII string identifying the synchronization source
   for this NTP server.  It is one of CDMA, CPU or NONE.  If it is NONE,
   then the server is not synchronized, has its Leap Indicator Bits in the Alarm
   state and is running at Stratum 16.  If it is CPU, then the server is
   free running on its NTP disciplined CPU clock at Stratum 11.

   Check the Stratum, Leap Indicator Bits and Time Figure of Merit for further
   information.  NTP reply packets from this server will have the reference
   identifier field set to cntpSyncSource if it is CDMA.  Otherwise
   it will be set to either 127.127.1.0 (CPU) or 0.0.0.0 (NONE)."
   ::= { cntp 8 }

cntpOffsetToCDMAReference OBJECT-TYPE
   SYNTAX DisplayString (SIZE (0..16))
   MAX-ACCESS read-only
   STATUS current
   DESCRIPTION
   "This is an ASCII string containing the floating value of the current
   offset in units of seconds of the NTP server CPU clock to the CDMA
   reference time.  Positive values imply that the NTP server clock is
   ahead of the CDMA reference time."
   ::= { cntp 9 }

cntpStratum OBJECT-TYPE
   SYNTAX INTEGER
   {
      cntpStratumOne  (1),
      cntpStratumFlywheeling (11),
      cntpStratumUnsync      (16)
   }
   MAX-ACCESS read-only
   STATUS current
   DESCRIPTION
   "This is an integer showing the current stratum level being reported by
   the NTP daemon in its reply packets to clients.  If it is 1, then the server
   is fully synchronized and delivering Stratum 1 accuracy.  If it is 16, then
   the server is unambiguously unsynchronized.

   If it is 11, and the previous stratum value was 1, then the server is
   flywheeling on the local CPU clock.  However, if the previous stratum value
   was 16, then the server has synchronized to its CPU Real Time Clock.

   NTP clients on the network should be configured to not use the time from
   this server if the stratum is not 1."
   ::= { cntp 10 }

cntpVersion OBJECT-TYPE
   SYNTAX DisplayString(SIZE(0..80))
   MAX-ACCESS read-only
   STATUS current
   DESCRIPTION
   "This is an ASCII string showing the NTP server firmware version."
   ::= { cntp 11 }

-- cdma branch of the Praecis Cntp subtree

cdmaTrapFaultStatusChange NOTIFICATION-TYPE
   OBJECTS { cdmaFaultStatus }
   STATUS current
   DESCRIPTION
   "A cdmaTrapFaultStatusChange trap signifies that the value of the fault
   status word reported by the CDMA sub-system has changed.  The current value
   is contained in the included cdmaFaultStatus."
   ::= { cdmatrap 1 }

cdmaFaultStatus OBJECT-TYPE
   SYNTAX BITS
   {
      cdmaNotUsed         (0),
      cdmaNTPNotPolling   (1),
      cdmaLOFailure       (2),
      cdmaLOPLLFlt        (3),
      cdmaFLASHWriteFlt   (4),
      cdmaFPGACfgFlt      (5),
      cdmaNoSignalTimeout (6),
      cdmaDACNearLimit    (7)
   }
   MAX-ACCESS read-only
   STATUS current
   DESCRIPTION
   "This is a bit string contained in one character representing the
   least significant two nibbles of the CDMA fault status word.  Unfortunately,
   SNMP numbers the bits in the reverse order, so that the enumerated values
   are backwards from the description contained in the User's Manual for the
   fault status field returned by the cdmastat command.  Each bit indicates
   a fault when set.  Currently defined fault states encoded in this value:

   Bit 7:    DAC controlling the TCXO is near the high or low limit.
   Bit 6:    Time Figure of Merit has been 9 (unsynchronized) for 1 hour.
   Bit 5:    Field Programmable Gate Array (FPGA) did not configure properly.
   Bit 4:    FLASH memory had a write fault.
   Bit 3:    Local Oscillator PLL fault.
   Bit 2:    Local Oscillator PLL failed.
   Bit 1:    NTP daemon is not polling the CDMA reference clock.
   Bit 0:    Not Used."
   ::= { cdma 1 }

cdmaTimeFigureOfMerit OBJECT-TYPE
   SYNTAX INTEGER
   {
      lessthan100us   (6),
      lessthan1ms     (7),
      lessthan10ms    (8),
      greaterthan10ms (9)
   }
   MAX-ACCESS read-only
   STATUS current
   DESCRIPTION
   "The Time Figure of Merit (TFOM) value ranges from 6 to 9 and indicates the
   current estimate of the worst case time error.  It is a logarithmic scale,
   with each increment indicating a tenfold increase in the worst case time
   error boundaries.  The scale is referenced to a worst case time error of
   100 picoseconds, equivalent to a TFOM of zero.  During normal locked
   operation the TFOM is 6 and implies a worst case time error of 100
   microseconds.

   During periods of signal loss, the CDMA sub-system will compute an
   extrapolated worst case time error.  One hour after the worst case time error
   has reached the value equivalent to a TFOM of 9, the NTP server will cease
   to send stratum 1 reply packets and an Alarm LED will be energized."
   ::= { cdma 2 }

cdmaSigProcState OBJECT-TYPE
   SYNTAX INTEGER
   {
      cdmaAcquiring       (0),
      cdmaDetected        (1),
      cdmaCodeLocking     (2),
      cdmaCarrierLocking  (4),
      cdmaLocked          (8)
   }
   MAX-ACCESS read-only
   STATUS current
   DESCRIPTION
   "Current CDMA signal processor state.  One of 0, 1, 2, 4 or 8, with 0
   indicating the acquisition state and 8 the fully locked on state."
   ::= { cdma 3 }

cdmaChannel OBJECT-TYPE
   SYNTAX INTEGER
   {
      priAbandclass0subclass0 (0),
      priBbandclass0subclass0 (1),
      secAbandclass0subclass0 (2),
      secBbandclass0subclass0 (3),
      priAbandclass0subclass1 (4),
      priBbandclass0subclass1 (5),
      secAbandclass0subclass1 (6),
      secBbandclass0subclass1 (7)
   }
   MAX-ACCESS read-only
   STATUS current
   DESCRIPTION
   "Current CDMA frequency band and channel being used.  Channels 0-3 are the
   North American cellular channels.  Channels 4-7 are the South Korean cellular
   channels."
   ::= { cdma 4 }

cdmaPNO OBJECT-TYPE
   SYNTAX INTEGER (0..511)
   MAX-ACCESS read-only
   STATUS current
   DESCRIPTION
   "Current Pseudo Noise Offset of the base station being tracked.  The value
   ranges from 0 to 511 and is in units of 64 Pseudo Noise Code chips.  This
   offset serves as a base station identifier that is analogous to the Pseudo
   Random Noise (PRN) codes used by the individual satellites in the GPS system."
   ::= { cdma 5 }

cdmaAGC OBJECT-TYPE
   SYNTAX INTEGER (0..255)
   MAX-ACCESS read-only
   STATUS current
   DESCRIPTION
   "Current 8 bit, Automatic Gain Control (AGC) DAC value.  Typical values
   are around 200, but proximity to the base station, type of building
   construction and orientation within the building have a strong influence on
   this value.  More positive values have the effect of increasing the RF gain."
   ::= { cdma 6 }

cdmaVCDAC OBJECT-TYPE
   SYNTAX INTEGER (0..65535)
   MAX-ACCESS read-only
   STATUS current
   DESCRIPTION
   "Current 16 bit, Voltage Controlled TCXO DAC value.  Typical range is 20000
   to 40000, where more positive numbers have the effect of raising the TCXO
   frequency."
   ::= { cdma 7 }

cdmaCarrierToNoiseRatio OBJECT-TYPE
   SYNTAX DisplayString (SIZE(0..4))
   MAX-ACCESS read-only
   STATUS current
   DESCRIPTION
   "ASCII string representing the current received CDMA signal carrier-to-noise
   ratio, a unitless quantity.  Numbers less than 2.5 indicate a very weak
   signal condition."
   ::= { cdma 8 }

cdmaFrameErrorRate OBJECT-TYPE
   SYNTAX DisplayString (SIZE(0..5))
   MAX-ACCESS read-only
   STATUS current
   DESCRIPTION
   "ASCII string representing the current sync channel message error rate,
   a number ranging from 0.000 to 1.000.  It indicates the proportion of
   messages received that fail the Cyclical Redundancy Check."
   ::= { cdma 9 }

cdmaLeapMode OBJECT-TYPE
   SYNTAX DisplayString (SIZE(0..80))
   MAX-ACCESS read-only
   STATUS current
   DESCRIPTION
   "ASCII string showing the current leap second mode of operation for the
   CDMA sub-system.  It is either AUTO or USER.  If the mode is USER, then the
   current and future values of the UTC to GPS leap second offset is also
   included."
   ::= { cdma 10 }

cdmaCurrentLeapSeconds OBJECT-TYPE
   SYNTAX INTEGER
   MAX-ACCESS read-only
   STATUS current
   DESCRIPTION
   "This value is the current difference in seconds between GPS time and UTC
   time.  GPS time is ahead of UTC time by this amount."
   ::= { cdma 11 }

cdmaFutureLeapSeconds OBJECT-TYPE
   SYNTAX INTEGER
   MAX-ACCESS read-only
   STATUS current
   DESCRIPTION
   "This value is the future difference in seconds between GPS time and UTC
   time.  Leap seconds may be inserted or deleted from the UTC timescale twice
   during the year:  Dec 31 and June 30 at UTC midnight.  If this value is the
   same as cdmaCurrentLeapSeconds, then no leap second insertion or deletion
   will occur at the next possible time.  If it is different, then the change
   will take affect at the next possible time.  GPS time will be ahead of UTC
   time by this amount."
   ::= { cdma 12 }

cdmaVersion OBJECT-TYPE
   SYNTAX DisplayString (SIZE(0..16))
   MAX-ACCESS read-only
   STATUS current
   DESCRIPTION
   "ASCII string showing the CDMA sub-system firmware and FPGA versions."
   ::= { cdma 13 }

-- Praecis Gntp Product Group

praecisGntp     OBJECT IDENTIFIER ::= { endRunTechnologiesMIB 2 }

gntp            OBJECT IDENTIFIER ::= { praecisGntp 0 }

gntptrap        OBJECT IDENTIFIER ::= { gntp 0 }

gps             OBJECT IDENTIFIER ::= { praecisGntp 1 }

gpstrap         OBJECT IDENTIFIER ::= { gps 0 }

-- gntp branch of the Praecis Gntp subtree

gntpTrapLeapIndBitsChange NOTIFICATION-TYPE
   OBJECTS { gntpLeapIndBits }
   STATUS current
   DESCRIPTION
   "A gntpTrapNTPLeapIndBitsChange trap signifies that the value of the leap
   indicator bits contained in the NTP reply packets sent by the time server
   has changed.  The current value of these bits is contained in the included
   gntpLeapIndBits.  The decimal value of these bits ranges from 0 to 3:

   0   is the no fault, no leap warning condition
   1   is the no fault, leap second insertion warning condition
   2   is the no fault, leap second deletion warning condition
   3   is the unsynchronized, alarm condition"
   ::= { gntptrap 1 }

gntpTrapStratumChange NOTIFICATION-TYPE
   OBJECTS { gntpStratum }
   STATUS current
   DESCRIPTION
   "A gntpTrapStratumChange trap signifies that the value of the stratum
   field contained in the NTP reply packets sent by the time server
   has changed.  The current value is contained in the included
   variable, gntpStratum.  The decimal value of this field ranges from 1 to 16:

   1   is the synchronized, actively locked to the reference UTC source stratum
   11  is the synchronized, but flywheeling on the local real time clock stratum
   16  is the unsynchronized stratum level"
   ::= { gntptrap 2 }

gntpRxPkts OBJECT-TYPE
   SYNTAX Counter32
   MAX-ACCESS read-only
   STATUS current
   DESCRIPTION
   "Total number of NTP request packets received by the NTP daemon."
   ::= { gntp 1 }

gntpTxPkts OBJECT-TYPE
   SYNTAX Counter32
   MAX-ACCESS read-only
   STATUS current
   DESCRIPTION
   "Total number of NTP reply packets transmitted by the NTP daemon."
   ::= { gntp 2 }

gntpIgnoredPkts OBJECT-TYPE
   SYNTAX Counter32
   MAX-ACCESS read-only
   STATUS current
   DESCRIPTION
   "Total number of NTP request packets ignored by the NTP daemon."
   ::= { gntp 3 }

gntpDroppedPkts OBJECT-TYPE
   SYNTAX Counter32
   MAX-ACCESS read-only
   STATUS current
   DESCRIPTION
   "Total number of NTP request packets dropped by the NTP daemon."
   ::= { gntp 4 }

gntpAuthFail OBJECT-TYPE
   SYNTAX Counter32
   MAX-ACCESS read-only
   STATUS current
   DESCRIPTION
   "Total number of authentication failures detected by the NTP daemon."
   ::= { gntp 5 }

gntpTimeFigureOfMerit OBJECT-TYPE
   SYNTAX INTEGER
   {
      lessthan1us         (4),
      lessthan10us        (5),
      lessthan100us       (6),
      lessthan1ms         (7),
      lessthan10ms        (8),
      greaterthan10ms     (9)
   }
   MAX-ACCESS read-only
   STATUS current
   DESCRIPTION
   "The Time Figure of Merit (TFOM) value ranges from 4 to 9 and indicates the
   current estimate of the worst case time error.  It is a logarithmic scale,
   with each increment indicating a tenfold increase in the worst case time
   error boundaries.

   The scale is referenced to a worst case time error of 100 picoseconds,
   equivalent to a TFOM of zero.  During normal locked operation with GPS the
   TFOM is 4 and implies a worst case time error of 1 microsecond.

   During periods of signal loss, the GPS sub-system will compute an
   extrapolated worst case time error.  One hour after the worst case time error
   has reached the value equivalent to a TFOM of 9, the NTP server will cease
   to send stratum 1 reply packets and an Alarm LED will be energized."
   ::= { gntp 6 }

gntpLeapIndBits OBJECT-TYPE
   SYNTAX INTEGER
   {
      noFaultorLeap   (0),
      leapInsWarning  (1),
      leapDelWarning  (2),
      unSynchronized  (3)
   }
   MAX-ACCESS read-only
   STATUS current
   DESCRIPTION
   "This is a status code indicating:  normal operation, a leap second to
   be inserted in the last minute of the current day, a leap second to be
   deleted in the last second of the day or an alarm condition indicating
   loss of timing synchronization.  The leap indicator field of NTP reply
   packets sent from this server is set to gntpLeapIndBits."
   ::= { gntp 7 }

gntpSyncSource OBJECT-TYPE
   SYNTAX DisplayString (SIZE (0..4))
   MAX-ACCESS read-only
   STATUS current
   DESCRIPTION
   "This is an ASCII string identifying the synchronization source
   for this NTP server.  It is one of GPS, CPU or NONE.  If it is NONE,
   then the server is not synchronized, has its Leap Indicator Bits in the Alarm
   state and is running at Stratum 16.  If it is CPU, then the server is
   running on its NTP disciplined CPU clock at Stratum 11.

   Check the Stratum, Leap Indicator Bits and Time Figure of Merit for further
   information.  NTP reply packets from this server will have the reference
   identifier field set to gntpSyncSource if it is GPS.  Otherwise
   it will be set to either 127.127.1.0 (CPU) or 0.0.0.0 (NONE)."
   ::= { gntp 8 }

gntpOffsetToGPSReference OBJECT-TYPE
   SYNTAX DisplayString (SIZE (0..16))
   MAX-ACCESS read-only
   STATUS current
   DESCRIPTION
   "This is an ASCII string containing the floating value of the current
   offset in units of seconds of the NTP server CPU clock to the GPS
   reference time.  Positive values imply that the NTP server clock is
   ahead of the GPS reference time."
   ::= { gntp 9 }

gntpStratum OBJECT-TYPE
   SYNTAX INTEGER
   {
      gntpStratumOne  (1),
      gntpStratumFlywheeling (11),
      gntpStratumUnsync      (16)
   }
   MAX-ACCESS read-only
   STATUS current
   DESCRIPTION
   "This is an integer showing the current stratum level being reported by
   the NTP daemon in its reply packets to clients.  If it is 1, then the server
   is fully synchronized and delivering Stratum 1 accuracy.  If it is 16, then
   the server is unambiguously unsynchronized.

   If it is 11, and the previous stratum value was 1, then the server is
   flywheeling on the local CPU clock.  However, if the previous stratum value
   was 16, then the server has synchronized to its CPU Real Time Clock.

   NTP clients on the network should be configured to not use the time from
   this server if the stratum is not 1."
   ::= { gntp 10 }

gntpVersion OBJECT-TYPE
   SYNTAX DisplayString(SIZE(0..80))
   MAX-ACCESS read-only
   STATUS current
   DESCRIPTION
   "This is an ASCII string showing the NTP server firmware version."
   ::= { gntp 11 }

-- gps branch of the Praecis Gntp subtree

gpsTrapFaultStatusChange NOTIFICATION-TYPE
   OBJECTS { gpsFaultStatus }
   STATUS current
   DESCRIPTION
   "A gpsTrapFaultStatusChange trap signifies that the value of the fault status
   word reported by the GPS sub-system has changed.  The current value is
   contained in the included gpsFaultStatus."
   ::= { gpstrap 1 }

gpsFaultStatus OBJECT-TYPE
   SYNTAX BITS
   {
      gpsAntennaFlt      (0),
      gpsNTPNotPolling   (1),
      gpsnotused0        (2),
      gpsnotused1        (3),
      gpsFLASHWriteFlt   (4),
      gpsFPGACfgFlt      (5),
      gpsNoSignalTimeout (6),
      gpsDACNearLimit    (7)
   }
   MAX-ACCESS read-only
   STATUS current
   DESCRIPTION
   "This is a bit string contained in one character representing the
   least significant two nibbles of the GPS fault status word.  Unfortunately,
   SNMP numbers the bits in the reverse order, so that the enumerated values
   are backwards from the description contained in the User's Manual for the
   fault status field returned by the gpsstat command.  Each bit indicates
   a fault when set.  Currently defined fault states encoded in this value:

   Bit 7:    DAC controlling the TCXO is near the high or low limit.
   Bit 6:    Time Figure of Merit has been 9 (unsynchronized) for 1 hour.
   Bit 5:    Field Programmable Gate Array (FPGA) did not configure properly.
   Bit 4:    FLASH memory had a write fault.
   Bit 3:    Not Used.
   Bit 2:    Not Used.
   Bit 1:    NTP daemon is not polling the GPS reference clock.
   Bit 0:    GPS antenna or feedline is shorted or open."
   ::= { gps 1 }

gpsTimeFigureOfMerit OBJECT-TYPE
   SYNTAX INTEGER
   {
      lessthan1us         (4),
      lessthan10us        (5),
      lessthan100us       (6),
      lessthan1ms         (7),
      lessthan10ms        (8),
      greaterthan10ms     (9)
   }
   MAX-ACCESS read-only
   STATUS current
   DESCRIPTION
   "The Time Figure of Merit (TFOM) value ranges from 4 to 9 and indicates
   the current estimate of the worst case time error.  It is a logarithmic
   scale, with each increment indicating a tenfold increase in the worst case
   time error boundaries.  The scale is referenced to a worst case time error
   of 100 picoseconds, equivalent to a TFOM of zero.  During normal locked
   operation the TFOM is 4 and implies a worst case time error of 1 microsecond.

   During periods of signal loss, the GPS sub-system will compute an
   extrapolated worst case time error.  One hour after the worst case time error
   has reached the value equivalent to a TFOM of 9, the NTP server will cease
   to send stratum 1 reply packets and an Alarm LED will be energized."
   ::= { gps 2 }

gpsSigProcState OBJECT-TYPE
   SYNTAX INTEGER
   {
      gpsAcquiring (0),
      gpsLocking   (1),
      gpsLocked    (2)
   }
   MAX-ACCESS read-only
   STATUS current
   DESCRIPTION
   "Current GPS signal processor state.  One of 0, 1 or 2, with 0 being the
   acquisition state and 2 the fully locked on state."
   ::= { gps 3 }

gpsNumTrackSats OBJECT-TYPE
   SYNTAX INTEGER (0..8)
   MAX-ACCESS read-only
   STATUS current
   DESCRIPTION
   "Current number of GPS satellites being tracked."
   ::= { gps 4 }

gpsVCDAC OBJECT-TYPE
   SYNTAX INTEGER (0..65535)
   MAX-ACCESS read-only
   STATUS current
   DESCRIPTION
   "Current 16 bit, Voltage Controlled TCXO DAC value.  Typical range is 20000
   to 40000, where more positive numbers have the effect of raising the TCXO
   frequency."
   ::= { gps 5 }

gpsAvgCarrierToNoiseRatiodB OBJECT-TYPE
   SYNTAX DisplayString (SIZE(0..4))
   MAX-ACCESS read-only
   STATUS current
   DESCRIPTION
   "ASCII string representing the current average carrier to noise ratio of all
   tracked satellites, in units of dB.  Values less than 35 indicate weak
   signal conditions."
   ::= { gps 6 }

gpsReferencePosition OBJECT-TYPE
   SYNTAX DisplayString (SIZE(0..80))
   MAX-ACCESS read-only
   STATUS current
   DESCRIPTION
   "WGS-84 latitude, longitude and height above the reference ellipsoid of the
   GPS antenna.  Ellipsoid height may deviate from local Mean Sea Level by as
   much as 100 meters."
   ::= { gps 7 }

gpsRefPosSource OBJECT-TYPE
   SYNTAX DisplayString(SIZE(0..3))
   MAX-ACCESS read-only
   STATUS current
   DESCRIPTION
   "ASCII string indicating the source of the GPS antenna reference position.
   It is one of:
   USR (user supplied),
   AVG (automatically determined by averaging thousands of 3-D position fixes,
   UNK (unknown)."
   ::= { gps 8 }

gpsCurrentLeapSeconds OBJECT-TYPE
   SYNTAX INTEGER
   MAX-ACCESS read-only
   STATUS current
   DESCRIPTION
   "This value is the current difference in seconds between GPS time and UTC
   time.  GPS time is ahead of UTC time by this amount."
   ::= { gps 9 }

gpsFutureLeapSeconds OBJECT-TYPE
   SYNTAX INTEGER
   MAX-ACCESS read-only
   STATUS current
   DESCRIPTION
   "This value is the future difference in seconds between GPS time and UTC
   time.  Leap seconds may be inserted or deleted from the UTC timescale twice
   during the year:  Dec 31 and June 30 at UTC midnight.  If this value is the
   same as cdmaCurrentLeapSeconds, then no leap second insertion or deletion
   will occur at the next possible time.  If it is different, then the change
   will take affect at the next possible time.  GPS time will be ahead of UTC
   time by this amount."
   ::= { gps 10 }

gpsVersion OBJECT-TYPE
   SYNTAX DisplayString(SIZE(0..16))
   MAX-ACCESS read-only
   STATUS current
   DESCRIPTION
   "ASCII string showing the GPS sub-system firmware and FPGA versions."
   ::= { gps 11 }

END
