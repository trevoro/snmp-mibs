-- extracted from draft-ietf-ion-scsp-mib-00.txt
-- at Mon Nov 15 17:11:08 1999

   SCSP-MIB DEFINITIONS ::= BEGIN

   IMPORTS
       MODULE-IDENTITY, OBJECT-TYPE, NOTIFICATION-TYPE,
       experimental, Integer32, IpAddress, Counter32
          FROM SNMPv2-SMI
       TEXTUAL-CONVENTION, RowStatus
          FROM SNMPv2-TC
       MODULE-COMPLIANCE, OBJECT-GROUP
          FROM SNMPv2-CONF
       ;



   scspMIB MODULE-IDENTITY
      LAST-UPDATED "9808200000Z" -- October 10, 1998
      ORGANIZATION "IETF Internetworking Over NBMA Working Group (ion)"
      CONTACT-INFO
          "Jim Luciani (luciani@BayNetworks.com)
           Bay Networks

           Cliff X. Wang (cliff_wang@vnet.ibm.com)
           Colin Verrilli (verrilli@vnet.ibm.com)
           IBM Corp."

      DESCRIPTION
           "This module defines a portion of the management
            information base (MIB) for managing Server Cache
            Synchronization protocols entities."
      ::= { experimental 2001 }
          -- Need to get an "official" experimental number from IANA


   -- *****************************************************************

   --   Textual Conversion

   -- *****************************************************************


   ScspPIDType ::= TEXTUAL-CONVENTION
       STATUS         current
       DESCRIPTION
            "The protocol type associated with a SCSP instance."
       SYNTAX         INTEGER {
                          atmarp(1),
                          nhrp(2),
                          mars(3),
                          dhcp(4),
                          lnni(5)
                      }


      ScspHFSMStateType ::= TEXTUAL-CONVENTION
          STATUS         current
          DESCRIPTION
                "The various states of the Hello Finite State Machine."
          SYNTAX         INTEGER {
                             down(1),
                             waiting(2),
                             uniConn(3),
                             biConn(4)
                         }

     ScspCAFSMStateType ::= TEXTUAL-CONVENTION
       STATUS         current
       DESCRIPTION
              "The various states of the Cache Alignment Finite
               State Machine."
       SYNTAX         INTEGER {
                          down(1),
                          msNego(2),
                          cacheSumm(3),
                          cacheUpdate(4),
                          aligned(5)
                      }



      SCSPVPIInteger ::= TEXTUAL-CONVENTION
         STATUS     current
         DESCRIPTION
             "An integer large enough to contain the value of a VPI."
         SYNTAX     Integer32 (0..255)

      SCSPVCIInteger ::= TEXTUAL-CONVENTION
         STATUS     current
         DESCRIPTION
             "An integer large enough to contain the value of a VCI."
         SYNTAX     Integer32 (0..65535)



   -- *****************************************************************
   --  Top Level structure of the SCSP MIB

   -- *****************************************************************


   scspObjects        OBJECT IDENTIFIER ::= { scspMIB 1}
   scspNotifications  OBJECT IDENTIFIER ::= { scspMIB 2} 
   scspConformance    OBJECT IDENTIFIER ::= { scspMIB 3}

   -- *****************************************************************

   --   SCSP MIB Objects

   -- *****************************************************************



   -- *****************************************************************

   --   SCSP Server Group Objects

   -- *****************************************************************



   scspServerGroupTable OBJECT-TYPE
       SYNTAX   SEQUENCE OF ScspServerGroupEntry
       MAX-ACCESS  not-accessible
       STATUS   current
       DESCRIPTION
             "The objects defined in this table are used to for the
              management of server groups. There is one entry in this
              table for each server group."
       ::= { scspObjects 1}


   scspServerGroupEntry OBJECT-TYPE
       SYNTAX   ScspServerGroupEntry
       MAX-ACCESS  not-accessible
       STATUS   current
       DESCRIPTION
             "Each entry contains attributes associated with a scsp
              server group."
       INDEX {scspServerGroupID, scspServerGroupPID }
       ::= { scspServerGroupTable 1}


   ScspServerGroupEntry ::= SEQUENCE {
       scspServerGroupID                  Integer32,
       scspServerGroupPID                 ScspPIDType,
       scspServerGroupRowStatus           RowStatus}


   scspServerGroupID  OBJECT-TYPE
       SYNTAX   Integer32 (0..65535)
       MAX-ACCESS  not-accessible
       STATUS   current
       DESCRIPTION
             "This is the Group ID of this SCSP server group instance."
       ::= { scspServerGroupEntry 1 }


   scspServerGroupPID  OBJECT-TYPE
       SYNTAX     ScspPIDType
       MAX-ACCESS  not-accessible
       STATUS   current
       DESCRIPTION
             "This is the protocol ID of this SCSP server group
              instance."
       ::= { scspServerGroupEntry 2 }



   scspServerGroupRowStatus  OBJECT-TYPE
       SYNTAX   RowStatus
       MAX-ACCESS  read-create
       STATUS   current
       DESCRIPTION
             "This object allows entries to be created and deleted
              from the scspServerGroupTable. This table is closely
              coupled with the scspLSTable, scspDCSTable, and the
              corresponding protocol dependent tables. A new row
              creation in this table results in creation of
              corresponding entries in the scspLSTable and scspDCSTable.
              In addition, entries in appropriate protocol dependent
              table may also be added. When the scspServerRowStatus is
              deleted by setting this object to destroy(6), this results
              in removing corresponding entries in scspLSTable,
              scspDCSTable, and those in corresponding protocol
              dependent table."
       REFERENCE
             "RFC 1903, 'Textual Conventions for version 2 of the
              Simple Network Management Protocol (SNMPv2).'"
       ::= { scspServerGroupEntry 3 }

   -- *****************************************************************

   --     SCSP LS Objects

   -- *****************************************************************

   scspLSTable OBJECT-TYPE
       SYNTAX   SEQUENCE OF ScspLSEntry
       MAX-ACCESS  not-accessible
       STATUS   current
       DESCRIPTION
             "The objects defined in this table are for the
              management of SCSP local server (LS)."
       ::= { scspObjects 2}


   scspLSEntry OBJECT-TYPE
       SYNTAX   ScspLSEntry
       MAX-ACCESS  not-accessible
       STATUS   current
       DESCRIPTION
             "Information about the Local Server in a SCSP group. Each
              entry contains attributes associated a LS."
       INDEX {scspServerGroupID,
              scspServerGroupPID,
              scspLSID
             }
       ::= { scspLSTable 1}


   ScspLSEntry ::= SEQUENCE {
       scspLSID                          OCTET STRING(SIZE(0..63)),
       scspLSHelloInterval               Integer32,
       scspLSDeadFactor                  Integer32,
       scspLSCAReXmInterval              Integer32,
       scspLSCSUSReXmtInterval           Integer32,
       scspLSCSUReXmtInterval            Integer32,
       scspLSCSAMaxReXmt                 Integer32,
       scspLSRowStatus                   RowStatus
       }



   scspLSID  OBJECT-TYPE
       SYNTAX   OCTET STRING(SIZE(0..63))
       MAX-ACCESS  not-accessible
       STATUS   current
       DESCRIPTION
             "This is the Local Server ID of this Local Server."
       ::= { scspLSEntry 1 }


   scspLSHelloInterval  OBJECT-TYPE
       SYNTAX   Integer32 (0..65535)
       MAX-ACCESS  read-create
       STATUS   current
       DESCRIPTION
             "This object contains the value for HelloInterval for
              the Local Server. It is the time (in seconds) between
              sending of consecutive Hello messages from this server."
       REFERENCE
             "SCSP draft, Section 2.1"
      ::= { scspLSEntry 2 }


   scspLSDeadFactor  OBJECT-TYPE
       SYNTAX   Integer32 (0..65535)
       MAX-ACCESS  read-create
       STATUS   current
       DESCRIPTION
             "This object contains the value for DeadFactor. The
              DeadFactor along with HelloInterval are sent with
              outgoing 'Hello' messages. If the DCS does not
              received 'Hello' message from this LS within the
              time out interval 'HelloInterval*DeadFactor'
              (in seconds), then the DCS MUST consider the LS to
              be stalled."
       REFERENCE
             "SCSP draft, Section 2.1"
       ::= { scspLSEntry 3 }


   scspLSCAReXmInterval  OBJECT-TYPE
       SYNTAX   Integer32 (0..65535)
       MAX-ACCESS  read-create
       STATUS   current
       DESCRIPTION
             "The time out interval (in seconds) for re-sending CA
               message to the DCS if no response is received."
       ::= { scspLSEntry 4 }


   scspLSCSUSReXmtInterval  OBJECT-TYPE
       SYNTAX   Integer32 (0..65535)
       MAX-ACCESS  read-create
       STATUS   current
       DESCRIPTION
             "The time out interval (in seconds) for re-sending
              CSUS Request to the DCS if not all CSA Records
              corresponding to the CSAS records in the CSUS
              message have been received."
       ::= { scspLSEntry  5 }


   scspLSCSUReXmtInterval  OBJECT-TYPE
       SYNTAX   Integer32 (0..65535)
       MAX-ACCESS  read-create
       STATUS   current
       DESCRIPTION
             "The time out interval (in seconds) for re-sending CSU
              Request to the DCS if not all CSA Records corresponding
              to the CSU request have not been acknowledged."
       ::= { scspLSEntry  6 }


   scspLSCSAMaxReXmt  OBJECT-TYPE
       SYNTAX   Integer32 (0..65535)
       MAX-ACCESS  read-create
       STATUS   current
       DESCRIPTION
             "The maximum number of retransmission of a CSA record.
              If acknowledge fails to occur when the maximum number
              is reached, an 'abnormal event' has happened between
              the LS/DCS link."
       ::= { scspLSEntry 7 }


   scspLSRowStatus  OBJECT-TYPE
       SYNTAX   RowStatus
       MAX-ACCESS  read-create
       STATUS   current
       DESCRIPTION
             "This object allows entries to be created and deleted
              from the scspLSTable. This table is closely coupled
              with DCS table and its corresponding protocol dependent
              tables. A new row creation in this table results
              in creation of new rows in the DCS table for each of
              its configured DCSs (peer servers). In addition,
              entries are created in the appropriate protocol
              dependent tables.  When the scspServerRowStatus is
              deleted by setting this object to destroy(6), this
              results in removing the corresponding entries in
              the DCS table of the same Server Group. In addition,
              entries in the corresponding protocol dependent table
              will also be removed."
       REFERENCE
             "RFC 1903."
       ::= { scspLSEntry 8 }



   -- *****************************************************************

   --     SCSP DCS Objects

   -- *****************************************************************

   scspDCSTable OBJECT-TYPE
       SYNTAX   SEQUENCE OF ScspDCSEntry
       MAX-ACCESS  not-accessible
       STATUS   current
       DESCRIPTION
             "The objects defined in this table are used for the
              management of the DCS session between the LS and DCS."
       ::= { scspObjects 3}


   scspDCSEntry OBJECT-TYPE
       SYNTAX   ScspDCSEntry
       MAX-ACCESS  not-accessible
       STATUS   current
       DESCRIPTION
             "Information about each DCS session between the LS and
              its DCSs. The table is indexed by scspServerGroupID,
              scspServerGroupPID, and scspDCSID."
       INDEX { scspServerGroupID,
               scspServerGroupPID,
               scspDCSID
              }
       ::= { scspDCSTable 1}

   ScspDCSEntry ::= SEQUENCE {
       scspDCSID                       OCTET STRING(SIZE(0..63)),
       scspDCSCAFSMState               ScspCAFSMStateType,
       scspDCSCASequence               Integer32,
       scspDCSCAIn                     Counter32,
       scspDCSCAOut                    Counter32,
       scspDCSCAInvalidIn              Counter32,
       scspDCSCADuplicateIn            Counter32,
       scspDCSMSState                  INTEGER,
       scspDCSCSUSIn                   Counter32,
       scspDCSCSUSOut                  Counter32,
       scspDCSCSUSInvalidIn        Counter32,
       scspDCSCSURequestIn             Counter32,
       scspDCSCSURequestOut            Counter32,
       scspDCSCSUReplyOut              Counter32,
       scspDCSCSUReplyIn               Counter32,
       scspDCSCSUInvalidRequestIn      Counter32,
       scspDCSCSUInvalidReplyIn        Counter32,
       scspDCSCSAIn                    Counter32,
       scspDCSCSAOut                   Counter32,
       scspDCSCSAReXmted               Counter32,
       scspDCSCSAReXmtQDepth           Integer32,
       scspDCSRowStatus                RowStatus }




   scspDCSID  OBJECT-TYPE
       SYNTAX   OCTET STRING(SIZE(0..63))
       MAX-ACCESS  not-accessible
       STATUS   current
       DESCRIPTION
             "This ID is used to identify a directly connected
              server(DCS)."
       ::= { scspDCSEntry 1 }

   scspDCSCAFSMState  OBJECT-TYPE
       SYNTAX   ScspCAFSMStateType
       MAX-ACCESS  read-only
       STATUS   current
       DESCRIPTION
             "The current state of the Cache Alignment Finite State
              Machine. The allowable states are:
                       down(1),
                       msNego(2),
                       cacheSumm(3),
                       cacheUpdate(4),
                       aligned(5)."
       REFERENCE
           "SCSP draft, Section 2.2"
       ::= { scspDCSEntry 2 }




   scspDCSCASequence  OBJECT-TYPE
       SYNTAX   Integer32 (-2147483648..2147483647)
       MAX-ACCESS  read-only
       STATUS   current
       DESCRIPTION
             "The current CA sequence number associated with
              this DCS."
       ::= { scspDCSEntry 3 }


   scspDCSCAIn  OBJECT-TYPE
       SYNTAX   Counter32
       MAX-ACCESS  read-only
       STATUS   current
       DESCRIPTION
             "The number of CA messages received from this DCS."
       ::= { scspDCSEntry 4 }


   scspDCSCAOut  OBJECT-TYPE
       SYNTAX   Counter32
       MAX-ACCESS  read-only
       STATUS   current
       DESCRIPTION
             "The number of CA messages sent to this DCS."
       ::= { scspDCSEntry 5 }

   scspDCSCAInvalidIn  OBJECT-TYPE
       SYNTAX   Counter32
       MAX-ACCESS  read-only
       STATUS   current
       DESCRIPTION
             "The number of invalid CA messages received from this
              DCS.
              During Master/Slave negotiation state, two types of
              messages are correct:
              1) CA from the DCS has the M, I, and O bits on, with
                 no CSAS records and sender's ID is larger than the
                 LSID.
              2) CA from the DCS has the M and I bits off and the
                 sender's ID is smaller than the LSID.
              All other types of CA messages are invalid and
              ignored. During Cache Summarize State, two kinds of
              message errors are possible:
              1) M bit in received CA is set incorrectly;
              2) CA sequence number is neither equal nor one
                 more than the current LS's CA sequence number when
                 LS is slave or CA sequence number is neither equal
                 nor one less than the current LS's CA sequence number
                 when LS is master. Other common errors include failed
                 check sum, failed authentication if applicable,
                 errors in the message fields."

       REFERENCE
              "SCSP draft, Section 2.2."
       ::= { scspDCSEntry 6 }


   scspDCSCADuplicateIn  OBJECT-TYPE
       SYNTAX   Counter32
       MAX-ACCESS  read-only
       STATUS   current
       DESCRIPTION
             "The number of duplicate CA messages received from
              this DCS. A CA message is considered duplicate when
              1)LS is master and received a CA message with its
                sequence number one less than the current sequence
                number; or
              2)LS is slave and received a CA message with its
                sequence number equal to the LS's current sequence
                number."
      REFERENCE
             "SCSP draft, Section 2.2"
      ::= { scspDCSEntry 7 }



   scspDCSMSState    OBJECT-TYPE
       SYNTAX   INTEGER {
                  master (1),
                  slave  (2)
       }
       MAX-ACCESS  read-only
       STATUS   current
       DESCRIPTION
             "The master/slave status of this DCS. This object
              should be ignored when CAFSM is in 'down' state."
       ::= { scspDCSEntry  8 }


   scspDCSCSUSIn   OBJECT-TYPE
       SYNTAX   Counter32
       MAX-ACCESS  read-only
       STATUS   current
       DESCRIPTION
             "The number of CSUS sent from this DCS to the LS."
       ::= { scspDCSEntry  9 }

   scspDCSCSUSOut   OBJECT-TYPE
       SYNTAX   Counter32
       MAX-ACCESS  read-only
       STATUS   current
       DESCRIPTION
             "The number of CSUS sent from LS to this DCS."
       ::= { scspDCSEntry  10 }


   scspDCSCSUSInvalidIn   OBJECT-TYPE
       SYNTAX   Counter32
       MAX-ACCESS  read-only
       STATUS   current
       DESCRIPTION
             "The number of Invalid CSUS sent from this DCS to the LS."
       ::= { scspDCSEntry  11 }

   scspDCSCSURequestIn  OBJECT-TYPE
       SYNTAX   Counter32
       MAX-ACCESS  read-only
       STATUS   current
       DESCRIPTION
             "The number of CSU requests LS received from this DCS."
       ::= { scspDCSEntry 12 }


   scspDCSCSUReplyOut  OBJECT-TYPE
       SYNTAX   Counter32
       MAX-ACCESS  read-only
       STATUS   current
       DESCRIPTION
             "The number of CSU replies sent from LS to this DCS."
       ::= { scspDCSEntry 13 }


   scspDCSCSURequestOut  OBJECT-TYPE
       SYNTAX   Counter32
       MAX-ACCESS  read-only
       STATUS   current
       DESCRIPTION
             "The number of CSU requests sent from LS to this DCS."
       ::= { scspDCSEntry 14 }


   scspDCSCSUReplyIn  OBJECT-TYPE
       SYNTAX   Counter32
       MAX-ACCESS  read-only
       STATUS   current
       DESCRIPTION
             "The number of CSU replies LS received from this DCS."
       ::= { scspDCSEntry 15 }

   scspDCSCSUInvalidRequestIn  OBJECT-TYPE
       SYNTAX   Counter32
       MAX-ACCESS  read-only
       STATUS   current
       DESCRIPTION
             "The number of invalid CSU requests LS received from
              this DCS. The possible errors in the CSU request
              messages: the received CSU request's Receiver ID is
              not equal to the LSID, etc.
              Other common errors include failed authentication if
              applicable, errors in the message fields, etc."
       ::= { scspDCSEntry 16 }



   scspDCSCSUInvalidReplyIn  OBJECT-TYPE
       SYNTAX   Counter32
       MAX-ACCESS  read-only
       STATUS   current
       DESCRIPTION
             "The number of invalid CSU replies LS received from
              this DCS. The possible errors in the CSU reply
              messages: the received CSU reply's Receiver ID is not
              equal to the LSID, etc.
              Other common errors include failed authentication if
              applicable, errors in the message fields, etc."
       ::= { scspDCSEntry 17 }



   scspDCSCSAIn  OBJECT-TYPE
       SYNTAX   Counter32
       MAX-ACCESS  read-only
       STATUS   current
       DESCRIPTION
             "The total number of CSA records received from
              this DCS to this LS."
       ::= { scspDCSEntry 18 }


   scspDCSCSAOut  OBJECT-TYPE
       SYNTAX   Counter32
       MAX-ACCESS  read-only
       STATUS   current
       DESCRIPTION
             "The total number of CSA records sent from LS
              to this DCS."
       ::= { scspDCSEntry 19 }

   scspDCSCSAReXmted  OBJECT-TYPE
       SYNTAX   Counter32
       MAX-ACCESS  read-only
       STATUS   current
       DESCRIPTION
             "The total number of CSA records re-transmited from LS
              to this DCS."
       ::= { scspDCSEntry 20 }

   scspDCSCSAReXmtQDepth  OBJECT-TYPE
       SYNTAX   Integer32 (0..65535)
       MAX-ACCESS  read-only
       STATUS   current
       DESCRIPTION
             "The depth of CSA Re-transmit queue associated with
              this DCS. The CSAs in the Re-transmit queue are
              pending to acknowledged."
       ::= { scspDCSEntry 21 }


   scspDCSRowStatus  OBJECT-TYPE
       SYNTAX   RowStatus
       MAX-ACCESS  read-create
       STATUS   current
       DESCRIPTION
             "This object allows DCS entries to be created and
              deleted from the scspDCSTable.  This table is closely
              coupled with its corresponding protocol dependent table.
              A new row creation in this table results in creation of
              a new row in the corresponding protocol dependent table.
              When the scspServerRowStatus is deleted by setting this
              object to destroy(6), this results in removing the
              corresponding entries in its corresponding protocol
              dependent table."
       REFERENCE
             "RFC 1903, 'Textual Conventions for version 2 of the
              Simple Network Management Protocol (SNMPv2).'"
       ::= { scspDCSEntry 22 }


   -- *****************************************************************

   --       Notifications

   -- *****************************************************************
   scspCSAReXmExceed NOTIFICATION-TYPE
       OBJECTS {
               scspServerGroupID,
               scspServerGroupPID,
               scspDCSID
       }
       STATUS  current
       DESCRIPTION
             "Retransmission of a CSA to this DCS has exceeded
              maximum retry limit, indicating an 'abnormal event'
              has happened between the LS/DCS association. The
              HSFM associated with this DCS is transitioned into
              the 'Waiting' state, and a 'scspHFSMWaiting' trap
              is also generated."
       ::= { scspNotifications 1 }


   -- *****************************************************************

   -- Conformance Definitions

   -- *****************************************************************

   scspCompliances OBJECT IDENTIFIER ::= { scspConformance 1 }
   scspGroups      OBJECT IDENTIFIER ::= { scspConformance 2 }

   -- *****************************************************************

   --  SCSP MIB Compliance Statements

   -- *****************************************************************

   scspCompliance MODULE-COMPLIANCE
       STATUS  current
       DESCRIPTION
             "The compliance statement for entities that are required
              for the management of SCSP."
       MODULE
          MANDATORY-GROUPS {
               scspLSGroup,
               scspDCSGroup
          }

      ::= { scspCompliances 1 }


   scspLSGroup OBJECT-GROUP
       OBJECTS {
              scspServerGroupID,
              scspServerGroupPID,
              scspLSID,
              scspLSHelloInterval,
              scspLSCAReXmInterval,
              scspLSCSUSReXmtInterval,
              scspLSCSUReXmtInterval,
              scspLSCSAMaxReXmt,
              scspLSDeadFactor
        }
       STATUS   current
       DESCRIPTION
             "A collection of objects which support the management of
              the Server group and the Local Server. This group is
              mandatory."
       ::= { scspGroups 1 }


   scspDCSGroup OBJECT-GROUP
       OBJECTS {
              scspDCSID,
              scspDCSCAFSMState,
              scspDCSCAIn,
              scspDCSCAOut,
              scspDCSCAInvalidIn,
              scspDCSCADuplicateIn,
              scspDCSMSState,
              scspDCSCSUSIn,
              scspDCSCSUSOut,
              scspDCSCSURequestIn,
              scspDCSCSURequestOut,
              scspDCSCSUReplyOut,
              scspDCSCSUReplyIn,
              scspDCSCSUInvalidRequestIn,
              scspDCSCSUInvalidReplyIn,
              scspDCSCSAIn,
              scspDCSCSAOut,
              scspDCSCSAReXmted,
              scspDCSCSAReXmtQDepth
        }
       STATUS   current
       DESCRIPTION
             "A collection of objects which support the management of
              the information exchange session between the LS and its
              associated DCS. This group is mandatory."
       ::= { scspGroups 2 }

     END
