-------------------------------------------------------
-- Copyright 1999 - Sun Microsystems, Inc. All Rights Reserved.
--
--
-------------------------------------------------------
-- Sun Management Center
-------------------------------------------------------

PRINT-SPOOL-SUNMANAGEMENTCENTER-MIB2 DEFINITIONS ::= BEGIN

  IMPORTS
        enterprises, MODULE-IDENTITY, OBJECT-TYPE,  Integer32
                FROM SNMPv2-SMI
         OBJECT-GROUP
                FROM SNMPv2-CONF
         DisplayString, RowStatus
               FROM SNMPv2-TC;


printSpool MODULE-IDENTITY
    LAST-UPDATED "9909201505Z"
    ORGANIZATION "Sun Microsystems Inc."
    CONTACT-INFO
        "        Sun Microsystems Inc.
       Customer Support
            Postal: 901 San Antonio Road
       Palo Alto, CA-94303-4900
    USA
                         Tel: 650-960-1300
                E-mail: service@sun.com"
    DESCRIPTION
        "The Print Spooler allows to monitor the status of the printer
        daemon, queue, and devices on the network."

    REVISION  "9909201505Z"
    DESCRIPTION
        "Rev 1.0  20th Sep 1999 15:05, Initial version Of MIB."
    ::= { modules 37 }

sun       OBJECT IDENTIFIER ::= { enterprises 42 }
prod      OBJECT IDENTIFIER ::= { sun 2 }
sunsymon  OBJECT IDENTIFIER ::= { prod 12 }
agent     OBJECT IDENTIFIER ::= { sunsymon 2 }
modules   OBJECT IDENTIFIER ::= { agent 2 }


prsLpschedGroup OBJECT-GROUP
        OBJECTS { prsLpschedState }
        STATUS current
        DESCRIPTION
        "Print request scheduler related statistics."
        ::= { printSpool 1 }

prsLpstatGroup OBJECT-GROUP
        OBJECTS { prsDevRowstatus, prsDevName, prsDevDesc, prsDevMachine,
                  prsDevDevice, prsDevState, prsQueueName, prsQueueState,
                  prsQueueJobs, prsQueueCurrent, prsQueueSize }
        STATUS current
        DESCRIPTION
        "Print device and print queue related statistics."
        ::= { printSpool 2 }

prsLpschedState OBJECT-TYPE
    SYNTAX      DisplayString
    MAX-ACCESS  read-only
    STATUS      current
    DESCRIPTION
                "The state of the lpsched process. The 
                 value may be Up or Down."
    ::= { prsLpschedGroup 1 }

prsDeviceTable OBJECT-TYPE
    SYNTAX      SEQUENCE OF PrsDeviceEntry
    MAX-ACCESS  not-accessible
    STATUS      current
    DESCRIPTION
                "Table of print device related information. Each
                 row corresponds to a print device."
    ::= { prsLpstatGroup 1 }

prsDeviceEntry OBJECT-TYPE
    SYNTAX      PrsDeviceEntry
    MAX-ACCESS  not-accessible
    STATUS      current
    DESCRIPTION
                "The entry contains information corresponding to
                 one print device."
    INDEX  { prsDevName }
    ::= { prsDeviceTable 1 }

PrsDeviceEntry ::=
    SEQUENCE {
        prsDevRowstatus
            RowStatus,
        prsDevName
            DisplayString,
        prsDevDesc
            DisplayString,
        prsDevMachine
            DisplayString,
        prsDevDevice
            DisplayString,
        prsDevState
            DisplayString
    }

prsDevRowstatus OBJECT-TYPE
    SYNTAX      RowStatus 
    MAX-ACCESS  read-write
    STATUS      current
    DESCRIPTION
                "The row status."
    ::= { prsDeviceEntry 1 }

prsDevName OBJECT-TYPE
    SYNTAX      DisplayString
    MAX-ACCESS  read-only
    STATUS      current
    DESCRIPTION
                "The name of the printer."
    ::= { prsDeviceEntry 2 }

prsDevDesc OBJECT-TYPE
    SYNTAX      DisplayString
    MAX-ACCESS  read-write
    STATUS      current
    DESCRIPTION
                "The description of the printer."
    ::= { prsDeviceEntry 3 }

prsDevMachine OBJECT-TYPE
    SYNTAX      DisplayString
    MAX-ACCESS  read-only
    STATUS      current
    DESCRIPTION
                "The name of the host machine for the printer."
    ::= { prsDeviceEntry 4 }

prsDevDevice OBJECT-TYPE
    SYNTAX      DisplayString
    MAX-ACCESS  read-only
    STATUS      current
    DESCRIPTION
                "The name of the device."
    ::= { prsDeviceEntry 5 }

prsDevState OBJECT-TYPE
    SYNTAX      DisplayString
    MAX-ACCESS  read-only
    STATUS      current
    DESCRIPTION
                "The state of the device.The values are 'enabled' or
                 'disabled'."
    ::= { prsDeviceEntry 6 }

prsQueueTable OBJECT-TYPE
    SYNTAX      SEQUENCE OF PrsQueueEntry
    MAX-ACCESS  not-accessible
    STATUS      current
    DESCRIPTION
                "Table of print queue related information. Each 
                 row corresponds to a print queue."
    ::= { prsLpstatGroup 2 }

prsQueueEntry OBJECT-TYPE
    SYNTAX      PrsQueueEntry
    MAX-ACCESS  not-accessible
    STATUS      current
    DESCRIPTION
                "The entry contains information corresponding to
                 one print queue."
    INDEX  { prsQueueName }
    ::= { prsQueueTable 1 }

PrsQueueEntry ::=
    SEQUENCE {
        prsQueueName
            DisplayString,
        prsQueueState
            DisplayString,
        prsQueueJobs
            Integer32,
        prsQueueCurrent
            DisplayString,
        prsQueueSize
            Integer32
    }

prsQueueName OBJECT-TYPE
    SYNTAX      DisplayString
    MAX-ACCESS  read-only
    STATUS      current
    DESCRIPTION
                "The Printer Queue Name."
    ::= { prsQueueEntry 1 }

prsQueueState OBJECT-TYPE
    SYNTAX      DisplayString
    MAX-ACCESS  read-only
    STATUS      current
    DESCRIPTION
                "The state of the Printer Queue.The values are
                 'accepting requests' or 'not accepting requests'."
    ::= { prsQueueEntry 2 }

prsQueueJobs OBJECT-TYPE
    SYNTAX      Integer32 (-2147483648..2147483647)
    MAX-ACCESS  read-only
    STATUS      current
    DESCRIPTION
                "The number of jobs in the printer queue."
    ::= { prsQueueEntry 3 }

prsQueueCurrent OBJECT-TYPE
    SYNTAX      DisplayString
    MAX-ACCESS  read-only
    STATUS      current
    DESCRIPTION
                "The current printer job."
    ::= { prsQueueEntry 4 }

prsQueueSize OBJECT-TYPE
    SYNTAX      Integer32 (-2147483648..2147483647)
    UNITS       "Bytes"
    MAX-ACCESS  read-only
    STATUS      current
    DESCRIPTION
                "The size of the Printer Queue."
    ::= { prsQueueEntry 5 }
END
