XEDIA-DS1-MIB DEFINITIONS ::= BEGIN

IMPORTS 
    MODULE-IDENTITY, OBJECT-TYPE,  Counter32, Integer32
        FROM SNMPv2-SMI
    TEXTUAL-CONVENTION
        FROM SNMPv2-TC
    dsx1ConfigEntry, dsx1CurrentEntry, dsx1IntervalEntry, dsx1TotalEntry
    FROM RFC1406-MIB
    MODULE-COMPLIANCE, OBJECT-GROUP
        FROM SNMPv2-CONF
    xediaMibs
        FROM XEDIA-REG
    ;    

xediaDs1MIB MODULE-IDENTITY
    LAST-UPDATED "9806170000Z" -- June 17, 1998
    ORGANIZATION "Xedia Corp."
    CONTACT-INFO
        "support@xedia.com"
    DESCRIPTION
        "This module defines additional objects for management of DS1 
        links in Xedia devices, above and beyond what is defined in the
        standard DS1 mib, and proposed drafts."
    ::= { xediaMibs 18 }

-- Top-level organization of the MIB

xDs1Objects          OBJECT IDENTIFIER ::= { xediaDs1MIB 1 }
xDs1Tables           OBJECT IDENTIFIER ::= { xediaDs1MIB 2 }
xDs1Conformance      OBJECT IDENTIFIER ::= { xediaDs1MIB 3 }

-- Textual Conventions

XDsx1LineStatus ::= TEXTUAL-CONVENTION
        STATUS  current
        DESCRIPTION
                "This type is a bit string representing a sum of line conditions, 
                 therefore, it can indicate multiple failures and loopback 
                 simultaneously. The value dsx1NoAlarm is set if and only if no
                 other flag is set."
        REFERENCE
                "DS1 MIB dsx1LineStatus"
        SYNTAX  BIT STRING {
                        noAlarm(0),          -- No alarm present
                        rcvFarEndLOF(1),     -- RX far end LOF, aka Yellow Alarm
                        xmitFarEndLOF(2),    -- near end sending LOF indication 
                        rcvAIS(3),           -- Receiving AIS failure state
                        xmitAIS(4),          -- Transmitting AIS
                        lossOfFrame(5),      -- LOF failure state
                        lossOfSignal(6),     -- LOS failure state
                        loopbackState(7),    -- Looping the received signal

                        t16AIS(8),           -- E1 TS16 AIS 
                        rcvFarEndLOMF(9),    -- RX far end TS16 LOMF 
                        xmitFarEndLOMF(10),  -- TX far TS16 LOMF
                        rcvTestCode(11),     -- Near End detects a test code
                        otherFailure(12)     -- Any line status not defined
                                             -- here
                }

--***************************************
-- Extensions to the DS1 'Config' Table
-- ***************************************
xDsx1ConfigTable        OBJECT-TYPE
    SYNTAX      SEQUENCE OF XDsx1ConfigEntry
    MAX-ACCESS  not-accessible
    STATUS      current
    DESCRIPTION
            "The Xedia DS1 Config table contains extensions to
             the DS1 Config table."
    ::= { xDs1Tables 1 }

xDsx1ConfigEntry        OBJECT-TYPE
    SYNTAX      XDsx1ConfigEntry
    MAX-ACCESS  not-accessible
    STATUS      current
    DESCRIPTION
            "An entry in the Xedia DS1 Config table."
    AUGMENTS    { dsx1ConfigEntry }
    ::= { xDsx1ConfigTable 1 }

XDsx1ConfigEntry ::=
    SEQUENCE {
        xdsx1LineStatus             XDsx1LineStatus,
        xdsx1LoopbackStatus         BIT STRING,
	xdsx1CfgCrcMode             INTEGER,
	xdsx1CfgLineBuildOut        INTEGER,
	xdsx1CfgLineInterface       INTEGER,
	xdsx1CfgInsertTVerrs        Integer32,
	xdsx1CfgInsertTFerrs        Integer32,
	xdsx1CfgInsertTCerrs        Integer32,
	xdsx1CfgInsertTBerrs        Integer32,
	xdsx1CfgChannelMask         BIT STRING,
	xdsx1OutOfFrames            Counter32,
	xdsx1ChangeOfFrameAlignment Counter32,
	xdsx1CfgLoopbackConfig      INTEGER,
	xdsx1CfgTestCode            INTEGER,
	xdsx1CfgLineCharacteristics INTEGER,
	xdsx1CfgLineType            INTEGER,
	xdsx1CfgLineCoding          INTEGER
    }

xdsx1LineStatus OBJECT-TYPE
    SYNTAX      XDsx1LineStatus
    MAX-ACCESS  read-only
    STATUS      current
    DESCRIPTION
        "Indicates the line status of the interface. This obect 
         is identical to dsx1LineStatus in the DS1 MIB except
         that it uses the SNMPv2 BIT STRING object type."
    ::= { xDsx1ConfigEntry 1 }

xdsx1LoopbackStatus OBJECT-TYPE
    SYNTAX  BIT STRING {  
                noLoopback(0),
		remotePayloadOrigNearEnd(1),
		remotelLineOrigNearEnd(2),
		localFramerOrigNearEnd(3),
		localAnalogOrigNearEnd(4),
		remotePayloadOrigFarEnd(5),
		remotelLineOrigFarEnd(6),
		localFramerOrigFarEnd(7),
		localAnalogOrigFarEnd(8)
            }
    MAX-ACCESS  read-only
    STATUS      current
    DESCRIPTION
        "Indicates the local and remote loopback status of the 
         interface. This object is identical to dsx1LoopbackStatus
         in the DS1 MIB except that it uses the SNMPv2 BIT STRING 
         object type."
    ::= { xDsx1ConfigEntry 2 }

xdsx1CfgCrcMode OBJECT-TYPE
    SYNTAX  INTEGER {
                crc16(1), 
                crc32(2),
                crcnone(3)
                }
    MAX-ACCESS  read-write
    STATUS      current
    DESCRIPTION
        "The configured CRC mode of the interface."
    DEFVAL      { crc16 }
    ::= { xDsx1ConfigEntry 3 }

xdsx1CfgLineBuildOut OBJECT-TYPE
     SYNTAX  INTEGER {
                 buildout0(1),
                 buildout7(2),
                 buildout15(3),
                 buildout22(4)
                 }
     MAX-ACCESS  read-write
     STATUS  current
     DESCRIPTION
	    "The line buildout of the ds1."
     DEFVAL      { buildout0 }
    ::= { xDsx1ConfigEntry 4 }

xdsx1CfgLineInterface OBJECT-TYPE
     SYNTAX  INTEGER {
                dsx000(1),
                dsx133(2),
                dsx266(3),
                dsx399(4),
                dsx533(5),
                dsxCSU(6),
                dsxE1(7)
                }
     MAX-ACCESS  read-write
     STATUS  current
     DESCRIPTION
	    "The line buildout of the ds1."
     DEFVAL      { dsxCSU }
    ::= { xDsx1ConfigEntry 5 }

xdsx1CfgInsertTVerrs OBJECT-TYPE
    SYNTAX  Integer32
    MAX-ACCESS  read-write
    STATUS      current
    DESCRIPTION
        "The number of Line Code Violation (LCV) errors to inject."
    DEFVAL      { 0 }
    ::= { xDsx1ConfigEntry 6 }

xdsx1CfgInsertTFerrs OBJECT-TYPE
    SYNTAX  Integer32
    MAX-ACCESS  read-write
    STATUS      current
    DESCRIPTION
        "The number of Frame Bit (FBE) errors to inject."
    DEFVAL      { 0 }
    ::= { xDsx1ConfigEntry 7 }

xdsx1CfgInsertTCerrs OBJECT-TYPE
    SYNTAX  Integer32
    MAX-ACCESS  read-write
    STATUS      current
    DESCRIPTION
        "The number of Checksum (CRC) errors to inject."
    DEFVAL      { 0 }
    ::= { xDsx1ConfigEntry 8 }

xdsx1CfgInsertTBerrs OBJECT-TYPE
    SYNTAX  Integer32
    MAX-ACCESS  read-write
    STATUS      current
    DESCRIPTION
        "The number of PRBS errors to inject."
    DEFVAL      { 0 }
    ::= { xDsx1ConfigEntry 9 }

xdsx1CfgChannelMask OBJECT-TYPE
     SYNTAX  BIT STRING {
                 c0(0),   c1(1),   c2(2),   c3(3),   c4(4),   c5(5),   c6(6), 
		 c7(7),   c8(8),   c9(9),   c10(10), c11(11), c12(12), c13(13), 
		 c14(14), c15(15), c16(16), c17(17), c18(18), c19(19), c20(20), 
		 c21(21), c22(22), c23(23), c24(24), c25(25), c26(26), c27(27), 
		 c28(28), c29(29), c30(30), c31(31) }
    MAX-ACCESS  read-write
    STATUS      current
    DESCRIPTION
        "The number of PRBS errors to inject."
    ::= { xDsx1ConfigEntry 10 }

xdsx1OutOfFrames OBJECT-TYPE
    SYNTAX      Counter32         
    MAX-ACCESS  read-only
    STATUS      current
    DESCRIPTION
           "The number of 'out of frame' errors." 
    ::= { xDsx1ConfigEntry 11 }

xdsx1ChangeOfFrameAlignment OBJECT-TYPE
    SYNTAX      Counter32         
    MAX-ACCESS  read-only
    STATUS      current
    DESCRIPTION
           "The number of times frames changed alignment."
    ::= { xDsx1ConfigEntry 12 }

xdsx1CfgLoopbackConfig OBJECT-TYPE
    SYNTAX  INTEGER {
		noLoop(1),
		remotePayloadLoop(2),
		remoteLineLoop(3),
		localFramer(4),
		localAnalog(5)
	    }
    MAX-ACCESS  read-write
    STATUS  current  
    DESCRIPTION
       "This variable represents the  loopback  configuration of 
        the DS1 interface.  Agents supporting read/write access 
        should return badValue in response to a requested loopback 
        state that the interface does not support.  The values mean:

       xdsx1NoLoop
	    Not in the loopback state.  A device  that
	    is not capable of performing a loopback on
	    the interface shall always return this  as
	    it's value.

       xdsx1PayloadLoop
	    The received signal at this  interface  is
	    looped  through  the device. Typically the
	    received signal is  looped  back  for  re-
	    transmission  after  it has passed through
	    the device's framing function.

       xdsx1LineLoop
	    The received signal at this interface does
	    not  go  through the device (minimum pene-
	    tration) but is looped back out.

       xdsx1Framer

       xdsx1Analog"
    DEFVAL         { noLoop }
    ::= { xDsx1ConfigEntry 13 }

xdsx1CfgTestCode OBJECT-TYPE
    SYNTAX  INTEGER {
                   sendNone(1),
                   sendPRBS2E11(2),
                   sendPRBS2E11f(3),
                   sendPRBS2E11z(4),
                   sendPRBS2E11fz(5),
                   sendPRBS2E15(6),
                   sendPRBS2E15f(7),
                   sendPRBS2E15z(8),
                   sendPRBS2E15fz(9),
                   sendPRBS2E20(10),
                   sendPRBS2E20f(11),
                   sendPRBS2E20z(12),
                   sendPRBS2E20fz(13),
                   sendPRBS2E23(14),
                   sendPRBS2E23f(15),
                   sendPRBS2E23z(16),
                   sendPRBS2E23fz(17)
	    }
    MAX-ACCESS  read-write
    STATUS  current  
    DESCRIPTION
       "This variable indicates what type of  code  is
       being sent across the DS1 interface by the dev-
       ice.  The values mean:

       xdsx1SendNone - sending looped or normal data

       xdsx1PRBS2E11  - E11, 
                   f  - framed-mode
                   z  - zero-limit mode
                   fz - framed-mode and zero-limit mode

       xdsx1PRBS2E15  - E15, 
                   f  - framed-mode
                   z  - zero-limit mode
                   fz - framed-mode and zero-limit mode

       xdsx1PRBS2E20  - E20, 
                   f  - framed-mode
                   z  - zero-limit mode
                   fz - framed-mode and zero-limit mode

       xdsx1PRBS2E23  - E23, 
                   f  - framed-mode
                   z  - zero-limit mode
                   fz - framed-mode and zero-limit mode"
    DEFVAL         { sendNone }
    ::= { xDsx1ConfigEntry 14 }


xdsx1CfgLineCharacteristics OBJECT-TYPE
     SYNTAX  INTEGER {
		  unknown(1),
                  t1dsx000ft(2),
                  t1dsx133ft(3),
                  t1dsx266ft(4),
                  t1dsx399ft(5),
                  t1dsx533ft(6),
                  t1csu00dbA(7),
                  t1csu07dbB(8),
                  t1csu15dbC(9),
                  t1csu22db(10),
                  e1(11)
                 }
     MAX-ACCESS  read-write
     STATUS  current
     DESCRIPTION
	    "The valid combinations of interface type, and buildout for
             the circuit."
    DEFVAL         { t1csu00dbA }
    ::= { xDsx1ConfigEntry 15 }

xdsx1CfgLineType OBJECT-TYPE
     SYNTAX  INTEGER {
                  other(1),
                  t1ESF(2),
                  t1D4(3),
                  e1FAS(4),
                  e1FAScrc(5)
                 }
     MAX-ACCESS  read-write
     STATUS  current
     DESCRIPTION
	    "The line type of the circuit."
    DEFVAL         { t1ESF }
    ::= { xDsx1ConfigEntry 16 }

xdsx1CfgLineCoding OBJECT-TYPE
     SYNTAX  INTEGER {
                -- JBZS (1),
                   b8zs (2),
                   hdb3 (3),
                -- ZBTSI (4),
                   ami (5),
                   amiInvertHDLC(6),
		   other(10) 
                 }
     MAX-ACCESS  read-write
     STATUS  current
     DESCRIPTION
	    "The line coding of the circuit."
    DEFVAL         { b8zs }
    ::= { xDsx1ConfigEntry 17 }

-- ***************************************
-- Extensions to the DS1 'Current' Table
-- ***************************************

xDsx1CurrentTable        OBJECT-TYPE
    SYNTAX      SEQUENCE OF XDsx1CurrentEntry
    MAX-ACCESS  not-accessible
    STATUS      current
    DESCRIPTION
            "The Xedia DS1 Current table contains extensions to
             the DS1 Current table which includes statistics 
             being collected for the current 15 minute interval."
    ::= { xDs1Tables 2 }
 
xDsx1CurrentEntry        OBJECT-TYPE
    SYNTAX      XDsx1CurrentEntry
    MAX-ACCESS  not-accessible
    STATUS      current
    DESCRIPTION
            "An entry in the Xedia DS1 Current table."
    AUGMENTS    { dsx1CurrentEntry}
    ::= { xDsx1CurrentTable 1 }

XDsx1CurrentEntry ::=
    SEQUENCE {
      xdsx1CurrentFBEs             Counter32,
      xdsx1CurrentFEBEs            Counter32,
      xdsx1CurrentCRCEs            Counter32,
      xdsx1CurrentLCEs             Counter32,
      xdsx1CurrentBEs              Counter32,
      xdsx1CurrentSlips            Counter32,
      xdsx1CurrentLineStatus       XDsx1LineStatus
    }

xdsx1CurrentFBEs OBJECT-TYPE
    SYNTAX      Counter32         
    MAX-ACCESS  read-only
    STATUS      current
    DESCRIPTION
           "The number of F Bit Errores encountered during the
	    current 15 minute interval."
    ::= { xDsx1CurrentEntry 1 }

xdsx1CurrentFEBEs OBJECT-TYPE
    SYNTAX      Counter32         
    MAX-ACCESS  read-only
    STATUS      current
    DESCRIPTION
           "The number of Far End Block Errors encountered
            in the current 15 minute interval."
    ::= {  xDsx1CurrentEntry 2 }

xdsx1CurrentCRCEs OBJECT-TYPE
    SYNTAX      Counter32        
    MAX-ACCESS  read-only
    STATUS      current
    DESCRIPTION
           "The number of CRC errors encountered during the 
	    current 15 minute interval."
    ::= {  xDsx1CurrentEntry 3 }

xdsx1CurrentLCEs OBJECT-TYPE
    SYNTAX      Counter32         
    MAX-ACCESS  read-only
    STATUS      current
    DESCRIPTION
           "The number of Line Coding Errors encountered during 
	    the current 15 minute interval."
    ::= {  xDsx1CurrentEntry 4 }

xdsx1CurrentBEs OBJECT-TYPE
    SYNTAX      Counter32         
    MAX-ACCESS  read-only
    STATUS      current
    DESCRIPTION
           "The number of Bit Errors encountered during 
	    the current 15 minute interval."
    ::= {  xDsx1CurrentEntry 5 }

xdsx1CurrentSlips OBJECT-TYPE
    SYNTAX      Counter32         
    MAX-ACCESS  read-only
    STATUS      current
    DESCRIPTION
           "The number of rx/tx slips encountered during 
	    the current 15 minute interval."
    ::= {  xDsx1CurrentEntry 6 }

xdsx1CurrentLineStatus  OBJECT-TYPE
    SYNTAX      XDsx1LineStatus
    MAX-ACCESS  read-only
    STATUS      current
    DESCRIPTION
           "The bitwise ORing of the dsx1LineStatus values (line 
            status) encountered during the current 15 
            minute interval. This object is useful in identifying 
            all xdsx1LineStatus conditions which occured during
            the interval including the NO_ALARM condition."
    ::= { xDsx1CurrentEntry 7 }

-- ***************************************
-- Extensions to the DS1 'Interval' Table
-- ***************************************

xDsx1IntervalTable        OBJECT-TYPE
    SYNTAX      SEQUENCE OF XDsx1IntervalEntry
    MAX-ACCESS  not-accessible
    STATUS      current
    DESCRIPTION
            "The Xedia DS1 Interval Table contains extensions to 
             the DS1 Interval table which includes statistics 
             collected over the previous 24 hours of operation.
             The past 24 hours are broken into 96 completed 15 
             minute intervals."
    ::= { xDs1Tables 3 }
 
xDsx1IntervalEntry        OBJECT-TYPE
    SYNTAX      XDsx1IntervalEntry
    MAX-ACCESS  not-accessible
    STATUS      current
    DESCRIPTION
            "An entry in the Xedia DS1 Interval Table."
    AUGMENTS    { dsx1IntervalEntry}
    ::= { xDsx1IntervalTable 1 }

XDsx1IntervalEntry ::=
    SEQUENCE {
      xdsx1IntervalFBEs             Counter32,
      xdsx1IntervalFEBEs            Counter32,
      xdsx1IntervalCRCEs            Counter32,
      xdsx1IntervalLCEs             Counter32,
      xdsx1IntervalBEs              Counter32,
      xdsx1IntervalSlips            Counter32,
      xdsx1IntervalLineStatus       XDsx1LineStatus
    }

--           "The number of F and M Frame Bit Errored Seconds 
--            encountered during the interval."
--     ::= { xDsx1IntervalEntry 6 }

xdsx1IntervalFBEs OBJECT-TYPE
    SYNTAX      Counter32         
    MAX-ACCESS  read-only
    STATUS      current
    DESCRIPTION
           "The number of F Bit Errores encountered during the
	    specified 15 minute interval."
    ::= { xDsx1IntervalEntry 1 }

xdsx1IntervalFEBEs OBJECT-TYPE
    SYNTAX      Counter32         
    MAX-ACCESS  read-only
    STATUS      current
    DESCRIPTION
           "The number of Far End Block Errors encountered
            in the specified 15 minute interval."
    ::= {  xDsx1IntervalEntry 2 }

xdsx1IntervalCRCEs OBJECT-TYPE
    SYNTAX      Counter32        
    MAX-ACCESS  read-only
    STATUS      current
    DESCRIPTION
           "The number of CRC errors encountered during the 
	    specified 15 minute interval."
    ::= {  xDsx1IntervalEntry 3 }

xdsx1IntervalLCEs OBJECT-TYPE
    SYNTAX      Counter32         
    MAX-ACCESS  read-only
    STATUS      current
    DESCRIPTION
           "The number of Line Coding Errors encountered during 
	    the specified 15 minute interval."
    ::= {  xDsx1IntervalEntry 4 }

xdsx1IntervalBEs OBJECT-TYPE
    SYNTAX      Counter32         
    MAX-ACCESS  read-only
    STATUS      current
    DESCRIPTION
           "The number of Bit Errors encountered during 
	    the specified 15 minute interval."
    ::= {  xDsx1IntervalEntry 5 }

xdsx1IntervalSlips OBJECT-TYPE
    SYNTAX      Counter32         
    MAX-ACCESS  read-only
    STATUS      current
    DESCRIPTION
           "The number of rx/tx slips encountered during 
	    the specified 15 minute interval."
    ::= {  xDsx1IntervalEntry 6 }

xdsx1IntervalLineStatus  OBJECT-TYPE
    SYNTAX      XDsx1LineStatus
    MAX-ACCESS  read-only
    STATUS      current
    DESCRIPTION
           "The bitwise ORing of the dsx1LineStatus values (line
            status) encountered during the specified 15 
            minute interval. This object is useful in identifying 
            all xdsx1LineStatus conditions which occured during
            the interval including the NO_ALARM condition."
    ::= { xDsx1IntervalEntry 7 }

-- ***************************************
-- Extensions to the DS1 'Total' Table
-- ***************************************

xDsx1TotalTable        OBJECT-TYPE
    SYNTAX      SEQUENCE OF XDsx1TotalEntry
    MAX-ACCESS  not-accessible
    STATUS      current
    DESCRIPTION
            "The Xedia DS1 Total Table contains extensions to the
             DS1 Total table which includes cumulative sums of the 
             various statistics for the 24 hour period preceding 
             the current interval. Invalid 15 minute intervals count 
             as 0."
    ::= { xDs1Tables 4 }
 
xDsx1TotalEntry        OBJECT-TYPE
    SYNTAX      XDsx1TotalEntry
    MAX-ACCESS  not-accessible
    STATUS      current
    DESCRIPTION
            "An entry in the Xedai DS1 Total Table."
    AUGMENTS    { dsx1TotalEntry}
    ::= { xDsx1TotalTable 1 }

XDsx1TotalEntry ::=
    SEQUENCE {
      xdsx1TotalFBEs             Counter32,
      xdsx1TotalFEBEs            Counter32,
      xdsx1TotalCRCEs            Counter32,
      xdsx1TotalLCEs             Counter32,
      xdsx1TotalBEs              Counter32,
      xdsx1TotalSlips            Counter32,
      xdsx1TotalLineStatus       XDsx1LineStatus
    }
 
xdsx1TotalFBEs OBJECT-TYPE
    SYNTAX      Counter32         
    MAX-ACCESS  read-only
    STATUS      current
    DESCRIPTION
           "The sum of F Bit Errores encountered during 
	    all 15 minute interval."
    ::= { xDsx1TotalEntry 1 }

xdsx1TotalFEBEs OBJECT-TYPE
    SYNTAX      Counter32         
    MAX-ACCESS  read-only
    STATUS      current
    DESCRIPTION
           "The sum of Far End Block Errors encountered for all
            of the 15 minute interval."
    ::= {  xDsx1TotalEntry 2 }

xdsx1TotalCRCEs OBJECT-TYPE
    SYNTAX      Counter32        
    MAX-ACCESS  read-only
    STATUS      current
    DESCRIPTION
           "The sum of CRC errors encountered for all
	    of the 15 minute interval."
    ::= {  xDsx1TotalEntry 3 }

xdsx1TotalLCEs OBJECT-TYPE
    SYNTAX      Counter32         
    MAX-ACCESS  read-only
    STATUS      current
    DESCRIPTION
           "The sum of Line Coding Errors encountered for all
	    of the 15 minute interval."
    ::= {  xDsx1TotalEntry 4 }

xdsx1TotalBEs OBJECT-TYPE
    SYNTAX      Counter32         
    MAX-ACCESS  read-only
    STATUS      current
    DESCRIPTION
           "The sum of Bit Errors encountered during 
	    of the 15 minute interval."
    ::= {  xDsx1TotalEntry 5 }

xdsx1TotalSlips OBJECT-TYPE
    SYNTAX      Counter32         
    MAX-ACCESS  read-only
    STATUS      current
    DESCRIPTION
           "The sum of rx/tx slips encountered during 
	    of the 15 minute interval."
    ::= {  xDsx1TotalEntry 6 }

xdsx1TotalLineStatus  OBJECT-TYPE
    SYNTAX      XDsx1LineStatus
    MAX-ACCESS  read-only
    STATUS      current
    DESCRIPTION
           "The bitwise ORing of the dsx1LineStatus values (line  
            status) encountered during all of the 15 
            minute intervals. This object is useful in identifying 
            all xdsx1LineStatus conditions which occured during
            the full range of intervals including the NO_ALARM condition."
    ::= { xDsx1TotalEntry 7 }

-- ****************************************************************
-- Conformance Information
-- ****************************************************************

xDs1Compliances OBJECT IDENTIFIER ::= { xDs1Conformance 1 }
xDs1Groups      OBJECT IDENTIFIER ::= { xDs1Conformance 2 }

--
-- Compliance Statements
--

xDs1Compliance MODULE-COMPLIANCE
    STATUS      current
    DESCRIPTION
        "The compliance statement for all agents that support this
        MIB. A compliant agent implements all objects defined in this
        MIB."
    MODULE  -- this module
    MANDATORY-GROUPS {
        xDs1AllGroup
    }
    ::= { xDs1Compliances 1 }

--
-- All Object Groups
--
xDs1AllGroup OBJECT-GROUP
    OBJECTS {
      xdsx1LineStatus,
      xdsx1LoopbackStatus,
      xdsx1CfgCrcMode,
      xdsx1CfgLineBuildOut,
      xdsx1CfgLineInterface,
      xdsx1CfgInsertTVerrs,
      xdsx1CfgInsertTFerrs,
      xdsx1CfgInsertTCerrs,
      xdsx1CfgInsertTBerrs,
      xdsx1CfgChannelMask,
      xdsx1OutOfFrames,
      xdsx1ChangeOfFrameAlignment,
      xdsx1CfgLoopbackConfig,
      xdsx1CfgTestCode,

      xdsx1CurrentFBEs,
      xdsx1CurrentFEBEs,
      xdsx1CurrentCRCEs,
      xdsx1CurrentLCEs,
      xdsx1CurrentBEs,
      xdsx1CurrentSlips,
      xdsx1CurrentLineStatus,

      xdsx1IntervalFBEs,
      xdsx1IntervalFEBEs,
      xdsx1IntervalCRCEs,
      xdsx1IntervalLCEs,
      xdsx1IntervalBEs,
      xdsx1IntervalSlips,
      xdsx1IntervalLineStatus,

      xdsx1TotalFBEs,
      xdsx1TotalFEBEs,
      xdsx1TotalCRCEs,
      xdsx1TotalLCEs,
      xdsx1TotalBEs,
      xdsx1TotalSlips,
      xdsx1TotalLineStatus,
      xdsx1CfgLineCharacteristics,
      xdsx1CfgLineType,
      xdsx1CfgLineCoding
    }
    STATUS      current
    DESCRIPTION
        "The set of all accessible objects in this MIB."
    ::= { xDs1Groups 1 }

END
