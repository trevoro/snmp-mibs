--
-- ANDOVER-CONTROLS-MIB.my
-- MIB generated by MG-SOFT Visual MIB Builder Version 3.0 Build 285
-- Monday, May 13, 2002 at 15:50:30
--

	ANDOVER-CONTROLS-MIB DEFINITIONS ::= BEGIN
 
		IMPORTS
			enterprises			
				FROM RFC1155-SMI			
			OBJECT-GROUP, MODULE-COMPLIANCE			
				FROM SNMPv2-CONF			
			OBJECT-TYPE, MODULE-IDENTITY, OBJECT-IDENTITY			
				FROM SNMPv2-SMI			
			DisplayString			
				FROM SNMPv2-TC;
	
	
		-- 1.3.6.1.4.1.10829
		andoverControls MODULE-IDENTITY 
			LAST-UPDATED "200210300946Z"		-- October 30, 2002 at 09:46 GMT
			ORGANIZATION 
				"Andover Controls Corporation"
			CONTACT-INFO 
				"Technical Support
				Andover Controls Corporation
				300 Brickstone Square
				Andover, MA 01810
				USA
				978-470-0555"
			DESCRIPTION 
				"This is the MIB module at the top of the
				Andover Controls enterprise group."
			REVISION "200210300946Z"		-- October 30, 2002 at 09:46 GMT
			DESCRIPTION 
				"Revision 1.0"
			::= { enterprises 10829 }

		
	
	
--
-- Node definitions
--
	
		-- 1.3.6.1.4.1.10829.1
		accAlarmAgent OBJECT-IDENTITY
			STATUS deprecated
			DESCRIPTION 
				"Cyberstation alarm group witch contains
				information about the last alarm sent out
				as a trap."
			::= { andoverControls 1 }
-- 
-- Children accSoftware (2) and accHardware (3) were 
-- defined but never used, so skip them.
-- 
		
		-- 1.3.6.1.4.1.10829.4
		accCommon OBJECT-IDENTITY
			STATUS current
			DESCRIPTION 
				"Group for items that may be common to more than one 
				product.
				"
			::= { andoverControls 4 }

		
		-- 1.3.6.1.4.1.10829.5
		accProduct OBJECT-IDENTITY
			STATUS current
			DESCRIPTION 
				"Group for items specific to a product or family
				of products. Children of this node will be product
				families."
			::= { andoverControls 5 }

		
		-- 1.3.6.1.4.1.10829.5.1
		accInfinetController OBJECT IDENTIFIER::= { accProduct 1 }

		
		-- 1.3.6.1.4.1.10829.5.2
		accNetController OBJECT IDENTIFIER::= { accProduct 2 }

		
		-- 1.3.6.1.4.1.10829.5.3
		accFrontEnd OBJECT IDENTIFIER::= { accProduct 3 }

		
		-- 1.3.6.1.4.1.10829.6
		accSystem OBJECT-IDENTITY
			STATUS current
			DESCRIPTION 
				"Similiar to MIB-II system group, except for Andover
				Controls specific information about the device."
			::= { andoverControls 6 }

		
		-- 1.3.6.1.4.1.10829.6.1
		accModel OBJECT-TYPE
			SYNTAX DisplayString (SIZE (0..32))
			MAX-ACCESS read-only
			STATUS current
			DESCRIPTION
				"Model name of this product."
			DEFVAL { "" }
			::= { accSystem 1 }

		
		-- 1.3.6.1.4.1.10829.6.2
		accFirmwareVersion OBJECT-TYPE
			SYNTAX DisplayString (SIZE (0..16))
			MAX-ACCESS read-only
			STATUS current
			DESCRIPTION
				"Version of the firmware running on device."
			::= { accSystem 2 }

		
		-- 1.3.6.1.4.1.10829.7
		accConformance OBJECT IDENTIFIER::= { andoverControls 7 }

		
		-- 1.3.6.1.4.1.10829.7.2
		accGroups OBJECT IDENTIFIER::= { accConformance 2 }

		
		-- 1.3.6.1.4.1.10829.7.2.1
		accSystemGroup OBJECT-GROUP
			OBJECTS { accModel, accFirmwareVersion }
			STATUS current
			DESCRIPTION 
				"Description."
			::= { accGroups 1 }

		
		-- 1.3.6.1.4.1.10829.7.3
		accCompliance OBJECT IDENTIFIER::= { accConformance 3 }

		
		-- 1.3.6.1.4.1.10829.7.3.1
		accBasicCompliance MODULE-COMPLIANCE
			STATUS current
			DESCRIPTION 
				"Compliance requires these nodes."
			MODULE -- this module
				MANDATORY-GROUPS { accSystemGroup }
			::= { accCompliance 1 }

		
	
	END

--
-- ANDOVER-CONTROLS-MIB.my
--
