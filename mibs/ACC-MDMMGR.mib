ACC-MDMMGR DEFINITIONS ::= BEGIN

    IMPORTS
	 OBJECT-TYPE, IpAddress, TimeTicks, Gauge, Counter FROM RFC1155-SMI
          accTrapLogSeqNum FROM ACC-SYSTEM
	accBRG, DisplayString, RowStatus, IfIndex, SmdsAddress
             FROM ACC-MIB;

-- Modem Manager Group
    accMdmMgr 	OBJECT IDENTIFIER ::= { accBRG 54 }
-- Branch for system level modem manager objects 
        accMdmMgrParms	OBJECT IDENTIFIER ::= { accMdmMgr 1 }
	    accMdmMgrMessageLevel	OBJECT-TYPE	
		SYNTAX	INTEGER (1..7)
		ACCESS	read-write
		STATUS  mandatory
		DESCRIPTION
		  " Modem management information message level"
		::= { accMdmMgrParms 1 }
	    accMdmMgrConnFails4Bad	OBJECT-TYPE	
		SYNTAX	INTEGER (0..10)
		ACCESS	read-write
		STATUS  mandatory
		DESCRIPTION
		  " Number of consecutive connection failures
                    detected before a modem is deemed bad.
                    A value of zero disables detection"
		::= { accMdmMgrParms 2 }
            accMdmMgrTotAssigns      OBJECT-TYPE
                SYNTAX  Counter
                ACCESS  read-only
                STATUS  mandatory
                DESCRIPTION
			"Total assignments indicates the total 
			number of modem assignments.  This number 
			is the sum of modem assignments from 
			all modem pools."
                ::= { accMdmMgrParms 3 }
            accMdmMgrTotConns      OBJECT-TYPE
                SYNTAX  Counter
                ACCESS  read-only
                STATUS  mandatory
                DESCRIPTION
                        "Total connections indicates the total 
			number of modem connections.  This number 
			is the sum of modem connections from 
			all modem pools." 
                ::= { accMdmMgrParms 4 }
            accMdmMgrLicInstTotal56ks      OBJECT-TYPE
                SYNTAX  Counter
                ACCESS  read-only
                STATUS  mandatory
                DESCRIPTION
                        "Total license 56K  indicates the total 
			number of licenses of the 56k license_type 
			that have been allocated since reset. 
			This number is the sum of standard and 
			supplemental licenses, if any."
                ::= { accMdmMgrParms 5 }
            accMdmMgrLicInstCurrent56ks      OBJECT-TYPE
                SYNTAX  Counter
                ACCESS  read-only
                STATUS  mandatory
                DESCRIPTION
                        "Current license 56K  indicates the current 
			number of licenses of the 56k license_type 
			that are currently allocated.  This number 
			is the sum of standard and supplemental 
			licenses, if any."
                ::= { accMdmMgrParms 6 }
            accMdmMgrLicInstPeak56ks      OBJECT-TYPE
                SYNTAX  Counter
                ACCESS  read-only
                STATUS  mandatory
                DESCRIPTION
                        "Peak license 56K  indicates the peak number 
			of licenses of the 56k license_type allocated 
			at one time.  This number is the sum of standard 
			and supplemental licenses, if any."
                ::= { accMdmMgrParms 7 }
            accMdmMgrLicInstDenial56ks      OBJECT-TYPE
                SYNTAX  Counter
                ACCESS  read-only
                STATUS  mandatory
                DESCRIPTION
                        "Denial 56K indicates the total number of 
			denials of licenses of the 56k license_type."
                ::= { accMdmMgrParms 8 }
            accMdmMgrLicInstTotalVoIPs      OBJECT-TYPE
                SYNTAX  Counter
                ACCESS  read-only
                STATUS  mandatory
                DESCRIPTION
                        "TBD"
                ::= { accMdmMgrParms 9 }
            accMdmMgrLicInstCurrentVoIPs      OBJECT-TYPE
                SYNTAX  Counter
                ACCESS  read-only
                STATUS  mandatory
                DESCRIPTION
                        "TBD"
                ::= { accMdmMgrParms 10 }
            accMdmMgrLicInstPeakVoIPs      OBJECT-TYPE
                SYNTAX  Counter
                ACCESS  read-only
                STATUS  mandatory
                DESCRIPTION
                        "TBD"
                ::= { accMdmMgrParms 11 }
            accMdmMgrLicInstDenialVoIPs     OBJECT-TYPE
                SYNTAX  Counter
                ACCESS  read-only
                STATUS  mandatory
                DESCRIPTION
                        "TBD"
                ::= { accMdmMgrParms 12 }
	-- End of system level parameters
	-- Branch for per-modem pool objects 
	accMdmMgrPoolTable	OBJECT-TYPE
	    SYNTAX	SEQUENCE OF AccMdmMgrPoolEntry
	    ACCESS	not-accessible
	    STATUS	mandatory
	    DESCRIPTION
	      " Modem pool table containing parameter and status
		information for all pool configured on this router."
	    ::= { accMdmMgr 2 }
	accMdmMgrPoolEntry	OBJECT-TYPE
	    SYNTAX	AccMdmMgrPoolEntry
	    ACCESS      not-accessible
	    STATUS      mandatory
    	    DESCRIPTION
	      " Configuration and status objects for a particular
		modem pool."
	    INDEX { accMdmMgrPoolName }
	    ::= { accMdmMgrPoolTable 1 }
	AccMdmMgrPoolEntry	::= SEQUENCE {
	    accMdmMgrPoolAction		    INTEGER,
	    accMdmMgrPoolSize		    INTEGER,
	    accMdmMgrPoolMaxTx		    INTEGER,
	    accMdmMgrPoolCarrDtct	    INTEGER,
	    accMdmMgrPoolCarrLoss	    INTEGER,
	    accMdmMgrPoolModType	    INTEGER,
	    accMdmMgrPoolCompProt	    INTEGER,
	    accMdmMgrPoolErrProt	    INTEGER,
	    accMdmMgrPoolPrefStart	    INTEGER,
	    accMdmMgrPoolPrefEnd	    INTEGER,
	    accMdmMgrPoolOutStart	    INTEGER,
	    accMdmMgrPoolOutEnd		    INTEGER,
	    accMdmMgrPoolAuxCfg		    OCTET STRING,
	    accMdmMgrPoolCurrConns	    INTEGER,
	    accMdmMgrPoolCurrAssigns	    INTEGER,
	    accMdmMgrPoolTotConns	    Counter,
	    accMdmMgrPoolTotAssigns	    Counter,
	    accMdmMgrPoolRsrcFails	    Counter,
	    accMdmMgrPoolConnFails	    Counter,
	    accMdmMgrPoolName		    OCTET STRING,
            accMdmMgrPoolErrProtMask        OCTET STRING,
            accMdmMgrPoolBadDiscs           Counter,
            accMdmMgrPoolModTypeCtrl        INTEGER,
            accMdmMgrPoolDroppedConns       Counter,
            accMdmMgrPoolHangUps            Counter,
            accMdmMgrPoolConnTimeout        INTEGER,
            accMdmMgrPoolDiscReasonCount    INTEGER,
            accMdmMgrPoolStartDelay         INTEGER,
            accMdmMgrPoolLicType            INTEGER,
            accMdmMgrPoolLicNumInst         INTEGER,
            accMdmMgrPoolLicStatus          INTEGER,
            accMdmMgrPoolLicInstCurrent56ks Counter,
            accMdmMgrPoolLicInstPeak56ks    Counter,
            accMdmMgrPoolLicInstDenial56ks  Counter,
            accMdmMgrPoolLicInstCurrentVoIPs   Counter,
            accMdmMgrPoolLicInstPeakVoIPs   Counter,
            accMdmMgrPoolLicInstDenialVoIPs Counter,
            accMdmMgrPoolMaxPwrV90 	    INTEGER,
	    accMdmMgrPoolMaxPwrV34	    INTEGER,
	    accMdmMgrPoolMaxPwrV32	    INTEGER
	    }
	    accMdmMgrPoolAction		OBJECT-TYPE
		SYNTAX	INTEGER {
		    add(1),
		    del(2)
		    }
		ACCESS	read-write
		STATUS	mandatory
		DESCRIPTION
		  "Action to add or delete a pool entry."
		::= { accMdmMgrPoolEntry 1 }
	    accMdmMgrPoolSize		OBJECT-TYPE
		SYNTAX	INTEGER
		ACCESS	read-write
		STATUS	mandatory
		DESCRIPTION
		  "Maximum number of modems that can be assigned
			to this pool."
		::= { accMdmMgrPoolEntry 2 }
	    accMdmMgrPoolMaxTx		OBJECT-TYPE
		SYNTAX	INTEGER
		ACCESS	read-write
		STATUS	mandatory
		DESCRIPTION
		  "Maximum transmit rate (bps) that modems assigned to this
			this pool can connect at."
		::= { accMdmMgrPoolEntry 3 }
	    accMdmMgrPoolCarrDtct	OBJECT-TYPE
		SYNTAX	INTEGER
		ACCESS	read-write
		STATUS	mandatory
		DESCRIPTION
		  "Carrier detect interval (ms) for modems assigned to
			this pool to use."
		::= { accMdmMgrPoolEntry 4 }
	    accMdmMgrPoolCarrLoss	OBJECT-TYPE
		SYNTAX	INTEGER
		ACCESS	read-write
		STATUS	mandatory
		DESCRIPTION
		  "Carrier loss interval (ms) for modems assigned to
			this pool to use."
		::= { accMdmMgrPoolEntry 5 }
	    accMdmMgrPoolModType	OBJECT-TYPE
		SYNTAX	INTEGER {
		    automode(1),
		    v110(14),
		    isdn(16),
		    v22b(22),
		    v32b(32),
		    v34(34),
		    k56(56),
		    v90(90)
		    }
		ACCESS	read-write
		STATUS	mandatory
		DESCRIPTION
		  "Modulation type to use for modems assigned to
		    this pool."
		::= { accMdmMgrPoolEntry 6 }
	    accMdmMgrPoolCompProt	OBJECT-TYPE
		SYNTAX	INTEGER {
		    enabled(1),
		    disabled(2)
		    }
		ACCESS	read-write
		STATUS	mandatory
		DESCRIPTION
		  "Enable/Disable compression protocol to use for 
		  modems assigned to this pool."
		::= { accMdmMgrPoolEntry 7 }
	    accMdmMgrPoolErrProt	OBJECT-TYPE
		SYNTAX	INTEGER {
		    auto(1),
		    lapm(2),
		    mnp(3),
		    buffered(4),
		    direct(5)
		    }
		ACCESS	read-write
		STATUS	mandatory
		DESCRIPTION
		  "Error correction to use for modems assigned to
		    this pool."
		::= { accMdmMgrPoolEntry 8 }
	    accMdmMgrPoolPrefStart	OBJECT-TYPE
		SYNTAX	INTEGER 
		ACCESS	read-write
		STATUS	mandatory
		DESCRIPTION
		  "The ifIndex for the start of the preferred modem range for
		    this pool."
		::= { accMdmMgrPoolEntry 9 }
	    accMdmMgrPoolPrefEnd	OBJECT-TYPE
		SYNTAX	INTEGER 
		ACCESS	read-write
		STATUS	mandatory
		DESCRIPTION
		  "The ifIndex for the end of the preferred modem range for
		    this pool."
		::= { accMdmMgrPoolEntry 10 }
	    accMdmMgrPoolOutStart	OBJECT-TYPE
		SYNTAX	INTEGER 
		ACCESS	read-write
		STATUS	mandatory
		DESCRIPTION
		  "The ifIndex for the start of the dialling interface range for
		    this pool."
		::= { accMdmMgrPoolEntry 11 }
	    accMdmMgrPoolOutEnd	OBJECT-TYPE
		SYNTAX	INTEGER 
		ACCESS	read-write
		STATUS	mandatory
		DESCRIPTION
		  "The ifIndex for the end of the dialling interface modem 
			range for this pool."
		::= { accMdmMgrPoolEntry 12 }
	    accMdmMgrPoolAuxCfg	OBJECT-TYPE
		SYNTAX	OCTET STRING 
		ACCESS	read-write
		STATUS	mandatory
		DESCRIPTION
		  "Auxillary NCI protocol data to issue to modems in this
		   pool before connection."
		::= { accMdmMgrPoolEntry 13 }
	    accMdmMgrPoolCurrConns	OBJECT-TYPE
		SYNTAX	INTEGER 
		ACCESS	read-only
		STATUS	mandatory
		DESCRIPTION
		  "The count of modems assigned to this pool that are	
		    currently connected."
		::= { accMdmMgrPoolEntry 14 }
	    accMdmMgrPoolCurrAssigns	OBJECT-TYPE
		SYNTAX	INTEGER 
		ACCESS	read-only
		STATUS	mandatory
		DESCRIPTION
		  "The count of modems currently assigned from this pool."
		::= { accMdmMgrPoolEntry 15 }
	    accMdmMgrPoolTotConns	OBJECT-TYPE
		SYNTAX	Counter 
		ACCESS	read-only
		STATUS	mandatory
		DESCRIPTION
		  "The count of modem calls that have been connected
		    from this pool."
		::= { accMdmMgrPoolEntry 16 }
	    accMdmMgrPoolTotAssigns	OBJECT-TYPE
		SYNTAX	Counter 
		ACCESS	read-only
		STATUS	mandatory
		DESCRIPTION
		  "The count of modem calls that have been assigned 
			modems from this pool."
		::= { accMdmMgrPoolEntry 17 }
	    accMdmMgrPoolRsrcFails	OBJECT-TYPE
		SYNTAX	Counter 
		ACCESS	read-only
		STATUS	mandatory
		DESCRIPTION
		  "The count of modem calls that have required modems
			from this pool, but have been rejected due
			to lack of available modems."
		::= { accMdmMgrPoolEntry 18 }
	    accMdmMgrPoolConnFails	OBJECT-TYPE
		SYNTAX	Counter 
		ACCESS	read-only
		STATUS	mandatory
		DESCRIPTION
		  "The count of modem calls that have been assigned modems
			from this pool, but have failed to connect."
		::= { accMdmMgrPoolEntry 19 }
	    accMdmMgrPoolName	OBJECT-TYPE
		SYNTAX	OCTET STRING 
		ACCESS	read-write
		STATUS	mandatory
		DESCRIPTION
		  "The name of this modem pool."
		::= { accMdmMgrPoolEntry 20 }
	    accMdmMgrPoolErrProtMask	OBJECT-TYPE
		SYNTAX	OCTET STRING 
		ACCESS	read-write
		STATUS	mandatory
		DESCRIPTION
		  "Combines error protocol types for the selected pool."
		::= { accMdmMgrPoolEntry 21 }
	    accMdmMgrPoolBadDiscs	OBJECT-TYPE
		SYNTAX	Counter
		ACCESS	read-write
		STATUS	obsolete
		DESCRIPTION
		  "Obsolete."
		::= { accMdmMgrPoolEntry 22 }
	    accMdmMgrPoolModTypeCtrl	OBJECT-TYPE
		SYNTAX	INTEGER {
		    unrestr(1),
		    restr(2)
		    }
		ACCESS	read-write
		STATUS	mandatory
		DESCRIPTION
		  "Modulation type control restricts the modulation type
			to one value for originating calls during test."
		::= { accMdmMgrPoolEntry 23 }
	    accMdmMgrPoolDroppedConns	OBJECT-TYPE
                SYNTAX  Counter
		ACCESS	read-only
		STATUS	mandatory
		DESCRIPTION
		  "Dropped Connections counts the number of normal near
			or normal far reasons before connection."
		::= { accMdmMgrPoolEntry 24 }
	    accMdmMgrPoolHangUps	OBJECT-TYPE
                SYNTAX  Counter
		ACCESS	read-only
		STATUS	mandatory
		DESCRIPTION
		  "Hangups counts a user-initiated normal near or far 
			reason before connection."
		::= { accMdmMgrPoolEntry 25 }
	    accMdmMgrPoolConnTimeout	OBJECT-TYPE
		SYNTAX	INTEGER 
		ACCESS	read-write
		STATUS	mandatory
		DESCRIPTION
		  "Sets the connection timeout.  This is the time from the
			call being routed to the server modem to the time
			the server modem times out waiting to connect."
		::= { accMdmMgrPoolEntry 26 }
            accMdmMgrPoolDiscReasonCount     OBJECT-TYPE
                SYNTAX  INTEGER
                ACCESS  read-write
                STATUS  mandatory
                DESCRIPTION
                  "not currently used"
                ::= { accMdmMgrPoolEntry 27 }
	    accMdmMgrPoolStartDelay	OBJECT-TYPE
		SYNTAX	INTEGER
		ACCESS	read-write
		STATUS	mandatory
		DESCRIPTION
		  "Sets the starting delay, also known as billing delay.
			This is the time from call being routed to the 
			server modem to the first tone back from the server."
		::= { accMdmMgrPoolEntry 28 }
            accMdmMgrPoolLicType        OBJECT-TYPE
                SYNTAX  INTEGER {
                    k56(53),
                    none(78),
                    voip(86)
                    }
                ACCESS  read-write
                STATUS  mandatory
                DESCRIPTION
                  "License type for this modem pool."
                ::= { accMdmMgrPoolEntry 29 }
            accMdmMgrPoolLicNumInst        OBJECT-TYPE
                SYNTAX  INTEGER
                ACCESS  read-write
                STATUS  mandatory
                DESCRIPTION
                  "Number of license instances"
                ::= { accMdmMgrPoolEntry 30 }
            accMdmMgrPoolLicStatus        OBJECT-TYPE
                SYNTAX  INTEGER {
                    add(1),
                    del(2)
                    }
                ACCESS  read-write
                STATUS  mandatory
                DESCRIPTION
                  "Action to add or delete a license entry."
                ::= { accMdmMgrPoolEntry 31 }
            accMdmMgrPoolLicInstCurrent56ks        OBJECT-TYPE
                SYNTAX  Counter
                ACCESS  read-only
                STATUS  mandatory
                DESCRIPTION
                  "Current count of 56k licenses for this pool."
                ::= { accMdmMgrPoolEntry 32 }
            accMdmMgrPoolLicInstPeak56ks       OBJECT-TYPE
                SYNTAX  Counter
                ACCESS  read-only
                STATUS  mandatory
                DESCRIPTION
                  "Peak count of 56k licenses for this pool."
                ::= { accMdmMgrPoolEntry 33 }
            accMdmMgrPoolLicInstDenial56ks       OBJECT-TYPE
                SYNTAX  Counter
                ACCESS  read-only
                STATUS  mandatory
                DESCRIPTION
                  "Total denials of 56k licenses for this pool."
                ::= { accMdmMgrPoolEntry 34 }
            accMdmMgrPoolLicInstCurrentVoIPs       OBJECT-TYPE
                SYNTAX  Counter
                ACCESS  read-only
                STATUS  mandatory
                DESCRIPTION
                  "Current count of VoIP licenses for this pool."
                ::= { accMdmMgrPoolEntry 35 }
            accMdmMgrPoolLicInstPeakVoIPs       OBJECT-TYPE
                SYNTAX  Counter
                ACCESS  read-only
                STATUS  mandatory
                DESCRIPTION
                  "Peak count of VoIP licenses for this pool."
                ::= { accMdmMgrPoolEntry 36 }
            accMdmMgrPoolLicInstDenialVoIPs       OBJECT-TYPE
                SYNTAX  Counter
                ACCESS  read-only
                STATUS  mandatory
                DESCRIPTION
                  "Total denials of VoIP licenses for this pool."
                ::= { accMdmMgrPoolEntry 37 }
	    accMdmMgrPoolMaxPwrV90	OBJECT-TYPE
		SYNTAX	INTEGER
		ACCESS	read-write
		STATUS	mandatory
		DESCRIPTION
		  "Max power level (-dB) for V.90 modem pool."
		::= { accMdmMgrPoolEntry 38 }
	    accMdmMgrPoolMaxPwrV34	OBJECT-TYPE
		SYNTAX	INTEGER
		ACCESS	read-write
		STATUS	mandatory
		DESCRIPTION
		  "Max power level (-dB) for V.34 modem pool."
		::= { accMdmMgrPoolEntry 39 }
	    accMdmMgrPoolMaxPwrV32	OBJECT-TYPE
		SYNTAX	INTEGER
		ACCESS	read-write
		STATUS	mandatory
		DESCRIPTION
		  "Max power level (-dB) for V.32 modem pool."
		::= { accMdmMgrPoolEntry 40 }
	-- End of Branch for per-modem pool objects 
	-- Branch for per-modem objects 
	accMdmMgrModemTable	OBJECT-TYPE
	    SYNTAX	SEQUENCE OF AccMdmMgrModemEntry
	    ACCESS	not-accessible
	    STATUS	mandatory
	    DESCRIPTION
	      " Modem table containing status
		information for all modems installed on this router."
	    ::= { accMdmMgr 3 }
	accMdmMgrModemEntry	OBJECT-TYPE
	    SYNTAX	AccMdmMgrModemEntry
	    ACCESS      not-accessible
	    STATUS      mandatory
    	    DESCRIPTION
	      " Status objects for a particular modem device."
	    INDEX { accMdmMgrModemName }
	    ::= { accMdmMgrModemTable 1 }
	AccMdmMgrModemEntry	::= SEQUENCE {
	    accMdmMgrModemState		INTEGER,
	    accMdmMgrModemConns		Counter,
	    accMdmMgrModemFails		Counter,
	    accMdmMgrModemRetrains	Counter,
	    accMdmMgrModemRxErrs	Counter,
	    accMdmMgrModemRetransmits	Counter,
	    accMdmMgrModemDiscReason	INTEGER,
	    accMdmMgrModemTxRate	INTEGER,
	    accMdmMgrModemRxRate	INTEGER,
	    accMdmMgrModemCompProt	INTEGER,
	    accMdmMgrModemCompPerc	INTEGER,
	    accMdmMgrModemModType	INTEGER,
	    accMdmMgrModemErrProt	INTEGER,
	    accMdmMgrModemAuxCfg	OCTET STRING,
	    accMdmMgrModemName		INTEGER,
	    accMdmMgrModemPool		OCTET STRING,
	    accMdmMgrModemConnName      INTEGER,		
	    accMdmMgrModemConnTxRate	INTEGER,		
	    accMdmMgrModemConnRxRate	INTEGER,		
	    accMdmMgrModemConnErrProt	INTEGER,		
	    accMdmMgrModemConnCompProt  INTEGER,		
	    accMdmMgrModemConnUser	OCTET STRING,		
	    accMdmMgrModemConnLogPort   OCTET STRING		
	    }
	    accMdmMgrModemState		OBJECT-TYPE
		SYNTAX	INTEGER {
		    connected(1),
		    disconnected(2),
                    oneFailure(3),
                    twoFailures(4),
                    threeFailures(5),
                    fourFailures(6),
                    fiveFailures(7),
                    sixFailures(8),
                    sevenFailures(9),
                    eightFailures(10),
                    nineFailures(11),
                    tenFailures(12)
		    }
		ACCESS	read-write
		STATUS	mandatory
		DESCRIPTION
		  "State of this modem device. It is either connected or
                   disconnected. If disconnected it may have suffered
                   connection failures, the (consecutive) number of which
                   can be deduced from the enumerated value.  The state
                   can be set only to the disconnected state, and only
                   if it is not in the connected state "
		::= { accMdmMgrModemEntry 1 }
	    accMdmMgrModemConns		OBJECT-TYPE
		SYNTAX	Counter
		ACCESS	read-only
		STATUS	mandatory
		DESCRIPTION
		  "Number of calls connected through this modem device."
		::= { accMdmMgrModemEntry 2 }
	    accMdmMgrModemFails		OBJECT-TYPE
		SYNTAX	Counter
		ACCESS	read-only
		STATUS	mandatory
		DESCRIPTION
		  "Number of calls attempted to connect through this
		   modem device that have failed."
		::= { accMdmMgrModemEntry 3 }
	    accMdmMgrModemRetrains		OBJECT-TYPE
		SYNTAX	Counter
		ACCESS	read-only
		STATUS	mandatory
		DESCRIPTION
		  "Count of retrains seen by this modem device."
		::= { accMdmMgrModemEntry 4 }
	    accMdmMgrModemRxErrs		OBJECT-TYPE
		SYNTAX	Counter
		ACCESS	read-only
		STATUS	mandatory
		DESCRIPTION
		  "Count of receive errors seen by this modem device."
		::= { accMdmMgrModemEntry 5 }
	    accMdmMgrModemRetransmits		OBJECT-TYPE
		SYNTAX	Counter
		ACCESS	read-only
		STATUS	mandatory
		DESCRIPTION
		  "Count of retransmissions attempted by this modem device."
		::= { accMdmMgrModemEntry 6 }
	    accMdmMgrModemDiscReason		OBJECT-TYPE
		SYNTAX	INTEGER {
		    nearEnd(1),
		    lossOfCarrier(5),
		    farEndNoErrorCorrect(6),
		    noRespToFeatNeg(7),
		    farEndSync(8),
		    noCommonFraming(9),
		    noCommonProtocol(10),
		    badRespToFeatNeg(11),
		    noSyncInfo(12),
		    farEnd(13),
		    noResponse(14),
		    protocolViolation(15)
		    }
		ACCESS	read-only
		STATUS	mandatory
		DESCRIPTION
		  "Reason for the modem disconnection for the last
		  connection made through this modem device."
		::= { accMdmMgrModemEntry 7 }
	    accMdmMgrModemTxRate		OBJECT-TYPE
		SYNTAX	INTEGER
		ACCESS	read-only
		STATUS	mandatory
		DESCRIPTION
		  "The bit rate of the data modulation carrier established
		  in the transmit direction for the current or last
		  connection on this modem device."
		::= { accMdmMgrModemEntry 8 }
	    accMdmMgrModemRxRate		OBJECT-TYPE
		SYNTAX	INTEGER
		ACCESS	read-only
		STATUS	mandatory
		DESCRIPTION
		  "The bit rate of the data modulation carrier established
		  in the receive direction for the current or last
		  connection on this modem device."
		::= { accMdmMgrModemEntry 9 }
	    accMdmMgrModemCompProt		OBJECT-TYPE
		SYNTAX	INTEGER {
		    v42bis(42),
		    mnp5(5),
		    none(255)
		    }
		ACCESS	read-only
		STATUS	mandatory
		DESCRIPTION
		  "The compression protocol established for the current or
		  last call on thie modem device."
		::= { accMdmMgrModemEntry 10 }
	    accMdmMgrModemCompPerc		OBJECT-TYPE
		SYNTAX	INTEGER
		ACCESS	read-only
		STATUS	mandatory
		DESCRIPTION
		  "The compression percentage obtained by the MNP5 or V42bis
		  protocol for the current or last call on this modem
		  device."
		::= { accMdmMgrModemEntry 11 }
	    accMdmMgrModemModType		OBJECT-TYPE
		SYNTAX	INTEGER {
                v17(1),
                v21(2),
                v22(3),
                v22b(4),
                v23(5),
                k56(6),
                v26t(7),
                v27t(8),
                v29(9),
                v32(10),
                v32b(11),
                v34(12),
		bell(13),
		v110(14),
		v90(15),
		isdn(16)
		    }
		ACCESS	read-only
		STATUS	mandatory
		DESCRIPTION
		  "The modulation protocol established for the current or
		  last call on thie modem device."
		::= { accMdmMgrModemEntry 12 }
	    accMdmMgrModemErrProt		OBJECT-TYPE
		SYNTAX	INTEGER {
                none(1),
                lapm(2), 
                alt(3),
                cell(4),
                direct(5),
		mnp(6)
		    }
		ACCESS	read-only
		STATUS	mandatory
		DESCRIPTION
		  "The error correction protocol established for the current or
		  last call on thie modem device."
		::= { accMdmMgrModemEntry 13 }
	    accMdmMgrModemAuxCfg	OBJECT-TYPE
		SYNTAX	OCTET STRING 
		ACCESS	read-write
		STATUS	mandatory
		DESCRIPTION
		  "Auxillary NCI protocol data to issue to this modem."
		::= { accMdmMgrModemEntry 14 }
	    accMdmMgrModemName		OBJECT-TYPE
		SYNTAX	INTEGER
		ACCESS	read-only
		STATUS	mandatory
		DESCRIPTION
		  "The ifIndex for this modem device."
		::= { accMdmMgrModemEntry 15 }
	    accMdmMgrModemPool		OBJECT-TYPE
		SYNTAX	OCTET STRING
		ACCESS	read-only
		STATUS	mandatory
		DESCRIPTION
		  "The pool name this modem is currently assigned to."
		::= { accMdmMgrModemEntry 16 }
            accMdmMgrModemConnName          OBJECT-TYPE
                SYNTAX  INTEGER
                ACCESS  read-only
                STATUS  mandatory
                DESCRIPTION
                  "The ifIndex for this ACTIVE modem device."
                ::= { accMdmMgrModemEntry 17 }
            accMdmMgrModemConnTxRate          OBJECT-TYPE
                SYNTAX  INTEGER
                ACCESS  read-only
                STATUS  mandatory
                DESCRIPTION
                  "The bit rate of the data modulation carrier established
                  in the transmit direction for the current 
                  connection on this ACTIVE modem device."
                ::= { accMdmMgrModemEntry 18 }
            accMdmMgrModemConnRxRate                OBJECT-TYPE
                SYNTAX  INTEGER
                ACCESS  read-only
                STATUS  mandatory
                DESCRIPTION
                  "The bit rate of the data modulation carrier established
                  in the receive direction for the current or last
                  connection on this modem device."
                ::= { accMdmMgrModemEntry 19 }
            accMdmMgrModemConnErrProt               OBJECT-TYPE
                SYNTAX  INTEGER {
                none(1),
                lapm(2),
                alt(3),
                cell(4),
                direct(5),
                mnp(6)
                    }
                ACCESS  read-only
                STATUS  mandatory
                DESCRIPTION
                  "The error correction protocol established for the current 
                   call on this modem device."
                ::= { accMdmMgrModemEntry 20 }
            accMdmMgrModemConnCompProt              OBJECT-TYPE
                SYNTAX  INTEGER {
                    v42bis(42),
                    mnp5(5),
                    none(255)
                    }
                ACCESS  read-only
                STATUS  mandatory
                DESCRIPTION
                  "The compression protocol established for the current
                   call on this modem device."
                ::= { accMdmMgrModemEntry 21 }
            accMdmMgrModemConnUser          OBJECT-TYPE
                SYNTAX  OCTET STRING
                ACCESS  read-only
                STATUS  mandatory
                DESCRIPTION
                  "The User connected to this modem device."
                ::= { accMdmMgrModemEntry 22 }
            accMdmMgrModemConnLogPort          OBJECT-TYPE
                SYNTAX  OCTET STRING
                ACCESS  read-only
                STATUS  mandatory
                DESCRIPTION
                  "The Logical Port associated to this modem device."
                ::= { accMdmMgrModemEntry 23 }
	-- Branch for modem disconnect statistics table (per pool) --
	accMdmMgrDiscStatTable	OBJECT-TYPE
	    SYNTAX	SEQUENCE OF AccMdmMgrDiscStatEntry
	    ACCESS	not-accessible
	    STATUS	mandatory
	    DESCRIPTION
	      "Modem disconnect statistics table (per pool)."
		::= { accMdmMgr 5 }
        accMdmMgrDiscStatEntry	OBJECT-TYPE
            SYNTAX	AccMdmMgrDiscStatEntry
	    ACCESS      not-accessible
	    STATUS      mandatory
	    DESCRIPTION
	     "."
	    INDEX { accMdmMgrPoolName }
	    ::= { accMdmMgrDiscStatTable 1 }
        AccMdmMgrDiscStatEntry	::= SEQUENCE {
		    accMdmMgrDiscStatPoolName		OCTET STRING,
		    accMdmMgrDiscStatNormalNears		Counter,
		    accMdmMgrDiscStatNormalFars		Counter,
		    accMdmMgrDiscStatInactivities		Counter,
		    accMdmMgrDiscStatCircuitLosses		Counter,
		    accMdmMgrDiscStatHalteds		Counter,
		    accMdmMgrDiscStatModTimeouts		Counter,
		    accMdmMgrDiscStatProtTimeouts		Counter,
		    accMdmMgrDiscStatBadControls		Counter,
		    accMdmMgrDiscStatFaxDetecteds		Counter,
		    accMdmMgrDiscStatCleardowns		Counter,
		    accMdmMgrDiscStatFuncUnsupporteds	Counter,
		    accMdmMgrDiscStatT30Sessions		Counter,
		    accMdmMgrDiscStatFX1Sessions		Counter,
		    accMdmMgrDiscStatDspDisc1s		Counter,
		    accMdmMgrDiscStatDspDisc2s		Counter,
		    accMdmMgrDiscStatDspDisc3s		Counter,
		    accMdmMgrDiscStatDspDisc4s		Counter,
		    accMdmMgrDiscStatLossOfCarriers		Counter,
		    accMdmMgrDiscStatModNegReqFails		Counter,
		    accMdmMgrDiscStatModReqFails		Counter,
		    accMdmMgrDiscStatModProtViolations	Counter,
		    accMdmMgrDiscStatModGeneralFails	Counter,
		    accMdmMgrDiscStatProtNegReqFails	Counter,
		    accMdmMgrDiscStatProtReqFails		Counter,
		    accMdmMgrDiscStatProtViolations		Counter,
		    accMdmMgrDiscStatProtCompFails		Counter,
		    accMdmMgrDiscStatProtGeneralFails	Counter,
		    accMdmMgrDiscStatProtNoResps		Counter,
		    accMdmMgrDiscStatProtStartFails		Counter,
		    accMdmMgrDiscStatProtGenTimeouts	Counter
		}
		accMdmMgrDiscStatPoolName		OBJECT-TYPE
		    SYNTAX  OCTET STRING
		    ACCESS	read-write
		    STATUS	mandatory
		    DESCRIPTION
		      "Modem Manager Disconnect Statistics Table -
			    modem pool name."
		    ::= { accMdmMgrDiscStatEntry 1 }
		accMdmMgrDiscStatNormalNears	OBJECT-TYPE
		    SYNTAX  Counter
		    ACCESS	read-write
		    STATUS	mandatory
		    DESCRIPTION
		      "Modem Manager Disconnect Statistics Table -
			    Normal Near statistic."
		    ::= { accMdmMgrDiscStatEntry 2 }
		accMdmMgrDiscStatNormalFars	OBJECT-TYPE
		    SYNTAX  Counter
		    ACCESS	read-write
		    STATUS	mandatory
		    DESCRIPTION
		      "Modem Manager Disconnect Statistics Table -
			    Normal Far statistic."
		    ::= { accMdmMgrDiscStatEntry 3 }
		accMdmMgrDiscStatInactivities	OBJECT-TYPE
		    SYNTAX  Counter
		    ACCESS	read-write
		    STATUS	mandatory
		    DESCRIPTION
		      "Modem Manager Disconnect Statistics Table -
			    Inactives count statistic."
		    ::= { accMdmMgrDiscStatEntry 4 }
		accMdmMgrDiscStatCircuitLosses	OBJECT-TYPE
		    SYNTAX  Counter
		    ACCESS	read-write
		    STATUS	mandatory
		    DESCRIPTION
		      "Modem Manager Disconnect Statistics Table -
			    Circuit Loss statistic."
		    ::= { accMdmMgrDiscStatEntry 5 }
		accMdmMgrDiscStatHalteds	OBJECT-TYPE
		    SYNTAX  Counter
		    ACCESS	read-write
		    STATUS	mandatory
		    DESCRIPTION
		      "Modem Manager Disconnect Statistics Table -
			    Halted statistic."
		    ::= { accMdmMgrDiscStatEntry 6 }
		accMdmMgrDiscStatModTimeouts	OBJECT-TYPE
		    SYNTAX  Counter
		    ACCESS	read-write
		    STATUS	mandatory
		    DESCRIPTION
		      "Modem Manager Disconnect Statistics Table -
			    Modulation Timeout statistic."
		    ::= { accMdmMgrDiscStatEntry 7 }
		accMdmMgrDiscStatProtTimeouts	OBJECT-TYPE
		    SYNTAX  Counter
		    ACCESS	read-write
		    STATUS	mandatory
		    DESCRIPTION
		      "Modem Manager Disconnect Statistics Table -
			    Protocol Timeout statistic."
		    ::= { accMdmMgrDiscStatEntry 8 }
		accMdmMgrDiscStatBadControls	OBJECT-TYPE
		    SYNTAX  Counter
		    ACCESS	read-write
		    STATUS	mandatory
		    DESCRIPTION
		      "Modem Manager Disconnect Statistics Table -
			    Bad Control statistic."
		    ::= { accMdmMgrDiscStatEntry 9 }
		accMdmMgrDiscStatFaxDetecteds	OBJECT-TYPE
		    SYNTAX  Counter
		    ACCESS	read-write
		    STATUS	mandatory
		    DESCRIPTION
		      "Modem Manager Disconnect Statistics Table -
			    FAX Detected statistic."
		    ::= { accMdmMgrDiscStatEntry 10 }
		accMdmMgrDiscStatCleardowns	OBJECT-TYPE
		    SYNTAX  Counter
		    ACCESS	read-write
		    STATUS	mandatory
		    DESCRIPTION
		      "Modem Manager Disconnect Statistics Table -
			    Clear Down statistic."
		    ::= { accMdmMgrDiscStatEntry 11 }
		accMdmMgrDiscStatFuncUnsupporteds	OBJECT-TYPE
		    SYNTAX  Counter
		    ACCESS	read-write
		    STATUS	mandatory
		    DESCRIPTION
		      "Modem Manager Disconnect Statistics Table -
			Unsupported Function statistic."
		::= { accMdmMgrDiscStatEntry 12 }
	    accMdmMgrDiscStatT30Sessions	OBJECT-TYPE
                SYNTAX  Counter
		ACCESS	read-write
		STATUS	mandatory
		DESCRIPTION
		  "Modem Manager Disconnect Statistics Table -
			T30 Sessions statistic."
		::= { accMdmMgrDiscStatEntry 13 }
	    accMdmMgrDiscStatFX1Sessions	OBJECT-TYPE
                SYNTAX  Counter
		ACCESS	read-write
		STATUS	mandatory
		DESCRIPTION
		  "Modem Manager Disconnect Statistics Table -
			FX1 Sessions statistic."
		::= { accMdmMgrDiscStatEntry 14 }
	    accMdmMgrDiscStatDspDisc1s	OBJECT-TYPE
                SYNTAX  Counter
		ACCESS	read-write
		STATUS	mandatory
		DESCRIPTION
		  "Modem Manager Disconnect Statistics Table -
			DSP Disconnect One statistic."
		::= { accMdmMgrDiscStatEntry 15 }
	    accMdmMgrDiscStatDspDisc2s	OBJECT-TYPE
                SYNTAX  Counter
		ACCESS	read-write
		STATUS	mandatory
		DESCRIPTION
		  "Modem Manager Disconnect Statistics Table -
			DSP Disconnect Two statistic."
		::= { accMdmMgrDiscStatEntry 16 }
	    accMdmMgrDiscStatDspDisc3s	OBJECT-TYPE
                SYNTAX  Counter
		ACCESS	read-write
		STATUS	mandatory
		DESCRIPTION
		  "Modem Manager Disconnect Statistics Table -
			DSP Disconnect Three statistic."
		::= { accMdmMgrDiscStatEntry 17 }
	    accMdmMgrDiscStatDspDisc4s	OBJECT-TYPE
                SYNTAX  Counter
		ACCESS	read-write
		STATUS	mandatory
		DESCRIPTION
		  "Modem Manager Disconnect Statistics Table -
			DSP Disconnect Four statistic."
		::= { accMdmMgrDiscStatEntry 18 }
	    accMdmMgrDiscStatLossOfCarriers	OBJECT-TYPE
                SYNTAX  Counter
		ACCESS	read-write
		STATUS	mandatory
		DESCRIPTION
		  "Modem Manager Disconnect Statistics Table -
			Loss of Carriers statistic."
		::= { accMdmMgrDiscStatEntry 19 }
	    accMdmMgrDiscStatModNegReqFails	OBJECT-TYPE
                SYNTAX  Counter
		ACCESS	read-write
		STATUS	mandatory
		DESCRIPTION
		  "Modem Manager Disconnect Statistics Table -
			Modulation Negotation Request Fail statistic."
		::= { accMdmMgrDiscStatEntry 20 }
	    accMdmMgrDiscStatModReqFails	OBJECT-TYPE
                SYNTAX  Counter
		ACCESS	read-write
		STATUS	mandatory
		DESCRIPTION
		  "Modem Manager Disconnect Statistics Table -
			Modulation Request Fail statistic."
		::= { accMdmMgrDiscStatEntry 21 }
	    accMdmMgrDiscStatModProtViolations	OBJECT-TYPE
                SYNTAX  Counter
		ACCESS	read-write
		STATUS	mandatory
		DESCRIPTION
		  "Modem Manager Disconnect Statistics Table -
			Modulation Protocol Violation statistic."
		::= { accMdmMgrDiscStatEntry 22 }
	    accMdmMgrDiscStatModGeneralFails	OBJECT-TYPE
                SYNTAX  Counter
		ACCESS	read-write
		STATUS	mandatory
		DESCRIPTION
		  "Modem Manager Disconnect Statistics Table -
			Modulation General Failure statistic."
		::= { accMdmMgrDiscStatEntry 23 }
	    accMdmMgrDiscStatProtNegReqFails	OBJECT-TYPE
                SYNTAX  Counter
		ACCESS	read-write
		STATUS	mandatory
		DESCRIPTION
		  "Modem Manager Disconnect Statistics Table -
			Protocol Negotiation Request Fail statistic."
		::= { accMdmMgrDiscStatEntry 24 }
	    accMdmMgrDiscStatProtReqFails	OBJECT-TYPE
                SYNTAX  Counter
		ACCESS	read-write
		STATUS	mandatory
		DESCRIPTION
		  "Modem Manager Disconnect Statistics Table -
			Protocol Negotiation Request Fail statistic."
		::= { accMdmMgrDiscStatEntry 25 }
	    accMdmMgrDiscStatProtViolations	OBJECT-TYPE
                SYNTAX  Counter
		ACCESS	read-write
		STATUS	mandatory
		DESCRIPTION
		  "Modem Manager Disconnect Statistics Table -
			Protocol Violations statistic."
		::= { accMdmMgrDiscStatEntry 26 }
	    accMdmMgrDiscStatProtCompFails	OBJECT-TYPE
                SYNTAX  Counter
		ACCESS	read-write
		STATUS	mandatory
		DESCRIPTION
		  "Modem Manager Disconnect Statistics Table -
			Compression Protocol Failure statistic."
		::= { accMdmMgrDiscStatEntry 27 }
	    accMdmMgrDiscStatProtGeneralFails	OBJECT-TYPE
                SYNTAX  Counter
		ACCESS	read-write
		STATUS	mandatory
		DESCRIPTION
		  "Modem Manager Disconnect Statistics Table -
			General Protocol Failure statistic."
		::= { accMdmMgrDiscStatEntry 28 }
	    accMdmMgrDiscStatProtNoResps	OBJECT-TYPE
                SYNTAX  Counter
		ACCESS	read-write
		STATUS	mandatory
		DESCRIPTION
		  "Modem Manager Disconnect Statistics Table -
			Protocol No Response statistic."
		::= { accMdmMgrDiscStatEntry 29 }
	    accMdmMgrDiscStatProtStartFails	OBJECT-TYPE
                SYNTAX  Counter
		ACCESS	read-write
		STATUS	mandatory
		DESCRIPTION
		  "Modem Manager Disconnect Statistics Table -
			Protocol Start Failure statistic."
		::= { accMdmMgrDiscStatEntry 30 }
	    accMdmMgrDiscStatProtGenTimeouts	OBJECT-TYPE
                SYNTAX  Counter
		ACCESS	read-write
		STATUS	mandatory
		DESCRIPTION
		  "Modem Manager Disconnect Statistics Table -
			General Protocol Timeout statistic."
		::= { accMdmMgrDiscStatEntry 31 }
-- The following are the objects for the Modem Async Pool MIB --
                accMdmMgrAsyncPoolTable OBJECT-TYPE
                        SYNTAX SEQUENCE OF AccMdmMgrAsyncPoolEntry
                        ACCESS not-accessible
                        STATUS mandatory
                        DESCRIPTION
                        "The Modem Async Pool Table"
                        ::= { accMdmMgr 6 }
                accMdmMgrAsyncPoolEntry OBJECT-TYPE
                        SYNTAX AccMdmMgrAsyncPoolEntry
                        ACCESS not-accessible
                        STATUS mandatory
                        DESCRIPTION
                        "An entry in the Modem Manager Async Pool Table"
                        INDEX  { accMdmMgrAsyncName }
                        ::= { accMdmMgrAsyncPoolTable 1 }
                AccMdmMgrAsyncPoolEntry ::= SEQUENCE {
                        accMdmMgrAsyncName DisplayString,
                        accMdmMgrAsyncFrmType INTEGER ,
                        accMdmMgrAsyncMaxRcvFrmInt INTEGER ,
                        accMdmMgrAsyncMaxRcvIdleInt INTEGER ,
                        accMdmMgrAsyncPoolEntryStatus INTEGER
                        }
                accMdmMgrAsyncName OBJECT-TYPE
                        SYNTAX  DisplayString
                        ACCESS  read-write
                        STATUS  mandatory
                        DESCRIPTION
                        "Name of the modem pool for which the parameters apply."
                        ::= { accMdmMgrAsyncPoolEntry 1 }
                accMdmMgrAsyncFrmType OBJECT-TYPE
                        SYNTAX  INTEGER {
                                deleted (1),
                                transparent(2)
                                }
                        ACCESS  read-write
                        STATUS  mandatory
                        DESCRIPTION
                        "Async framing type. Transparent framing is used to
                        support async POS devices"
                        ::= { accMdmMgrAsyncPoolEntry 2 }
                accMdmMgrAsyncMaxRcvFrmInt OBJECT-TYPE
                        SYNTAX  INTEGER (10..512)
                        ACCESS  read-write
                        STATUS  mandatory
                        DESCRIPTION
                        "Maximum total character intervals before a receive
                        frame is closed off and delivered for forwarding."
                        ::= { accMdmMgrAsyncPoolEntry 3 }
                accMdmMgrAsyncMaxRcvIdleInt OBJECT-TYPE
                        SYNTAX  INTEGER (5..255)
                        ACCESS  read-write
                        STATUS  mandatory
                        DESCRIPTION
                        "Maximum idle character intervals between characters
                        before a receive frame is closed off and delivered for
                        forwarding."
                        ::= { accMdmMgrAsyncPoolEntry 4 }
                accMdmMgrAsyncPoolEntryStatus OBJECT-TYPE
                        SYNTAX  INTEGER {
                                valid(1),
                                deleted(2)
                                }
                        ACCESS  read-write
                        STATUS  mandatory
                        DESCRIPTION
                        "Status of the pool entry, valid or deleted."
                        ::= { accMdmMgrAsyncPoolEntry 5 }

END
