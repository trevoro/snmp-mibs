Wellfleet-AT-MIB DEFINITIONS ::= BEGIN

-- Created by mdl2asn version 3.1
-- Creation date: Wed Aug 30 16:36:54 EDT 1995


    IMPORTS

      IpAddress, Counter 
        FROM RFC1155-SMI
      OBJECT-TYPE
        FROM RFC-1212
      DisplayString 
        FROM RFC1213-MIB
      wfAppletalkGroup
        FROM Wellfleet-COMMON-MIB;


    wfAppleBase	OBJECT IDENTIFIER ::= { wfAppletalkGroup 1 }

    wfAppleBaseDelete OBJECT-TYPE
        SYNTAX	INTEGER {
    		    created(1),
    		    deleted(2)
    		}
        ACCESS	read-write
        STATUS	mandatory
        DESCRIPTION
                "Create/Delete parameter for determining whether
                or not AppleTalk is configured on this slot."
        DEFVAL	{ created }
        ::= { wfAppleBase 1 }

    wfAppleBaseDisable OBJECT-TYPE
        SYNTAX	INTEGER {
    		    enabled(1),
    		    disabled(2)
    		}
        ACCESS	read-write
        STATUS	mandatory
        DESCRIPTION
                "Enable/Disable parameter for determining whether
                or not to startup AppleTalk."
        DEFVAL	{ enabled }
        ::= { wfAppleBase 2 }

    wfAppleBaseState OBJECT-TYPE
        SYNTAX	INTEGER {
    		    up(1),
    		    down(2),
    		    init(3),
    		    notpres(4)
    		}
        ACCESS	read-only
        STATUS	mandatory
        DESCRIPTION
                "This parameter relfects the current state of AppleTalk."
        DEFVAL	{ down }
        ::= { wfAppleBase 3 }

    wfAppleBaseDebugLevel OBJECT-TYPE
        SYNTAX	INTEGER
        ACCESS	read-write
        STATUS	mandatory
        DESCRIPTION
                "Appletalk has control of what debug and info messages
                are printed."
        ::= { wfAppleBase 4 }

    wfAppleBaseDdpQueLen OBJECT-TYPE
        SYNTAX	INTEGER(10..2147483647)
        ACCESS	read-write
        STATUS	mandatory
        DESCRIPTION
                "wfAppleBaseDdpQueLen is no longer used."
        DEFVAL	{ 20 }
        ::= { wfAppleBase 5 }

    wfAppleBaseHomedPort OBJECT-TYPE
        SYNTAX	INTEGER
        ACCESS	read-write
        STATUS	mandatory
        DESCRIPTION
                "The circuit number of the port on which NBP will register this
                router."
        ::= { wfAppleBase 6 }

    wfAppleBaseTotalNets OBJECT-TYPE
        SYNTAX	INTEGER
        ACCESS	read-only
        STATUS	mandatory
        DESCRIPTION
                "The total number of networks from all
                routing protocols."
        ::= { wfAppleBase 7 }

    wfAppleBaseTotalZones OBJECT-TYPE
        SYNTAX	INTEGER
        ACCESS	read-only
        STATUS	mandatory
        DESCRIPTION
                "The total number of zone/rtmp associations. Also
                the total number of instances of zones in the
                mib."
        ::= { wfAppleBase 8 }

    wfAppleBaseTotalZoneNames OBJECT-TYPE
        SYNTAX	INTEGER
        ACCESS	read-only
        STATUS	mandatory
        DESCRIPTION
                "The total number of unique zone names."
        ::= { wfAppleBase 9 }

    wfAppleBaseTotalAarpEntries OBJECT-TYPE
        SYNTAX	INTEGER
        ACCESS	read-only
        STATUS	mandatory
        DESCRIPTION
                "The total number of AARP entries."
        ::= { wfAppleBase 10 }

    wfAppleBaseEstimatedNets OBJECT-TYPE
        SYNTAX	INTEGER
        ACCESS	read-write
        STATUS	mandatory
        DESCRIPTION
                "This parameter indicates the estimated number of networks
                that the router will need to keep in its routing table."
        ::= { wfAppleBase 11 }

    wfAppleBaseEstimatedHosts OBJECT-TYPE
        SYNTAX	INTEGER
        ACCESS	read-write
        STATUS	mandatory
        DESCRIPTION
                "This parameter indicates the estimated number of end stations
                that the router will need to keep in its AARP table.  This should
                not include end stations that are reached through another router."
        ::= { wfAppleBase 12 }

    wfAppleMacIPBaseDelete OBJECT-TYPE
        SYNTAX  INTEGER {
                    created(1),
                    deleted(2)
                }
        ACCESS  read-write
        STATUS  mandatory
        DESCRIPTION
                "Create/Delete parameter for determining whether
                or not MacIP is configured on this box."
        DEFVAL  { deleted }
        ::= { wfAppleBase 13 }

    wfAppleMacIPBaseDisable OBJECT-TYPE
        SYNTAX  INTEGER {
                    enabled(1),
                    disabled(2)
                }
        ACCESS  read-write
        STATUS  mandatory
        DESCRIPTION
                "Enable/Disable parameter for determining whether
                or not to startup MacIP."
        DEFVAL  { disabled }
        ::= { wfAppleBase 14 }

    wfAppleMacIPBaseState OBJECT-TYPE
        SYNTAX  INTEGER {
                    up(1),
                    down(2),
                    init(3),
                    notpres(4)
                }
        ACCESS  read-only
        STATUS  mandatory
        DESCRIPTION
                "This parameter relfects the current state of MACIP."
        DEFVAL  { down }
        ::= { wfAppleBase 15 }

    wfAppleMacIPZone OBJECT-TYPE
        SYNTAX  DisplayString
        ACCESS  read-write
        STATUS  mandatory
        DESCRIPTION
                "The zone that this router is in. (For MacIP)"
        ::= { wfAppleBase 16 }

    wfMacIPAddress1 OBJECT-TYPE
        SYNTAX  IpAddress
        ACCESS  read-write
        STATUS  mandatory
        DESCRIPTION
                "The base IP address used for assignment of addresses"
        ::= { wfAppleBase 17 }

    wfMacIPLowerIpAddress1 OBJECT-TYPE
        SYNTAX  INTEGER (1..254)
        ACCESS  read-write
        STATUS  mandatory
        DESCRIPTION
                "The base IP address used for assignment of addresses"
        DEFVAL  { 1 }
        ::= { wfAppleBase 18 }

    wfMacIPUpperIpAddress1 OBJECT-TYPE
        SYNTAX  INTEGER (1..254)
        ACCESS  read-write
        STATUS  mandatory
        DESCRIPTION
                "The base IP address used for assignment of addresses"
        DEFVAL  { 1 }
        ::= { wfAppleBase 19 }

    wfMacIPAddress2 OBJECT-TYPE
        SYNTAX  IpAddress
        ACCESS  read-write
        STATUS  mandatory
        DESCRIPTION
                "The base IP address used for assignment of addresses"
        ::= { wfAppleBase 20 }

    wfMacIPLowerIpAddress2 OBJECT-TYPE
        SYNTAX  INTEGER (1..254)
        ACCESS  read-write
        STATUS  mandatory
        DESCRIPTION
                "The base IP address used for assignment of addresses"
        DEFVAL  { 1 }
        ::= { wfAppleBase 21 }

    wfMacIPUpperIpAddress2 OBJECT-TYPE
        SYNTAX  INTEGER (1..254)
        ACCESS  read-write
        STATUS  mandatory
        DESCRIPTION
                "The base IP address used for assignment of addresses"
        DEFVAL  { 1 }
        ::= { wfAppleBase 22 }

    wfMacIPAddress3 OBJECT-TYPE
        SYNTAX  IpAddress
        ACCESS  read-write
        STATUS  mandatory
        DESCRIPTION
                "The base IP address used for assignment of addresses"
        ::= { wfAppleBase 23 }

    wfMacIPLowerIpAddress3 OBJECT-TYPE
        SYNTAX  INTEGER (1..254)
        ACCESS  read-write
        STATUS  mandatory
        DESCRIPTION
                "The base IP address used for assignment of addresses"
        DEFVAL  { 1 }
        ::= { wfAppleBase 24 }

    wfMacIPUpperIpAddress3 OBJECT-TYPE
        SYNTAX  INTEGER (1..254)
        ACCESS  read-write
        STATUS  mandatory
        DESCRIPTION
                "The base IP address used for assignment of addresses"
        DEFVAL  { 1 }
        ::= { wfAppleBase 25 }

    wfAppleMacIPAddressTimeOut OBJECT-TYPE
        SYNTAX  INTEGER (1..255)
        ACCESS  read-write
        STATUS  mandatory
        DESCRIPTION
                "The base IP address used for assignment of addresses"
        DEFVAL  { 5 }
        ::= { wfAppleBase 26 }

    wfAppleMacIPServerRequests OBJECT-TYPE
        SYNTAX  INTEGER
        ACCESS  read-only
        STATUS  mandatory
        DESCRIPTION
                "The Number of times this router has been asked if it
                 is an MacIP Server"
        ::= { wfAppleBase 27 }

   wfAppleMacIPServerResponces OBJECT-TYPE
        SYNTAX  INTEGER
        ACCESS  read-only
        STATUS  mandatory
        DESCRIPTION
                "The Number of times this router has responded to server
                 requests."
        ::= { wfAppleBase 28 }

    wfAppleRtmpTable OBJECT-TYPE
        SYNTAX	SEQUENCE OF WfAppleRtmpEntry
        ACCESS	not-accessible
        STATUS	mandatory
        DESCRIPTION
                "The table of elements of AppleTalk's routing RTMP table"
        ::= { wfAppletalkGroup 2 }

    wfAppleRtmpEntry OBJECT-TYPE
        SYNTAX	WfAppleRtmpEntry
        ACCESS	not-accessible
        STATUS	mandatory
        DESCRIPTION
                "An entry in the Routing table"
        INDEX	{ wfAppleRtmpNetStart,
    		  wfAppleRtmpNetEnd }
        ::= { wfAppleRtmpTable 1 }

    WfAppleRtmpEntry ::= SEQUENCE {
    	    wfAppleRtmpNetStart
    		INTEGER,
    	    wfAppleRtmpNetEnd
    		INTEGER,
    	    wfAppleRtmpPort
    		INTEGER,
    	    wfAppleRtmpHops
    		INTEGER,
    	    wfAppleRtmpNextHopNet
    		INTEGER,
    	    wfAppleRtmpNextHopNode
    		INTEGER,
    	    wfAppleRtmpState
    		INTEGER,
    	    wfAppleRtmpProto
    		INTEGER,
    	    wfAppleRtmpAurpNextHopIpAddress
    		IpAddress
        }

    wfAppleRtmpNetStart OBJECT-TYPE
        SYNTAX	INTEGER
        ACCESS	read-only
        STATUS	mandatory
        DESCRIPTION
                "The destinatination network range of this
                route to which this entry pertains.  The route
                is considered the best route to that network.
                There wil only be one route to a single destination.
                The address will be in the form of
                [network min - network max]."
        ::= { wfAppleRtmpEntry 1 }

    wfAppleRtmpNetEnd OBJECT-TYPE
        SYNTAX	INTEGER
        ACCESS	read-only
        STATUS	mandatory
        DESCRIPTION
                "The network max in the destination network range
                to which the routing entry pertains."
        ::= { wfAppleRtmpEntry 2 }

    wfAppleRtmpPort OBJECT-TYPE
        SYNTAX	INTEGER
        ACCESS	read-only
        STATUS	mandatory
        DESCRIPTION
                "The index value which uniquely identifies the
                local interface through which the next hop of
                this route should be reached.  The interface
                identified by a particular value of this index
                is the same interface as identified by the same
                value of ifIndex."
        ::= { wfAppleRtmpEntry 3 }

    wfAppleRtmpHops OBJECT-TYPE
        SYNTAX	INTEGER
        ACCESS	read-only
        STATUS	mandatory
        DESCRIPTION
                "The routing metric to get to this destination
                network.  The measurement is in terms of hops."
        ::= { wfAppleRtmpEntry 4 }

    wfAppleRtmpNextHopNet OBJECT-TYPE
        SYNTAX	INTEGER
        ACCESS	read-only
        STATUS	mandatory
        DESCRIPTION
                "The AppleTalk net of the next hop router for this route."
        ::= { wfAppleRtmpEntry 5 }

    wfAppleRtmpNextHopNode OBJECT-TYPE
        SYNTAX	INTEGER
        ACCESS	read-only
        STATUS	mandatory
        DESCRIPTION
                "The AppleTalk node of the next hop router for this route."
        ::= { wfAppleRtmpEntry 6 }

    wfAppleRtmpState OBJECT-TYPE
        SYNTAX	INTEGER {
    		    good(1),
    		    suspect(2),
    		    goingbad(3),
    		    bad(4)
    		}
        ACCESS	read-only
        STATUS	mandatory
        DESCRIPTION
                "The state of this routing entry: 1 = Good,
                2 = Suspect, 3 = GoingBad, or 4 = Bad."
        ::= { wfAppleRtmpEntry 7 }

    wfAppleRtmpProto OBJECT-TYPE
        SYNTAX	INTEGER {
    		    rtmp(1),
    		    aurp(2),
    		    static(3)
    		}
        ACCESS	read-only
        STATUS	mandatory
        DESCRIPTION
                "The protocol this routing entry was learned through:
                1 = RTMP, 2 = AURP, 3 = Static Route."
        ::= { wfAppleRtmpEntry 8 }

    wfAppleRtmpAurpNextHopIpAddress OBJECT-TYPE
        SYNTAX	IpAddress
        ACCESS	read-only
        STATUS	mandatory
        DESCRIPTION
                "The next hop address if this route was learned
                through AURP."
        ::= { wfAppleRtmpEntry 9 }

    wfApplePortTable OBJECT-TYPE
        SYNTAX	SEQUENCE OF WfApplePortEntry
        ACCESS	not-accessible
        STATUS	mandatory
        DESCRIPTION
                "The port descriptor table that describes the
                configuration parameters for this port of
                the AppleTalk Router."
        ::= { wfAppletalkGroup 3 }

    wfApplePortEntry OBJECT-TYPE
        SYNTAX	WfApplePortEntry
        ACCESS	not-accessible
        STATUS	mandatory
        DESCRIPTION
                "An entry in the Port Descriptor table"
        INDEX	{ wfApplePortCircuit }
        ::= { wfApplePortTable 1 }

    WfApplePortEntry ::= SEQUENCE {
    	    wfApplePortDelete
    		INTEGER,
    	    wfApplePortDisable
    		INTEGER,
    	    wfApplePortCircuit
    		INTEGER,
    	    wfApplePortState
    		INTEGER,
    	    wfApplePortType
    		INTEGER,
    	    wfApplePortCksumDisable
    		INTEGER,
    	    wfApplePortTrEndStation
    		INTEGER,
    	    wfApplePortGniForever
    		INTEGER,
    	    wfApplePortAarpFlush
    		INTEGER,
    	    wfApplePortMacAddress
    		OCTET STRING,
    	    wfApplePortNodeId
    		INTEGER,
    	    wfApplePortNetwork
    		INTEGER,
    	    wfApplePortNetStart
    		INTEGER,
    	    wfApplePortNetEnd
    		INTEGER,
    	    wfApplePortDfltZone
    		DisplayString,
    	    wfApplePortCurMacAddress
    		OCTET STRING,
    	    wfApplePortCurNodeId
    		INTEGER,
    	    wfApplePortCurNetwork
    		INTEGER,
    	    wfApplePortCurNetStart
    		INTEGER,
    	    wfApplePortCurNetEnd
    		INTEGER,
    	    wfApplePortCurDfltZone
    		DisplayString,
    	    wfApplePortAarpProbeRxs
    		Counter,
    	    wfApplePortAarpProbeTxs
    		Counter,
    	    wfApplePortAarpReqRxs
    		Counter,
    	    wfApplePortAarpReqTxs
    		Counter,
    	    wfApplePortAarpRspRxs
    		Counter,
    	    wfApplePortAarpRspTxs
    		Counter,
    	    wfApplePortDdpOutRequests
    		Counter,
    	    wfApplePortDdpInReceives
    		Counter,
    	    wfApplePortDdpInLocalDatagrams
    		Counter,
    	    wfApplePortDdpNoProtocolHandlers
    		Counter,
    	    wfApplePortDdpTooShortErrors
    		Counter,
    	    wfApplePortDdpTooLongErrors
    		Counter,
    	    wfApplePortDdpChecksumErrors
    		Counter,
    	    wfApplePortDdpForwRequests
    		Counter,
    	    wfApplePortDdpOutNoRoutes
    		Counter,
    	    wfApplePortDdpBroadcastErrors
    		Counter,
    	    wfApplePortDdpHopCountErrors
    		Counter,
    	    wfApplePortRtmpInDataPkts
    		Counter,
    	    wfApplePortRtmpOutDataPkts
    		Counter,
    	    wfApplePortRtmpInRequestPkts
    		Counter,
    	    wfApplePortRtmpNextIREqualChanges
    		Counter,
    	    wfApplePortRtmpNextIRLessChanges
    		Counter,
    	    wfApplePortRtmpRouteDeletes
    		Counter,
    	    wfApplePortRtmpNetworkMismatchErrors
    		Counter,
    	    wfApplePortRtmpRoutingTableOverflows
    		Counter,
    	    wfApplePortZipInZipQueries
    		Counter,
    	    wfApplePortZipInZipReplies
    		Counter,
    	    wfApplePortZipOutZipReplies
    		Counter,
    	    wfApplePortZipInZipExtendedReplies
    		Counter,
    	    wfApplePortZipOutZipExtendedReplies
    		Counter,
    	    wfApplePortZipInGetZoneLists
    		Counter,
    	    wfApplePortZipOutGetZoneListReplies
    		Counter,
    	    wfApplePortZipInGetLocalZones
    		Counter,
    	    wfApplePortZipOutGetLocalZoneReplies
    		Counter,
    	    wfApplePortZipInGetMyZones
    		Counter,
    	    wfApplePortZipOutGetMyZoneReplies
    		Counter,
    	    wfApplePortZipZoneConflictErrors
    		Counter,
    	    wfApplePortZipInGetNetInfos
    		Counter,
    	    wfApplePortZipOutGetNetInfoReplies
    		Counter,
    	    wfApplePortZipZoneOutInvalids
    		Counter,
    	    wfApplePortZipAddressInvalids
    		Counter,
    	    wfApplePortZipOutGetNetInfos
    		Counter,
    	    wfApplePortZipInGetNetInfoReplies
    		Counter,
    	    wfApplePortZipOutZipQueries
    		Counter,
    	    wfApplePortZipInErrors
    		Counter,
    	    wfApplePortNbpInLookUpRequests
    		Counter,
    	    wfApplePortNbpInLookUpReplies
    		Counter,
    	    wfApplePortNbpInBroadcastRequests
    		Counter,
    	    wfApplePortNbpInForwardRequests
    		Counter,
    	    wfApplePortNbpOutLookUpRequests
    		Counter,
    	    wfApplePortNbpOutLookUpReplies
    		Counter,
    	    wfApplePortNbpOutBroadcastRequests
    		Counter,
    	    wfApplePortNbpOutForwardRequests
    		Counter,
    	    wfApplePortNbpRegistrationFailures
    		Counter,
    	    wfApplePortNbpInErrors
    		Counter,
    	    wfApplePortEchoRequests
    		Counter,
    	    wfApplePortEchoReplies
    		Counter,
    	    wfApplePortInterfaceCost
    		INTEGER,
    	    wfApplePortWanBroadcastAddress
    		OCTET STRING,
    	    wfApplePortWanSplitHorizonDisable
    		INTEGER,
    	    wfApplePortZoneFilterType
    		INTEGER,
            wfApplePortMacIPDisable
                INTEGER
        }

    wfApplePortDelete OBJECT-TYPE
        SYNTAX	INTEGER {
    		    created(1),
    		    deleted(2)
    		}
        ACCESS	read-write
        STATUS	mandatory
        DESCRIPTION
                "Create/Delete parameter. Users perform an SNMP SET
                operation on this object to create/delete an AppleTalk
                interface. The default is create."
        DEFVAL	{ created }
        ::= { wfApplePortEntry 1 }

    wfApplePortDisable OBJECT-TYPE
        SYNTAX	INTEGER {
    		    enabled(1),
    		    disabled(2)
    		}
        ACCESS	read-write
        STATUS	mandatory
        DESCRIPTION
                "Enable/Disable parameter. Users perforn an SNMP SET
                operation on this object to enable/disable an AppleTalk
                interface.  Default is enabled."
        DEFVAL	{ enabled }
        ::= { wfApplePortEntry 2 }

    wfApplePortCircuit OBJECT-TYPE
        SYNTAX	INTEGER
        ACCESS	read-only
        STATUS	mandatory
        DESCRIPTION
                "The circuit number for this interface"
        ::= { wfApplePortEntry 3 }

    wfApplePortState OBJECT-TYPE
        SYNTAX	INTEGER {
    		    up(1),
    		    down(2)
    		}
        ACCESS	read-only
        STATUS	mandatory
        DESCRIPTION
                "The current state of the AppleTalk port."
        DEFVAL	{ down }
        ::= { wfApplePortEntry 4 }

    wfApplePortType OBJECT-TYPE
        SYNTAX	INTEGER
        ACCESS	read-write
        STATUS	mandatory
        DESCRIPTION
                "wfApplePortType is reserved for future use"
        ::= { wfApplePortEntry 5 }

    wfApplePortCksumDisable OBJECT-TYPE
        SYNTAX	INTEGER {
    		    enabled(1),
    		    disabled(2)
    		}
        ACCESS	read-write
        STATUS	mandatory
        DESCRIPTION
                "Flag to enable/disable the calculation of the
                DDP checksum for packets sourced by the router
                over this interface.  This value has no effect
                on incoming packets."
        DEFVAL	{ disabled }
        ::= { wfApplePortEntry 6 }

    wfApplePortTrEndStation OBJECT-TYPE
        SYNTAX	INTEGER {
    		    enabled(1),
    		    disabled(2)
    		}
        ACCESS	read-write
        STATUS	mandatory
        DESCRIPTION
                "When an interface is running token ring this attribute
                allows for end station source routing. If the interface
                is not running token ring the attribute has no meaning."
        DEFVAL	{ disabled }
        ::= { wfApplePortEntry 7 }

    wfApplePortGniForever OBJECT-TYPE
        SYNTAX	INTEGER
        ACCESS	read-write
        STATUS	obsolete
        DESCRIPTION
                "wfApplePortGniForever is ignored. A non-seed interface will send
                GetNetInfos every 10 seconds until it gets a response."
        ::= { wfApplePortEntry 8 }

    wfApplePortAarpFlush OBJECT-TYPE
        SYNTAX	INTEGER
        ACCESS	read-write
        STATUS	mandatory
        DESCRIPTION
                "The maximum age (in minutes) of an aarp entry before it is deleted.
                Defaults to 12 hours.  Minimum values is five minutes."
        ::= { wfApplePortEntry 9 }

    wfApplePortMacAddress OBJECT-TYPE
        SYNTAX	OCTET STRING
        ACCESS	read-write
        STATUS	mandatory
        DESCRIPTION
                "Configured mac address"
        ::= { wfApplePortEntry 10 }

    wfApplePortNodeId OBJECT-TYPE
        SYNTAX	INTEGER
        ACCESS	read-write
        STATUS	mandatory
        DESCRIPTION
                "The AppleTalk node id configured for this port/interface.
                If PortNodeId or PortNetwork is zero the interface will try to
                acquire an address dynamically."
        ::= { wfApplePortEntry 11 }

    wfApplePortNetwork OBJECT-TYPE
        SYNTAX	INTEGER
        ACCESS	read-write
        STATUS	mandatory
        DESCRIPTION
                "The AppleTalk network number configured for this port/interface.
                If PortNodeId or PortNetwork is zero the interface will try to
                acquire an address dynamically."
        ::= { wfApplePortEntry 12 }

    wfApplePortNetStart OBJECT-TYPE
        SYNTAX	INTEGER
        ACCESS	read-write
        STATUS	mandatory
        DESCRIPTION
                "The Network start value in the network range for this interface/port.
                If this is zero, the port is considered non-seed."
        ::= { wfApplePortEntry 13 }

    wfApplePortNetEnd OBJECT-TYPE
        SYNTAX	INTEGER
        ACCESS	read-write
        STATUS	mandatory
        DESCRIPTION
                "The Network end value in the network range
                for this interface/port."
        ::= { wfApplePortEntry 14 }

    wfApplePortDfltZone OBJECT-TYPE
        SYNTAX	DisplayString
        ACCESS	read-write
        STATUS	mandatory
        DESCRIPTION
                "The default zone name for this network range/
                interface. "
        ::= { wfApplePortEntry 15 }

    wfApplePortCurMacAddress OBJECT-TYPE
        SYNTAX	OCTET STRING
        ACCESS	read-only
        STATUS	mandatory
        DESCRIPTION
                "Mac Address used"
        ::= { wfApplePortEntry 16 }

    wfApplePortCurNodeId OBJECT-TYPE
        SYNTAX	INTEGER
        ACCESS	read-only
        STATUS	mandatory
        DESCRIPTION
                "The AppleTalk node id of this port"
        ::= { wfApplePortEntry 17 }

    wfApplePortCurNetwork OBJECT-TYPE
        SYNTAX	INTEGER
        ACCESS	read-only
        STATUS	mandatory
        DESCRIPTION
                "The network number for this port."
        ::= { wfApplePortEntry 18 }

    wfApplePortCurNetStart OBJECT-TYPE
        SYNTAX	INTEGER
        ACCESS	read-only
        STATUS	mandatory
        DESCRIPTION
                "The Network start value in the network range
                for this port."
        ::= { wfApplePortEntry 19 }

    wfApplePortCurNetEnd OBJECT-TYPE
        SYNTAX	INTEGER
        ACCESS	read-only
        STATUS	mandatory
        DESCRIPTION
                "The Network end value in the network range
                for this port."
        ::= { wfApplePortEntry 20 }

    wfApplePortCurDfltZone OBJECT-TYPE
        SYNTAX	DisplayString
        ACCESS	read-only
        STATUS	mandatory
        DESCRIPTION
                "The default zone name for this port"
        ::= { wfApplePortEntry 21 }

    wfApplePortAarpProbeRxs OBJECT-TYPE
        SYNTAX	Counter
        ACCESS	read-only
        STATUS	mandatory
        DESCRIPTION
                "The number of AARP Probe packets received on
                this interface."
        ::= { wfApplePortEntry 22 }

    wfApplePortAarpProbeTxs OBJECT-TYPE
        SYNTAX	Counter
        ACCESS	read-only
        STATUS	mandatory
        DESCRIPTION
                "The number of AARP Probe packets transmitted on
                this interface."
        ::= { wfApplePortEntry 23 }

    wfApplePortAarpReqRxs OBJECT-TYPE
        SYNTAX	Counter
        ACCESS	read-only
        STATUS	mandatory
        DESCRIPTION
                "The number of AARP Request packets received on
                this interface."
        ::= { wfApplePortEntry 24 }

    wfApplePortAarpReqTxs OBJECT-TYPE
        SYNTAX	Counter
        ACCESS	read-only
        STATUS	mandatory
        DESCRIPTION
                "The number of AARP Request packets transmitted on
                this interface."
        ::= { wfApplePortEntry 25 }

    wfApplePortAarpRspRxs OBJECT-TYPE
        SYNTAX	Counter
        ACCESS	read-only
        STATUS	mandatory
        DESCRIPTION
                "The number of AARP Response packets received on
                this interface."
        ::= { wfApplePortEntry 26 }

    wfApplePortAarpRspTxs OBJECT-TYPE
        SYNTAX	Counter
        ACCESS	read-only
        STATUS	mandatory
        DESCRIPTION
                "The number of AARP Response packets transmitted on
                this interface."
        ::= { wfApplePortEntry 27 }

    wfApplePortDdpOutRequests OBJECT-TYPE
        SYNTAX	Counter
        ACCESS	read-only
        STATUS	mandatory
        DESCRIPTION
                "The total number of DDP datagrams which were supplied
                to DDP by local DDP clients in requests for
                transmission.  Note that this counter does not
                include any datagrams counted in ddpForwRequests."
        ::= { wfApplePortEntry 28 }

    wfApplePortDdpInReceives OBJECT-TYPE
        SYNTAX	Counter
        ACCESS	read-only
        STATUS	mandatory
        DESCRIPTION
                "The total number of input datagrams received by DDP,
                including those received in error."
        ::= { wfApplePortEntry 29 }

    wfApplePortDdpInLocalDatagrams OBJECT-TYPE
        SYNTAX	Counter
        ACCESS	read-only
        STATUS	mandatory
        DESCRIPTION
                "The total number of input DDP datagrams for which this
                entity was their final DDP destination."
        ::= { wfApplePortEntry 30 }

    wfApplePortDdpNoProtocolHandlers OBJECT-TYPE
        SYNTAX	Counter
        ACCESS	read-only
        STATUS	mandatory
        DESCRIPTION
                "The total number of DDP datagrams addressed to this
                entity that were addressed to an upper layer protocol
                for which no protocol handler existed."
        ::= { wfApplePortEntry 31 }

    wfApplePortDdpTooShortErrors OBJECT-TYPE
        SYNTAX	Counter
        ACCESS	read-only
        STATUS	mandatory
        DESCRIPTION
                "The total number of input DDP datagrams dropped because
                the received data length was less than the data length
                specified in the DDP header or the received data length
                was less than the length of the expected DDP header."
        ::= { wfApplePortEntry 32 }

    wfApplePortDdpTooLongErrors OBJECT-TYPE
        SYNTAX	Counter
        ACCESS	read-only
        STATUS	mandatory
        DESCRIPTION
                "The total number of input DDP datagrams dropped because
                the received data length was greater than the data length
                specified in the DDP header or because they exceeded the
                maximum DDP datagram size."
        ::= { wfApplePortEntry 33 }

    wfApplePortDdpChecksumErrors OBJECT-TYPE
        SYNTAX	Counter
        ACCESS	read-only
        STATUS	mandatory
        DESCRIPTION
                "The total number of input DDP datagrams for which this
                DDP entity was their final destination, and which were
                dropped because of a checksum error."
        ::= { wfApplePortEntry 34 }

    wfApplePortDdpForwRequests OBJECT-TYPE
        SYNTAX	Counter
        ACCESS	read-only
        STATUS	mandatory
        DESCRIPTION
                "The number of input datagrams for which this entity was
                not their final DDP destination, as a result of which an
                attempt was made to find a route to forward them to that
                final destination."
        ::= { wfApplePortEntry 35 }

    wfApplePortDdpOutNoRoutes OBJECT-TYPE
        SYNTAX	Counter
        ACCESS	read-only
        STATUS	mandatory
        DESCRIPTION
                "The total number of DDP datagrams dropped because a
                route could not be found to their final destination."
        ::= { wfApplePortEntry 36 }

    wfApplePortDdpBroadcastErrors OBJECT-TYPE
        SYNTAX	Counter
        ACCESS	read-only
        STATUS	mandatory
        DESCRIPTION
                "The total number of input DDP datagrams dropped because
                this entity was not their final destination and they
                were addressed to the link level broadcast."
        ::= { wfApplePortEntry 37 }

    wfApplePortDdpHopCountErrors OBJECT-TYPE
        SYNTAX	Counter
        ACCESS	read-only
        STATUS	mandatory
        DESCRIPTION
                "The total number of input DDP datagrams dropped because
                this entity was not their final destination and their
                hop count would exceed 15."
        ::= { wfApplePortEntry 38 }

    wfApplePortRtmpInDataPkts OBJECT-TYPE
        SYNTAX	Counter
        ACCESS	read-only
        STATUS	mandatory
        DESCRIPTION
                "A count of the number of good RTMP data packets
                received by this entity."
        ::= { wfApplePortEntry 39 }

    wfApplePortRtmpOutDataPkts OBJECT-TYPE
        SYNTAX	Counter
        ACCESS	read-only
        STATUS	mandatory
        DESCRIPTION
                "A count of the number of RTMP packets sent by this
                entity."
        ::= { wfApplePortEntry 40 }

    wfApplePortRtmpInRequestPkts OBJECT-TYPE
        SYNTAX	Counter
        ACCESS	read-only
        STATUS	mandatory
        DESCRIPTION
                "A count of the number of good RTMP Request packets
                received by this entity."
        ::= { wfApplePortEntry 41 }

    wfApplePortRtmpNextIREqualChanges OBJECT-TYPE
        SYNTAX	Counter
        ACCESS	read-only
        STATUS	mandatory
        DESCRIPTION
                "A count of the number of times RTMP changes the Next
                Internet Router in a routing entry because the hop count
                advertised in a routing tuple was equal to the current
                hop count for a particular network."
        ::= { wfApplePortEntry 42 }

    wfApplePortRtmpNextIRLessChanges OBJECT-TYPE
        SYNTAX	Counter
        ACCESS	read-only
        STATUS	mandatory
        DESCRIPTION
                "A count of the number of times RTMP changes the Next
                Internet Router in a routing entry because the hop count
                advertised in a routing tuple was less than the current
                hop count for a particular network."
        ::= { wfApplePortEntry 43 }

    wfApplePortRtmpRouteDeletes OBJECT-TYPE
        SYNTAX	Counter
        ACCESS	read-only
        STATUS	mandatory
        DESCRIPTION
                "A count of the number of times RTMP deletes a route because
                it was aged out of the table.  This can help to detect
                routing problems."
        ::= { wfApplePortEntry 44 }

    wfApplePortRtmpNetworkMismatchErrors OBJECT-TYPE
        SYNTAX	Counter
        ACCESS	read-only
        STATUS	mandatory
        DESCRIPTION
                "The number of times RTMP receives a Data packet from a
                router who claims to be on a different network than that
                configured for the receiving port.  This can help to
                detect configuration errors."
        ::= { wfApplePortEntry 45 }

    wfApplePortRtmpRoutingTableOverflows OBJECT-TYPE
        SYNTAX	Counter
        ACCESS	read-only
        STATUS	mandatory
        DESCRIPTION
                "The number of times RTMP attempted to add a route
                to the RTMP table but failed due to overflow."
        ::= { wfApplePortEntry 46 }

    wfApplePortZipInZipQueries OBJECT-TYPE
        SYNTAX	Counter
        ACCESS	read-only
        STATUS	mandatory
        DESCRIPTION
                "The number of ZIP Queries received by this entity."
        ::= { wfApplePortEntry 47 }

    wfApplePortZipInZipReplies OBJECT-TYPE
        SYNTAX	Counter
        ACCESS	read-only
        STATUS	mandatory
        DESCRIPTION
                "The number of ZIP Replies received by this entity."
        ::= { wfApplePortEntry 48 }

    wfApplePortZipOutZipReplies OBJECT-TYPE
        SYNTAX	Counter
        ACCESS	read-only
        STATUS	mandatory
        DESCRIPTION
                "The number of ZIP Replies sent by this entity."
        ::= { wfApplePortEntry 49 }

    wfApplePortZipInZipExtendedReplies OBJECT-TYPE
        SYNTAX	Counter
        ACCESS	read-only
        STATUS	mandatory
        DESCRIPTION
                "The number of ZIP Extended Replies received by this entity."
        ::= { wfApplePortEntry 50 }

    wfApplePortZipOutZipExtendedReplies OBJECT-TYPE
        SYNTAX	Counter
        ACCESS	read-only
        STATUS	mandatory
        DESCRIPTION
                "The number of ZIP Extended Replies sent by this entity."
        ::= { wfApplePortEntry 51 }

    wfApplePortZipInGetZoneLists OBJECT-TYPE
        SYNTAX	Counter
        ACCESS	read-only
        STATUS	mandatory
        DESCRIPTION
                "The number of ZIP GetZoneList transactions received by
                this entity."
        ::= { wfApplePortEntry 52 }

    wfApplePortZipOutGetZoneListReplies OBJECT-TYPE
        SYNTAX	Counter
        ACCESS	read-only
        STATUS	mandatory
        DESCRIPTION
                "The number of ZIP GetZoneListReply transactions sent by
                this entity."
        ::= { wfApplePortEntry 53 }

    wfApplePortZipInGetLocalZones OBJECT-TYPE
        SYNTAX	Counter
        ACCESS	read-only
        STATUS	mandatory
        DESCRIPTION
                "The number of ZIP GetLocalZone transactions received
                by this entity."
        ::= { wfApplePortEntry 54 }

    wfApplePortZipOutGetLocalZoneReplies OBJECT-TYPE
        SYNTAX	Counter
        ACCESS	read-only
        STATUS	mandatory
        DESCRIPTION
                "The number of ZIP GetLocalZoneReply transactions sent
                by this entity."
        ::= { wfApplePortEntry 55 }

    wfApplePortZipInGetMyZones OBJECT-TYPE
        SYNTAX	Counter
        ACCESS	read-only
        STATUS	obsolete
        DESCRIPTION
                "The number of ZIP GetMyZone transactions received by
                this entity."
        ::= { wfApplePortEntry 56 }

    wfApplePortZipOutGetMyZoneReplies OBJECT-TYPE
        SYNTAX	Counter
        ACCESS	read-only
        STATUS	obsolete
        DESCRIPTION
                "The number of ZIP GetMyZoneReply transactions sent by
                this entity."
        ::= { wfApplePortEntry 57 }

    wfApplePortZipZoneConflictErrors OBJECT-TYPE
        SYNTAX	Counter
        ACCESS	read-only
        STATUS	mandatory
        DESCRIPTION
                "The number of times a conflict has been detected between
                this entity's zone information and another entity's
                zone information."
        ::= { wfApplePortEntry 58 }

    wfApplePortZipInGetNetInfos OBJECT-TYPE
        SYNTAX	Counter
        ACCESS	read-only
        STATUS	mandatory
        DESCRIPTION
                "The number of ZIP GetNetInfo packets received on this
                port by this entity."
        ::= { wfApplePortEntry 59 }

    wfApplePortZipOutGetNetInfoReplies OBJECT-TYPE
        SYNTAX	Counter
        ACCESS	read-only
        STATUS	mandatory
        DESCRIPTION
                "The number of ZIP GetNetInfoReply packets sent out this
                port by this entity."
        ::= { wfApplePortEntry 60 }

    wfApplePortZipZoneOutInvalids OBJECT-TYPE
        SYNTAX	Counter
        ACCESS	read-only
        STATUS	mandatory
        DESCRIPTION
                "The number of times this entity has sent a ZIP GetNetInfo
                Reply with the zone invalid bit set in response to a
                GetNetInfo Request with an invalid zone name."
        ::= { wfApplePortEntry 61 }

    wfApplePortZipAddressInvalids OBJECT-TYPE
        SYNTAX	Counter
        ACCESS	read-only
        STATUS	mandatory
        DESCRIPTION
                "The number of times this entity had to broadcast a ZIP
                GetNetInfo Reply because the GetNetInfo Request had an
                invalid address."
        ::= { wfApplePortEntry 62 }

    wfApplePortZipOutGetNetInfos OBJECT-TYPE
        SYNTAX	Counter
        ACCESS	read-only
        STATUS	mandatory
        DESCRIPTION
                "The number of ZIP GetNetInfo packets sent out this port
                by this entity."
        ::= { wfApplePortEntry 63 }

    wfApplePortZipInGetNetInfoReplies OBJECT-TYPE
        SYNTAX	Counter
        ACCESS	read-only
        STATUS	mandatory
        DESCRIPTION
                "The number of ZIP GetNetInfoReply packets received on
                this port by this entity."
        ::= { wfApplePortEntry 64 }

    wfApplePortZipOutZipQueries OBJECT-TYPE
        SYNTAX	Counter
        ACCESS	read-only
        STATUS	mandatory
        DESCRIPTION
                "The number of ZIP Queries sent by this entity."
        ::= { wfApplePortEntry 65 }

    wfApplePortZipInErrors OBJECT-TYPE
        SYNTAX	Counter
        ACCESS	read-only
        STATUS	mandatory
        DESCRIPTION
                "The number of ZIP packets received by this entity
                that were rejected for any error."
        ::= { wfApplePortEntry 66 }

    wfApplePortNbpInLookUpRequests OBJECT-TYPE
        SYNTAX	Counter
        ACCESS	read-only
        STATUS	mandatory
        DESCRIPTION
                "The number of NBP LookUp Requests received."
        ::= { wfApplePortEntry 67 }

    wfApplePortNbpInLookUpReplies OBJECT-TYPE
        SYNTAX	Counter
        ACCESS	read-only
        STATUS	mandatory
        DESCRIPTION
                "The number of NBP LookUp Replies received."
        ::= { wfApplePortEntry 68 }

    wfApplePortNbpInBroadcastRequests OBJECT-TYPE
        SYNTAX	Counter
        ACCESS	read-only
        STATUS	mandatory
        DESCRIPTION
                "The number of NBP Broadcast Requests received."
        ::= { wfApplePortEntry 69 }

    wfApplePortNbpInForwardRequests OBJECT-TYPE
        SYNTAX	Counter
        ACCESS	read-only
        STATUS	mandatory
        DESCRIPTION
                "The number of NBP Forward Requests received."
        ::= { wfApplePortEntry 70 }

    wfApplePortNbpOutLookUpRequests OBJECT-TYPE
        SYNTAX	Counter
        ACCESS	read-only
        STATUS	mandatory
        DESCRIPTION
                "The number of NBP LookUp Requests sent."
        ::= { wfApplePortEntry 71 }

    wfApplePortNbpOutLookUpReplies OBJECT-TYPE
        SYNTAX	Counter
        ACCESS	read-only
        STATUS	mandatory
        DESCRIPTION
                "The number of NBP LookUp Replies sent."
        ::= { wfApplePortEntry 72 }

    wfApplePortNbpOutBroadcastRequests OBJECT-TYPE
        SYNTAX	Counter
        ACCESS	read-only
        STATUS	mandatory
        DESCRIPTION
                "The number of NBP Broadcast Requests sent."
        ::= { wfApplePortEntry 73 }

    wfApplePortNbpOutForwardRequests OBJECT-TYPE
        SYNTAX	Counter
        ACCESS	read-only
        STATUS	mandatory
        DESCRIPTION
                "The number of NBP Forward Requests sent."
        ::= { wfApplePortEntry 74 }

    wfApplePortNbpRegistrationFailures OBJECT-TYPE
        SYNTAX	Counter
        ACCESS	read-only
        STATUS	mandatory
        DESCRIPTION
                "The number of times this node experienced a failure in
                attempting to register an NBP entity."
        ::= { wfApplePortEntry 75 }

    wfApplePortNbpInErrors OBJECT-TYPE
        SYNTAX	Counter
        ACCESS	read-only
        STATUS	mandatory
        DESCRIPTION
                "The number of NBP packets received by this entity that were
                rejected for any error."
        ::= { wfApplePortEntry 76 }

    wfApplePortEchoRequests OBJECT-TYPE
        SYNTAX	Counter
        ACCESS	read-only
        STATUS	mandatory
        DESCRIPTION
                "The number of AppleTalk Echo requests received."
        ::= { wfApplePortEntry 77 }

    wfApplePortEchoReplies OBJECT-TYPE
        SYNTAX	Counter
        ACCESS	read-only
        STATUS	mandatory
        DESCRIPTION
                "The number of AppleTalk Echo replies sent."
        ::= { wfApplePortEntry 78 }

    wfApplePortInterfaceCost OBJECT-TYPE
        SYNTAX	INTEGER {
    		    cost(15)
    		}
        ACCESS	read-write
        STATUS	mandatory
        DESCRIPTION
                "RTMP Cost for this interface."
        ::= { wfApplePortEntry 79 }

    wfApplePortWanBroadcastAddress OBJECT-TYPE
        SYNTAX	OCTET STRING
        ACCESS	read-write
        STATUS	mandatory
        DESCRIPTION
                "Frame Relay, SMDS, or ATM broadcast address"
        ::= { wfApplePortEntry 80 }

    wfApplePortWanSplitHorizonDisable OBJECT-TYPE
        SYNTAX	INTEGER {
    		    enabled(1),
    		    disabled(2)
    		}
        ACCESS	read-write
        STATUS	mandatory
        DESCRIPTION
                "WAN (Frame Relay or ATM) split horizon enabled"
        DEFVAL	{ enabled }
        ::= { wfApplePortEntry 81 }

    wfApplePortZoneFilterType OBJECT-TYPE
        SYNTAX	INTEGER {
    		    allow(1),
    		    deny(2),
    		    partallow(3),
    		    partdeny(4)
    		}
        ACCESS	read-write
        STATUS	mandatory
        DESCRIPTION
                "Controls zone filtering on this interface. An allow indicates that
                any wfAppleZoneFilterEntry is a zone that is allowed on the
                interface. A deny indicates that any ZoneFilterEntry is a zone that
                should not be advertised out this interface.  No ZoneFilterEntrys
                indicates that all nets and zones are being advertised."
        DEFVAL	{ deny }
        ::= { wfApplePortEntry 82 }

    wfApplePortMacIPDisable OBJECT-TYPE
        SYNTAX  INTEGER {
                    enabled(1),
                    disabled(2)
                }
        ACCESS  read-write
        STATUS  mandatory
        DESCRIPTION
                "Enable/Disable parameter for MacIP."
        DEFVAL  { disabled }
        ::= { wfApplePortEntry 83 }

    wfAppleLclZoneTable OBJECT-TYPE
        SYNTAX	SEQUENCE OF WfAppleLclZoneEntry
        ACCESS	not-accessible
        STATUS	mandatory
        DESCRIPTION
                "The Local Zone table describes a list of zone names s
                serviced by a particular AppleTalk port/interface.
                In other words, the list of zone names that are
                associated with a particular network range."
        ::= { wfAppletalkGroup 4 }

    wfAppleLclZoneEntry OBJECT-TYPE
        SYNTAX	WfAppleLclZoneEntry
        ACCESS	not-accessible
        STATUS	mandatory
        DESCRIPTION
                "An entry in the Local Zone table"
        INDEX	{ wfAppleLclZonePortCircuit,
    		  wfAppleLclZoneIndex }
        ::= { wfAppleLclZoneTable 1 }

    WfAppleLclZoneEntry ::= SEQUENCE {
    	    wfAppleLclZoneDelete
    		INTEGER,
    	    wfAppleLclZonePortCircuit
    		INTEGER,
    	    wfAppleLclZoneIndex
    		INTEGER,
    	    wfAppleLclZoneName
    		DisplayString
        }

    wfAppleLclZoneDelete OBJECT-TYPE
        SYNTAX	INTEGER {
    		    created(1),
    		    deleted(2)
    		}
        ACCESS	read-write
        STATUS	mandatory
        DESCRIPTION
                "Create/Delete parameter for adding/deleting a
                zone name to the Local Zone List for a particular
                AppleTalk network interface."
        DEFVAL	{ created }
        ::= { wfAppleLclZoneEntry 1 }

    wfAppleLclZonePortCircuit OBJECT-TYPE
        SYNTAX	INTEGER
        ACCESS	read-only
        STATUS	mandatory
        DESCRIPTION
                "The circuit number for the corresponding AppleTalk interface
                /port for this zone list. "
        ::= { wfAppleLclZoneEntry 2 }

    wfAppleLclZoneIndex OBJECT-TYPE
        SYNTAX	INTEGER
        ACCESS	read-only
        STATUS	mandatory
        DESCRIPTION
                "A unique value for this zone name."
        ::= { wfAppleLclZoneEntry 3 }

    wfAppleLclZoneName OBJECT-TYPE
        SYNTAX	DisplayString
        ACCESS	read-write
        STATUS	mandatory
        DESCRIPTION
                "One of the local zone names defined for this/
                interface. "
        ::= { wfAppleLclZoneEntry 4 }

    wfAppleAarpTable OBJECT-TYPE
        SYNTAX	SEQUENCE OF WfAppleAarpEntry
        ACCESS	not-accessible
        STATUS	mandatory
        DESCRIPTION
                "The AppleTalk Address Translation table
                contains a mapping of AppleTalk Network addresses
                to its corresponding physical address."
        ::= { wfAppletalkGroup 5 }

    wfAppleAarpEntry OBJECT-TYPE
        SYNTAX	WfAppleAarpEntry
        ACCESS	not-accessible
        STATUS	mandatory
        DESCRIPTION
                "An entry in the Address Mapping table"
        INDEX	{ wfAppleAarpNet,
    		  wfAppleAarpNode,
    		  wfAppleAarpIfIndex }
        ::= { wfAppleAarpTable 1 }

    WfAppleAarpEntry ::= SEQUENCE {
    	    wfAppleAarpIfIndex
    		INTEGER,
    	    wfAppleAarpNet
    		INTEGER,
    	    wfAppleAarpNode
    		INTEGER,
    	    wfAppleAarpPhysAddress
    		OCTET STRING
        }

    wfAppleAarpIfIndex OBJECT-TYPE
        SYNTAX	INTEGER
        ACCESS	read-only
        STATUS	mandatory
        DESCRIPTION
                "The unique value for this interface/cct. This
                value is the same interface as identified by
                the value of ifIndex."
        ::= { wfAppleAarpEntry 1 }

    wfAppleAarpNet OBJECT-TYPE
        SYNTAX	INTEGER
        ACCESS	read-only
        STATUS	mandatory
        DESCRIPTION
                "The host's AppleTalk address (Net.Nodeid). This
                address corresponds to the media-dependent 'physical'
                address for this host."
        ::= { wfAppleAarpEntry 2 }

    wfAppleAarpNode OBJECT-TYPE
        SYNTAX	INTEGER
        ACCESS	read-only
        STATUS	mandatory
        DESCRIPTION
                "The host's AppleTalk address (Net.Nodeid). This
                address corresponds to the media-dependent 'physical'
                address for this host."
        ::= { wfAppleAarpEntry 3 }

    wfAppleAarpPhysAddress OBJECT-TYPE
        SYNTAX	OCTET STRING
        ACCESS	read-only
        STATUS	mandatory
        DESCRIPTION
                "The media-dependent 'physical' address."
        ::= { wfAppleAarpEntry 4 }

    wfAppleZipTable OBJECT-TYPE
        SYNTAX	SEQUENCE OF WfAppleZipEntry
        ACCESS	not-accessible
        STATUS	mandatory
        DESCRIPTION
                "The Zone Information table for reachable AppleTalk
                Networks."
        ::= { wfAppletalkGroup 6 }

    wfAppleZipEntry OBJECT-TYPE
        SYNTAX	WfAppleZipEntry
        ACCESS	not-accessible
        STATUS	mandatory
        DESCRIPTION
                "An entry in the Zone Information table"
        INDEX	{ wfAppleZipZoneNetStart,
    		  wfAppleZipIndex }
        ::= { wfAppleZipTable 1 }

    WfAppleZipEntry ::= SEQUENCE {
    	    wfAppleZipZoneNetStart
    		INTEGER,
    	    wfAppleZipZoneNetEnd
    		INTEGER,
    	    wfAppleZipIndex
    		INTEGER,
    	    wfAppleZipZoneName
    		DisplayString,
    	    wfAppleZipZoneState
    		INTEGER
        }

    wfAppleZipZoneNetStart OBJECT-TYPE
        SYNTAX	INTEGER
        ACCESS	read-only
        STATUS	mandatory
        DESCRIPTION
                "The network that starts the range for this entry."
        ::= { wfAppleZipEntry 1 }

    wfAppleZipZoneNetEnd OBJECT-TYPE
        SYNTAX	INTEGER
        ACCESS	read-only
        STATUS	mandatory
        DESCRIPTION
                "The network that ends the range for this entry."
        ::= { wfAppleZipEntry 2 }

    wfAppleZipIndex OBJECT-TYPE
        SYNTAX	INTEGER
        ACCESS	read-only
        STATUS	mandatory
        DESCRIPTION
                "The unique value for this zone name."
        ::= { wfAppleZipEntry 3 }

    wfAppleZipZoneName OBJECT-TYPE
        SYNTAX	DisplayString
        ACCESS	read-only
        STATUS	mandatory
        DESCRIPTION
                "The ASCII xone name of this entry."
        ::= { wfAppleZipEntry 4 }

    wfAppleZipZoneState OBJECT-TYPE
        SYNTAX	INTEGER {
    		    valid(1),
    		    invalid(2)
    		}
        ACCESS	read-only
        STATUS	mandatory
        DESCRIPTION
                "The state of the ZIP entry."
        ::= { wfAppleZipEntry 5 }

    wfAppleZoneFilterTable OBJECT-TYPE
        SYNTAX	SEQUENCE OF WfAppleZoneFilterEntry
        ACCESS	not-accessible
        STATUS	mandatory
        DESCRIPTION
                "The zone filter table describes a list of zone names
                filtered on a given AppleTalk port/interface."
        ::= { wfAppletalkGroup 7 }

    wfAppleZoneFilterEntry OBJECT-TYPE
        SYNTAX	WfAppleZoneFilterEntry
        ACCESS	not-accessible
        STATUS	mandatory
        DESCRIPTION
                "An entry in the Zone Filter table"
        INDEX	{ wfAppleZoneFilterIndex }
        ::= { wfAppleZoneFilterTable 1 }

    WfAppleZoneFilterEntry ::= SEQUENCE {
    	    wfAppleZoneFilterDelete
    		INTEGER,
    	    wfAppleZoneFilterCircuit
    		INTEGER,
    	    wfAppleZoneFilterIpAddress
    		IpAddress,
    	    wfAppleZoneFilterCircuitType
    		INTEGER,
    	    wfAppleZoneFilterIndex
    		INTEGER,
    	    wfAppleZoneFilterName
    		DisplayString
        }

    wfAppleZoneFilterDelete OBJECT-TYPE
        SYNTAX	INTEGER {
    		    created(1),
    		    deleted(2)
    		}
        ACCESS	read-write
        STATUS	mandatory
        DESCRIPTION
                "Create/Delete parameter for adding/deleting a
                zone name to the filter list for a particular
                AppleTalk network interface."
        DEFVAL	{ created }
        ::= { wfAppleZoneFilterEntry 1 }

    wfAppleZoneFilterCircuit OBJECT-TYPE
        SYNTAX	INTEGER
        ACCESS	read-write
        STATUS	mandatory
        DESCRIPTION
                "The circuit number for the corresponding AppleTalk interface
                for filtered zone entry.  This is only valid if
                wfAppleZoneFilterCircuitType is RTMP"
        ::= { wfAppleZoneFilterEntry 2 }

    wfAppleZoneFilterIpAddress OBJECT-TYPE
        SYNTAX	IpAddress
        ACCESS	read-write
        STATUS	mandatory
        DESCRIPTION
                "The IP address for the corresponding AURP interface for filtered
                zone entry.  This is only valid if wfAppleZoneFilterCircuitType
                is AURP."
        ::= { wfAppleZoneFilterEntry 3 }

    wfAppleZoneFilterCircuitType OBJECT-TYPE
        SYNTAX	INTEGER {
    		    rtmp(1),
    		    aurp(2)
    		}
        ACCESS	read-write
        STATUS	mandatory
        DESCRIPTION
                "The type of the circuit the filter is applied on. If RTMP, then
                wfAppleZoneFilterCircuit is used.  If AURP, then
                wfAppleZoneFilterIpAddress is used."
        DEFVAL	{ rtmp }
        ::= { wfAppleZoneFilterEntry 4 }

    wfAppleZoneFilterIndex OBJECT-TYPE
        SYNTAX	INTEGER
        ACCESS	read-only
        STATUS	mandatory
        DESCRIPTION
                "A unique value for this filtered zone name."
        ::= { wfAppleZoneFilterEntry 5 }

    wfAppleZoneFilterName OBJECT-TYPE
        SYNTAX	DisplayString
        ACCESS	read-write
        STATUS	mandatory
        DESCRIPTION
                "One of the zone names filtered on this/
                interface."
        ::= { wfAppleZoneFilterEntry 6 }

    wfAppleAurpBase	OBJECT IDENTIFIER ::= { wfAppletalkGroup 8 }

    wfAppleAurpBaseDelete OBJECT-TYPE
        SYNTAX	INTEGER {
    		    created(1),
    		    deleted(2)
    		}
        ACCESS	read-write
        STATUS	mandatory
        DESCRIPTION
                "Create/Delete parameter for determining whether
                or not AURP is configured on this box."
        DEFVAL	{ created }
        ::= { wfAppleAurpBase 1 }

    wfAppleAurpBaseDisable OBJECT-TYPE
        SYNTAX	INTEGER {
    		    enabled(1),
    		    disabled(2)
    		}
        ACCESS	read-write
        STATUS	mandatory
        DESCRIPTION
                "Enable/Disable parameter for determining whether
                or not to startup AURP."
        DEFVAL	{ enabled }
        ::= { wfAppleAurpBase 2 }

    wfAppleAurpBaseState OBJECT-TYPE
        SYNTAX	INTEGER {
    		    up(1),
    		    down(2),
    		    init(3),
    		    notpres(4)
    		}
        ACCESS	read-only
        STATUS	mandatory
        DESCRIPTION
                "This parameter relfects the current state of AURP."
        DEFVAL	{ down }
        ::= { wfAppleAurpBase 3 }

    wfAppleAurpBaseDomain OBJECT-TYPE
        SYNTAX	OCTET STRING
        ACCESS	read-write
        STATUS	mandatory
        DESCRIPTION
                "The domain identfier for the domain that this
                router resides in."
        ::= { wfAppleAurpBase 4 }

    wfAppleAurpBaseIpAddress OBJECT-TYPE
        SYNTAX	IpAddress
        ACCESS	read-write
        STATUS	mandatory
        DESCRIPTION
                "The IP address configured on this router that AURP should use
                for all of its connections "
        ::= { wfAppleAurpBase 5 }

    wfAppleAurpBasePromiscuous OBJECT-TYPE
        SYNTAX	INTEGER {
    		    notpromisc(1),
    		    promisc(2)
    		}
        ACCESS	read-write
        STATUS	mandatory
        DESCRIPTION
                "AURP Promiscuous mode not supported."
        DEFVAL	{ notpromisc }
        ::= { wfAppleAurpBase 6 }

    wfAppleAurpBaseInAcceptedOpenReqs OBJECT-TYPE
        SYNTAX	Counter
        ACCESS	read-only
        STATUS	mandatory
        DESCRIPTION
                "The number of Open Requests that were accepted."
        ::= { wfAppleAurpBase 7 }

    wfAppleAurpBaseInRejectedOpenReqs OBJECT-TYPE
        SYNTAX	Counter
        ACCESS	read-only
        STATUS	mandatory
        DESCRIPTION
                "The number of Open Requests that were rejected."
        ::= { wfAppleAurpBase 8 }

    wfAppleAurpBaseInRouterDowns OBJECT-TYPE
        SYNTAX	Counter
        ACCESS	read-only
        STATUS	mandatory
        DESCRIPTION
                "The number of Router Down packets that were received."
        ::= { wfAppleAurpBase 9 }

    wfAppleAurpBaseInPktsNoPeers OBJECT-TYPE
        SYNTAX	Counter
        ACCESS	read-only
        STATUS	mandatory
        DESCRIPTION
                "The number of packets received from UDP for which there
                is no valid connection."
        ::= { wfAppleAurpBase 10 }

    wfAppleAurpBaseInInvalidVerions OBJECT-TYPE
        SYNTAX	Counter
        ACCESS	read-only
        STATUS	mandatory
        DESCRIPTION
                "The number of invalid version error received on this
                tunnel. "
        ::= { wfAppleAurpBase 11 }

    wfAppleAurpTable OBJECT-TYPE
        SYNTAX	SEQUENCE OF WfAppleAurpEntry
        ACCESS	not-accessible
        STATUS	mandatory
        DESCRIPTION
                "Each AURP connection has an entry in this table"
        ::= { wfAppletalkGroup 9 }

    wfAppleAurpEntry OBJECT-TYPE
        SYNTAX	WfAppleAurpEntry
        ACCESS	not-accessible
        STATUS	mandatory
        DESCRIPTION
                "An entry in the AURP connection table."
        INDEX	{ wfAppleAurpEntryIpAddress }
        ::= { wfAppleAurpTable 1 }

    WfAppleAurpEntry ::= SEQUENCE {
    	    wfAppleAurpEntryDelete
    		INTEGER,
    	    wfAppleAurpEntryDisable
    		INTEGER,
    	    wfAppleAurpEntryState
    		INTEGER,
    	    wfAppleAurpEntryIpAddress
    		IpAddress,
    	    wfAppleAurpEntryZoneFilterType
    		INTEGER,
    	    wfAppleAurpEntryTimeoutCommand
    		INTEGER,
    	    wfAppleAurpEntryRetryCommand
    		INTEGER,
    	    wfAppleAurpEntryUpdateRate
    		INTEGER,
    	    wfAppleAurpEntryLhfTimeout
    		INTEGER,
    	    wfAppleAurpEntryHopCountReduction
    		INTEGER,
    	    wfAppleAurpEntryInterfaceCost
    		INTEGER,
    	    wfAppleAurpEntrySuiFlags
    		INTEGER,
    	    wfAppleAurpEntryType
    		INTEGER,
    	    wfAppleAurpEntryPeerDomainId
    		IpAddress,
    	    wfAppleAurpEntryPeerUpdateRate
    		INTEGER,
    	    wfAppleAurpEntryPeerEnvironment
    		INTEGER,
    	    wfAppleAurpEntryPeerSuiFlags
    		INTEGER,
    	    wfAppleAurpEntryCliConnId
    		INTEGER,
    	    wfAppleAurpEntrySrvConnId
    		INTEGER,
    	    wfAppleAurpEntryCliSeqNum
    		INTEGER,
    	    wfAppleAurpEntrySrvSeqNum
    		INTEGER,
    	    wfAppleAurpEntryCommandRetries
    		Counter,
    	    wfAppleAurpEntryInDelayedDuplicates
    		Counter,
    	    wfAppleAurpEntryInInvalidConnIds
    		Counter,
    	    wfAppleAurpEntryInInvalidCommands
    		Counter,
    	    wfAppleAurpEntryInInvalidSubCodes
    		Counter,
    	    wfAppleAurpEntryInPkts
    		Counter,
    	    wfAppleAurpEntryOutPkts
    		Counter,
    	    wfAppleAurpEntryInDdpPkts
    		Counter,
    	    wfAppleAurpEntryOutDdpPkts
    		Counter,
    	    wfAppleAurpEntryOutNoRoutes
    		Counter,
    	    wfAppleAurpEntryHopCountErrors
    		Counter,
    	    wfAppleAurpEntryHopCountAdjustments
    		Counter,
    	    wfAppleAurpEntryInAurpPkts
    		Counter,
    	    wfAppleAurpEntryOutAurpPkts
    		Counter,
    	    wfAppleAurpEntryInOpenRequests
    		Counter,
    	    wfAppleAurpEntryOutOpenRequests
    		Counter,
    	    wfAppleAurpEntryInOpenResponses
    		Counter,
    	    wfAppleAurpEntryOutOpenResponses
    		Counter,
    	    wfAppleAurpEntryInRiRequests
    		Counter,
    	    wfAppleAurpEntryOutRiRequests
    		Counter,
    	    wfAppleAurpEntryInRiResponses
    		Counter,
    	    wfAppleAurpEntryOutRiResponses
    		Counter,
    	    wfAppleAurpEntryInRiAcks
    		Counter,
    	    wfAppleAurpEntryOutRiAcks
    		Counter,
    	    wfAppleAurpEntryInRiUpdates
    		Counter,
    	    wfAppleAurpEntryOutRiUpdates
    		Counter,
    	    wfAppleAurpEntryInUpdateNullEvents
    		Counter,
    	    wfAppleAurpEntryOutUpdateNullEvents
    		Counter,
    	    wfAppleAurpEntryInUpdateNetAdds
    		Counter,
    	    wfAppleAurpEntryOutUpdateNetAdds
    		Counter,
    	    wfAppleAurpEntryInUpdateNetDeletes
    		Counter,
    	    wfAppleAurpEntryOutUpdateNetDeletes
    		Counter,
    	    wfAppleAurpEntryInUpdateNetRouteChanges
    		Counter,
    	    wfAppleAurpEntryOutUpdateNetRouteChanges
    		Counter,
    	    wfAppleAurpEntryInUpdateNetDistanceChanges
    		Counter,
    	    wfAppleAurpEntryOutUpdateNetDistanceChanges
    		Counter,
    	    wfAppleAurpEntryInUpdateZoneChanges
    		Counter,
    	    wfAppleAurpEntryOutUpdateZoneChanges
    		Counter,
    	    wfAppleAurpEntryInUpdateInvalidEvents
    		Counter,
    	    wfAppleAurpEntryOutUpdateInvalidEvents
    		Counter,
    	    wfAppleAurpEntryInZiRequests
    		Counter,
    	    wfAppleAurpEntryOutZiRequests
    		Counter,
    	    wfAppleAurpEntryInZiResponses
    		Counter,
    	    wfAppleAurpEntryOutZiResponses
    		Counter,
    	    wfAppleAurpEntryInGdzlRequests
    		Counter,
    	    wfAppleAurpEntryOutGdzlRequests
    		Counter,
    	    wfAppleAurpEntryInGdzlResponses
    		Counter,
    	    wfAppleAurpEntryOutGdzlResponses
    		Counter,
    	    wfAppleAurpEntryInGznRequests
    		Counter,
    	    wfAppleAurpEntryOutGznRequests
    		Counter,
    	    wfAppleAurpEntryInGznResponses
    		Counter,
    	    wfAppleAurpEntryOutGznResponses
    		Counter,
    	    wfAppleAurpEntryInTickles
    		Counter,
    	    wfAppleAurpEntryOutTickles
    		Counter,
    	    wfAppleAurpEntryInTickleAcks
    		Counter,
    	    wfAppleAurpEntryOutTickleAcks
    		Counter,
    	    wfAppleAurpEntryInRouterDowns
    		Counter,
    	    wfAppleAurpEntryOutRouterDowns
    		Counter,
    	    wfAppleAurpEntryZoneFiltDfltZone
    		DisplayString
        }

    wfAppleAurpEntryDelete OBJECT-TYPE
        SYNTAX	INTEGER {
    		    created(1),
    		    deleted(2)
    		}
        ACCESS	read-write
        STATUS	mandatory
        DESCRIPTION
                "Create/Delete para1meter. Users perform an SNMP SET
                operation on this object to create/delete an AppleTalk
                AURP interface. The default is create."
        DEFVAL	{ created }
        ::= { wfAppleAurpEntry 1 }

    wfAppleAurpEntryDisable OBJECT-TYPE
        SYNTAX	INTEGER {
    		    enabled(1),
    		    disabled(2)
    		}
        ACCESS	read-write
        STATUS	mandatory
        DESCRIPTION
                "Enable/Disable parameter. Users perforn an SNMP SET
                operation on this object to enable/disable an AppleTalk
                AURP interface.  Default is enabled."
        DEFVAL	{ enabled }
        ::= { wfAppleAurpEntry 2 }

    wfAppleAurpEntryState OBJECT-TYPE
        SYNTAX	INTEGER {
    		    up(1),
    		    down(2)
    		}
        ACCESS	read-only
        STATUS	mandatory
        DESCRIPTION
                "The current state of the Aurp Entry."
        DEFVAL	{ down }
        ::= { wfAppleAurpEntry 3 }

    wfAppleAurpEntryIpAddress OBJECT-TYPE
        SYNTAX	IpAddress
        ACCESS	read-only
        STATUS	mandatory
        DESCRIPTION
                "Ip address of the remote AURP router with which the connection
                will be made"
        ::= { wfAppleAurpEntry 4 }

    wfAppleAurpEntryZoneFilterType OBJECT-TYPE
        SYNTAX	INTEGER {
    		    allow(1),
    		    deny(2),
    		    partallow(3),
    		    partdeny(4)
    		}
        ACCESS	read-write
        STATUS	mandatory
        DESCRIPTION
                "controls zone filtering on this interface. An allow indicates that
                any wfAppleZoneFilterEntry is a zone that is allowed on the
                interface. A deny indicates that any ZoneFilterEntry is a zone that
                should not be advertised out this interface.  No ZoneFilterEntrys
                indicates that all nets and zones are being advertised."
        DEFVAL	{ deny }
        ::= { wfAppleAurpEntry 5 }

    wfAppleAurpEntryTimeoutCommand OBJECT-TYPE
        SYNTAX	INTEGER(1..1000)
        ACCESS	read-write
        STATUS	mandatory
        DESCRIPTION
                "The amout of time in seconds to wait for an ack before
                retrying a command."
        DEFVAL	{ 3 }
        ::= { wfAppleAurpEntry 6 }

    wfAppleAurpEntryRetryCommand OBJECT-TYPE
        SYNTAX	INTEGER(1..100)
        ACCESS	read-write
        STATUS	mandatory
        DESCRIPTION
                "The number of attempts at a command before determining that
                the peer is no longer responding."
        DEFVAL	{ 3 }
        ::= { wfAppleAurpEntry 7 }

    wfAppleAurpEntryUpdateRate OBJECT-TYPE
        SYNTAX	INTEGER(10..604800)
        ACCESS	read-write
        STATUS	mandatory
        DESCRIPTION
                "The rate at which routing table updates are sent on
                this connection, in seconds.  This value should be a
                multiple of ten."
        DEFVAL	{ 30 }
        ::= { wfAppleAurpEntry 8 }

    wfAppleAurpEntryLhfTimeout OBJECT-TYPE
        SYNTAX	INTEGER(30..31536000)
        ACCESS	read-write
        STATUS	mandatory
        DESCRIPTION
                "The number of seconds to wait for an RI-Rsp, RI-Upd,
                or ZI-Rsp before sending a tickle request, in seconds.
                This value should be a multiple of ten."
        DEFVAL	{ 90 }
        ::= { wfAppleAurpEntry 9 }

    wfAppleAurpEntryHopCountReduction OBJECT-TYPE
        SYNTAX	INTEGER {
    		    enabled(1),
    		    disabled(2)
    		}
        ACCESS	read-write
        STATUS	mandatory
        DESCRIPTION
                "Enable/Disable for hop count reduction on this
                connection."
        DEFVAL	{ disabled }
        ::= { wfAppleAurpEntry 10 }

    wfAppleAurpEntryInterfaceCost OBJECT-TYPE
        SYNTAX	INTEGER
        ACCESS	read-write
        STATUS	mandatory
        DESCRIPTION
                "Additional cost to add to hop count as advertised in
                RI-Rsp and RI-Upd."
        ::= { wfAppleAurpEntry 11 }

    wfAppleAurpEntrySuiFlags OBJECT-TYPE
        SYNTAX	INTEGER {
    		    all(30720)
    		}
        ACCESS	read-write
        STATUS	mandatory
        DESCRIPTION
                "The Send Update Information flags. This value matches
                the 16 bit field sent in OReq and RI-Req packets.  The
                bits are broken down as follows:
                   0x4000 = Net Add
                   0x2000 = Net Delete/Net Route Change
                   0x1000 = Net Distance Change
                   0x0800 = Zone Change
                These should be 'OR'ed together for desired updates.
                e.g. for all updates 0x4000 | 0x2000 | 0x1000 | 0x8000 =
                0x7800 = 30720"
        DEFVAL	{ all }
        ::= { wfAppleAurpEntry 12 }

    wfAppleAurpEntryType OBJECT-TYPE
        SYNTAX	INTEGER
        ACCESS	read-write
        STATUS	mandatory
        DESCRIPTION
                "Reserved for future use"
        ::= { wfAppleAurpEntry 13 }

    wfAppleAurpEntryPeerDomainId OBJECT-TYPE
        SYNTAX	IpAddress
        ACCESS	read-only
        STATUS	mandatory
        DESCRIPTION
                "The peer's Domain Indicator."
        ::= { wfAppleAurpEntry 14 }

    wfAppleAurpEntryPeerUpdateRate OBJECT-TYPE
        SYNTAX	INTEGER
        ACCESS	read-only
        STATUS	mandatory
        DESCRIPTION
                "The update interval specified by the peer in its Open
                Response, in tens of seconds."
        ::= { wfAppleAurpEntry 15 }

    wfAppleAurpEntryPeerEnvironment OBJECT-TYPE
        SYNTAX	INTEGER
        ACCESS	read-only
        STATUS	mandatory
        DESCRIPTION
                "The Environment flags found in the peer's Open Response"
        ::= { wfAppleAurpEntry 16 }

    wfAppleAurpEntryPeerSuiFlags OBJECT-TYPE
        SYNTAX	INTEGER
        ACCESS	read-only
        STATUS	mandatory
        DESCRIPTION
                "The Send Update Information flags found in the peer's
                Open Request and RI Request."
        ::= { wfAppleAurpEntry 17 }

    wfAppleAurpEntryCliConnId OBJECT-TYPE
        SYNTAX	INTEGER
        ACCESS	read-only
        STATUS	mandatory
        DESCRIPTION
                "This connection's client connection ID."
        ::= { wfAppleAurpEntry 18 }

    wfAppleAurpEntrySrvConnId OBJECT-TYPE
        SYNTAX	INTEGER
        ACCESS	read-only
        STATUS	mandatory
        DESCRIPTION
                "This connection's server connection ID."
        ::= { wfAppleAurpEntry 19 }

    wfAppleAurpEntryCliSeqNum OBJECT-TYPE
        SYNTAX	INTEGER
        ACCESS	read-only
        STATUS	mandatory
        DESCRIPTION
                "This connection's client sequence number."
        ::= { wfAppleAurpEntry 20 }

    wfAppleAurpEntrySrvSeqNum OBJECT-TYPE
        SYNTAX	INTEGER
        ACCESS	read-only
        STATUS	mandatory
        DESCRIPTION
                "This connection's server sequence number."
        ::= { wfAppleAurpEntry 21 }

    wfAppleAurpEntryCommandRetries OBJECT-TYPE
        SYNTAX	Counter
        ACCESS	read-only
        STATUS	mandatory
        DESCRIPTION
                "The number of commands that were retried."
        ::= { wfAppleAurpEntry 22 }

    wfAppleAurpEntryInDelayedDuplicates OBJECT-TYPE
        SYNTAX	Counter
        ACCESS	read-only
        STATUS	mandatory
        DESCRIPTION
                "The number of AURP packets that were received whose
                sequence number was one less than that expected."
        ::= { wfAppleAurpEntry 23 }

    wfAppleAurpEntryInInvalidConnIds OBJECT-TYPE
        SYNTAX	Counter
        ACCESS	read-only
        STATUS	mandatory
        DESCRIPTION
                "The number of packets received with bad connection IDs."
        ::= { wfAppleAurpEntry 24 }

    wfAppleAurpEntryInInvalidCommands OBJECT-TYPE
        SYNTAX	Counter
        ACCESS	read-only
        STATUS	mandatory
        DESCRIPTION
                "The number of AURP packets received that had an illegal
                value in the command field."
        ::= { wfAppleAurpEntry 25 }

    wfAppleAurpEntryInInvalidSubCodes OBJECT-TYPE
        SYNTAX	Counter
        ACCESS	read-only
        STATUS	mandatory
        DESCRIPTION
                "The number of AURP Zone packets received that had an illegal
                value in the sub command field."
        ::= { wfAppleAurpEntry 26 }

    wfAppleAurpEntryInPkts OBJECT-TYPE
        SYNTAX	Counter
        ACCESS	read-only
        STATUS	mandatory
        DESCRIPTION
                "The total number of packets received on this connection."
        ::= { wfAppleAurpEntry 27 }

    wfAppleAurpEntryOutPkts OBJECT-TYPE
        SYNTAX	Counter
        ACCESS	read-only
        STATUS	mandatory
        DESCRIPTION
                "The total number of packets transmitted on this connection."
        ::= { wfAppleAurpEntry 28 }

    wfAppleAurpEntryInDdpPkts OBJECT-TYPE
        SYNTAX	Counter
        ACCESS	read-only
        STATUS	mandatory
        DESCRIPTION
                "The number of data packets received."
        ::= { wfAppleAurpEntry 29 }

    wfAppleAurpEntryOutDdpPkts OBJECT-TYPE
        SYNTAX	Counter
        ACCESS	read-only
        STATUS	mandatory
        DESCRIPTION
                "The number of data packets transmitted."
        ::= { wfAppleAurpEntry 30 }

    wfAppleAurpEntryOutNoRoutes OBJECT-TYPE
        SYNTAX	Counter
        ACCESS	read-only
        STATUS	mandatory
        DESCRIPTION
                "The number of DDP packets dropped because a
                route could not be found to their final destination. "
        ::= { wfAppleAurpEntry 31 }

    wfAppleAurpEntryHopCountErrors OBJECT-TYPE
        SYNTAX	Counter
        ACCESS	read-only
        STATUS	mandatory
        DESCRIPTION
                "The total number of input DDP datagrams dropped because
                their hop count would exceed 15."
        ::= { wfAppleAurpEntry 32 }

    wfAppleAurpEntryHopCountAdjustments OBJECT-TYPE
        SYNTAX	Counter
        ACCESS	read-only
        STATUS	mandatory
        DESCRIPTION
                "The total number of input DDP datagrams that had their
                hop count adjusted (if hop count reduction is enabled)."
        ::= { wfAppleAurpEntry 33 }

    wfAppleAurpEntryInAurpPkts OBJECT-TYPE
        SYNTAX	Counter
        ACCESS	read-only
        STATUS	mandatory
        DESCRIPTION
                "The number of routing packets received"
        ::= { wfAppleAurpEntry 34 }

    wfAppleAurpEntryOutAurpPkts OBJECT-TYPE
        SYNTAX	Counter
        ACCESS	read-only
        STATUS	mandatory
        DESCRIPTION
                "The number of routing packets transmitted."
        ::= { wfAppleAurpEntry 35 }

    wfAppleAurpEntryInOpenRequests OBJECT-TYPE
        SYNTAX	Counter
        ACCESS	read-only
        STATUS	mandatory
        DESCRIPTION
                "The number of Open Requests received."
        ::= { wfAppleAurpEntry 36 }

    wfAppleAurpEntryOutOpenRequests OBJECT-TYPE
        SYNTAX	Counter
        ACCESS	read-only
        STATUS	mandatory
        DESCRIPTION
                "The number of Open Requests transmitted."
        ::= { wfAppleAurpEntry 37 }

    wfAppleAurpEntryInOpenResponses OBJECT-TYPE
        SYNTAX	Counter
        ACCESS	read-only
        STATUS	mandatory
        DESCRIPTION
                "The number of Open Responses received."
        ::= { wfAppleAurpEntry 38 }

    wfAppleAurpEntryOutOpenResponses OBJECT-TYPE
        SYNTAX	Counter
        ACCESS	read-only
        STATUS	mandatory
        DESCRIPTION
                "The number of Open Responses transmitted."
        ::= { wfAppleAurpEntry 39 }

    wfAppleAurpEntryInRiRequests OBJECT-TYPE
        SYNTAX	Counter
        ACCESS	read-only
        STATUS	mandatory
        DESCRIPTION
                "The number of Routing Information Requests received."
        ::= { wfAppleAurpEntry 40 }

    wfAppleAurpEntryOutRiRequests OBJECT-TYPE
        SYNTAX	Counter
        ACCESS	read-only
        STATUS	mandatory
        DESCRIPTION
                "The number of Routing Information Requests transmitted."
        ::= { wfAppleAurpEntry 41 }

    wfAppleAurpEntryInRiResponses OBJECT-TYPE
        SYNTAX	Counter
        ACCESS	read-only
        STATUS	mandatory
        DESCRIPTION
                "The number of Routing Information Responses received."
        ::= { wfAppleAurpEntry 42 }

    wfAppleAurpEntryOutRiResponses OBJECT-TYPE
        SYNTAX	Counter
        ACCESS	read-only
        STATUS	mandatory
        DESCRIPTION
                "The number of Routing Information Responses transmitted."
        ::= { wfAppleAurpEntry 43 }

    wfAppleAurpEntryInRiAcks OBJECT-TYPE
        SYNTAX	Counter
        ACCESS	read-only
        STATUS	mandatory
        DESCRIPTION
                "The number of Routing Information Acknowledgements received."
        ::= { wfAppleAurpEntry 44 }

    wfAppleAurpEntryOutRiAcks OBJECT-TYPE
        SYNTAX	Counter
        ACCESS	read-only
        STATUS	mandatory
        DESCRIPTION
                "The number of Routing Information Acknowledgements transmitted."
        ::= { wfAppleAurpEntry 45 }

    wfAppleAurpEntryInRiUpdates OBJECT-TYPE
        SYNTAX	Counter
        ACCESS	read-only
        STATUS	mandatory
        DESCRIPTION
                "The number of Routing Information Updates received."
        ::= { wfAppleAurpEntry 46 }

    wfAppleAurpEntryOutRiUpdates OBJECT-TYPE
        SYNTAX	Counter
        ACCESS	read-only
        STATUS	mandatory
        DESCRIPTION
                "The number of Routing Information Updates transmitted."
        ::= { wfAppleAurpEntry 47 }

    wfAppleAurpEntryInUpdateNullEvents OBJECT-TYPE
        SYNTAX	Counter
        ACCESS	read-only
        STATUS	mandatory
        DESCRIPTION
                "The number of Null update events received."
        ::= { wfAppleAurpEntry 48 }

    wfAppleAurpEntryOutUpdateNullEvents OBJECT-TYPE
        SYNTAX	Counter
        ACCESS	read-only
        STATUS	mandatory
        DESCRIPTION
                "The number of update events transmitted."
        ::= { wfAppleAurpEntry 49 }

    wfAppleAurpEntryInUpdateNetAdds OBJECT-TYPE
        SYNTAX	Counter
        ACCESS	read-only
        STATUS	mandatory
        DESCRIPTION
                "The number of Net Added update events received."
        ::= { wfAppleAurpEntry 50 }

    wfAppleAurpEntryOutUpdateNetAdds OBJECT-TYPE
        SYNTAX	Counter
        ACCESS	read-only
        STATUS	mandatory
        DESCRIPTION
                "The number of Net Added update events transmitted."
        ::= { wfAppleAurpEntry 51 }

    wfAppleAurpEntryInUpdateNetDeletes OBJECT-TYPE
        SYNTAX	Counter
        ACCESS	read-only
        STATUS	mandatory
        DESCRIPTION
                "The number of Net Deleted update events received."
        ::= { wfAppleAurpEntry 52 }

    wfAppleAurpEntryOutUpdateNetDeletes OBJECT-TYPE
        SYNTAX	Counter
        ACCESS	read-only
        STATUS	mandatory
        DESCRIPTION
                "The number of Net Deleted update events transmitted."
        ::= { wfAppleAurpEntry 53 }

    wfAppleAurpEntryInUpdateNetRouteChanges OBJECT-TYPE
        SYNTAX	Counter
        ACCESS	read-only
        STATUS	mandatory
        DESCRIPTION
                "The number of Net Route Change update events received."
        ::= { wfAppleAurpEntry 54 }

    wfAppleAurpEntryOutUpdateNetRouteChanges OBJECT-TYPE
        SYNTAX	Counter
        ACCESS	read-only
        STATUS	mandatory
        DESCRIPTION
                "The number of Net Route Change update events transmitted."
        ::= { wfAppleAurpEntry 55 }

    wfAppleAurpEntryInUpdateNetDistanceChanges OBJECT-TYPE
        SYNTAX	Counter
        ACCESS	read-only
        STATUS	mandatory
        DESCRIPTION
                "The number of Net Distance Change update events received."
        ::= { wfAppleAurpEntry 56 }

    wfAppleAurpEntryOutUpdateNetDistanceChanges OBJECT-TYPE
        SYNTAX	Counter
        ACCESS	read-only
        STATUS	mandatory
        DESCRIPTION
                "The number of Net Distance Change update events transmitted."
        ::= { wfAppleAurpEntry 57 }

    wfAppleAurpEntryInUpdateZoneChanges OBJECT-TYPE
        SYNTAX	Counter
        ACCESS	read-only
        STATUS	mandatory
        DESCRIPTION
                "The number of Zone Change update events received."
        ::= { wfAppleAurpEntry 58 }

    wfAppleAurpEntryOutUpdateZoneChanges OBJECT-TYPE
        SYNTAX	Counter
        ACCESS	read-only
        STATUS	mandatory
        DESCRIPTION
                "The number of Zone Change update events transmitted."
        ::= { wfAppleAurpEntry 59 }

    wfAppleAurpEntryInUpdateInvalidEvents OBJECT-TYPE
        SYNTAX	Counter
        ACCESS	read-only
        STATUS	mandatory
        DESCRIPTION
                "The number of invalid update events received."
        ::= { wfAppleAurpEntry 60 }

    wfAppleAurpEntryOutUpdateInvalidEvents OBJECT-TYPE
        SYNTAX	Counter
        ACCESS	read-only
        STATUS	mandatory
        DESCRIPTION
                "The number of invalid update events transmitted."
        ::= { wfAppleAurpEntry 61 }

    wfAppleAurpEntryInZiRequests OBJECT-TYPE
        SYNTAX	Counter
        ACCESS	read-only
        STATUS	mandatory
        DESCRIPTION
                "The number of Zone Information requests received. (This
                doesn't include RI-Acks with the SZI flag set)."
        ::= { wfAppleAurpEntry 62 }

    wfAppleAurpEntryOutZiRequests OBJECT-TYPE
        SYNTAX	Counter
        ACCESS	read-only
        STATUS	mandatory
        DESCRIPTION
                "The number of Zone Information requests transmitted."
        ::= { wfAppleAurpEntry 63 }

    wfAppleAurpEntryInZiResponses OBJECT-TYPE
        SYNTAX	Counter
        ACCESS	read-only
        STATUS	mandatory
        DESCRIPTION
                "The number of Zone Information responses received."
        ::= { wfAppleAurpEntry 64 }

    wfAppleAurpEntryOutZiResponses OBJECT-TYPE
        SYNTAX	Counter
        ACCESS	read-only
        STATUS	mandatory
        DESCRIPTION
                "The number of Zone Information responses transmitted."
        ::= { wfAppleAurpEntry 65 }

    wfAppleAurpEntryInGdzlRequests OBJECT-TYPE
        SYNTAX	Counter
        ACCESS	read-only
        STATUS	mandatory
        DESCRIPTION
                "The number of Get Domain Zone List requests received."
        ::= { wfAppleAurpEntry 66 }

    wfAppleAurpEntryOutGdzlRequests OBJECT-TYPE
        SYNTAX	Counter
        ACCESS	read-only
        STATUS	mandatory
        DESCRIPTION
                "The number of Get Domain Zone List requests transmitted."
        ::= { wfAppleAurpEntry 67 }

    wfAppleAurpEntryInGdzlResponses OBJECT-TYPE
        SYNTAX	Counter
        ACCESS	read-only
        STATUS	mandatory
        DESCRIPTION
                "The number of Get Domain Zone List responses received."
        ::= { wfAppleAurpEntry 68 }

    wfAppleAurpEntryOutGdzlResponses OBJECT-TYPE
        SYNTAX	Counter
        ACCESS	read-only
        STATUS	mandatory
        DESCRIPTION
                "The number of Get Domain Zone List responses transmitted."
        ::= { wfAppleAurpEntry 69 }

    wfAppleAurpEntryInGznRequests OBJECT-TYPE
        SYNTAX	Counter
        ACCESS	read-only
        STATUS	mandatory
        DESCRIPTION
                "The number of Get Zone Nets requests received."
        ::= { wfAppleAurpEntry 70 }

    wfAppleAurpEntryOutGznRequests OBJECT-TYPE
        SYNTAX	Counter
        ACCESS	read-only
        STATUS	mandatory
        DESCRIPTION
                "The number of Get Zone Nets requests transmitted."
        ::= { wfAppleAurpEntry 71 }

    wfAppleAurpEntryInGznResponses OBJECT-TYPE
        SYNTAX	Counter
        ACCESS	read-only
        STATUS	mandatory
        DESCRIPTION
                "The number of Get Zone Nets responses received."
        ::= { wfAppleAurpEntry 72 }

    wfAppleAurpEntryOutGznResponses OBJECT-TYPE
        SYNTAX	Counter
        ACCESS	read-only
        STATUS	mandatory
        DESCRIPTION
                "The number of Get Zone Nets responses transmitted."
        ::= { wfAppleAurpEntry 73 }

    wfAppleAurpEntryInTickles OBJECT-TYPE
        SYNTAX	Counter
        ACCESS	read-only
        STATUS	mandatory
        DESCRIPTION
                "The number of Tickle Requests received."
        ::= { wfAppleAurpEntry 74 }

    wfAppleAurpEntryOutTickles OBJECT-TYPE
        SYNTAX	Counter
        ACCESS	read-only
        STATUS	mandatory
        DESCRIPTION
                "The number of Tickle Requests transmitted."
        ::= { wfAppleAurpEntry 75 }

    wfAppleAurpEntryInTickleAcks OBJECT-TYPE
        SYNTAX	Counter
        ACCESS	read-only
        STATUS	mandatory
        DESCRIPTION
                "The number of Tickle Acknowledgements received."
        ::= { wfAppleAurpEntry 76 }

    wfAppleAurpEntryOutTickleAcks OBJECT-TYPE
        SYNTAX	Counter
        ACCESS	read-only
        STATUS	mandatory
        DESCRIPTION
                "The number of Tickle Acknowledgements transmitted."
        ::= { wfAppleAurpEntry 77 }

    wfAppleAurpEntryInRouterDowns OBJECT-TYPE
        SYNTAX	Counter
        ACCESS	read-only
        STATUS	mandatory
        DESCRIPTION
                "The number of Router Down notifications received."
        ::= { wfAppleAurpEntry 78 }

    wfAppleAurpEntryOutRouterDowns OBJECT-TYPE
        SYNTAX	Counter
        ACCESS	read-only
        STATUS	mandatory
        DESCRIPTION
                "The number of Router Down notifications transmitted."
        ::= { wfAppleAurpEntry 79 }

    wfAppleAurpEntryZoneFiltDfltZone OBJECT-TYPE
        SYNTAX	DisplayString
        ACCESS	read-write
        STATUS	mandatory
        DESCRIPTION
                "The default zone to give to networks that have all
                of their real zones filtered (by PARTDENY or
                PARTALLOW zone filtering) out this connection."
        ::= { wfAppleAurpEntry 80 }

    wfAppleAggrStats	OBJECT IDENTIFIER ::= { wfAppletalkGroup 10 }

    wfAppleAggrInPkts OBJECT-TYPE
        SYNTAX	Counter
        ACCESS	read-only
        STATUS	mandatory
        DESCRIPTION
                "The total number of datagrams received"
        ::= { wfAppleAggrStats 1 }

    wfAppleAggrOutPkts OBJECT-TYPE
        SYNTAX	Counter
        ACCESS	read-only
        STATUS	mandatory
        DESCRIPTION
                "The total number of datagrams sent (includes datagrams
                forwarded)"
        ::= { wfAppleAggrStats 2 }

    wfAppleAggrFwdDatagrams OBJECT-TYPE
        SYNTAX	Counter
        ACCESS	read-only
        STATUS	mandatory
        DESCRIPTION
                "The total number of datagrams forwarded"
        ::= { wfAppleAggrStats 3 }

    wfAppleAggrInXsumErrs OBJECT-TYPE
        SYNTAX	Counter
        ACCESS	read-only
        STATUS	mandatory
        DESCRIPTION
                "The total number of datagrams destined for a local
                entity that were dropped because of a checksum error."
        ::= { wfAppleAggrStats 4 }

    wfAppleAggrInHopCountErrs OBJECT-TYPE
        SYNTAX	Counter
        ACCESS	read-only
        STATUS	mandatory
        DESCRIPTION
                "The total number of datagrams that could not be
                forwarded because they would exceed the hop-count
                limit(15)."
        ::= { wfAppleAggrStats 5 }

    wfAppleAggrInTooShorts OBJECT-TYPE
        SYNTAX	Counter
        ACCESS	read-only
        STATUS	mandatory
        DESCRIPTION
                "The total number of input DDP datagrams dropped because
                the received data length was less than the data length
                specified in the DDP header or the received data length
                was less than the length of the expected DDP header."
        ::= { wfAppleAggrStats 6 }

    wfAppleAggrInTooLongs OBJECT-TYPE
        SYNTAX	Counter
        ACCESS	read-only
        STATUS	mandatory
        DESCRIPTION
                "The total number of input DDP datagrams dropped because
                the received data length was greater than the data length
                specified in the DDP header or because they exceeded the
                maximum DDP datagram size."
        ::= { wfAppleAggrStats 7 }

    wfAppleAggrOutNoRoutes OBJECT-TYPE
        SYNTAX	Counter
        ACCESS	read-only
        STATUS	mandatory
        DESCRIPTION
                "The total number of datagrams queued for transmission thet
                were discarded because the destination was unreachable."
        ::= { wfAppleAggrStats 8 }

    wfAppleAggrInLocalDests OBJECT-TYPE
        SYNTAX	Counter
        ACCESS	read-only
        STATUS	mandatory
        DESCRIPTION
                "The total number of datagrams destined for a local entity
                (not forwarded)."
        ::= { wfAppleAggrStats 9 }

    wfAppleAggrInRtmps OBJECT-TYPE
        SYNTAX	Counter
        ACCESS	read-only
        STATUS	mandatory
        DESCRIPTION
                "The total number of RTMP packets received"
        ::= { wfAppleAggrStats 10 }

    wfAppleAggrOutRtmps OBJECT-TYPE
        SYNTAX	Counter
        ACCESS	read-only
        STATUS	mandatory
        DESCRIPTION
                "The total number of RTMP packets sent"
        ::= { wfAppleAggrStats 11 }

    END  -- Wellfleet-AT-MIB
