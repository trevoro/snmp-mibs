-- *****************************************************************
-- CISCO-INT-SERV-CAPABILITY.my
--
-- AGENT-CAPABILITIES for INT-SERV-MIB 
--
-- Copyright(c) 2002 by Cisco Systems,Inc.
--
-- Author: 
-- *****************************************************************

CISCO-INT-SERV-CAPABILITY DEFINITIONS ::= BEGIN
IMPORTS
        MODULE-IDENTITY
                FROM SNMPv2-SMI
        AGENT-CAPABILITIES
                FROM SNMPv2-CONF
        ciscoAgentCapability
                FROM CISCO-SMI;   

ciscoIntServCapability MODULE-IDENTITY
        LAST-UPDATED    "200206210000Z"
        ORGANIZATION    "Cisco Systems, Inc."
        CONTACT-INFO
                "       Cisco Systems
                        Customer Service

                Postal: 170 W Tasman Drive
                        San Jose, CA  95134
                        USA

                        Tel: +1 800 553-NETS

                E-mail: cs-rsvp@cisco.com"
        DESCRIPTION
                "The Agent Capabilities for INT-SERV-MIB."
        ::= { ciscoAgentCapability 9999 }

ciscoIntServCapabilityVismV3R00 AGENT-CAPABILITIES
PRODUCT-RELEASE      "VISM Release 3.00"
STATUS               current
DESCRIPTION          "INT-SERV-MIB Capabilities."

    SUPPORTS INT-SERV-MIB
	INCLUDES {intSrvIfAttribGroup, intSrvFlowsGroup, intSrvGenObjectsGroup}

	VARIATION    intSrvIfAttribFlows
        ACCESS       not-implemented
        DESCRIPTION  "Not supported."

	VARIATION    intSrvIfAttribPropagationDelay
        ACCESS       not-implemented
        DESCRIPTION  "Not supported."

	VARIATION    intSrvIfAttribStatus
	ACCESS       read-only
	DESCRIPTION  "write access is not supported."

	VARIATION    intSrvFlowType
	ACCESS       read-only
	DESCRIPTION  "write access is not supported."

	VARIATION    intSrvFlowOwner
	ACCESS       read-only
	DESCRIPTION  "write access is not supported."

	VARIATION    intSrvFlowDestAddr
	ACCESS       read-only
	DESCRIPTION  "write access is not supported."

	VARIATION    intSrvFlowSenderAddr
	ACCESS       read-only
	DESCRIPTION  "write access is not supported."

	VARIATION    intSrvFlowDestAddrLength
	ACCESS       read-only
	DESCRIPTION  "write access is not supported."

	VARIATION    intSrvFlowProtocol
	ACCESS       read-only
	DESCRIPTION  "write access is not supported."

	VARIATION    intSrvFlowSenderAddrLength
	ACCESS       read-only
	DESCRIPTION  "write access is not supported."

	VARIATION    intSrvFlowDestPort
	ACCESS       read-only
	DESCRIPTION  "write access is not supported."

	VARIATION    intSrvFlowPort
	ACCESS       read-only
	DESCRIPTION  "write access is not supported."

	VARIATION    intSrvFlowFlowId
        ACCESS       not-implemented
        DESCRIPTION  "Not supported."

	VARIATION    intSrvFlowInterface
	ACCESS       read-only
	DESCRIPTION  "write access is not supported."

	VARIATION    intSrvFlowIfAddr
	ACCESS       read-only
	DESCRIPTION  "write access is not supported."

	VARIATION    intSrvFlowRate
	ACCESS       read-only
	DESCRIPTION  "write access is not supported."

	VARIATION    intSrvFlowBurst
	ACCESS       read-only
	DESCRIPTION  "write access is not supported."

	VARIATION    intSrvFlowWeight
	ACCESS       read-only
	DESCRIPTION  "write access is not supported."

	VARIATION    intSrvFlowQueue
	ACCESS       read-only
	DESCRIPTION  "write access is not supported."

	VARIATION    intSrvFlowMinTU
        ACCESS       not-implemented
        DESCRIPTION     "Not supported."

	VARIATION    intSrvFlowMaxTU
        ACCESS       not-implemented
        DESCRIPTION     "Not supported."

	VARIATION    intSrvFlowBestEffort
        ACCESS       not-implemented
        DESCRIPTION  "Not supported."

	VARIATION    intSrvFlowPoliced
        ACCESS       not-implemented
        DESCRIPTION  "Not supported."

	VARIATION    intSrvFlowDiscard
	ACCESS       read-only
	DESCRIPTION  "write access is not supported."

	VARIATION    intSrvFlowService
        ACCESS       not-implemented
        DESCRIPTION  "Not supported."

	VARIATION    intSrvFlowOrder
        ACCESS       not-implemented
        DESCRIPTION  "Not supported."

	VARIATION    intSrvFlowStatus
	ACCESS       read-only
	DESCRIPTION  "write access is not supported."

	VARIATION    intSrvFlowNewIndex
	ACCESS       read-only
	DESCRIPTION  "write access is not supported."

        ::= { ciscoIntServCapability 1 }
END
