-- *****************************************************************************
-- Unisphere-Data-IGMP-CONF
--
-- SNMP Agent Capabilities definitions for the IGMP MIB.
--
-- Copyright (c) 2001 Unisphere Networks, Inc.  All rights reserved.
-- *****************************************************************************

Unisphere-Data-IGMP-CONF DEFINITIONS ::= BEGIN

IMPORTS
    MODULE-IDENTITY
        FROM SNMPv2-SMI
    AGENT-CAPABILITIES
        FROM SNMPv2-CONF
    usDataAgents
        FROM Unisphere-Data-Agents
    usdIgmpProxyInterfaceGroup,
    usdIgmpProxyCacheGroup
        FROM Unisphere-Data-IGMP-MIB;

usdIgmpAgent MODULE-IDENTITY
    LAST-UPDATED "200103281720Z"  -- 28-Mar-01 12:20 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the IGMP component of the SNMP
        agent in the Unisphere Routing Switch family of products."
    -- Revision History
    REVISION    "200103281720Z"  -- 28-Mar-01 12:20 PM EST  - RX 3.2
    DESCRIPTION
        "The initial release of this management information module."
    ::= { usDataAgents 19 }

usdIgmpAgentV1 AGENT-CAPABILITIES
    PRODUCT-RELEASE
        "Version 1 of the IGMP component of the Unisphere Routing Switch SNMP
        agent.  This version of the IGMP component is supported in the Unisphere
        RX 3.0 and subsequent system releases."
    STATUS      current
    DESCRIPTION
        "The MIB supported by the SNMP agent for the IGMP application in the
        Unisphere Routing Switch."

    SUPPORTS        Unisphere-Data-IGMP-MIB
        INCLUDES  { usdIgmpProxyInterfaceGroup,
                    usdIgmpProxyCacheGroup }

    ::= { usdIgmpAgent 1 }

END
