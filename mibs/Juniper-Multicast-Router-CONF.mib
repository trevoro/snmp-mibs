-- *****************************************************************************
-- Juniper-Multicast-Router-CONF
--
-- SNMP Agent Capabilities definitions for the multicast router MIB.
--
-- Copyright (c) 2002 Unisphere Networks, Inc.
-- Copyright (c) 2002, 2003 Juniper Networks, Inc.
--   All rights reserved.
-- *****************************************************************************

Juniper-Multicast-Router-CONF  DEFINITIONS ::= BEGIN

IMPORTS
    MODULE-IDENTITY
        FROM SNMPv2-SMI
    AGENT-CAPABILITIES
        FROM SNMPv2-CONF
    juniAgents
        FROM Juniper-Agents;

juniMRouterAgent  MODULE-IDENTITY
    LAST-UPDATED "200609021332Z"  -- 02-Sep-06 07:02 PM EST
    ORGANIZATION "Juniper Networks, Inc."
    CONTACT-INFO
        "       Juniper Networks, Inc.
        Postal: 10 Technology Park Drive
                Westford, MA  01886-3146
                USA
        Tel:    +1 978 589 5800
        E-mail: mib@Juniper.net"
    DESCRIPTION
        "The agent capabilities definitions for the multicast router component
        of the SNMP agent in the Juniper E-series family of products."
    -- Revision History
    REVISION   "200609021102Z"  -- 02-Sep-06 07:02 PM EDT  - JUNOSe 8.0
    DESCRIPTION
        "Scalar attribute rsMcastRpfDisable is supported for the Juniper-MROUTER-MIB."
    REVISION    "200210282004Z"  -- 28-Oct-02 03:04 PM EST  - JUNOSe 5.0
    DESCRIPTION
        "Replaced Unisphere names with Juniper names.
         Added support for the Juniper-MROUTER-MIB."
    REVISION    "200204012017Z"  -- 01-Apr-02 03:17 PM EST  - JUNOSe 4.1
    DESCRIPTION
        "The initial release of this management information module."
    ::= { juniAgents 55 }


-- *****************************************************************************
-- Multicast Router SNMP Agent Capabilities definitions
-- *****************************************************************************
juniMRouterAgentV1  AGENT-CAPABILITIES
    PRODUCT-RELEASE
        "Version 1 of the multicast router component of the JUNOSe SNMP agent.
        This version of the multicast router component was supported in JUNOSe
        4.1 and subsequent 4.x system releases."
    STATUS      obsolete
    DESCRIPTION
        "The MIBs supported by the SNMP agent for the multicast router
        application in JUNOSe.  These capabilities became obsolete when support
        was added for the Juniper-MROUTER-MIB."
    SUPPORTS    IPMROUTE-STD-MIB
        INCLUDES {
            ipMRouteMIBBasicGroup,
            ipMRouteMIBHopCountGroup,
            ipMRouteMIBPktsOutGroup,
            ipMRouteMIBHCInterfaceGroup,
            ipMRouteMIBRouteGroup,
            ipMRouteMIBPktsGroup }
    ::= { juniMRouterAgent 1 }

juniMRouterAgentV2  AGENT-CAPABILITIES
    PRODUCT-RELEASE
        "Version 2 of the multicast router component of the JUNOSe SNMP agent.
        This version of the multicast router component is supported in the
        Juniper JUNOSe 5.0 and subsequent system releases."
    STATUS      obsolete
    DESCRIPTION
        "The MIB supported by the SNMP agent for the multicast router
        application in JUNOSe. These capabilities became obsolete when support
        was added juniMcastGlobalConfGroup for the Juniper-MROUTER-MIB."
    SUPPORTS    IPMROUTE-STD-MIB
        INCLUDES {
            ipMRouteMIBBasicGroup,
            ipMRouteMIBHopCountGroup,
            ipMRouteMIBPktsOutGroup,
            ipMRouteMIBHCInterfaceGroup,
            ipMRouteMIBRouteGroup,
            ipMRouteMIBPktsGroup }
    SUPPORTS    Juniper-MROUTER-MIB
        INCLUDES {
            juniMcastRpfRouteConfGroup }
    ::= { juniMRouterAgent 2 }

juniMRouterAgentV3  AGENT-CAPABILITIES
    PRODUCT-RELEASE
        "Version 3 of the multicast router component of the JUNOSe SNMP agent.
        This version of the multicast router component is supported in the
        Juniper JUNOSe 8.0 and subsequent system releases."
    STATUS      current
    DESCRIPTION
        "The MIB supported by the SNMP agent for the multicast router
        application in JUNOSe."
    SUPPORTS    IPMROUTE-STD-MIB
        INCLUDES {
            ipMRouteMIBBasicGroup,
            ipMRouteMIBHopCountGroup,
            ipMRouteMIBPktsOutGroup,
            ipMRouteMIBHCInterfaceGroup,
            ipMRouteMIBRouteGroup,
            ipMRouteMIBPktsGroup }
    SUPPORTS    Juniper-MROUTER-MIB
        INCLUDES {
            juniMcastRpfRouteConfGroup,
            juniMcastGlobalConfGroup }
    ::= { juniMRouterAgent 3 }

END
