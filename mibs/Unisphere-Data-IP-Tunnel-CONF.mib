-- *****************************************************************************
-- Unisphere-Data-IP-Tunnel-CONF
--
-- SNMP Agent Capabilities definitions for the Ip Tunnel MIB.
--
-- Copyright (c) 2001 Unisphere Networks, Inc.  All rights reserved.
-- *****************************************************************************

Unisphere-Data-IP-Tunnel-CONF DEFINITIONS ::= BEGIN

IMPORTS
    MODULE-IDENTITY
        FROM SNMPv2-SMI
    AGENT-CAPABILITIES
        FROM SNMPv2-CONF
    usDataAgents
        FROM Unisphere-Data-Agents
    usdIpTunnelInterfaceGroup
        FROM Unisphere-Data-IP-TUNNEL-MIB;

usdIpTunnelAgent MODULE-IDENTITY
    LAST-UPDATED "200103292213Z"  -- 29-Mar-01 05:13 PM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the IP Tunnel (GRE/DVMRP) MIB
        component of the SNMP agent in the Unisphere Routing Switch family of
        products."
    -- Revision History
    REVISION    "200103292213Z"  -- 29-Mar-01 05:13 PM EST  - RX 3.2
    DESCRIPTION
        "The initial release of this management information module."
    ::= { usDataAgents 47 }

usdIpTunnelAgentV1 AGENT-CAPABILITIES
    PRODUCT-RELEASE
        "Version 1 of the Ip Tunnel component of the Unisphere Routing Switch
        SNMP agent.  This version of the Ip Tunnel component is supported in the
        Unisphere RX 3.2 and subsequent system releases."
    STATUS      current
    DESCRIPTION
        "The MIB supported by the SNMP agent for the Ip Tunnel application
        in the Unisphere Routing Switch."

    SUPPORTS    Unisphere-Data-IP-TUNNEL-MIB
        INCLUDES  { usdIpTunnelInterfaceGroup }

    ::= { usdIpTunnelAgent 1 }

END
