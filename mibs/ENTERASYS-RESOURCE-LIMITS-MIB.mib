ENTERASYS-RESOURCE-LIMITS-MIB DEFINITIONS ::= BEGIN

-- enterasys-resource-limits-mib.txt 
--
--  Part Number:
--
--

--  This module provides authoritative definitions for Enterasys
--  Networks' Platform Resource Limits MIB

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright December, 2013 Enterasys Networks, Inc.

IMPORTS
    MODULE-IDENTITY, OBJECT-TYPE, Unsigned32
        FROM SNMPv2-SMI
    MODULE-COMPLIANCE, OBJECT-GROUP
        FROM SNMPv2-CONF
    TEXTUAL-CONVENTION
        FROM SNMPv2-TC
    etsysModules
        FROM ENTERASYS-MIB-NAMES;

etsysResourceLimitsMIB MODULE-IDENTITY
    LAST-UPDATED "201312161622Z"  -- Mon Dec 16 16:22 UTC 2013
    ORGANIZATION "Enterasys Networks, Inc"
    CONTACT-INFO
        "Postal:  Enterasys Networks
                  9 Northeastern Blvd.
                  Salem, NH 03079 USA

         Phone:   +1 603 952 5000
         E-mail:  support@enterasys.com
         WWW:     http://www.enterasys.com"

    DESCRIPTION
        "This MIB module defines a portion of the SNMP MIB under
         the Enterasys Networks enterprise OID pertaining to
         the Platform Resource Limits MIB."

    REVISION    "201312161622Z"  -- Mon Dec 16 16:22 UTC 2013
    DESCRIPTION "Initial version of this MIB module."

    ::= { etsysModules 876 }

-- -------------------------------------------------------------
-- Textual Conventions
-- -------------------------------------------------------------
EtsysResourceLimitsProfiles ::= TEXTUAL-CONVENTION
    STATUS  current
    DESCRIPTION
        "This textual convention defines the list of profiles for 
         setting the limits of the resource allocation.

            default(0) - Limits of resource allocation is based on what
                         the managed entity defines by default.
            router1(1) - This profile allocates more resource to router-
                         related parameters than switch-related parameters
                         of the managed entity.
            router2(2) - This profile is a variant of router1.
            switch (3) - This profile allocates more resource to switch-
                         related parameters than router-related parameters
                         of the managed entity."
    SYNTAX      INTEGER {
                    default( 0 ),
                    router1( 1 ),
                    router2( 2 ),
                    switch ( 3 )
                }

-- -------------------------------------------------------------
-- Object and Conformance Definitions
-- -------------------------------------------------------------
etsysResourceLimitsObjects
    OBJECT IDENTIFIER ::= { etsysResourceLimitsMIB 1 }

etsysResourceLimitsConformance
    OBJECT IDENTIFIER ::= { etsysResourceLimitsMIB 2 }

-- -------------------------------------------------------------
-- Object Definitions
-- -------------------------------------------------------------
etsysResourceLimitsProfile
    OBJECT IDENTIFIER ::= { etsysResourceLimitsObjects 1 }

-- -------------------------------------------------------------
-- The Enterasys Resource Limits Profile Definitions
-- -------------------------------------------------------------

etsysResourceLimitsProfileAdmin OBJECT-TYPE
    SYNTAX      EtsysResourceLimitsProfiles 
    MAX-ACCESS  read-write
    STATUS      current
    DESCRIPTION
        "Indicates the configured profile for resource allocation."
    ::= { etsysResourceLimitsProfile 1 }

etsysResourceLimitsProfileOperational OBJECT-TYPE
    SYNTAX      EtsysResourceLimitsProfiles
    MAX-ACCESS  read-only
    STATUS      current
    DESCRIPTION
        "Indicates the operational profile for resource allocation."
    ::= { etsysResourceLimitsProfile 2 }

etsysResourceLimitsProfileCapabilities OBJECT-TYPE
    SYNTAX      BITS {
                    default( 0 ),
                    router1( 1 ),
                    router2( 2 ),
                    switch ( 3 )
                }
    MAX-ACCESS  read-only
    STATUS      current
    DESCRIPTION
        "Indicates the profiles supported by the managed entity.

            default(0) - Limits of resource allocation is based on what
                         the managed entity defines by default.
            router1(1) - This profile allocates more resource to router-
                         related parameters than switch-related parameters
                         of the managed entity.
            router2(2) - This profile is a variant of router1.
            switch (3) - This profile allocates more resource to switch-
                         related parameters than router-related parameters
                         of the managed entity."
    ::= { etsysResourceLimitsProfile 3 }

etsysResourceLimitsProfileTable OBJECT-TYPE
    SYNTAX      SEQUENCE OF EtsysResourceLimitsProfileEntry
    MAX-ACCESS  not-accessible
    STATUS      current
    DESCRIPTION
        "A table that contains information about individual components
         of a profile. Each profile defines and includes exactly the
         same components to which the limits will be applied."
    ::= { etsysResourceLimitsProfile 4 }

etsysResourceLimitsProfileEntry OBJECT-TYPE
    SYNTAX      EtsysResourceLimitsProfileEntry 
    MAX-ACCESS  not-accessible
    STATUS      current
    DESCRIPTION
        "Enterasys Resource Limits Profile Table entry."
    INDEX { etsysResourceLimitsProfileIndex }
    ::= { etsysResourceLimitsProfileTable 1 }

EtsysResourceLimitsProfileEntry ::=
    SEQUENCE {
        etsysResourceLimitsProfileIndex 
            EtsysResourceLimitsProfiles,
        etsysResourceLimitsProfileAuthenticatedUsers
            Unsigned32,
        etsysResourceLimitsProfileMacRules
            Unsigned32,
        etsysResourceLimitsProfileIpv6Rules
            Unsigned32,
        etsysResourceLimitsProfileIpv4Rules
            Unsigned32,
        etsysResourceLimitsProfileL2Rules
            Unsigned32,
        etsysResourceLimitsProfileIpv6IngressAcl
            Unsigned32,
        etsysResourceLimitsProfileIpv6Pbr
            Unsigned32,
        etsysResourceLimitsProfileIpv4IngressAcl
            Unsigned32,
        etsysResourceLimitsProfileIpv4Pbr
            Unsigned32,
        etsysResourceLimitsProfileL2IngressAcl
            Unsigned32,
        etsysResourceLimitsProfileIpv6EgressAcl
            Unsigned32,
        etsysResourceLimitsProfileIpv4EgressAcl
            Unsigned32,
        etsysResourceLimitsProfileL2EgressAcl
            Unsigned32
    }

etsysResourceLimitsProfileIndex OBJECT-TYPE
    SYNTAX      EtsysResourceLimitsProfiles 
    MAX-ACCESS  not-accessible
    STATUS      current
    DESCRIPTION
        "The index to the Resource Limits Profile Table."
    ::= { etsysResourceLimitsProfileEntry 1 }

etsysResourceLimitsProfileAuthenticatedUsers OBJECT-TYPE
    SYNTAX      Unsigned32
    MAX-ACCESS  read-only
    STATUS      current
    DESCRIPTION
        "Indicates the limit for Authenticated Users"
    ::= { etsysResourceLimitsProfileEntry 2 }

etsysResourceLimitsProfileMacRules OBJECT-TYPE
    SYNTAX      Unsigned32
    MAX-ACCESS  read-only
    STATUS      current
    DESCRIPTION
        "Indicates the limit for MAC Rules."
    ::= { etsysResourceLimitsProfileEntry 3 }

etsysResourceLimitsProfileIpv6Rules OBJECT-TYPE
    SYNTAX      Unsigned32
    MAX-ACCESS  read-only
    STATUS      current
    DESCRIPTION
        "Indicates the limit for IPV6 Rules."
    ::= { etsysResourceLimitsProfileEntry 4 }

etsysResourceLimitsProfileIpv4Rules OBJECT-TYPE
    SYNTAX      Unsigned32
    MAX-ACCESS  read-only
    STATUS      current
    DESCRIPTION
        "Indicates the limit for IPV4 Rules."
    ::= { etsysResourceLimitsProfileEntry 5 }

etsysResourceLimitsProfileL2Rules OBJECT-TYPE
    SYNTAX      Unsigned32
    MAX-ACCESS  read-only
    STATUS      current
    DESCRIPTION
        "Indicates the limit for L2 Rules."
    ::= { etsysResourceLimitsProfileEntry 6 }

etsysResourceLimitsProfileIpv6IngressAcl OBJECT-TYPE
    SYNTAX      Unsigned32
    MAX-ACCESS  read-only
    STATUS      current
    DESCRIPTION
        "Indicates the limit for IPV6 Ingress ACL."
    ::= { etsysResourceLimitsProfileEntry 7 }

etsysResourceLimitsProfileIpv6Pbr OBJECT-TYPE
    SYNTAX      Unsigned32
    MAX-ACCESS  read-only
    STATUS      current
    DESCRIPTION
        "Indicates the limit for IPV6 PBR."
    ::= { etsysResourceLimitsProfileEntry 8 }

etsysResourceLimitsProfileIpv4IngressAcl OBJECT-TYPE
    SYNTAX      Unsigned32
    MAX-ACCESS  read-only
    STATUS      current
    DESCRIPTION
        "Indicates the limit for IPV4 Ingress ACL."
    ::= { etsysResourceLimitsProfileEntry 9 }

etsysResourceLimitsProfileIpv4Pbr OBJECT-TYPE
    SYNTAX      Unsigned32
    MAX-ACCESS  read-only
    STATUS      current
    DESCRIPTION
        "Indicates the limit for IPV4 PBR."
    ::= { etsysResourceLimitsProfileEntry 10 }

etsysResourceLimitsProfileL2IngressAcl OBJECT-TYPE
    SYNTAX      Unsigned32
    MAX-ACCESS  read-only
    STATUS      current
    DESCRIPTION
        "Indicates the limit for L2 Ingress ACL."
    ::= { etsysResourceLimitsProfileEntry 11 }

etsysResourceLimitsProfileIpv6EgressAcl OBJECT-TYPE
    SYNTAX      Unsigned32
    MAX-ACCESS  read-only
    STATUS      current
    DESCRIPTION
        "Indicates the limit for IPV6 Egress ACL."
    ::= { etsysResourceLimitsProfileEntry 12 }

etsysResourceLimitsProfileIpv4EgressAcl OBJECT-TYPE
    SYNTAX      Unsigned32
    MAX-ACCESS  read-only
    STATUS      current
    DESCRIPTION
        "Indicates the limit for IPV4 Egress ACL."
    ::= { etsysResourceLimitsProfileEntry 13 }

etsysResourceLimitsProfileL2EgressAcl OBJECT-TYPE
    SYNTAX      Unsigned32
    MAX-ACCESS  read-only
    STATUS      current
    DESCRIPTION
        "Indicates the limit for L2 Egress ACL."
    ::= { etsysResourceLimitsProfileEntry 14 }

-- -------------------------------------------------------------
-- Conformance Information
-- -------------------------------------------------------------
etsysResourceLimitsGroups
    OBJECT IDENTIFIER ::= { etsysResourceLimitsConformance 1 }

etsysResourceLimitsCompliances
    OBJECT IDENTIFIER ::= { etsysResourceLimitsConformance 2 }

-- -------------------------------------------------------------
-- Units of conformance
-- -------------------------------------------------------------
etsysResourceLimitsProfileGroup OBJECT-GROUP
    OBJECTS {
       etsysResourceLimitsProfileAdmin,
       etsysResourceLimitsProfileOperational,
       etsysResourceLimitsProfileCapabilities
    }
    STATUS      current
    DESCRIPTION
        "A collection of objects providing information related to
         the device's resource allocation profile."
    ::= { etsysResourceLimitsGroups 1 }

etsysResourceLimitsProfileTableGroup OBJECT-GROUP
    OBJECTS {
        etsysResourceLimitsProfileAuthenticatedUsers,
        etsysResourceLimitsProfileMacRules,
        etsysResourceLimitsProfileIpv6Rules,
        etsysResourceLimitsProfileIpv4Rules,
        etsysResourceLimitsProfileL2Rules,
        etsysResourceLimitsProfileIpv6IngressAcl,
        etsysResourceLimitsProfileIpv6Pbr,
        etsysResourceLimitsProfileIpv4IngressAcl,
        etsysResourceLimitsProfileIpv4Pbr,
        etsysResourceLimitsProfileL2IngressAcl,
        etsysResourceLimitsProfileIpv6EgressAcl,
        etsysResourceLimitsProfileIpv4EgressAcl,
        etsysResourceLimitsProfileL2EgressAcl
    }
    STATUS      current
    DESCRIPTION
        "A collection of objects providing information related to
         individual components included in each resource profile."
    ::= { etsysResourceLimitsGroups 2 }

-- -------------------------------------------------------------
-- Compliance statements
-- -------------------------------------------------------------
etsysResourceLimitsProfileCompliance MODULE-COMPLIANCE
    STATUS      current
    DESCRIPTION
        "The compliance statement for devices that support
         Enterasys Resource Limits Profile MIB."
    MODULE
        MANDATORY-GROUPS {
           etsysResourceLimitsProfileGroup,
           etsysResourceLimitsProfileTableGroup
        } 
    ::= { etsysResourceLimitsCompliances 1 }

END
