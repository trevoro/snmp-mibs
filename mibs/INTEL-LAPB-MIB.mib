INTEL-LAPB-MIB DEFINITIONS ::= BEGIN

-- Copyright (C) 1997 Intel Corporation. All rights reserved.
--
-- LAPB MIB
--
-- Proprietary MIB containing information about LAPB.
--
-- Build 1
--

IMPORTS
		Counter FROM RFC1155-SMI
    mib2ext                    FROM INTEL-GEN-MIB
    OBJECT-TYPE                FROM RFC-1212;

    lapb2                      OBJECT IDENTIFIER ::= { mib2ext 31 }
    lapbFrameType	        OBJECT IDENTIFIER ::= { lapb2 1 }

lapbFrameTypeTable OBJECT-TYPE
    SYNTAX SEQUENCE OF LapbFrameTypeEntry
    ACCESS not-accessible
    STATUS mandatory
    DESCRIPTION "The LAPB frame type counters."
    ::= { lapbFrameType 1 }

lapbFrameTypeEntry OBJECT-TYPE
    SYNTAX LapbFrameTypeEntry
    ACCESS not-accessible
    STATUS mandatory
    DESCRIPTION ""
    INDEX { lapbFrameTypeIndex }
    ::= { lapbFrameTypeTable 1 }

LapbFrameTypeEntry ::= SEQUENCE {
                        lapbFrameTypeIndex
                           INTEGER,
                        lapbFrameTypeRxInfo
                           Counter,
                        lapbFrameTypeTxInfo
                           Counter,
                        lapbFrameTypeRxRR
                           Counter,
                        lapbFrameTypeTxRR
                           Counter,
                        lapbFrameTypeRxRNR
                           Counter,
                        lapbFrameTypeTxRNR
                           Counter,
                        lapbFrameTypeRxREJ
                           Counter,
                        lapbFrameTypeTxREJ
                           Counter,
                        lapbFrameTypeRxFRMR
                           Counter,
                        lapbFrameTypeTxFRMR
                           Counter,
                        lapbFrameTypeRxSABM
                           Counter,
                        lapbFrameTypeTxSABM
                           Counter,
                        lapbFrameTypeRxUA
                           Counter,
                        lapbFrameTypeTxUA
                           Counter,
                        lapbFrameTypeRxDISC
                           Counter,
                        lapbFrameTypeTxDISC
                           Counter,
                        lapbFrameTypeRxDM
                           Counter,
                        lapbFrameTypeTxDM
                           Counter,
                        lapbFrameTypeRxPOLL
                           Counter,
                        lapbFrameTypeTxPOLL
                           Counter,
                        lapbFrameTypeRxFINAL
                           Counter,
                        lapbFrameTypeTxFINAL
                           Counter,
                        lapbFrameTypeRxComUndef
                           Counter,
                        lapbFrameTypeRxIllAddr
                           Counter,
                        lapbFrameTypeRxLong
                           Counter,
                        lapbFrameTypeTxRe
                           Counter,
                        lapbFrameTypeReset
                           Counter
                        }

lapbFrameTypeIndex OBJECT-TYPE
    SYNTAX INTEGER
    ACCESS read-only
    STATUS mandatory
    DESCRIPTION "The IfIndex for the LAPB layer of the inspected link."
    ::= { lapbFrameTypeEntry 1 }

lapbFrameTypeRxInfo OBJECT-TYPE
    SYNTAX Counter
    ACCESS read-only
    STATUS mandatory
    DESCRIPTION "The number of received Info frames."
    ::= { lapbFrameTypeEntry 2 }

lapbFrameTypeTxInfo OBJECT-TYPE
    SYNTAX Counter
    ACCESS read-only
    STATUS mandatory
    DESCRIPTION "The number of transmitted Info frames."
    ::= { lapbFrameTypeEntry 3 }

lapbFrameTypeRxRR OBJECT-TYPE
    SYNTAX Counter
    ACCESS read-only
    STATUS mandatory
    DESCRIPTION "The number of received RRs."
    ::= { lapbFrameTypeEntry 4 }

lapbFrameTypeTxRR OBJECT-TYPE
    SYNTAX Counter
    ACCESS read-only
    STATUS mandatory
    DESCRIPTION "The number of transmitted RRs"
    ::= { lapbFrameTypeEntry 5 }

lapbFrameTypeRxRNR OBJECT-TYPE
    SYNTAX Counter
    ACCESS read-only
    STATUS mandatory
    DESCRIPTION "The number of received RNRs"
    ::= { lapbFrameTypeEntry 6 }

lapbFrameTypeTxRNR OBJECT-TYPE
    SYNTAX Counter
    ACCESS read-only
    STATUS mandatory
    DESCRIPTION "The number of transmitted RNRs"
    ::= { lapbFrameTypeEntry 7 }

lapbFrameTypeRxREJ OBJECT-TYPE
    SYNTAX Counter
    ACCESS read-only
    STATUS mandatory
    DESCRIPTION "The number of received REJs"
    ::= { lapbFrameTypeEntry 8 }

lapbFrameTypeTxREJ OBJECT-TYPE
    SYNTAX Counter
    ACCESS read-only
    STATUS mandatory
    DESCRIPTION "The number of transmitted REJs"
    ::= { lapbFrameTypeEntry 9 }

lapbFrameTypeRxFRMR OBJECT-TYPE
    SYNTAX Counter
    ACCESS read-only
    STATUS mandatory
    DESCRIPTION "The number of received FRMRs"
    ::= { lapbFrameTypeEntry 10 }

lapbFrameTypeTxFRMR OBJECT-TYPE
    SYNTAX Counter
    ACCESS read-only
    STATUS mandatory
    DESCRIPTION "The number of transmitted FRMRs"
    ::= { lapbFrameTypeEntry 11 }

lapbFrameTypeRxSABM OBJECT-TYPE
    SYNTAX Counter
    ACCESS read-only
    STATUS mandatory
    DESCRIPTION "The number of received SABMs"
    ::= { lapbFrameTypeEntry 12 }

lapbFrameTypeTxSABM OBJECT-TYPE
    SYNTAX Counter
    ACCESS read-only
    STATUS mandatory
    DESCRIPTION "The number of transmitted SABMs"
    ::= { lapbFrameTypeEntry 13 }

lapbFrameTypeRxUA OBJECT-TYPE
    SYNTAX Counter
    ACCESS read-only
    STATUS mandatory
    DESCRIPTION "The number of received UAs"
    ::= { lapbFrameTypeEntry 14 }

lapbFrameTypeTxUA OBJECT-TYPE
    SYNTAX Counter
    ACCESS read-only
    STATUS mandatory
    DESCRIPTION "The number of transmitted UAs"
    ::= { lapbFrameTypeEntry 15 }

lapbFrameTypeRxDISC OBJECT-TYPE
    SYNTAX Counter
    ACCESS read-only
    STATUS mandatory
    DESCRIPTION "The number of received DISCs"
    ::= { lapbFrameTypeEntry 16 }

lapbFrameTypeTxDISC OBJECT-TYPE
    SYNTAX Counter
    ACCESS read-only
    STATUS mandatory
    DESCRIPTION "The number of transmitted DISCs"
    ::= { lapbFrameTypeEntry 17 }

lapbFrameTypeRxDM OBJECT-TYPE
    SYNTAX Counter
    ACCESS read-only
    STATUS mandatory
    DESCRIPTION "The number of received DMs"
    ::= { lapbFrameTypeEntry 18 }

lapbFrameTypeTxDM OBJECT-TYPE
    SYNTAX Counter
    ACCESS read-only
    STATUS mandatory
    DESCRIPTION "The number of transmitted DMs"
    ::= { lapbFrameTypeEntry 19 }

lapbFrameTypeRxPOLL OBJECT-TYPE
    SYNTAX Counter
    ACCESS read-only
    STATUS mandatory
    DESCRIPTION "The number of received frames with the POLL flag set"
    ::= { lapbFrameTypeEntry 20 }

lapbFrameTypeTxPOLL OBJECT-TYPE
    SYNTAX Counter
    ACCESS read-only
    STATUS mandatory
    DESCRIPTION "The number of transmitted frames with the POLL flag set"
    ::= { lapbFrameTypeEntry 21 }

lapbFrameTypeRxFINAL OBJECT-TYPE
    SYNTAX Counter
    ACCESS read-only
    STATUS mandatory
    DESCRIPTION "The number of received frames with the FINAL flag set"
    ::= { lapbFrameTypeEntry 22 }

lapbFrameTypeTxFINAL OBJECT-TYPE
    SYNTAX Counter
    ACCESS read-only
    STATUS mandatory
    DESCRIPTION "The number of transmitted frames with the FINAL flag set"
    ::= { lapbFrameTypeEntry 23 }

lapbFrameTypeRxComUndef OBJECT-TYPE
    SYNTAX Counter
    ACCESS read-only
    STATUS mandatory
    DESCRIPTION "The number of received frames with unknown command code."
    ::= { lapbFrameTypeEntry 24 }

lapbFrameTypeRxIllAddr OBJECT-TYPE
    SYNTAX Counter
    ACCESS read-only
    STATUS mandatory
    DESCRIPTION "The number of received frames with illegal address fields."
    ::= { lapbFrameTypeEntry 25 }

lapbFrameTypeRxLong OBJECT-TYPE
    SYNTAX Counter
    ACCESS read-only
    STATUS mandatory
    DESCRIPTION "The number of received frames that were too long."
    ::= { lapbFrameTypeEntry 26 }

lapbFrameTypeTxRe OBJECT-TYPE
    SYNTAX Counter
    ACCESS read-only
    STATUS mandatory
    DESCRIPTION "The number of times one or more frames had to be retransmitted."
    ::= { lapbFrameTypeEntry 27 }

lapbFrameTypeReset OBJECT-TYPE
    SYNTAX Counter
    ACCESS read-only
    STATUS mandatory
    DESCRIPTION "The number of times the link was reset due to the reception of a SABM while up."
    ::= { lapbFrameTypeEntry 28 }

END
