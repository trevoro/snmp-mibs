-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-MIB DEFINITIONS ::= BEGIN

IMPORTS
    TimeTicks, internet, enterprises, Counter
            FROM RFC1155-SMI
    OBJECT-TYPE
            FROM RFC-1212
    ifIndex, DisplayString
            FROM RFC1213-MIB
    TRAP-TYPE
            FROM RFC-1215
	Integer32, Counter32 FROM SNMPv2-SMI;

mitel OBJECT IDENTIFIER ::= { enterprises 1027 }
-- MODULE-IDENTITY
--  LastUpdated
--    9903010000Z
--  OrgName
--    MITEL Corporation
--  ContactInfo
--    Standards Group,
--     Postal:    MITEL Corporation
--     350 Legget Drive, PO Box 13089
--     Kanata, Ontario
--     Canada  K2K 1X3
--     Tel: +1 613 592 2122
--     Fax: +1 613 592 4784
--     E-mail: std@mitel.com
--  Descr
--    The top-level MITEL MIB module.
--  RevDate
--    9603010000Z
--  RevDescr
--    Mitel MIB Version 2.0

-- **********************
-- For SNMPv1 compliance:
-- **********************

snmpV2          OBJECT IDENTIFIER ::= { internet 6 }
snmpDomains     OBJECT IDENTIFIER ::= { snmpV2 1 }
snmpUDPDomain   OBJECT IDENTIFIER ::= { snmpDomains 1 }
--Counter32 ::= Counter
--Integer32 ::= INTEGER (-2147483648..2147483647)
InterfaceIndex ::= INTEGER
TruthValue ::= INTEGER {
        true(1),
        false(2)
        }
RowStatus ::= INTEGER {
        active(1),
        notInService(2),
        notReady(3),
        createAndGo(4),
        createAndWait(5),
        destroy(6)
        }
TimeStamp ::= TimeTicks
TimeInterval ::= INTEGER(0..2147483647)


mitelIdentification OBJECT IDENTIFIER ::= { mitel 1 }
-- OBJECT-IDENTITY
--  Status
--    mandatory
--  Descr
--    The identification subtree. Leaves in this subtree are
--     used for the sysObjectID field in the MIB-II system tree or
--     other similar OID fields.

mitelExperimental OBJECT IDENTIFIER ::= { mitel 2 }
-- OBJECT-IDENTITY
--  Status
--    mandatory
--  Descr
--    The experimental MIB development subtree. The branches 
--     in this subtree should follow the format of the mitelProprietary 
--     subtree.

mitelExtensions OBJECT IDENTIFIER ::= { mitel 3 }
-- OBJECT-IDENTITY
--  Status
--    mandatory
--  Descr
--    The standards extension subtree. Used for extensions to 
--     any of the standard subtrees under the MIB-II subtree.

mitelProprietary OBJECT IDENTIFIER ::= { mitel 4 }
-- OBJECT-IDENTITY
--  Status
--    mandatory
--  Descr
--    The managed information subtree. Leaves in this subtree 
--     are generic devices or protocols that can be managed.

mitelConformance OBJECT IDENTIFIER ::= { mitel 5 }
-- OBJECT-IDENTITY
--  Status
--    mandatory
--  Descr
--    The conformance subtree. Leaves in this subtree 
--     identify compliance grouping and requirements.

mitelIdMgmtPlatforms OBJECT IDENTIFIER ::= { mitelIdentification 1 }
-- OBJECT-IDENTITY
--  Status
--    mandatory
--  Descr
--    Products used to manage MITEL equipment.

mitelIdCallServers OBJECT IDENTIFIER ::= { mitelIdentification 2 }
-- OBJECT-IDENTITY
--  Status
--    mandatory
--  Descr
--    Products providing call processing capabilities.

mitelIdTerminals OBJECT IDENTIFIER ::= { mitelIdentification 3 }
-- OBJECT-IDENTITY
--  Status
--    mandatory
--  Descr
--    Desktop products.

mitelIdInterfaces OBJECT IDENTIFIER ::= { mitelIdentification 4 }
-- OBJECT-IDENTITY
--  Status
--    mandatory
--  Descr
--    Products providing the interface between a call 
--     processing entity and a network or terminal.

mitelIdCtiPlatforms OBJECT IDENTIFIER ::= { mitelIdentification 5 }
-- OBJECT-IDENTITY
--  Status
--    mandatory
--  Descr
--    Products providing computer-telephony integration 
--     capabilities.

mitelIdMgmtOpsMgr OBJECT IDENTIFIER ::= { mitelIdMgmtPlatforms 1 }
-- OBJECT-IDENTITY
--  Status
--    mandatory
--  Descr
--    The OPS Manager platform.

mitelIdCsMc2 OBJECT IDENTIFIER ::= { mitelIdCallServers 1 }
-- OBJECT-IDENTITY
--  Status
--    mandatory
--  Descr
--    The MC-2 call server.

mitelIdCs2000Light OBJECT IDENTIFIER ::= {mitelIdCallServers 2}


mitelExtInterfaces OBJECT IDENTIFIER ::= { mitelExtensions 2 }
-- OBJECT-IDENTITY
--  Status
--    mandatory
--  Descr
--    Proprietary extensions to the MIB-II subtree.

mitelPropApplications OBJECT IDENTIFIER ::= { mitelProprietary 1 }
-- OBJECT-IDENTITY
--  Status
--    mandatory
--  Descr
--    Manageable applications.

mitelPropTransmission OBJECT IDENTIFIER ::= { mitelProprietary 2 }
-- OBJECT-IDENTITY
--  Status
--    mandatory
--  Descr
--    MITEL proprietary transmission media.

mitelPropProtocols OBJECT IDENTIFIER ::= { mitelProprietary 3 }
-- OBJECT-IDENTITY
--  Status
--    mandatory
--  Descr
--    Manageable proprietary protocols.

mitelPropUtilities OBJECT IDENTIFIER ::= { mitelProprietary 4 }
-- OBJECT-IDENTITY
--  Status
--    mandatory
--  Descr
--    Manageable utilities and middleware.

mitelPropHardware OBJECT IDENTIFIER ::= { mitelProprietary 5 }
-- OBJECT-IDENTITY
--  Status
--    mandatory
--  Descr
--    Management of proprietary hardware.

mitelPropNotifications OBJECT IDENTIFIER ::= { mitelProprietary 6 }
-- OBJECT-IDENTITY
--  Status
--    mandatory
--  Descr
--    Control and histroy of proprietary notifications.

mitelPropReset OBJECT IDENTIFIER ::= { mitelProprietary 7 }
-- OBJECT-IDENTITY
--  Status
--    mandatory
--  Descr
--    Access for remote reset of agent and platform.

-- ************************************
-- The mitelPropApplication subtree ...
-- ************************************

mitelAppCallServer OBJECT IDENTIFIER ::= {mitelPropApplications 1}


mitelNotifTraps OBJECT IDENTIFIER ::= { mitelPropNotifications 1 }
-- OBJECT-IDENTITY
--  Status
--    mandatory
--  Descr
--    The common traps supported by MITEL agents.
--     These traps may be acknowledged or 
--     unacknowledged. If acknowledged, the
--     mitelUnackTblStatus OID will indicate the
--     object to which a subsequent SetRequest
--     is required to acknowledge the Trap. If
--     unacknowledged, the mitelUnackTblStatus
--     variable name will indicate a row index
--     of 0 (i.e. invalid).

mitelConfCompliances OBJECT IDENTIFIER ::= { mitelConformance 1 }
-- OBJECT-IDENTITY
--  Status
--    mandatory
--  Descr
--    The compliance subtree. Leaves in this subtree are
--    used for defining the ways in which an agent can
--    claim compliance with this or other MITEL MIBs.

mitelConfGroups OBJECT IDENTIFIER ::= { mitelConformance 2 }
-- OBJECT-IDENTITY
--  Status
--    mandatory
--  Descr
--    The group subtree. Leaves in this subtree identify
--    object groupings used in the compliance statements.

mitelGrpCommon OBJECT IDENTIFIER ::= { mitelConfGroups 1 }
-- OBJECT-IDENTITY
--  Status
--    mandatory
--  Descr
--    The groups associated with the MITEL MIB.

mitelGrpOpsMgr OBJECT IDENTIFIER ::= { mitelConfGroups 2 }
-- OBJECT-IDENTITY
--  Status
--    mandatory
--  Descr
--    The groups associated with the OPS Manager MIB.

mitelGrpCs2000 OBJECT IDENTIFIER ::= {mitelConfGroups 3}
-- OBJECT-IDENTITY
-- Status 
--  mandatory
-- Descr
-- The groups associated with the SX2000 MIB"


mitelConfAgents OBJECT IDENTIFIER ::= { mitelConformance 3 }
-- OBJECT-IDENTITY
--  Status
--    mandatory
--  Descr
--    The agent capabilities subtree. Leaves in this subtree
--    are used for defining the capabilities of a particular
--    agent implementation regarding the MIB compliance
--    statements.

TDomain ::= OBJECT IDENTIFIER
-- TEXTUAL-CONVENTION
--  Status
--    mandatory
--  Descr
--    Denotes a kind of transport service.
--    
--    Some possible values, such as snmpUDPDomain, are defined in
--    'Transport Mappings for Version 2 of the Simple Network
--    Management Protocol (SNMPv2)'.

TAddress ::= OCTET STRING(SIZE(1..255))
-- TEXTUAL-CONVENTION
--  Status
--    mandatory
--  Descr
--    Denotes a transport service address.
--    
--    For snmpUDPDomain, a TAddress is 6 octets long, the initial 4
--    octets containing the IP-address in network-byte order and the
--    last 2 containing the UDP port in network-byte order.  Consult
--    'Transport Mappings for Version 2 of the Simple Network
--    Management Protocol (SNMPv2)' for further information on
--    snmpUDPDomain.

MitelIfType ::= INTEGER {
        dnic(1)
        }
-- TEXTUAL-CONVENTION
--  Status
--    mandatory
--  Descr
--    The MITEL-defined interface type.
--    Additions to this list must be provided
--    by the MITEL Standards Group.

MitelNotifyTransportType ::= INTEGER {
        mitelNotifTransV1Trap(1),
        mitelNotifTransV2Trap(2),
        mitelNotifTransInform(3)
        }
-- TEXTUAL-CONVENTION
--  Status
--    mandatory
--  Descr
--    The method of transporting a notification
--    to an interested manager.

mitelIfNumber OBJECT-TYPE
    SYNTAX Integer32
    ACCESS read-only
    STATUS mandatory
    DESCRIPTION
        "The number of MITEL proprietary interfaces 
        (regardless of their current state) present on 
        this system."
    ::= { mitelExtInterfaces 1 }

mitelIfTable OBJECT-TYPE
    SYNTAX SEQUENCE OF MitelIfTableEntry
    ACCESS not-accessible
    STATUS mandatory
    DESCRIPTION
        "A list of interface entries.  The number of entries
        is given by the value of mitelIfNumber. The table 
        consists of one row for each MITEL-specific interface,
        and is indexed by the ifIndex value of the corresponding
        row in the MIB-II ifTable."
    ::= { mitelExtInterfaces 2 }

mitelIfTableEntry OBJECT-TYPE
    SYNTAX MitelIfTableEntry
    ACCESS not-accessible
    STATUS mandatory
    DESCRIPTION
        "An entry containing management information applicable
        to a particular interface."
    INDEX { ifIndex }
    ::= { mitelIfTable 1 }

MitelIfTableEntry ::= SEQUENCE {
    mitelIfTblType MitelIfType
    }

mitelIfTblType OBJECT-TYPE
    SYNTAX MitelIfType
--    Rsyntax INTEGER {
--        dnic(1)
--        }
    ACCESS read-only
    STATUS mandatory
    DESCRIPTION
        "The type of interface.  Additional values for 
        mitelIfTblType are assigned by the Standards Group, 
        through updating the syntax of the MitelIfType 
        textual convention. This row is deleted automatically
        when the corresponding ifTable row is deleted."
    ::= { mitelIfTableEntry 1 }

mitelResetReason OBJECT-TYPE
    SYNTAX INTEGER {
        shutdown(1),
        coldStart(2),
        warmStart(3)
        }
    ACCESS read-only
    STATUS mandatory
    DESCRIPTION
        "Indicates the reason for the last mitelTrapsReset
        notification generated. The shutdown(1) is only
        visible in a mitelTrapsReset notification, and
        indicates that the agent is shutting down, to be
        followed at an unspecified time by a coldStart.
        It is expected that agents may want to expand the
        syntax in an agent-specific manner (e.g. to identify
        specific components)."
    ::= { mitelPropReset 1 }

mitelResetPlatform OBJECT-TYPE
    SYNTAX TruthValue
--    Rsyntax INTEGER {
--        true(1),
--        false(2)
--        }
    ACCESS read-write
    STATUS mandatory
    DESCRIPTION
        "Write true(1) to this object to reset the
        agent platform (coldStart). This object always
        reads as false."
    ::= { mitelPropReset 2 }

mitelResetAgent OBJECT-TYPE
    SYNTAX TruthValue
--    Rsyntax INTEGER {
--        true(1),
--        false(2)
--        }
    ACCESS read-write
    STATUS mandatory
    DESCRIPTION
        "Write true(1) to this object to reset the
        agent itself (warmStart). This object always
        reads as false."
    ::= { mitelPropReset 3 }

mitelNotifCount OBJECT-TYPE
    SYNTAX Integer32
    ACCESS read-only
    STATUS mandatory
    DESCRIPTION
        "The number of MITEL-defined notifications 
        supported by this agent."
    ::= { mitelPropNotifications 2 }

mitelNotifEnableTable OBJECT-TYPE
    SYNTAX SEQUENCE OF MitelNotifEnableTableEntry
    ACCESS not-accessible
    STATUS mandatory
    DESCRIPTION
        "A list of the MITEL-defined notifications
        supported by this agent. The number of entries
        in the table is defined by mitelNotifCount. This
        table is maintained in non-volatile memory, and
        is re-built upon agent restart."
    ::= { mitelPropNotifications 3 }

mitelNotifEnableTableEntry OBJECT-TYPE
    SYNTAX MitelNotifEnableTableEntry
    ACCESS not-accessible
    STATUS mandatory
    DESCRIPTION
        "An entry containing notification information."
    INDEX { mitelNotifEnblTblIndex }
    ::= { mitelNotifEnableTable 1 }



MitelNotifEnableTableEntry ::= SEQUENCE {
    mitelNotifEnblTblIndex INTEGER,
    mitelNotifEnblTblOid OBJECT IDENTIFIER,
    mitelNotifEnblTblEnable TruthValue,
    mitelNotifEnblTblAck TruthValue,
    mitelNotifEnblTblOccurrences Counter32,
    mitelNotifEnblTblDescr DisplayString
    }

mitelNotifEnblTblIndex OBJECT-TYPE
    SYNTAX INTEGER
    ACCESS read-only -- not-accessible
    STATUS mandatory
    DESCRIPTION
        "The index of this row. A unique value,
        greater than zero, for each row. This value
        is sent as the specific-trap value when
        an SNMPv1 Trap-PDU is used. For this
        reason, the notification OID must always
        map to the same value on every platform."
    ::= { mitelNotifEnableTableEntry 1 }

        -- ************************************
        -- The list of defined notifications.
        -- ************************************

        -- Module        Index    Definition
        -- ======        =====    ==========
        -- MITEL-MIB     1-99     Reserved for Corporate MIB
        -- MITEL-MIB     1          mitelTrapsCommLost
        -- MITEL-MIB     2          mitelTrapsReset
        -- OPSMGR-MIB    101-199  Reserved for OPS Mgr MIB
        -- OPSMGR-MIB    101        mitelOmNotifAlarm
        -- OPSMGR-MIB    102        mitelOmNotifComponentChange
        -- MTL-CS2000-MIB 201-299 Reserved for MITEL CS2000 MIB
        -- MTL-CS2000-MIB 201       mitelCs2000NotifAlarm


mitelNotifEnblTblOid OBJECT-TYPE
    SYNTAX OBJECT IDENTIFIER
    ACCESS read-only
    STATUS mandatory
    DESCRIPTION
        "The OID value of the notification. This
        is the value of the corresponding
        NOTIFICATION-TYPE macro. For SNMPv1
        agents, this is implemented as zeroDotZero
        (from RFC1442)."
    ::= { mitelNotifEnableTableEntry 2 }

mitelNotifEnblTblEnable OBJECT-TYPE
    SYNTAX TruthValue
--    Rsyntax INTEGER {
--        true(1),
--        false(2)
--        }
    ACCESS read-write
    STATUS mandatory
    DESCRIPTION
        "True if the generation of this notification 
        (to all registered managers) is enabled."
    ::= { mitelNotifEnableTableEntry 3 }

mitelNotifEnblTblAck OBJECT-TYPE
    SYNTAX TruthValue
--    Rsyntax INTEGER {
--        true(1),
--        false(2)
--        }
    ACCESS read-write
    STATUS mandatory
    DESCRIPTION
        "True if the notification is to be acknowledged
        by at least one manager. A false setting
        indicates that the mitelNotifMgrTblTimeout and
        mitelNotifMgrTblRetries values are ignored."
    ::= { mitelNotifEnableTableEntry 4 }

mitelNotifEnblTblOccurrences OBJECT-TYPE
    SYNTAX Counter32
    ACCESS read-only
    STATUS mandatory
    DESCRIPTION
        "A count of the number of times the conditions
        that would generate this trap have been detected
        at this agent since the last reset, regardless of
        whether the trap is enabled or not."
    ::= { mitelNotifEnableTableEntry 5 }

mitelNotifEnblTblDescr OBJECT-TYPE
    SYNTAX DisplayString
--    Rsyntax OCTET STRING(SIZE(0..255))
    ACCESS read-only
    STATUS mandatory
    DESCRIPTION
        "Textual description of this notification."
    ::= { mitelNotifEnableTableEntry 6 }

mitelNotifManagerTable OBJECT-TYPE
    SYNTAX SEQUENCE OF MitelNotifManagerTableEntry
    ACCESS not-accessible
    STATUS mandatory
    DESCRIPTION
        "A list of the managers that are receiving
        notifications from this agent. This table
        is kept in non-volatile memory, and is rebuilt
        upon agent restart."
    ::= { mitelPropNotifications 4 }

mitelNotifManagerTableEntry OBJECT-TYPE
    SYNTAX MitelNotifManagerTableEntry
    ACCESS not-accessible
    STATUS mandatory
    DESCRIPTION
        "An entry containing manager information."
    INDEX { mitelNotifMgrTblIndex }
    ::= { mitelNotifManagerTable 1 }

MitelNotifManagerTableEntry ::= SEQUENCE {
    mitelNotifMgrTblIndex INTEGER,
    mitelNotifMgrTblStatus RowStatus,
    mitelNotifMgrTblTransport MitelNotifyTransportType,
    mitelNotifMgrTblDomain TDomain,
    mitelNotifMgrTblAddress TAddress,
    mitelNotifMgrTblTimeout TimeInterval,
    mitelNotifMgrTblRetries INTEGER(1..10),
    mitelNotifMgrTblLife TimeInterval,
    mitelNotifMgrTblCommunity OCTET STRING,
    mitelNotifMgrTblName DisplayString
    }

mitelNotifMgrTblIndex OBJECT-TYPE
    SYNTAX INTEGER
    ACCESS read-only -- not-accessible
    STATUS mandatory
    DESCRIPTION
        "The index of this row. A unique value,
        greater than zero, for each row. It is
        recommended that values are assigned
        contiguously starting from 1."
    ::= { mitelNotifManagerTableEntry 1 }

mitelNotifMgrTblStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status column used for creating,
        modifying, and deleting instances of the
        columnar objects in the manager table."
    DEFVAL { active }
    ::= { mitelNotifManagerTableEntry 2 }

mitelNotifMgrTblTransport OBJECT-TYPE
    SYNTAX MitelNotifyTransportType
--    Rsyntax INTEGER {
--        mitelNotifTransV1Trap(1),
--        mitelNotifTransV2Trap(2),
--        mitelNotifTransInform(3)
--        }
    ACCESS read-write
    STATUS mandatory
    DESCRIPTION
        "Defines how notifications are sent to this
        manager (either InformRequest or Trap)."
    DEFVAL { mitelNotifTransV1Trap }
    ::= { mitelNotifManagerTableEntry 3 }

mitelNotifMgrTblDomain OBJECT-TYPE
    SYNTAX TDomain
--    Rsyntax OBJECT IDENTIFIER
    ACCESS read-write
    STATUS mandatory
    DESCRIPTION
        "The transport domain of this manager."
    DEFVAL { snmpUDPDomain }
    ::= { mitelNotifManagerTableEntry 4 }

mitelNotifMgrTblAddress OBJECT-TYPE
    SYNTAX TAddress
--    Rsyntax OCTET STRING(SIZE(1..255))
    ACCESS read-write
    STATUS mandatory
    DESCRIPTION
        "The transport domain address at which to send
        the notification."
    DEFVAL { 'c00002000489'h }
    ::= { mitelNotifManagerTableEntry 5 }

mitelNotifMgrTblTimeout OBJECT-TYPE
    SYNTAX TimeInterval
--    Rsyntax INTEGER(0..2147483647)
    ACCESS read-write
    STATUS mandatory
    DESCRIPTION
        "Number of 1/100ths of a second until a trap
        confirmation from this manager is deemed to
        have failed. This only applies for traps in
        mitelNotifEnableTable where mitelNotifEnblTblAck
        is true."
    DEFVAL { 1000 }
    ::= { mitelNotifManagerTableEntry 6 }

mitelNotifMgrTblRetries OBJECT-TYPE
    SYNTAX INTEGER(1..10)
    ACCESS read-write
    STATUS mandatory
    DESCRIPTION
        "Number of times the agent will attempt to
        retry sending a trap when the confirmation
        is not received. If the trap is not confirmed
        on the last retry, the mitelNotifHistTblConfirmed
        object will be false. This only applies for traps in
        mitelNotifEnableTable where mitelNotifEnblTblAck
        is true."
    DEFVAL { 3 }
    ::= { mitelNotifManagerTableEntry 7 }

mitelNotifMgrTblLife OBJECT-TYPE
    SYNTAX TimeInterval
--    Rsyntax INTEGER(0..2147483647)
    ACCESS read-write
    STATUS mandatory
    DESCRIPTION
        "Number of 1/100ths of a second until this row
        is deleted. If initially set to 0, this row
        will exist forever. Normal use of this field
        is to set it to a long timeout (e.g. 1 day)
        and then reset it at a shorter interval
        (e.g. every 12 hours)."
    DEFVAL { 8640000 }
    ::= { mitelNotifManagerTableEntry 8 }

mitelNotifMgrTblCommunity OBJECT-TYPE
    SYNTAX OCTET STRING
    ACCESS read-write
    STATUS mandatory
    DESCRIPTION
        "The community string to send in the notification."
    DEFVAL { "public" }
    ::= { mitelNotifManagerTableEntry 9 }

mitelNotifMgrTblName OBJECT-TYPE
    SYNTAX DisplayString
--    Rsyntax OCTET STRING(SIZE(0..255))
    ACCESS read-write
    STATUS mandatory
    DESCRIPTION
        "The administrative name of this manager."
    DEFVAL { "None specified." }
    ::= { mitelNotifManagerTableEntry 10 }

mitelNotifHistoryMax OBJECT-TYPE
    SYNTAX Integer32
    ACCESS read-write
    STATUS mandatory
    DESCRIPTION
        "The maximum size of the notification history table.
        Must be greater than or equal to zero... zero
        indicating the table is not used."
    DEFVAL { 100 }
    ::= { mitelPropNotifications 5 }

mitelNotifHistorySize OBJECT-TYPE
    SYNTAX Integer32
    ACCESS read-only
    STATUS mandatory
    DESCRIPTION
        "The current size of the notification history table."
    ::= { mitelPropNotifications 6 }

mitelNotifHistoryTable OBJECT-TYPE
    SYNTAX SEQUENCE OF MitelNotifHistoryTableEntry
    ACCESS not-accessible
    STATUS mandatory
    DESCRIPTION
        "A history of the recent notifications originated
        from this agent. One entry is generated per
        notification, regardless of the number of managers
        registered to receive the notification. The number of
        entries is given by mitelNotifHistorySize. The table
        cannot grow beyond mitelNotifHistoryMax... older
        entries are bumped off once the table reaches the
        maximum size."
    ::= { mitelPropNotifications 7 }

mitelNotifHistoryTableEntry OBJECT-TYPE
    SYNTAX MitelNotifHistoryTableEntry
    ACCESS not-accessible
    STATUS mandatory
    DESCRIPTION
        "An entry containing notification information."
    INDEX { mitelNotifHistTblIndex }
    ::= { mitelNotifHistoryTable 1 }

MitelNotifHistoryTableEntry ::= SEQUENCE {
    mitelNotifHistTblIndex INTEGER,
    mitelNotifHistTblId INTEGER,
    mitelNotifHistTblTime TimeStamp,
    mitelNotifHistTblIfIndex InterfaceIndex,
    mitelNotifHistTblConfirmed TruthValue
    }

mitelNotifHistTblIndex OBJECT-TYPE
    SYNTAX INTEGER
    ACCESS read-only -- not-accessible
    STATUS mandatory
    DESCRIPTION
        "The index of this row. A unique value,
         greater than zero, for each row. It is
         recommended that values are assigned
         contiguously starting from 1."
    ::= { mitelNotifHistoryTableEntry 1 }

mitelNotifHistTblId OBJECT-TYPE
    SYNTAX INTEGER
    ACCESS read-only
    STATUS mandatory
    DESCRIPTION
        "The index value of the corresponding
        notification entry in mitelNotifEnableTable
        (i.e. mitelNotifEnblTblIndex)."
    ::= { mitelNotifHistoryTableEntry 2 }

mitelNotifHistTblTime OBJECT-TYPE
    SYNTAX TimeStamp
--    Rsyntax TimeTicks
    ACCESS read-only
    STATUS mandatory
    DESCRIPTION
        "The time the notification was sent."
    ::= { mitelNotifHistoryTableEntry 3 }

mitelNotifHistTblIfIndex OBJECT-TYPE
    SYNTAX InterfaceIndex
--    Rsyntax Integer32
    ACCESS read-only
    STATUS mandatory
    DESCRIPTION
        "The ifIndex value corresponding to the
        ifTable entry of the originating interface
        (if any). Value is 0 if the notification
        is not associated with an ifTable entry."
    ::= { mitelNotifHistoryTableEntry 4 }

mitelNotifHistTblConfirmed OBJECT-TYPE
    SYNTAX TruthValue
--    Rsyntax INTEGER {
--        true(1),
--        false(2)
--        }
    ACCESS read-only
    STATUS mandatory
    DESCRIPTION
        "Indicates whether or not this notification
        was confirmed by at least one manager. Note
        this object is only applicable when the
        corresponding row of mitelNotifEnableTable has
        mitelNotifEnblTblAck set to true."
    ::= { mitelNotifHistoryTableEntry 5 }

mitelNotifUnackTable OBJECT-TYPE
    SYNTAX SEQUENCE OF MitelNotifUnackTableEntry
    ACCESS not-accessible
    STATUS mandatory
    DESCRIPTION
        "A list of notifications sent from this agent
        that are expected to be acknowledged, but have
        not yet received the acknowledgement. One entry
        is created for each acknowledgable notification
        transmitted from this agent. Managers are expected
        to delete the rows in this table to acknowledge
        receipt of the notification. To do so, the index
        is provided in the notification sent to the manager.
        Any unacknowledged notifications are removed at
        the agent's discretion. This table is kept
        in volatile memory."
    ::= { mitelPropNotifications 8 }

mitelNotifUnackTableEntry OBJECT-TYPE
    SYNTAX MitelNotifUnackTableEntry
    ACCESS not-accessible
    STATUS mandatory
    DESCRIPTION
        "An entry containing unacknowledged notification
        information."
    INDEX { mitelNotifUnackTblIndex }
    ::= { mitelNotifUnackTable 1 }

MitelNotifUnackTableEntry ::= SEQUENCE {
    mitelNotifUnackTblIndex INTEGER,
    mitelNotifUnackTblStatus INTEGER,
    mitelNotifUnackTblHistory INTEGER,
    mitelNotifUnackTblManager INTEGER,
    mitelNotifUnackTblRetriesLeft Integer32
    }

mitelNotifUnackTblIndex OBJECT-TYPE
    SYNTAX INTEGER
    ACCESS read-only -- not-accessible
    STATUS mandatory
    DESCRIPTION
        "The index of this row. A unique value,
        greater than zero, for each row. It is
        recommended that values are assigned
        contiguously starting from 1, and that
        they are not re-used (to allow for
        duplicated Set Requests for destruction
        of the row)."
    ::= { mitelNotifUnackTableEntry 1 }

mitelNotifUnackTblStatus OBJECT-TYPE
    SYNTAX INTEGER {
        active(1),
        notInService(2),
        destory(6)
        }
    ACCESS read-write
    STATUS mandatory
    DESCRIPTION
        "The status of this row. A status of active
        indicates that an acknowledgement is still expected.
        Write a destroy(6) here to acknowledge this 
        notification. A status of notInService indicates
        that no acknowledgement is expected."
    ::= { mitelNotifUnackTableEntry 2 }

mitelNotifUnackTblHistory OBJECT-TYPE
    SYNTAX INTEGER
    ACCESS read-only
    STATUS mandatory
    DESCRIPTION
        "The index into the mitelNotifHistoryTable
        that identifies this notification. If 0,
        the mitelNotifHistoryTable entry was not
        created or has been deleted."
    ::= { mitelNotifUnackTableEntry 3 }

mitelNotifUnackTblManager OBJECT-TYPE
    SYNTAX INTEGER
    ACCESS read-only
    STATUS mandatory
    DESCRIPTION
        "The index into the mitelNotifManagerTable
        that identifies this notification. If 0,
        the mitelNotifManagerTable entry has been deleted."
    ::= { mitelNotifUnackTableEntry 4 }

mitelNotifUnackTblRetriesLeft OBJECT-TYPE
    SYNTAX Integer32
    ACCESS read-only
    STATUS mandatory
    DESCRIPTION
        "The number of retransmission retries left to
        attempt. This starts at the mitelNotifMgrTblRetries
        value for the corresponding manager. If 0 is
        reached, the last retry has been attempted."
    ::= { mitelNotifUnackTableEntry 5 }

mitelNotifAgentAddress OBJECT-TYPE
    SYNTAX TAddress
--    Rsyntax OCTET STRING(SIZE(1..255))
    ACCESS read-only
    STATUS mandatory
    DESCRIPTION
        "The domain address of this agent, used only
        in notifications to identify the sending
        agent. In SNMPv1 implementations, this maps
        to the agent-addr field of the SNMPv1-Trap PDU."
    ::= { mitelPropNotifications 9 }

mitelTrapsCommLost TRAP-TYPE
--?? Non-reverse mappable trap
    ENTERPRISE mitelNotifTraps
    VARIABLES {
        mitelNotifUnackTblStatus,
        mitelNotifMgrTblDomain, mitelNotifMgrTblAddress }
--  Status
--    mandatory
    DESCRIPTION
        "This notification is generated whenever the agent
         detects the final timeout of a row in the
         mitelNotifUnackTable. When this occurs, the row
         corresponding to the manager in mitelNotifManagerTable
         is set to a RowStatus value of notInService(2), and
         no further notifications will be sent to the manager
         until the RowStatus is set back to active(1)."
    ::= 1

mitelTrapsReset TRAP-TYPE
--?? Non-reverse mappable trap
    ENTERPRISE mitelNotifTraps
    VARIABLES {
        mitelNotifUnackTblStatus, mitelResetReason }
--  Status
--    mandatory
    DESCRIPTION
        "This notification is generated whenever the agent
         detects a reset, either from coldStart, warmStart,
         or a reset of some part of the hardware. The nature
         of the reset is provided in mitelResetReason. This
         notification does not preclude simultaneous
         generation of a warm/coldStart trap."
    ::= 2

mitelGrpCmnNotifBasic OBJECT IDENTIFIER ::= { mitelGrpCommon 2 }
-- OBJECT-GROUP
--  Status
--    mandatory
--  Descr
--    The collection of objects providing information on
--    the agent's support of MITEL-specific notifications.
--  objects
--    mitelNotifCount, mitelNotifEnblTblOid, 
--    mitelNotifEnblTblEnable, mitelNotifEnblTblAck, 
--    mitelNotifEnblTblOccurrences, mitelNotifEnblTblDescr, 
--    mitelNotifAgentAddress

mitelGrpCmnNotifManagers OBJECT IDENTIFIER ::= { mitelGrpCommon 3 }
-- OBJECT-GROUP
--  Status
--    mandatory
--  Descr
--    A collection of objects providing information
--    about the managers registered with the agent to
--    receive notifications.
--  objects
--    mitelNotifMgrTblStatus, mitelNotifMgrTblTransport, 
--    mitelNotifMgrTblDomain, mitelNotifMgrTblAddress, 
--    mitelNotifMgrTblTimeout, mitelNotifMgrTblRetries, 
--    mitelNotifMgrTblLife, mitelNotifMgrTblCommunity, 
--    mitelNotifMgrTblName

mitelGrpCmnNotifHistory OBJECT IDENTIFIER ::= { mitelGrpCommon 4 }
-- OBJECT-GROUP
--  Status
--    mandatory
--  Descr
--    The collection of objects providing notification
--    history tracking.
--  objects
--    mitelNotifHistoryMax, mitelNotifHistorySize, 
--    mitelNotifHistTblId, mitelNotifHistTblTime, 
--    mitelNotifHistTblIfIndex, mitelNotifHistTblConfirmed

mitelGrpCmnNotifAck OBJECT IDENTIFIER ::= { mitelGrpCommon 5 }
-- OBJECT-GROUP
--  Status
--    mandatory
--  Descr
--    A collection of objects providing a reliable
--    trap mechanism for notifying managers.
--  objects
--    mitelNotifUnackTblStatus, mitelNotifUnackTblHistory, 
--    mitelNotifUnackTblManager, mitelNotifUnackTblRetriesLeft

mitelGrpCmnInterfaces OBJECT IDENTIFIER ::= { mitelGrpCommon 6 }
-- OBJECT-GROUP
--  Status
--    mandatory
--  Descr
--    The objects in the MIB-II interfaces extension.
--  objects
--    mitelIfNumber, mitelIfTblType

mitelGrpCmnReset OBJECT IDENTIFIER ::= { mitelGrpCommon 7 }
-- OBJECT-GROUP
--  Status
--    mandatory
--  Descr
--    The objects for supporting remote reset.
--  objects
--    mitelResetReason, mitelResetPlatform, mitelResetAgent

mitelComplMitel OBJECT IDENTIFIER ::= { mitelConfCompliances 1 }
-- MODULE-COMPLIANCE
--  Status
--    mandatory
--  Descr
--    The compliance statement for SNMPv2 entities which
--     implement the MITEL MIB.
--  Module
--    >>current<<
--   MandGroup
--    mitelGrpCmnNotifBasic
--   ObjVar
--    mitelNotifEnblTblEnable
--   ObjVar
--    mitelNotifEnblTblAck
--   OptGroup
--    mitelGrpCmnNotifManagers
--   ObjVar
--    mitelNotifMgrTblStatus
--   ObjVar
--    mitelNotifMgrTblTransport
--   ObjVar
--    mitelNotifMgrTblDomain
--   ObjVar
--    mitelNotifMgrTblAddress
--   ObjVar
--    mitelNotifMgrTblTimeout
--   ObjVar
--    mitelNotifMgrTblRetries
--   ObjVar
--    mitelNotifMgrTblLife
--   ObjVar
--    mitelNotifMgrTblCommunity
--   ObjVar
--    mitelNotifMgrTblName
--   OptGroup
--    mitelGrpCmnInterfaces


END
