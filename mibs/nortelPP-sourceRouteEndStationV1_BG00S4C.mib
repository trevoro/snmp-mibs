Nortel-Magellan-Passport-SourceRouteEndStationMIB
DEFINITIONS ::= BEGIN



IMPORTS

      OBJECT-TYPE
   FROM RFC-1212

      passportMIBs
   FROM Nortel-Magellan-Passport-UsefulDefinitionsMIB

      Counter32,
      DisplayString,
      StorageType,
      RowStatus,
      Gauge32,
      Unsigned32
   FROM Nortel-Magellan-Passport-StandardTextualConventionsMIB

      AsciiString,
      DashedHexString,
      NonReplicated,
      HexString,
      AsciiStringIndex
   FROM Nortel-Magellan-Passport-TextualConventionsMIB

      vrIndex,
      vr
   FROM Nortel-Magellan-Passport-VirtualRouterMIB;




-- LAST-UPDATED   "9706300000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     SourceRouteEndStation Enterprise MIB."

sourceRouteEndStationMIB OBJECT IDENTIFIER ::= { passportMIBs 54 }










-- Vr/<string> SourceRouteEndStation
-- This component defines source routing for source routing end stations.

vrSres OBJECT IDENTIFIER ::= { vr 13 }



vrSresRowStatusTable OBJECT-TYPE
   SYNTAX     SEQUENCE OF VrSresRowStatusEntry
   ACCESS     not-accessible
   STATUS     mandatory
   DESCRIPTION
     "This entry controls the addition and deletion of 
      vrSres components."
::= { vrSres 1 }

vrSresRowStatusEntry OBJECT-TYPE
   SYNTAX     VrSresRowStatusEntry
   ACCESS     not-accessible
   STATUS     mandatory
   DESCRIPTION
     "A single entry in the table represents a single 
      vrSres component."
   INDEX {
      vrIndex,
      vrSresIndex }
::= { vrSresRowStatusTable 1 }

VrSresRowStatusEntry ::= SEQUENCE {
   vrSresRowStatus
      RowStatus,
   vrSresComponentName
      DisplayString,
   vrSresStorageType
      StorageType,
   vrSresIndex
      NonReplicated }

vrSresRowStatus OBJECT-TYPE
   SYNTAX     RowStatus 
   ACCESS     read-write
   STATUS     mandatory
   DESCRIPTION
     "This variable is used as the basis for SNMP naming of
      vrSres components.
      These components can be added and deleted."
::= { vrSresRowStatusEntry 1 }

vrSresComponentName OBJECT-TYPE
   SYNTAX     DisplayString 
   ACCESS     read-only
   STATUS     mandatory
   DESCRIPTION
     "This variable provides the component's string name for
      use with the ASCII Console Interface"
::= { vrSresRowStatusEntry 2 }

vrSresStorageType OBJECT-TYPE
   SYNTAX     StorageType 
   ACCESS     read-only
   STATUS     mandatory
   DESCRIPTION
     "This variable represents the storage type value for the
      vrSres tables."
::= { vrSresRowStatusEntry 4 }

vrSresIndex OBJECT-TYPE
   SYNTAX     NonReplicated 
   ACCESS     not-accessible
   STATUS     mandatory
   DESCRIPTION
     "This variable represents the index for the vrSres tables."
::= { vrSresRowStatusEntry 10 }

vrSresAdminControlTable OBJECT-TYPE
   SYNTAX     SEQUENCE OF VrSresAdminControlEntry
   ACCESS     not-accessible
   STATUS     mandatory
   DESCRIPTION
     "This group includes the Administrative Control attribute. This attribute 
      defines the current administrative state of this component."
::= { vrSres 10 }

vrSresAdminControlEntry OBJECT-TYPE
   SYNTAX     VrSresAdminControlEntry
   ACCESS     not-accessible
   STATUS     mandatory
   DESCRIPTION
     "An entry in the vrSresAdminControlTable."
   INDEX {
      vrIndex,
      vrSresIndex }
::= { vrSresAdminControlTable 1 }

VrSresAdminControlEntry ::= SEQUENCE {
   vrSresSnmpAdminStatus
      INTEGER }

vrSresSnmpAdminStatus OBJECT-TYPE
   SYNTAX     INTEGER  {
                 up(1),
                 down(2),
                 testing(3) }
   ACCESS     read-only
   STATUS     mandatory
   DESCRIPTION
     "This attribute is used to set the desired state of the interface. The up state 
      indicates the interface is operational and packet forwarding is allowed. 
      The down state indicates the interface is not operational and packet 
      forwarding is unavailable. The testing state indicates that no operational 
      packets can be passed. Changing this attribute from its default value of 
      up is not allowed at this time."
   DEFVAL     { up }
::= { vrSresAdminControlEntry 1 }

vrSresProvTable OBJECT-TYPE
   SYNTAX     SEQUENCE OF VrSresProvEntry
   ACCESS     not-accessible
   STATUS     mandatory
   DESCRIPTION
     "This group contains the provisioned attributes for the 
      SourceRouteEndStation component."
::= { vrSres 11 }

vrSresProvEntry OBJECT-TYPE
   SYNTAX     VrSresProvEntry
   ACCESS     not-accessible
   STATUS     mandatory
   DESCRIPTION
     "An entry in the vrSresProvTable."
   INDEX {
      vrIndex,
      vrSresIndex }
::= { vrSresProvTable 1 }

VrSresProvEntry ::= SEQUENCE {
   vrSresRouteTableNumEntries
      Unsigned32,
   vrSresAgingTime
      Unsigned32,
   vrSresRouteDescriptorLength
      Unsigned32 }

vrSresRouteTableNumEntries OBJECT-TYPE
   SYNTAX     Unsigned32 (0..65535)
   ACCESS     read-write
   STATUS     mandatory
   DESCRIPTION
     "This attribute identifies the maximum number of entries in the 
      SourceRouteEndStation routing table. Before you change it, check the 
      network configuration to see how many protocol ports, such as IpPort or 
      IpxPort, under Vr Pp have endStationSupport set to enable. The value of 
      routeTableNumEntries also depends on the VirtualRouter attribute 
      sresMaxHeapSpace.
      
      Consider the following attributes of the SourceRouteEndStation 
      component when adjusting this number: 
      - rtEntriesUsed
      - rtEntriesFree
      - rtEntriesDenied"
   DEFVAL     { 5000 }
::= { vrSresProvEntry 1 }

vrSresAgingTime OBJECT-TYPE
   SYNTAX     Unsigned32 (200..1000000)
   ACCESS     read-write
   STATUS     mandatory
   DESCRIPTION
     "This attribute specifies the time period used in seconds, to age out 
      learned entries in the routing table."
   DEFVAL     { 900 }
::= { vrSresProvEntry 2 }

vrSresRouteDescriptorLength OBJECT-TYPE
   SYNTAX     Unsigned32 (8..14)
   ACCESS     read-only
   STATUS     mandatory
   DESCRIPTION
     "This attribute indicates the maximum number of route descriptors 
      supported by this implementation. The maximum number of hops will 
      be one less because one route descriptor is always required for the 
      destination. This attribute affects the amount of memory used by the 
      route entry table. The larger this attribute is, the more memory the route 
      entry table will use."
   DEFVAL     { 14 }
::= { vrSresProvEntry 3 }

vrSresOperStatusTable OBJECT-TYPE
   SYNTAX     SEQUENCE OF VrSresOperStatusEntry
   ACCESS     not-accessible
   STATUS     mandatory
   DESCRIPTION
     "This group includes the Operational Status attribute. This attribute 
      defines the current operational state of this component."
::= { vrSres 12 }

vrSresOperStatusEntry OBJECT-TYPE
   SYNTAX     VrSresOperStatusEntry
   ACCESS     not-accessible
   STATUS     mandatory
   DESCRIPTION
     "An entry in the vrSresOperStatusTable."
   INDEX {
      vrIndex,
      vrSresIndex }
::= { vrSresOperStatusTable 1 }

VrSresOperStatusEntry ::= SEQUENCE {
   vrSresSnmpOperStatus
      INTEGER }

vrSresSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrSresOperStatusEntry 1 }

vrSresStateTable OBJECT-TYPE
   SYNTAX     SEQUENCE OF VrSresStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrSres 13 }

vrSresStateEntry OBJECT-TYPE
   SYNTAX     VrSresStateEntry
   ACCESS     not-accessible
   STATUS     mandatory
   DESCRIPTION
     "An entry in the vrSresStateTable."
   INDEX {
      vrIndex,
      vrSresIndex }
::= { vrSresStateTable 1 }

VrSresStateEntry ::= SEQUENCE {
   vrSresAdminState
      INTEGER,
   vrSresOperationalState
      INTEGER,
   vrSresUsageState
      INTEGER }

vrSresAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrSresStateEntry 1 }

vrSresOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrSresStateEntry 2 }

vrSresUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrSresStateEntry 3 }

vrSresOperTable OBJECT-TYPE
   SYNTAX     SEQUENCE OF VrSresOperEntry
   ACCESS     not-accessible
   STATUS     mandatory
   DESCRIPTION
     "This group contains the operational attributes for the 
      SourceRouteEndStation component."
::= { vrSres 14 }

vrSresOperEntry OBJECT-TYPE
   SYNTAX     VrSresOperEntry
   ACCESS     not-accessible
   STATUS     mandatory
   DESCRIPTION
     "An entry in the vrSresOperTable."
   INDEX {
      vrIndex,
      vrSresIndex }
::= { vrSresOperTable 1 }

VrSresOperEntry ::= SEQUENCE {
   vrSresRtEntriesUsed
      Gauge32,
   vrSresRtEntriesFree
      Gauge32,
   vrSresRtEntriesDenied
      Counter32 }

vrSresRtEntriesUsed OBJECT-TYPE
   SYNTAX     Gauge32 (0..65535)
   ACCESS     read-only
   STATUS     mandatory
   DESCRIPTION
     "This attribute specifies the total number of SourceRouteEndStation 
      routing table entries. The value is limited by the attribute 
      routeTableNumEntries, which is a provisionable attribute. If the value is 
      consistently approaching the value of routeTableNumEntries, it is 
      advisable to increase the value provisioned for routeTableNumEntries. It 
      indicates a potential shortage of routing table entries in the future."
   DEFVAL     { 0 }
::= { vrSresOperEntry 1 }

vrSresRtEntriesFree OBJECT-TYPE
   SYNTAX     Gauge32 (0..65535)
   ACCESS     read-only
   STATUS     mandatory
   DESCRIPTION
     "This attribute is indicative of the number of Sres routing table entries 
      free. A consistently high value for this attribute indicates that there is a 
      resource surplus here, in terms of the memory requirements of the 
      routing table. This surplus could be utilized elsewhere if need be. The 
      value of this attribute is directly influenced by the value of the attribute 
      routeTableNumEntries."
   DEFVAL     { 0 }
::= { vrSresOperEntry 2 }

vrSresRtEntriesDenied OBJECT-TYPE
   SYNTAX     Counter32 
   ACCESS     read-only
   STATUS     mandatory
   DESCRIPTION
     "This attribute counts the number of times a SourceRouteEndStation 
      routing table entry was unavailable. Each count indicates an instance of 
      a new route which could not be learned because of a lack of routing 
      table entries. A rapid increase indicates a shortage of routing table 
      entries. To rectify this, increase the number of routing table entries 
      through the provisioned attribute routeTableNumEntries under the 
      SourceRouteEndStation component. This counter wraps around its 
      maximum value of 4294967295."
::= { vrSresOperEntry 3 }

-- 
-- *** THIS SUBTREE CURRENTLY NOT IMPLEMENTED ***
-- 

-- Vr/<string> Sres RouteEntry/xx-xx-xx-xx-xx-xx,<string>
-- This component is used to contain the data associated with a source 
-- routing destination address. Each entry represents one row in the Route 
-- Table. The table is indexed by the route destination MAC address in 
-- canonical format and ProtocolPort name.

vrSresRe OBJECT IDENTIFIER ::= { vrSres 2 }



vrSresReRowStatusTable OBJECT-TYPE
   SYNTAX     SEQUENCE OF VrSresReRowStatusEntry
   ACCESS     not-accessible
   STATUS     mandatory
   DESCRIPTION
     "*** THIS TABLE CURRENTLY NOT IMPLEMENTED ***

      This entry controls the addition and deletion of 
      vrSresRe components."
::= { vrSresRe 1 }

vrSresReRowStatusEntry OBJECT-TYPE
   SYNTAX     VrSresReRowStatusEntry
   ACCESS     not-accessible
   STATUS     mandatory
   DESCRIPTION
     "A single entry in the table represents a single 
      vrSresRe component."
   INDEX {
      vrIndex,
      vrSresIndex,
      vrSresReDestMacAddressIndex,
      vrSresReProtocolPortNameIndex }
::= { vrSresReRowStatusTable 1 }

VrSresReRowStatusEntry ::= SEQUENCE {
   vrSresReRowStatus
      RowStatus,
   vrSresReComponentName
      DisplayString,
   vrSresReStorageType
      StorageType,
   vrSresReDestMacAddressIndex
      DashedHexString,
   vrSresReProtocolPortNameIndex
      AsciiStringIndex }

vrSresReRowStatus OBJECT-TYPE
   SYNTAX     RowStatus 
   ACCESS     read-only
   STATUS     mandatory
   DESCRIPTION
     "This variable is used as the basis for SNMP naming of
      vrSresRe components.
      These components cannot be added nor deleted."
::= { vrSresReRowStatusEntry 1 }

vrSresReComponentName OBJECT-TYPE
   SYNTAX     DisplayString 
   ACCESS     read-only
   STATUS     mandatory
   DESCRIPTION
     "This variable provides the component's string name for
      use with the ASCII Console Interface"
::= { vrSresReRowStatusEntry 2 }

vrSresReStorageType OBJECT-TYPE
   SYNTAX     StorageType 
   ACCESS     read-only
   STATUS     mandatory
   DESCRIPTION
     "This variable represents the storage type value for the
      vrSresRe tables."
::= { vrSresReRowStatusEntry 4 }

vrSresReDestMacAddressIndex OBJECT-TYPE
   SYNTAX     DashedHexString (SIZE (6))
   ACCESS     not-accessible
   STATUS     mandatory
   DESCRIPTION
     "This variable represents an index for the vrSresRe tables."
::= { vrSresReRowStatusEntry 10 }

vrSresReProtocolPortNameIndex OBJECT-TYPE
   SYNTAX     AsciiStringIndex (SIZE (1..20))
   ACCESS     not-accessible
   STATUS     mandatory
   DESCRIPTION
     "This variable represents an index for the vrSresRe tables."
::= { vrSresReRowStatusEntry 11 }

vrSresReOperTable OBJECT-TYPE
   SYNTAX     SEQUENCE OF VrSresReOperEntry
   ACCESS     not-accessible
   STATUS     mandatory
   DESCRIPTION
     "*** THIS TABLE CURRENTLY NOT IMPLEMENTED ***

      This group contains information relating to a source routing destination 
      address."
::= { vrSresRe 10 }

vrSresReOperEntry OBJECT-TYPE
   SYNTAX     VrSresReOperEntry
   ACCESS     not-accessible
   STATUS     mandatory
   DESCRIPTION
     "An entry in the vrSresReOperTable."
   INDEX {
      vrIndex,
      vrSresIndex,
      vrSresReDestMacAddressIndex,
      vrSresReProtocolPortNameIndex }
::= { vrSresReOperTable 1 }

VrSresReOperEntry ::= SEQUENCE {
   vrSresReRouteControl
      HexString,
   vrSresReRifLength
      Unsigned32,
   vrSresReRdDirection
      INTEGER,
   vrSresReRouteDescr
      AsciiString }

vrSresReRouteControl OBJECT-TYPE
   SYNTAX     HexString (SIZE (2))
   ACCESS     read-only
   STATUS     mandatory
   DESCRIPTION
     "This is the value of the routing control field for this route."
::= { vrSresReOperEntry 1 }

vrSresReRifLength OBJECT-TYPE
   SYNTAX     Unsigned32 (2..30)
   ACCESS     read-only
   STATUS     mandatory
   DESCRIPTION
     "This attribute is used to display the length of the routing information 
      field in the routing control field."
::= { vrSresReOperEntry 2 }

vrSresReRdDirection OBJECT-TYPE
   SYNTAX     INTEGER  {
                 leftToRight(0),
                 rightToLeft(1),
                 noRif(2) }
   ACCESS     read-only
   STATUS     mandatory
   DESCRIPTION
     "This attribute indicates the direction to use routing descriptors (RDs). If 
      set to leftToRight the routing descriptors, displayed in routeDescr, will 
      be interpreted from left to right. If set to rightToLeft they will be 
      interpreted from right to left. If rifLength is zero, this attribute will be 
      set to noRif to indicate that there are no routing descriptors to be read."
::= { vrSresReOperEntry 3 }

vrSresReRouteDescr OBJECT-TYPE
   SYNTAX     AsciiString (SIZE (0..90))
   ACCESS     read-only
   STATUS     mandatory
   DESCRIPTION
     "This is the embedded sequence of bridge and ring IDs for this route. For 
      destinations on the local ring, the value of this attribute is the zero-
      length string. Refer to rdDirection for the direction in which to read the 
      route descriptors. The format of the hexadecimal data displayed is as 
      follows:
      
      12 bit Ring Number - 4 bit Bridge Number...
      XXX-X XXX-X XXX-X..."
::= { vrSresReOperEntry 4 }




-- 
-- Version and Compliance statements
-- 



-- Object-Group Statement:
-- A list of all current accessible leaf objects.

-- OBJECTS { vrSresAdminState,
--           vrSresComponentName,
--           vrSresStorageType,
--           vrSresRowStatus,
--           vrSresRouteTableNumEntries,
--           vrSresReComponentName,
--           vrSresSnmpAdminStatus,
--           vrSresRouteDescriptorLength,
--           vrSresAgingTime,
--           vrSresReRifLength,
--           vrSresOperationalState,
--           vrSresReRouteDescr,
--           vrSresRtEntriesDenied,
--           vrSresReStorageType,
--           vrSresReRowStatus,
--           vrSresSnmpOperStatus,
--           vrSresReRdDirection,
--           vrSresRtEntriesFree,
--           vrSresReRouteControl,
--           vrSresRtEntriesUsed,
--           vrSresUsageState }
-- STATUS  mandatory
-- DESCRIPTION
--   "A list of all current accessible leaf objects."

sourceRouteEndStationGroup OBJECT IDENTIFIER ::= { sourceRouteEndStationMIB 1 }
sourceRouteEndStationGroupBD OBJECT IDENTIFIER ::= { sourceRouteEndStationGroup 4 }
sourceRouteEndStationGroupBD01 OBJECT IDENTIFIER ::= { sourceRouteEndStationGroupBD 2 }
sourceRouteEndStationGroupBD01A OBJECT IDENTIFIER ::= { sourceRouteEndStationGroupBD01 2 }



-- Agent-Capabilities Statement:

-- PRODUCT-RELEASE "Passport Release 7.0 SourceRouteEndStation."
-- STATUS          mandatory
-- DESCRIPTION     "SourceRouteEndStation MIB: MIB Version BD01A,
--                  Software Version BG00S4C."
-- SUPPORTS        Nortel-Magellan-Passport-SourceRouteEndStationMIB
--    INCLUDES     { sourceRouteEndStationGroupBD01A }

sourceRouteEndStationCapabilities OBJECT IDENTIFIER ::= { sourceRouteEndStationMIB 3 }
sourceRouteEndStationCapabilitiesBD OBJECT IDENTIFIER ::= { sourceRouteEndStationCapabilities 4 }
sourceRouteEndStationCapabilitiesBD01 OBJECT IDENTIFIER ::= { sourceRouteEndStationCapabilitiesBD 2 }
sourceRouteEndStationCapabilitiesBD01A OBJECT IDENTIFIER ::= { sourceRouteEndStationCapabilitiesBD01 2 }





END
