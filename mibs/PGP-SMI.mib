-- --------------------------------------------------------------------
-- Copyright (C) 2004 PGP Corporation
-- All rights reserved.
--
-- PGP Structure of Management Information
-- --------------------------------------------------------------------

PGP-SMI DEFINITIONS ::= BEGIN

	IMPORTS
		OBJECT-IDENTITY, MODULE-IDENTITY, OBJECT-TYPE, enterprises		FROM SNMPv2-SMI;

	pgp MODULE-IDENTITY
		LAST-UPDATED "200412080000Z"
		ORGANIZATION "PGP Corporation"
		CONTACT-INFO
			"			PGP Corporation
			Internet:	http://www.pgp.com"

		DESCRIPTION
			"The Structure of Management Information for PGP Corporation."

		REVISION "200412080000Z"
		DESCRIPTION "Initial version of this MIB module."

		::= { enterprises 17766 }

	products OBJECT-IDENTITY
		STATUS current
		DESCRIPTION
			"products is the root OID from which subtrees for each
			PGP product are allocated."
		::= { pgp 1 }

END
