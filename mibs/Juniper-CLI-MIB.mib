-- *****************************************************************************
-- Juniper-CLI-MIB
--
-- Juniper Networks Enterprise MIB
--   Command Line Interface (CLI) security MIB
--
-- Copyright (c) 1998, 1999 Redstone Communications, Inc.
-- Copyright (c) 1999 Unisphere Networks, Inc.
-- Copyright (c) 2002 Juniper Networks, Inc.
--   All Rights Reserved.
-- *****************************************************************************

Juniper-CLI-MIB  DEFINITIONS ::= BEGIN

IMPORTS
    MODULE-IDENTITY, OBJECT-TYPE, NOTIFICATION-TYPE
        FROM SNMPv2-SMI
    DisplayString, DateAndTime, TruthValue
        FROM SNMPv2-TC
    MODULE-COMPLIANCE, OBJECT-GROUP, NOTIFICATION-GROUP
        FROM SNMPv2-CONF
    juniMibs
        FROM Juniper-MIBs
    JuniLogSeverity
        FROM Juniper-TC;

juniCliMIB  MODULE-IDENTITY
    LAST-UPDATED "200209162144Z"  -- 16-Sep-02 05:44 PM EDT
    ORGANIZATION "Juniper Networks, Inc."
    CONTACT-INFO
        "       Juniper Networks, Inc.
        Postal: 10 Technology Park Drive
                Westford MA  01886-3146
                USA
        Tel:    +1 978 589 5800
        Email:  mib@Juniper.net"
    DESCRIPTION
        "The Command Line Interface (CLI) security MIB for the
        Juniper Networks enterprise."
    -- Revision History
    REVISION    "200209162144Z"  -- 16-Sep-02 05:44 PM EDT  - JUNOSe 5.0
    DESCRIPTION
        "Replaced Unisphere names with Juniper names."
    REVISION    "200009261350Z"  -- 26-Sep-00 09:50 AM EDT  - JUNOSe 3.0
    DESCRIPTION
        "Make it SMIv2 conformant."
    REVISION      "9912010000Z"  -- 01-Dec-99
    DESCRIPTION
        "Initial version of this MIB module."
    ::= { juniMibs 30 }


-- +++++++++++++++++++++++++++++++++++++++++++++++++++++++++++++++++++++++++++++
-- MIB Structure
-- +++++++++++++++++++++++++++++++++++++++++++++++++++++++++++++++++++++++++++++
juniCliTrap          OBJECT IDENTIFIER ::= { juniCliMIB 0 }
juniCliObjects       OBJECT IDENTIFIER ::= { juniCliMIB 1 }
juniCliConformance   OBJECT IDENTIFIER ::= { juniCliMIB 2 }


-- +++++++++++++++++++++++++++++++++++++++++++++++++++++++++++++++++++++++++++++
-- Managed objects
-- +++++++++++++++++++++++++++++++++++++++++++++++++++++++++++++++++++++++++++++
--
-- Object Groups
--
juniCliGeneral       OBJECT IDENTIFIER ::= { juniCliObjects 1 }
juniCliSecurity      OBJECT IDENTIFIER ::= { juniCliObjects 2 }

juniCliSecurityTrapEnable  OBJECT-TYPE
    SYNTAX      TruthValue
    MAX-ACCESS  read-write
    STATUS      current
    DESCRIPTION
        "An indication of whether the juniCliSecurityAlert notifications are
        enabled."
    ::= { juniCliGeneral 1 }


-- +++++++++++++++++++++++++++++++++++++++++++++++++++++++++++++++++++++++++++++
-- Traps & Trap Control
-- +++++++++++++++++++++++++++++++++++++++++++++++++++++++++++++++++++++++++++++
juniCliSecurityAlertPriority  OBJECT-TYPE
    SYNTAX      JuniLogSeverity
    MAX-ACCESS  accessible-for-notify
    STATUS      current
    DESCRIPTION
        "The priority level of the cli security alert."
    ::= { juniCliSecurity 1 }

juniCliSecurityAlertMessage  OBJECT-TYPE
    SYNTAX      DisplayString
    MAX-ACCESS  accessible-for-notify
    STATUS      current
    DESCRIPTION
        "The cli security alert message."
    ::= { juniCliSecurity 2 }

juniCliSecurityAlertTime  OBJECT-TYPE
    SYNTAX      DateAndTime
    MAX-ACCESS  accessible-for-notify
    STATUS      current
    DESCRIPTION
        "The date and time of this cliSecurityAlert."
    ::= { juniCliSecurity 3 }


juniCliSecurityAlert  NOTIFICATION-TYPE
    OBJECTS {
        juniCliSecurityAlertPriority,
        juniCliSecurityAlertMessage,
        juniCliSecurityAlertTime }
    STATUS      current
    DESCRIPTION
        "Reports a cli security alert.  Events such as the following generate
        this notification when it is enabled:
            - Logins/logouts from telnet or console access
            - Logins/logout from SSH
            - Access from unknown IP addreses
            - Access list accept or failures
            - Successful and unsuccessful authentications "
    ::= { juniCliTrap 1 }


-- +++++++++++++++++++++++++++++++++++++++++++++++++++++++++++++++++++++++++++++
-- Conformance information
-- +++++++++++++++++++++++++++++++++++++++++++++++++++++++++++++++++++++++++++++
juniCliCompliances  OBJECT IDENTIFIER ::= { juniCliConformance 1 }
juniCliGroups       OBJECT IDENTIFIER ::= { juniCliConformance 2 }

--
-- compliance statements
--
juniCliCompliance  MODULE-COMPLIANCE
    STATUS      current
    DESCRIPTION
        "The compliance statement for entities that implement the Juniper CLI
        MIB."
    MODULE   -- this module
        MANDATORY-GROUPS {
            juniCliGroup,
            juniCliSecurityAlertGroup,
            juniCliSecurityTrapGroup }
    ::= { juniCliCompliances 1 }

--
-- units of conformance
--
juniCliGroup  OBJECT-GROUP
    OBJECTS {
        juniCliSecurityTrapEnable }
    STATUS      current
    DESCRIPTION
        "A management object pertaining to CLI security configuration."
    ::= { juniCliGroups 1 }

juniCliSecurityAlertGroup  OBJECT-GROUP
    OBJECTS {
        juniCliSecurityAlertPriority,
        juniCliSecurityAlertMessage,
        juniCliSecurityAlertTime }
    STATUS      current
    DESCRIPTION
        "A collection of management objects pertaining to CLI security alert
        notification."
    ::= { juniCliGroups 2 }

juniCliSecurityTrapGroup  NOTIFICATION-GROUP
    NOTIFICATIONS {
        juniCliSecurityAlert }
    STATUS      current
    DESCRIPTION
        "A management notification pertaining to CLI security operations."
    ::= { juniCliGroups 3 }

END
