-- ----------------------------------------------------------------------------
--                  HUAWEI MUSA Enterprise MIB   
--                                       Musa FRC MIB 
--      Copyright (c) 1999-2002 HUA WEI TECH CO.,LTD.
--      All rights reserved.
--
--  Created by:  DAIYUEHUA
--  Create date: 2000-11-24
--  Modify date: 2000-11-24
-- ----------------------------------------------------------------------------
HUAWEI-FRC-MA5100-MIB DEFINITIONS ::= BEGIN
IMPORTS
        OBJECT-TYPE
                        FROM RFC-1212
        Counter
                        FROM RFC1155-SMI
        hwMa5100Mib, hwMusaFrameIndex, hwMusaSlotIndex   
                        FROM HUAWEI-MUSA-MA5100-MIB;
  						
    
    -- ------------------------------------------------------------------------
    -- FR manage variable
    -- ------------------------------------------------------------------------
    hwMusaFrcMib    OBJECT IDENTIFIER ::= { hwMa5100Mib 9 }
    
    
    -- ******************************************************************
    -- FRC board attribute table
    hwMusaFrcBoardTable    OBJECT-TYPE
        SYNTAX      SEQUENCE OF HwMusaFrcBoardEntry
        ACCESS      not-accessible
        STATUS      mandatory
    DESCRIPTION
    "Musa Frc board configuration table."
    ::= { hwMusaFrcMib 1 }

   hwMusaFrcBoardEntry    OBJECT-TYPE
        SYNTAX         HwMusaFrcBoardEntry
        ACCESS         not-accessible
        STATUS         mandatory
    DESCRIPTION
    "This list contains Musa Frc Board variables."
    INDEX { hwMusaFrameIndex,
            hwMusaSlotIndex}
    ::= { hwMusaFrcBoardTable  1 }
 
   HwMusaFrcBoardEntry    ::= SEQUENCE  {
            hwMusaFrcPvcAlarmEnable       INTEGER,
            hwMusaFrcBoardClearStatistic    INTEGER,   
            hwMusaFrcClockMode   			INTEGER, 
            hwMusaFrcPhyPortId   			INTEGER,
            hwMusaFrcPhyPortType			INTEGER
            } 

    hwMusaFrcPvcAlarmEnable  OBJECT-TYPE
        SYNTAX  INTEGER{
                        disable(0),
                        enable(1)
                        }
        ACCESS  read-write
        STATUS  mandatory
        DESCRIPTION
        "The Frc PVC alarm enable or disable."
    ::= { hwMusaFrcBoardEntry 1 }   

    hwMusaFrcBoardClearStatistic  OBJECT-TYPE
        SYNTAX  INTEGER
        ACCESS  write-only
        STATUS  mandatory
        DESCRIPTION
        "Clear the Frc board statisitcs."
    ::= { hwMusaFrcBoardEntry 2 }   

    hwMusaFrcClockMode  OBJECT-TYPE
        SYNTAX  INTEGER{
                        local(0),
                        backplate(1),
                        line(2)
                        }
        ACCESS  read-write
        STATUS  mandatory
        DESCRIPTION
        "The phy port Clock Mode."
    ::= { hwMusaFrcBoardEntry 3 }

    hwMusaFrcPhyPortId  OBJECT-TYPE
        SYNTAX  INTEGER(0..7)
        ACCESS  read-write
        STATUS  mandatory
        DESCRIPTION
        "the index of the port."
    ::= { hwMusaFrcBoardEntry 4 }     

    hwMusaFrcPhyPortType  OBJECT-TYPE
        SYNTAX  INTEGER{
                        e1(1),
                        t1(2),
                        v35(3)
                        }
        ACCESS  read-only
        STATUS  mandatory
        DESCRIPTION
        "physical port type."
    ::= { hwMusaFrcBoardEntry 5 } 
            
    -- **************************************************
    -- FRC PHY port line interface table
    
    hwMusaFrcPhyPortLineIfTable    OBJECT-TYPE
        SYNTAX      SEQUENCE OF HwMusaFrcPhyPortLineIfEntry
        ACCESS      not-accessible
        STATUS      mandatory
    DESCRIPTION
    "Musa Frc phy port line Interface table."
    ::= { hwMusaFrcMib 2 }

   hwMusaFrcPhyPortLineIfEntry    OBJECT-TYPE
        SYNTAX         HwMusaFrcPhyPortLineIfEntry
        ACCESS         not-accessible
        STATUS         mandatory
    DESCRIPTION
    "This list contains Musa Frc phy port line If variables."
    INDEX { hwMusaFrameIndex,
            hwMusaSlotIndex ,
            hwMusaFrcPhyPortId   }
    ::= { hwMusaFrcPhyPortLineIfTable  1 }
 
   HwMusaFrcPhyPortLineIfEntry    ::= SEQUENCE  {
            hwMusaFrcMainClock                  INTEGER,
            hwMusaFrcT1HaulMode          	INTEGER,
            hwMusaFrcT1E1Crc               	INTEGER,
            hwMusaFrcT1FrameFormat              INTEGER,
            hwMusaFrcT1LineCode              	INTEGER,
            hwMusaFrcV35ClockMode               INTEGER,
            hwMusaFrcT1E1TsBitMap		INTEGER,
            hwMusaFrcClockLoopMode     		INTEGER,
            hwMusaFrcLoopState     		INTEGER,
            hwMusaFrcV35InvertTxClock 		INTEGER,
            hwMusaFrcSingleTimeSlotId           INTEGER
            } 
                       
    hwMusaFrcMainClock  OBJECT-TYPE
        SYNTAX  INTEGER{
                        local(0),
                        backplate(1),
                        line(2)
                        }
        ACCESS  read-write
        STATUS  mandatory
        DESCRIPTION
        "The main clock.
         local,backplate,line."
    ::= { hwMusaFrcPhyPortLineIfEntry 1 }

    hwMusaFrcT1HaulMode  OBJECT-TYPE
        SYNTAX  INTEGER{
                        short(0),
                        long(1)
                        }
        ACCESS  read-write
        STATUS  mandatory
        DESCRIPTION
        "The T1 short/long haul mode."
    ::= { hwMusaFrcPhyPortLineIfEntry 2 }
                        
    hwMusaFrcT1E1Crc  OBJECT-TYPE
        SYNTAX  INTEGER{
                        no(0),
                        yes(1)
                        }
        ACCESS  read-write
        STATUS  mandatory
        DESCRIPTION
        "The T1 crc, when T1 is ESF frame format."
    ::= { hwMusaFrcPhyPortLineIfEntry 3 }
                        
    hwMusaFrcT1FrameFormat  OBJECT-TYPE
        SYNTAX  INTEGER{
                        t1esf(0),
                        t1d44mf(1),
                        t1d412mf(2)
                        }
        ACCESS  read-write
        STATUS  mandatory
        DESCRIPTION
        "The T1 frame format."
    ::= { hwMusaFrcPhyPortLineIfEntry 4 }

    hwMusaFrcT1LineCode  OBJECT-TYPE
        SYNTAX  INTEGER{
                        b8zs(0),
                        ami(1)
                        }
        ACCESS  read-write
        STATUS  mandatory
        DESCRIPTION
        "The T1 line code."
    ::= { hwMusaFrcPhyPortLineIfEntry 5 }
    
    hwMusaFrcV35ClockMode  OBJECT-TYPE
        SYNTAX  INTEGER{
                        dceinner(0),
                        dceslave(1),
                        dceouter(2),
                        dteinner(3),
                        dteslave(4),
                        dteouter(5)                        
                        }
        ACCESS  read-write
        STATUS  mandatory
        DESCRIPTION
        "The V35 clock mode."
    ::= { hwMusaFrcPhyPortLineIfEntry 6 }

    hwMusaFrcT1E1TsBitMap  OBJECT-TYPE
        SYNTAX  INTEGER
        ACCESS  read-only
        STATUS  mandatory
        DESCRIPTION
        "The TS bit map."
    ::= { hwMusaFrcPhyPortLineIfEntry 7 }
    
        
    hwMusaFrcClockLoopMode  OBJECT-TYPE
        SYNTAX  INTEGER{
                        payloop(0),
                        remoteloop(1),
                        single-timeslot(2)
                        }
        ACCESS  read-write
        STATUS  mandatory
        DESCRIPTION
        "The phy port Clock loop mode."
    ::= { hwMusaFrcPhyPortLineIfEntry 8 }       
    
        hwMusaFrcLoopState  OBJECT-TYPE
        SYNTAX  INTEGER{
                        noloop(0),
                        loop(1)
                        }
        ACCESS  read-write
        STATUS  mandatory
        DESCRIPTION
        "The phy port Clock loop state."
    ::= { hwMusaFrcPhyPortLineIfEntry 9 } 

        hwMusaFrcV35InvertTxClock  OBJECT-TYPE
        SYNTAX  INTEGER{
                        off(0),
                        on(1)
                        }
        ACCESS  read-write
        STATUS  mandatory
        DESCRIPTION
        "The V35 port Clock invert phase."
    ::= { hwMusaFrcPhyPortLineIfEntry 10 } 
    
        hwMusaFrcSingleTimeSlotId  OBJECT-TYPE
        SYNTAX  INTEGER(1..31)
        ACCESS  read-write
        STATUS  mandatory
        DESCRIPTION
        "The timeslot id of single timeslot loopback."
    ::= { hwMusaFrcPhyPortLineIfEntry 11 }
    
    -- ******************************************************
    -- FRC PHY port alarm table
    
    hwMusaFrcPhyPortAlarmTable    OBJECT-TYPE
        SYNTAX      SEQUENCE OF HwMusaFrcPhyPortAlarmEntry
        ACCESS      not-accessible
        STATUS      mandatory
    DESCRIPTION
    "Musa Frc phy port alarm table."
    ::= { hwMusaFrcMib 3 }

   hwMusaFrcPhyPortAlarmEntry    OBJECT-TYPE
        SYNTAX         HwMusaFrcPhyPortAlarmEntry
        ACCESS         not-accessible
        STATUS         mandatory
    DESCRIPTION
    "This list contains Musa Frc phy port Alarm variables."
    INDEX { hwMusaFrameIndex,
            hwMusaSlotIndex ,
            hwMusaFrcPhyPortId   }
    ::= { hwMusaFrcPhyPortAlarmTable  1 }
 
   HwMusaFrcPhyPortAlarmEntry    ::= SEQUENCE  {
            hwMusaFrcAlarmSw                 INTEGER,
            hwMusaFrcRACTS        INTEGER,
            hwMusaFrcLFADSR          INTEGER,
            hwMusaFrcLOSPLL               INTEGER,
            hwMusaFrcAISDCD              INTEGER,
            hwMusaFrcAlarmCount              INTEGER,
            hwMusaFrcDTR             INTEGER,
            hwMusaFrcRTS             INTEGER, 
            hwMusaFrcSCOL            INTEGER 
            } 
            
    hwMusaFrcAlarmSw  OBJECT-TYPE
        SYNTAX  INTEGER{
                        disable(0),
                        enable(1)
                        }
        ACCESS  read-write
        STATUS  mandatory
        DESCRIPTION
        "The phy port alarm switch."
    ::= { hwMusaFrcPhyPortAlarmEntry 1 }                    
            
    hwMusaFrcRACTS  OBJECT-TYPE
        SYNTAX  INTEGER{
                        noalarmup(0),
                        alarmdown(1)   
                        }
        ACCESS  read-only
        STATUS  mandatory
        DESCRIPTION
        "The E1/T1 phy port remote alarm or V35 phy port CTS alarm."
    ::= { hwMusaFrcPhyPortAlarmEntry 2 }  
        
    hwMusaFrcLFADSR  OBJECT-TYPE
        SYNTAX  INTEGER{
                        noalarmup(0),
                        alarmdown(1)   
                        }
        ACCESS  read-only
        STATUS  mandatory
        DESCRIPTION
        "The E1/T1 phy port LFA or V35 phy port DSR alarm."
    ::= { hwMusaFrcPhyPortAlarmEntry 3 }
    
    hwMusaFrcLOSPLL  OBJECT-TYPE
        SYNTAX  INTEGER{
                        noalarmup(0),
                        alarmdown(1)   
                        }
        ACCESS  read-only
        STATUS  mandatory
        DESCRIPTION
        "The E1/T1 phy port LOS alarm or V35 phy port PLL alarm."
    ::= { hwMusaFrcPhyPortAlarmEntry 4 }
    
    hwMusaFrcAISDCD  OBJECT-TYPE
        SYNTAX  INTEGER{
                        noalarmup(0),
                        alarmdown(1)                        
                        }
        ACCESS  read-only
        STATUS  mandatory
        DESCRIPTION
        "The E1/T1 phy port AIS alarm OR V35 phy port DCD alarm."
    ::= { hwMusaFrcPhyPortAlarmEntry 5 }    
    
    hwMusaFrcAlarmCount  OBJECT-TYPE
        SYNTAX  INTEGER
        ACCESS  read-only
        STATUS  mandatory
        DESCRIPTION
        "The phy port alarm count."
    ::= { hwMusaFrcPhyPortAlarmEntry 6 } 
    
    hwMusaFrcDTR       OBJECT-TYPE       
        SYNTAX  INTEGER{
                        up(0),
                        down(1)   
                        }
        ACCESS  read-only
        STATUS  mandatory
        DESCRIPTION
        "The V35 phy port DTR alarm."
    ::= { hwMusaFrcPhyPortAlarmEntry 7 } 
    
    hwMusaFrcRTS       OBJECT-TYPE       
        SYNTAX  INTEGER{
                        up(0),
                        down(1)   
                        }
        ACCESS  read-only
        STATUS  mandatory
        DESCRIPTION
        "The V35 phy port RTS alarm."
    ::= { hwMusaFrcPhyPortAlarmEntry 8 }     
   
    hwMusaFrcSCOL       OBJECT-TYPE       
        SYNTAX  INTEGER{
                        noalarm(0),
                        alarm(1)   
                        }
        ACCESS  read-only
        STATUS  mandatory
        DESCRIPTION
        "The phy port SCOL alarm."
    ::= { hwMusaFrcPhyPortAlarmEntry 9 }         
       

    -- **********************************************************
    -- FRC Logic Port Table
    
    hwMusaFrcLogicPortTable    OBJECT-TYPE
        SYNTAX      SEQUENCE OF HwMusaFrcLogicPortEntry
        ACCESS      not-accessible
        STATUS      mandatory
    DESCRIPTION
    "Musa Frc logic port table."
    ::= { hwMusaFrcMib 4 }

   hwMusaFrcLogicPortEntry    OBJECT-TYPE
        SYNTAX         HwMusaFrcLogicPortEntry
        ACCESS         not-accessible
        STATUS         mandatory
    DESCRIPTION
    "This list contains Musa Fr logic port variables."
    INDEX { hwMusaFrameIndex,
            hwMusaSlotIndex ,
            hwMusaFrcLogicPortId   }
    ::= { hwMusaFrcLogicPortTable  1 }
 
   HwMusaFrcLogicPortEntry    ::= SEQUENCE  {
            hwMusaFrcLogicPortId                 INTEGER,
            hwMusaFrcPhyPort        INTEGER,
            hwMusaFrcE1T1TsBitMapV35NValue        INTEGER,
            hwMusaFrcDlciType        INTEGER,
            hwMusaFrcFreeBandwidth        INTEGER,
            hwMusaFrcServiceFlag        INTEGER,
            hwMusaFrcPortActivate          INTEGER,
            hwMusaFrcLogicPortOperate  INTEGER
            } 
            
    hwMusaFrcLogicPortId  OBJECT-TYPE
        SYNTAX  INTEGER(0..7)
        ACCESS  not-accessible
        STATUS  mandatory
        DESCRIPTION
        "The Fr Logical Port ID."
    ::= { hwMusaFrcLogicPortEntry 1 }    

    hwMusaFrcPhyPort     OBJECT-TYPE
        SYNTAX  INTEGER(0..7)
        ACCESS  read-write
        STATUS  mandatory
        DESCRIPTION
        "The Fr phy Port."
    ::= { hwMusaFrcLogicPortEntry 2 }    

    hwMusaFrcE1T1TsBitMapV35NValue     OBJECT-TYPE
        SYNTAX  INTEGER 
        ACCESS  read-write
        STATUS  mandatory
        DESCRIPTION
        "The E1/T1 TS bit Map or V35 N value."
    ::= { hwMusaFrcLogicPortEntry 3 }    

    hwMusaFrcDlciType     OBJECT-TYPE
        SYNTAX  INTEGER (1..5)
        ACCESS  read-write
        STATUS  mandatory
        DESCRIPTION
        "The DLCI type."
    ::= { hwMusaFrcLogicPortEntry 4 } 


    hwMusaFrcFreeBandwidth     OBJECT-TYPE
        SYNTAX  INTEGER 
        ACCESS  read-only
        STATUS  mandatory
        DESCRIPTION
        "The free bandwidth."
    ::= { hwMusaFrcLogicPortEntry 5 } 

    hwMusaFrcServiceFlag     OBJECT-TYPE
        SYNTAX  INTEGER{
	                network11(0),
	                service(1),
	                hdlc(2),
	                networkN1(3),
	                frIwf(4)
                        } 
        ACCESS  read-only
        STATUS  mandatory
        DESCRIPTION
        "The service FLAG."
    ::= { hwMusaFrcLogicPortEntry 6 } 

    hwMusaFrcPortActivate     OBJECT-TYPE
        SYNTAX  INTEGER{
                        block(0),
                        unblock(1)
                        }
        ACCESS  read-write
        STATUS  mandatory
        DESCRIPTION
        "The active flag."
    ::= { hwMusaFrcLogicPortEntry 7 }     
    
    hwMusaFrcLogicPortOperate     OBJECT-TYPE
        SYNTAX  INTEGER{
                        add(0),
                        del(1)
                        }
        ACCESS  read-write
        STATUS  mandatory
        DESCRIPTION
        "The operat."
    ::= { hwMusaFrcLogicPortEntry 8 }     


    -- ------------------------------------------------------------------------
    -- Signalling Port configuration Table
    -- ------------------------------------------------------------------------
  
    hwMusaFrcLogPortSigTable	OBJECT-TYPE
	SYNTAX	SEQUENCE OF HwMusaFrcLogPortSigEntry
	ACCESS	not-accessible
	STATUS	mandatory
	DESCRIPTION
	" This table contains information of system pvc"
    ::= { hwMusaFrcMib 5 }
           
    hwMusaFrcLogPortSigEntry    OBJECT-TYPE
        SYNTAX   HwMusaFrcLogPortSigEntry
        ACCESS   not-accessible
        STATUS   mandatory
        DESCRIPTION
        "This list contains FR port information parameters."
        INDEX { hwMusaFrameIndex,
            hwMusaSlotIndex ,
            hwMusaFrcLogPortSigSide,
            hwMusaFrcLogicPortId   }
    ::= { hwMusaFrcLogPortSigTable  1}        
    
   HwMusaFrcLogPortSigEntry     ::= SEQUENCE  {
            hwMusaFrcLogPortSigSide            INTEGER,   
            hwMusaFrcLogPortSigProtocalType            INTEGER,
            hwMusaFrcLogPortSigPortType        INTEGER,
            hwMusaFrcLogPortSigN391            INTEGER,
            hwMusaFrcLogPortSigUserN392        INTEGER,
            hwMusaFrcLogPortSigUserN393        INTEGER,
            hwMusaFrcLogPortSigNetN392         INTEGER,
            hwMusaFrcLogPortSigNetN393         INTEGER,   
            hwMusaFrcLogPortSigT391            INTEGER,
            hwMusaFrcLogPortSigT392            INTEGER,
            hwMusaFrcLogPortSigOper            INTEGER         
            }
  
   hwMusaFrcLogPortSigSide      OBJECT-TYPE
	SYNTAX	INTEGER{
	        frside(0),
	        atmside(1)
	        }
	ACCESS	not-accessible
	STATUS	mandatory
	DESCRIPTION
	"Singnalling port side"
    ::= { hwMusaFrcLogPortSigEntry 1 }      
    
   hwMusaFrcLogPortSigProtocalType      OBJECT-TYPE
	SYNTAX	INTEGER{
	        q933a (0),
	        ansit167d (1),
	        cisiolmi  (2)
	        }
	ACCESS	read-write
	STATUS	mandatory
	DESCRIPTION
	""
    ::= { hwMusaFrcLogPortSigEntry 2 }   
    
   hwMusaFrcLogPortSigPortType      OBJECT-TYPE
	SYNTAX	INTEGER{
	        user (1),
	        net  (2),
	        bid  (3)
	        }
	ACCESS	read-write
	STATUS	mandatory
	DESCRIPTION
	""
    ::= { hwMusaFrcLogPortSigEntry 3 } 
    
   hwMusaFrcLogPortSigN391      OBJECT-TYPE
	SYNTAX	INTEGER(1..255)
	ACCESS	read-write
	STATUS	mandatory
	DESCRIPTION
	"N391"
    ::= { hwMusaFrcLogPortSigEntry 4 }       
    
   hwMusaFrcLogPortSigUserN392      OBJECT-TYPE
	SYNTAX	INTEGER(1..10)
	ACCESS	read-write
	STATUS	mandatory
	DESCRIPTION
	"UserN392"
    ::= { hwMusaFrcLogPortSigEntry 5 } 
    
   hwMusaFrcLogPortSigUserN393      OBJECT-TYPE
	SYNTAX	INTEGER(1..10)
	ACCESS	read-write
	STATUS	mandatory
	DESCRIPTION
	"UserN393"
    ::= { hwMusaFrcLogPortSigEntry 6 }     
    
   hwMusaFrcLogPortSigNetN392      OBJECT-TYPE
	SYNTAX	INTEGER(1..10)
	ACCESS	read-write
	STATUS	mandatory
	DESCRIPTION
	"NetN392"
    ::= { hwMusaFrcLogPortSigEntry 7 } 
    
   hwMusaFrcLogPortSigNetN393      OBJECT-TYPE
	SYNTAX	INTEGER(1..10)
	ACCESS	read-write
	STATUS	mandatory
	DESCRIPTION
	"NetN393"
    ::= { hwMusaFrcLogPortSigEntry 8 }      
    
   hwMusaFrcLogPortSigT391      OBJECT-TYPE
	SYNTAX	INTEGER(5..255)
	ACCESS	read-write
	STATUS	mandatory
	DESCRIPTION
	"T391"
    ::= { hwMusaFrcLogPortSigEntry 9 }      
    
   hwMusaFrcLogPortSigT392      OBJECT-TYPE
	SYNTAX	INTEGER(6..255)
	ACCESS	read-write
	STATUS	mandatory
	DESCRIPTION
	"T392"
    ::= { hwMusaFrcLogPortSigEntry 10 }          

   hwMusaFrcLogPortSigOper      OBJECT-TYPE
	SYNTAX	INTEGER{
	        add (0),
	        del (1)
	        }
	ACCESS	read-write
	STATUS	mandatory
	DESCRIPTION
	"Signalling port operation"
    ::= { hwMusaFrcLogPortSigEntry 11 }    
   
    -- ------------------------------------------------------------------------
    -- IWF configuration table
    -- ------------------------------------------------------------------------
  
    hwMusaFrcIwfTable	OBJECT-TYPE
	SYNTAX	SEQUENCE OF HwMusaFrcIwfEntry
	ACCESS	not-accessible
	STATUS	mandatory
	DESCRIPTION
	" This table contains Fr Iwf"
    ::= { hwMusaFrcMib 6 }
           
    hwMusaFrcIwfEntry    OBJECT-TYPE
        SYNTAX   HwMusaFrcIwfEntry
        ACCESS   not-accessible
        STATUS   mandatory
        DESCRIPTION
        "This list contains Fr Iwf."
        INDEX { hwMusaFrameIndex,
            hwMusaSlotIndex ,
            hwMusaFrcIwfCcid}
    ::= { hwMusaFrcIwfTable  1}        
    
   HwMusaFrcIwfEntry     ::= SEQUENCE  {
            hwMusaFrcIwfCcid            INTEGER,   
            hwMusaFrcConnectMode             INTEGER,   
            hwMusaFrcLogicPort            INTEGER,
            hwMusaFrcDlci        INTEGER,
            hwMusaFrcAtmVcc            INTEGER,
            hwMusaFrcAtmDlci        INTEGER,
            hwMusaFrcEfci        INTEGER,
            hwMusaFrcDe         INTEGER,
            hwMusaFrcClp         INTEGER,   
            hwMusaFrcCir            INTEGER,
            hwMusaFrcEir            INTEGER,
            hwMusaFrcServiceMode            INTEGER,
            hwMusaFrcOperate            INTEGER
            }
  
   hwMusaFrcIwfCcid      OBJECT-TYPE
	SYNTAX	INTEGER(0..999)	        
	ACCESS	not-accessible
	STATUS	mandatory
	DESCRIPTION
	"IWF CCID"
    ::= { hwMusaFrcIwfEntry 1 }     

   hwMusaFrcConnectMode      OBJECT-TYPE
	SYNTAX	INTEGER{
	                network11(0),
	                service(1),
	                hdlc(2),
	                networkN1(3),
	                frIwf(4)}
	ACCESS	read-write
	STATUS	mandatory
	DESCRIPTION
	"FR connect mode"
    ::= { hwMusaFrcIwfEntry 2 }     

   hwMusaFrcLogicPort      OBJECT-TYPE
	SYNTAX	INTEGER(0..494)
	ACCESS	read-write
	STATUS	mandatory
	DESCRIPTION
	"logical port"
    ::= { hwMusaFrcIwfEntry 3 }     
    

   hwMusaFrcDlci      OBJECT-TYPE
	SYNTAX	INTEGER
	ACCESS	read-write
	STATUS	mandatory
	DESCRIPTION
	"logical port dlci"
    ::= { hwMusaFrcIwfEntry 4 }         
        
   hwMusaFrcAtmVcc      OBJECT-TYPE
	SYNTAX	INTEGER(0..494)
	ACCESS	read-write
	STATUS	mandatory
	DESCRIPTION
	"atm vcc"
    ::= { hwMusaFrcIwfEntry 5 }       
    
   hwMusaFrcAtmDlci      OBJECT-TYPE
	SYNTAX	INTEGER
	ACCESS	read-write
	STATUS	mandatory
	DESCRIPTION
	"atm vcc"
    ::= { hwMusaFrcIwfEntry 6 }       
    
   hwMusaFrcEfci      OBJECT-TYPE
	SYNTAX	INTEGER{
	                efcn(0),
	                valure0(1)
	                }
	ACCESS	read-write
	STATUS	mandatory
	DESCRIPTION
	"atm efci"
    ::= { hwMusaFrcIwfEntry 7}       
    
   hwMusaFrcDe      OBJECT-TYPE
	SYNTAX	INTEGER{
	                 netdeClpFrsscs(0),
	                 netdeFrsscs(1),
	                 srvdeClp(2),
	                 srvde0(3),
	                 srvde1(4)
	                }
	ACCESS	read-write
	STATUS	mandatory
	DESCRIPTION
	"atm de"
    ::= { hwMusaFrcIwfEntry 8}
    
   hwMusaFrcClp      OBJECT-TYPE
	SYNTAX	INTEGER{
	                 clpDe(0),
	                 clp0(1),
	                 clp1(2)
	                }
	ACCESS	read-write
	STATUS	mandatory
	DESCRIPTION
	"atm clp"
    ::= { hwMusaFrcIwfEntry 9}
    
   hwMusaFrcCir      OBJECT-TYPE
	SYNTAX	INTEGER(0..2048)
	ACCESS	read-write
	STATUS	mandatory
	DESCRIPTION
	"atm cir"
    ::= { hwMusaFrcIwfEntry 10}        
    
   hwMusaFrcEir      OBJECT-TYPE
	SYNTAX	INTEGER(0..1984)
	ACCESS	read-write
	STATUS	mandatory
	DESCRIPTION
	"atm eir"
    ::= { hwMusaFrcIwfEntry 11}    
    
   hwMusaFrcServiceMode      OBJECT-TYPE
	SYNTAX	INTEGER(0..1)
	ACCESS	read-write
	STATUS	mandatory
	DESCRIPTION
	"atm eir"
    ::= { hwMusaFrcIwfEntry 12}                
    
   hwMusaFrcOperate      OBJECT-TYPE
	SYNTAX	INTEGER{
	                add(0),
	                del(1)
	                }
	ACCESS	read-write
	STATUS	mandatory
	DESCRIPTION
	"iwf operate"
    ::= { hwMusaFrcIwfEntry 13}   
     
    -- @@@@@@@@@@@@@@@@@@@@@@@@@@@@@@@@@@@@@@@@@@@@@@@@@@@@@@@@@@@@@@@@@@@@@@
    -- **********************************************************************
        
    -- ------------------------------------------------------------------------
    --  FR Logic Port Statistic Table
    -- ------------------------------------------------------------------------
  
    hwMusaFrcLogicPortStatisTable	OBJECT-TYPE
	SYNTAX	SEQUENCE OF HwMusaFrcLogicPortStatisEntry
	ACCESS	not-accessible
	STATUS	mandatory
	DESCRIPTION
	" This table contains LogicPortStatis"
    ::= { hwMusaFrcMib 7 }
           
    hwMusaFrcLogicPortStatisEntry    OBJECT-TYPE
        SYNTAX   HwMusaFrcLogicPortStatisEntry
        ACCESS   not-accessible
        STATUS   mandatory
        DESCRIPTION
        "This list contains Logical Port Statistic."
        INDEX { hwMusaFrameIndex,
                hwMusaSlotIndex,
                hwMusaFrcLogicPortId}
    ::= { hwMusaFrcLogicPortStatisTable  1}        
    
   HwMusaFrcLogicPortStatisEntry     ::= SEQUENCE  {
            hwMusaFrcLogicPortActive            INTEGER,   
            hwMusaFrcCongestState             INTEGER,   
            hwMusaFrcInFrameCount            Counter,
            hwMusaFrcInByteCount        Counter,
            hwMusaFrcInLossParkageC            Counter,
            hwMusaFrcOutFrameCount            Counter,
            hwMusaFrcOutByteCount        Counter,
            hwMusaFrcOutLossParkageC            Counter
            }
            
   hwMusaFrcLogicPortActive       OBJECT-TYPE
	SYNTAX	INTEGER{
	                inactive(0),
	                active(1)
	                }
	ACCESS	read-only
	STATUS	mandatory
	DESCRIPTION
	"Active state."
    ::= { hwMusaFrcLogicPortStatisEntry 1 }    
                  
   hwMusaFrcCongestState      OBJECT-TYPE
	SYNTAX	INTEGER{
	                no(0),
	                yes(1),
	                serious(2)
	                }        
	ACCESS	read-only
	STATUS	mandatory
	DESCRIPTION
	"Congest state."
    ::= { hwMusaFrcLogicPortStatisEntry 2 }    
                   
   hwMusaFrcInFrameCount      OBJECT-TYPE
	SYNTAX	Counter        
	ACCESS	read-only
	STATUS	mandatory
	DESCRIPTION
	"In frame count."
    ::= { hwMusaFrcLogicPortStatisEntry 3 }    
                            
   hwMusaFrcInByteCount      OBJECT-TYPE
	SYNTAX	Counter        
	ACCESS	read-only
	STATUS	mandatory
	DESCRIPTION
	"In BYTE count."
    ::= { hwMusaFrcLogicPortStatisEntry 4 }    
                
   hwMusaFrcInLossParkageC      OBJECT-TYPE
	SYNTAX	Counter        
	ACCESS	read-only
	STATUS	mandatory
	DESCRIPTION
	"IN parkage count."
    ::= { hwMusaFrcLogicPortStatisEntry 5 }    
                
   hwMusaFrcOutFrameCount      OBJECT-TYPE
	SYNTAX	Counter        
	ACCESS	read-only
	STATUS	mandatory
	DESCRIPTION
	"Output frame count."
    ::= { hwMusaFrcLogicPortStatisEntry 6 }    
   
   hwMusaFrcOutByteCount      OBJECT-TYPE
	SYNTAX	Counter        
	ACCESS	read-only
	STATUS	mandatory
	DESCRIPTION
	"Output BYTE count."
    ::= { hwMusaFrcLogicPortStatisEntry 7 }    
  
   hwMusaFrcOutLossParkageC      OBJECT-TYPE
	SYNTAX	Counter        
	ACCESS	read-only
	STATUS	mandatory
	DESCRIPTION
	"Output loss parkage count."
    ::= { hwMusaFrcLogicPortStatisEntry 8 }    
            
    -- @@@@@@@@@@@@@@@@@@@@@@@@@@@@@@@@@@@@@@@@@@@@@@@@@@@@@@@@@@@@@@@@@@@@@@
    -- **********************************************************************
        
    -- ------------------------------------------------------------------------
    --  Atm Logic Port Statistic Table
    -- ------------------------------------------------------------------------
  
    hwMusaFrcAtmPortStatisTable	OBJECT-TYPE
	SYNTAX	SEQUENCE OF HwMusaFrcAtmPortStatisEntry
	ACCESS	not-accessible
	STATUS	mandatory
	DESCRIPTION
	" This table contains Atm PortStatis"
    ::= { hwMusaFrcMib 8 }
           
    hwMusaFrcAtmPortStatisEntry    OBJECT-TYPE
        SYNTAX   HwMusaFrcAtmPortStatisEntry
        ACCESS   not-accessible
        STATUS   mandatory
        DESCRIPTION
        "This list contains Atm Port Statistic."
        INDEX { hwMusaFrameIndex,
                hwMusaSlotIndex,
                hwMusaFrcAtmVcc}
    ::= { hwMusaFrcAtmPortStatisTable  1}        
    
   HwMusaFrcAtmPortStatisEntry     ::= SEQUENCE  {
            hwMusaFrcAtmPortActive            INTEGER,   
            hwMusaFrcAtmCongestState             INTEGER,
            hwMusaFrcAtmInFrames            Counter,
            hwMusaFrcAtmInBytes            Counter,
            hwMusaFrcAtmInDiscards            Counter,
            hwMusaFrcAtmOutFrames            Counter,
            hwMusaFrcAtmOutBytes            Counter,
            hwMusaFrcAtmOutDiscards            Counter
            }
            
   hwMusaFrcAtmPortActive       OBJECT-TYPE
	SYNTAX	INTEGER{
	                inactive(0),
	                active(1)
	                }
	ACCESS	read-only
	STATUS	mandatory
	DESCRIPTION
	"Active state."
    ::= { hwMusaFrcAtmPortStatisEntry 1 }    
       
   hwMusaFrcAtmCongestState      OBJECT-TYPE
	SYNTAX	INTEGER{
	                no(0),
	                yes(1),
	                serious(2)
	                }        
	ACCESS	read-only
	STATUS	mandatory
	DESCRIPTION
	"Congest state."
    ::= { hwMusaFrcAtmPortStatisEntry 2 }    
            
   hwMusaFrcAtmInFrames      OBJECT-TYPE
	SYNTAX	Counter        
	ACCESS	read-only
	STATUS	mandatory
	DESCRIPTION
	"In loss parkage count."
    ::= { hwMusaFrcAtmPortStatisEntry 3 }    

   hwMusaFrcAtmInBytes      OBJECT-TYPE
	SYNTAX	Counter        
	ACCESS	read-only
	STATUS	mandatory
	DESCRIPTION
	"Output loss parkage count."
    ::= { hwMusaFrcAtmPortStatisEntry 4 }    

   hwMusaFrcAtmInDiscards      OBJECT-TYPE
	SYNTAX	Counter        
	ACCESS	read-only
	STATUS	mandatory
	DESCRIPTION
	"In loss parkage count."
    ::= { hwMusaFrcAtmPortStatisEntry 5 }    

   hwMusaFrcAtmOutFrames      OBJECT-TYPE
	SYNTAX	Counter        
	ACCESS	read-only
	STATUS	mandatory
	DESCRIPTION
	"Output loss parkage count."
    ::= { hwMusaFrcAtmPortStatisEntry 6 }    
       
   hwMusaFrcAtmOutBytes      OBJECT-TYPE
	SYNTAX	Counter        
	ACCESS	read-only
	STATUS	mandatory
	DESCRIPTION
	"In loss parkage count."
    ::= { hwMusaFrcAtmPortStatisEntry 7 }    

   hwMusaFrcAtmOutDiscards      OBJECT-TYPE
	SYNTAX	Counter        
	ACCESS	read-only
	STATUS	mandatory
	DESCRIPTION
	"Output loss parkage count."
    ::= { hwMusaFrcAtmPortStatisEntry 8 }                                    
    
    -- @@@@@@@@@@@@@@@@@@@@@@@@@@@@@@@@@@@@@@@@@@@@@@@@@@@@@@@@@@@@@@@@@@@@@@
    -- **********************************************************************
        
    -- ------------------------------------------------------------------------
    --  Signalling Port Statistic Table
    -- ------------------------------------------------------------------------
  
    hwMusaFrcSigPortStatisTable	OBJECT-TYPE
	SYNTAX	SEQUENCE OF HwMusaFrcSigPortStatisEntry
	ACCESS	not-accessible
	STATUS	mandatory
	DESCRIPTION
	" This table contains signal Port Statis"
    ::= { hwMusaFrcMib 9 }
           
    hwMusaFrcSigPortStatisEntry    OBJECT-TYPE
        SYNTAX   HwMusaFrcSigPortStatisEntry
        ACCESS   not-accessible
        STATUS   mandatory
        DESCRIPTION
        "This list contains Sig Port Statistic."
        INDEX { hwMusaFrameIndex,
                hwMusaSlotIndex,
                hwMusaFrcLogPortSigSide,
                hwMusaFrcLogicPortId}
    ::= { hwMusaFrcSigPortStatisTable  1}        
    
   HwMusaFrcSigPortStatisEntry     ::= SEQUENCE  {
            hwMusaFrcSigType            INTEGER,   
            hwMusaFrcSigPortSide             INTEGER,
            hwMusaFrcUserLinkC            Counter,
            hwMusaFrcUserProtocalC          Counter,
            hwMusaFrcUserDeactC          Counter,
            hwMusaFrcNetworkLinkC          Counter,
            hwMusaFrcNetworkProtocalC          Counter,
            hwMusaFrcNetworkDeactC          Counter,
            hwMusaFrcSendFrameC           Counter,
            hwMusaFrcRecvFrameC           Counter
            }
            
   hwMusaFrcSigType       OBJECT-TYPE
	SYNTAX	INTEGER{
	                userside(1),
	                networkside(2),
	                bidside(3)
	                }
	ACCESS	read-write
	STATUS	mandatory
	DESCRIPTION
	"signal port type."
    ::= { hwMusaFrcSigPortStatisEntry 1 }                  
    
   hwMusaFrcSigPortSide       OBJECT-TYPE
	SYNTAX	INTEGER{
	                fr(0),
	                atm(1)
	                }
	ACCESS	read-write
	STATUS	mandatory
	DESCRIPTION
	"signal port side."
    ::= { hwMusaFrcSigPortStatisEntry 2 }                  
    
   hwMusaFrcUserLinkC       OBJECT-TYPE
	SYNTAX	Counter
	ACCESS	read-write
	STATUS	mandatory
	DESCRIPTION
	"User link error count."
    ::= { hwMusaFrcSigPortStatisEntry 3 } 
    
   hwMusaFrcUserProtocalC       OBJECT-TYPE
	SYNTAX	Counter
	ACCESS	read-write
	STATUS	mandatory
	DESCRIPTION
	"User protocal error count."
    ::= { hwMusaFrcSigPortStatisEntry 4 } 
                    
   hwMusaFrcUserDeactC       OBJECT-TYPE
	SYNTAX	Counter
	ACCESS	read-write
	STATUS	mandatory
	DESCRIPTION
	"User port deactive count."
    ::= { hwMusaFrcSigPortStatisEntry 5 } 

    
   hwMusaFrcNetworkLinkC       OBJECT-TYPE
	SYNTAX	Counter
	ACCESS	read-write
	STATUS	mandatory
	DESCRIPTION
	"Network link error count."
    ::= { hwMusaFrcSigPortStatisEntry 6 } 
    
   hwMusaFrcNetworkProtocalC       OBJECT-TYPE
	SYNTAX	Counter
	ACCESS	read-write
	STATUS	mandatory
	DESCRIPTION
	"Network protocal error count."
    ::= { hwMusaFrcSigPortStatisEntry 7 } 
                    
   hwMusaFrcNetworkDeactC       OBJECT-TYPE
	SYNTAX	Counter
	ACCESS	read-write
	STATUS	mandatory
	DESCRIPTION
	"Network port deactive count."
    ::= { hwMusaFrcSigPortStatisEntry 8 }                         
    
    hwMusaFrcSendFrameC       OBJECT-TYPE
	SYNTAX	Counter
	ACCESS	read-write
	STATUS	mandatory
	DESCRIPTION
	"The number of sended frames."
    ::= { hwMusaFrcSigPortStatisEntry 9 }                         
    
    hwMusaFrcRecvFrameC       OBJECT-TYPE
	SYNTAX	Counter
	ACCESS	read-write
	STATUS	mandatory
	DESCRIPTION
	"The number of received frames."
    ::= { hwMusaFrcSigPortStatisEntry 10 }                         

    -- @@@@@@@@@@@@@@@@@@@@@@@@@@@@@@@@@@@@@@@@@@@@@@@@@@@@@@@@@@@@@@@@@@@@@@
    -- **********************************************************************
        
    -- ------------------------------------------------------------------------
    --  IWF Statistic Table
    -- ------------------------------------------------------------------------
  
    hwMusaFrcIwfStatisTable	OBJECT-TYPE
	SYNTAX	SEQUENCE OF HwMusaFrcIwfStatisEntry
	ACCESS	not-accessible
	STATUS	mandatory
	DESCRIPTION
	" This table contains Iwf Statis"
    ::= { hwMusaFrcMib 10 }
           
    hwMusaFrcIwfStatisEntry    OBJECT-TYPE
        SYNTAX   HwMusaFrcIwfStatisEntry
        ACCESS   not-accessible
        STATUS   mandatory
        DESCRIPTION
        "This list contains Iwf Statistic."
        INDEX { hwMusaFrameIndex,
                hwMusaSlotIndex,
                hwMusaFrcIwfCcid}
    ::= { hwMusaFrcIwfStatisTable  1}        
    
   HwMusaFrcIwfStatisEntry     ::= SEQUENCE  {
            hwMusaFrcPvcType            INTEGER,   
            hwMusaFrcPortId             INTEGER,
            hwMusaFrcPortDlci            INTEGER,
            hwMusaFrcUpInFrames          Counter,
            hwMusaFrcUpInBytes          Counter,
            hwMusaFrcUpInDiscards          Counter,
            hwMusaFrcUpOutFrames          Counter,
            hwMusaFrcUpOutBytes          Counter,
            hwMusaFrcUpOutDiscards          Counter,
            hwMusaFrcAtmPort          INTEGER,
            hwMusaFrcAtmPortDlci          INTEGER,
            hwMusaFrcDownInFrames          Counter,
            hwMusaFrcDownInBytes          Counter,
            hwMusaFrcDownInDiscards          Counter,
            hwMusaFrcDownOutFrames          Counter,
            hwMusaFrcDownOutBytes          Counter,
            hwMusaFrcDownOutDiscards          Counter,
            hwMusaFrcIwfActive          INTEGER
            }
            
   hwMusaFrcPvcType       OBJECT-TYPE
	SYNTAX	INTEGER{
	                networkiwf(0),
	                serviceiwf(1),
	                hdlc(2),
	                ppp(3)
	                }
	ACCESS	read-write
	STATUS	mandatory
	DESCRIPTION
	"pvc type."
    ::= { hwMusaFrcIwfStatisEntry 1 }                  
            
   hwMusaFrcPortId       OBJECT-TYPE
	SYNTAX	INTEGER
	ACCESS	read-write
	STATUS	mandatory
	DESCRIPTION
	"Fr Port type."
    ::= { hwMusaFrcIwfStatisEntry 2 } 
            
   hwMusaFrcPortDlci       OBJECT-TYPE
	SYNTAX	INTEGER
	ACCESS	read-write
	STATUS	mandatory
	DESCRIPTION
	"Fr Port DLCI."
    ::= { hwMusaFrcIwfStatisEntry 3 } 
            
   hwMusaFrcUpInFrames       OBJECT-TYPE
	SYNTAX	Counter
	ACCESS	read-write
	STATUS	mandatory
	DESCRIPTION
	"Fr in package."
    ::= { hwMusaFrcIwfStatisEntry 4 }     
            
   hwMusaFrcUpInBytes       OBJECT-TYPE
	SYNTAX	Counter
	ACCESS	read-write
	STATUS	mandatory
	DESCRIPTION
	"Fr Port DLCI."
    ::= { hwMusaFrcIwfStatisEntry 5 }     
                
   hwMusaFrcUpInDiscards       OBJECT-TYPE
	SYNTAX	Counter
	ACCESS	read-write
	STATUS	mandatory
	DESCRIPTION
	"Fr Port DLCI."
    ::= { hwMusaFrcIwfStatisEntry 6 }  
            
   hwMusaFrcUpOutFrames       OBJECT-TYPE
	SYNTAX	Counter
	ACCESS	read-write
	STATUS	mandatory
	DESCRIPTION
	"Fr in package."
    ::= { hwMusaFrcIwfStatisEntry 7 }     
            
   hwMusaFrcUpOutBytes       OBJECT-TYPE
	SYNTAX	Counter
	ACCESS	read-write
	STATUS	mandatory
	DESCRIPTION
	"Fr Port DLCI."
    ::= { hwMusaFrcIwfStatisEntry 8 }     
                
   hwMusaFrcUpOutDiscards       OBJECT-TYPE
	SYNTAX	Counter
	ACCESS	read-write
	STATUS	mandatory
	DESCRIPTION
	"Fr Port DLCI."
    ::= { hwMusaFrcIwfStatisEntry 9 }             
                    
   hwMusaFrcAtmPort       OBJECT-TYPE
	SYNTAX	INTEGER
	ACCESS	read-write
	STATUS	mandatory
	DESCRIPTION
	"Atm port."
    ::= { hwMusaFrcIwfStatisEntry 10 }                 
                    
   hwMusaFrcAtmPortDlci       OBJECT-TYPE
	SYNTAX	INTEGER
	ACCESS	read-write
	STATUS	mandatory
	DESCRIPTION
	"Atm port."
    ::= { hwMusaFrcIwfStatisEntry 11 }                        
            
   hwMusaFrcDownInFrames       OBJECT-TYPE
	SYNTAX	Counter
	ACCESS	read-write
	STATUS	mandatory
	DESCRIPTION
	"Atm port."
    ::= { hwMusaFrcIwfStatisEntry 12 } 

                    
   hwMusaFrcDownInBytes       OBJECT-TYPE
	SYNTAX	Counter
	ACCESS	read-write
	STATUS	mandatory
	DESCRIPTION
	"Atm port."
    ::= { hwMusaFrcIwfStatisEntry 13 } 

   hwMusaFrcDownInDiscards       OBJECT-TYPE
	SYNTAX	Counter
	ACCESS	read-write
	STATUS	mandatory
	DESCRIPTION
	"Atm port."
    ::= { hwMusaFrcIwfStatisEntry 14 } 

                    
   hwMusaFrcDownOutFrames       OBJECT-TYPE
	SYNTAX	Counter
	ACCESS	read-write
	STATUS	mandatory
	DESCRIPTION
	"Atm port."
    ::= { hwMusaFrcIwfStatisEntry 15 } 

   hwMusaFrcDownOutBytes       OBJECT-TYPE
	SYNTAX	Counter
	ACCESS	read-write
	STATUS	mandatory
	DESCRIPTION
	"Atm port."
    ::= { hwMusaFrcIwfStatisEntry 16 } 

                    
   hwMusaFrcDownOutDiscards       OBJECT-TYPE
	SYNTAX	Counter
	ACCESS	read-write
	STATUS	mandatory
	DESCRIPTION
	"Atm port."
    ::= { hwMusaFrcIwfStatisEntry 17 } 
                        
   hwMusaFrcIwfActive       OBJECT-TYPE
	SYNTAX	INTEGER
	ACCESS	read-write
	STATUS	mandatory
	DESCRIPTION
	"Iwf active."
    ::= { hwMusaFrcIwfStatisEntry 18 } 
    
    -- ------------------------------------------------------------------------
    --  FR board PHY port statistic table
    -- ------------------------------------------------------------------------
   
   hwMusaFrcPhyStatisGroup  OBJECT IDENTIFIER ::= { hwMusaFrcMib 11 }

    -- @@@@@@@@@@@@@@@@@@@@@@@@@@@@@@@@@@@@@@@@@@@@@@@@@@@@@@@@@@@@@@@@@@@@@@
    -- **********************************************************************
        
    -- ------------------------------------------------------------------------
    --  FR board PHY-MCC1/MCC2 statistic table
    -- ------------------------------------------------------------------------
   hwMusaFrcPhyMCCStatisTable	OBJECT-TYPE
	SYNTAX	SEQUENCE OF HwMusaFrcPhyMCCStatisEntry
	ACCESS	not-accessible
	STATUS	mandatory
	DESCRIPTION
	" This table contains Phy-MCC Statis"
    ::= { hwMusaFrcPhyStatisGroup 1 }
    
       hwMusaFrcPhyMCCStatisEntry    OBJECT-TYPE
        SYNTAX   HwMusaFrcPhyMCCStatisEntry
        ACCESS   not-accessible
        STATUS   mandatory
        DESCRIPTION
        "This list contains Phy-MCC Statistic."
        INDEX { hwMusaFrameIndex,
                hwMusaSlotIndex,
                hwMusaMccType
              }
      ::= { hwMusaFrcPhyMCCStatisTable  1}
      
       HwMusaFrcPhyMCCStatisEntry     ::= SEQUENCE  {
            hwMusaMccType             INTEGER,     
            hwMusaFrcMccTxSucc         Counter,   
            hwMusaFrcMccRxSucc         Counter,
            hwMusaFrcMccRxQOV          Counter,
            hwMusaFrcMccRxMRF          Counter,
            hwMusaFrcMccRxLRF          Counter,
            hwMusaFrcMccRxIDL          Counter,
            hwMusaFrcMccRxBSY          Counter,
            hwMusaFrcMccRxLG           Counter,
            hwMusaFrcMccRxNO           Counter,
            hwMusaFrcMccRxAB           Counter,
            hwMusaFrcMccRxCR           Counter,
            hwMusaFrcMccTxRxNID        Counter,
            hwMusaFrcMccTxQOV          Counter,
            hwMusaFrcMccTxGUN          Counter,
            hwMusaFrcMccTxGOV          Counter,
            hwMusaFrcMccTxUN           Counter,
            hwMusaFrcMccTxNoBD         Counter,
            hwMusaFrcMccRxNoBuff       Counter
            }
            
        hwMusaMccType           OBJECT-TYPE
		 SYNTAX	INTEGER { mcc1(1),
		                  mcc2(2) 
		                }
		 ACCESS	read-only
		 STATUS	mandatory
		 DESCRIPTION
		 "MCC type."
	     ::= { hwMusaFrcPhyMCCStatisEntry 1 }      
	     
	    hwMusaFrcMccTxSucc       OBJECT-TYPE
		 SYNTAX	Counter
		 ACCESS	read-only
		 STATUS	mandatory
		 DESCRIPTION
		 "The frames of MCC send successfully."
	     ::= { hwMusaFrcPhyMCCStatisEntry 2 }      
	     
      
        hwMusaFrcMccRxSucc         OBJECT-TYPE
		 SYNTAX	Counter
		 ACCESS	read-only
		 STATUS	mandatory
		 DESCRIPTION
		 "The frames of MCC reveiced successfully."
	     ::= { hwMusaFrcPhyMCCStatisEntry 3 }
	     
        hwMusaFrcMccRxQOV          OBJECT-TYPE
		 SYNTAX	Counter
		 ACCESS	read-only
		 STATUS	mandatory
		 DESCRIPTION
		 "MCC reveice queue overflow."
	     ::= { hwMusaFrcPhyMCCStatisEntry 4 }
	     
        hwMusaFrcMccRxMRF          OBJECT-TYPE
		 SYNTAX	Counter
		 ACCESS	read-only
		 STATUS	mandatory
		 DESCRIPTION
		 "The frames MCC reveiveed over the max length."
	     ::= { hwMusaFrcPhyMCCStatisEntry 5 }
	     
        hwMusaFrcMccRxLRF          OBJECT-TYPE
		 SYNTAX	Counter
		 ACCESS	read-only
		 STATUS	mandatory
		 DESCRIPTION
		 "The frames of MCC reveiveed underlength."
	     ::= { hwMusaFrcPhyMCCStatisEntry 6 }
	     
        hwMusaFrcMccRxIDL          OBJECT-TYPE
		 SYNTAX	Counter
		 ACCESS	read-only
		 STATUS	mandatory
		 DESCRIPTION
		 "The first IDELE-frame head in many frames."
	     ::= { hwMusaFrcPhyMCCStatisEntry 7 }
	     
        hwMusaFrcMccRxBSY          OBJECT-TYPE
		 SYNTAX	Counter
		 ACCESS	read-only
		 STATUS	mandatory
		 DESCRIPTION
		 "MCC has no idle BD when reveice frame."
	     ::= { hwMusaFrcPhyMCCStatisEntry 8 }
	     
        hwMusaFrcMccRxLG           OBJECT-TYPE
		 SYNTAX	Counter
		 ACCESS	read-only
		 STATUS	mandatory
		 DESCRIPTION
		 "The frames of MCC reveiveed overlength."
	     ::= { hwMusaFrcPhyMCCStatisEntry 9 }
	     
        hwMusaFrcMccRxNO           OBJECT-TYPE
		 SYNTAX	Counter
		 ACCESS	read-only
		 STATUS	mandatory
		 DESCRIPTION
		 "MCC接收到非字节对齐帧."
	     ::= { hwMusaFrcPhyMCCStatisEntry 10 }
	     
        hwMusaFrcMccRxAB           OBJECT-TYPE
		 SYNTAX	Counter
		 ACCESS	read-only
		 STATUS	mandatory
		 DESCRIPTION
		 "MCC连续收到7个比特的1."
	     ::= { hwMusaFrcPhyMCCStatisEntry 11 }
	     
        hwMusaFrcMccRxCR           OBJECT-TYPE
		 SYNTAX	Counter
		 ACCESS	read-only
		 STATUS	mandatory
		 DESCRIPTION
		 "MCC接收到CRC校验错的数据帧."
	     ::= { hwMusaFrcPhyMCCStatisEntry 12 }
	     
        hwMusaFrcMccTxRxNID        OBJECT-TYPE
		 SYNTAX	Counter
		 ACCESS	read-only
		 STATUS	mandatory
		 DESCRIPTION
		 "MCC接收到的非IDLE帧."
	     ::= { hwMusaFrcPhyMCCStatisEntry 13 }
	     
        hwMusaFrcMccTxQOV          OBJECT-TYPE
		 SYNTAX	Counter
		 ACCESS	read-only
		 STATUS	mandatory
		 DESCRIPTION
		 "MCC发送中断队列溢出."
	     ::= { hwMusaFrcPhyMCCStatisEntry 14 }
	     
        hwMusaFrcMccTxGUN          OBJECT-TYPE
		 SYNTAX	Counter
		 ACCESS	read-only
		 STATUS	mandatory
		 DESCRIPTION
		 "MCC发送低负荷."
	     ::= { hwMusaFrcPhyMCCStatisEntry 15 }
	     
        hwMusaFrcMccTxGOV          OBJECT-TYPE
		 SYNTAX	Counter
		 ACCESS	read-only
		 STATUS	mandatory
		 DESCRIPTION
		 "MCC接收超负荷."
	     ::= { hwMusaFrcPhyMCCStatisEntry 16 }
	     
        hwMusaFrcMccTxUN           OBJECT-TYPE
		 SYNTAX	Counter
		 ACCESS	read-only
		 STATUS	mandatory
		 DESCRIPTION
		 "CP指示无数据发送."
	     ::= { hwMusaFrcPhyMCCStatisEntry 17 }
	     
        hwMusaFrcMccTxNoBD         OBJECT-TYPE
		 SYNTAX	Counter
		 ACCESS	read-only
		 STATUS	mandatory
		 DESCRIPTION
		 "发送数据时所有BD满."
	     ::= { hwMusaFrcPhyMCCStatisEntry 18 }
	     
        hwMusaFrcMccRxNoBuff       OBJECT-TYPE
		 SYNTAX	Counter
		 ACCESS	read-only
		 STATUS	mandatory
		 DESCRIPTION
		 "数据接收时分配不到Buffer."
	     ::= { hwMusaFrcPhyMCCStatisEntry 19 }
        
        
    -- @@@@@@@@@@@@@@@@@@@@@@@@@@@@@@@@@@@@@@@@@@@@@@@@@@@@@@@@@@@@@@@@@@@@@@
    -- **********************************************************************
        
    -- ------------------------------------------------------------------------
    --  FR板PHY-SAR统计表
    -- ------------------------------------------------------------------------
   hwMusaFrcPhySARStatisTable	OBJECT-TYPE
	SYNTAX	SEQUENCE OF HwMusaFrcPhySARStatisEntry
	ACCESS	not-accessible
	STATUS	mandatory
	DESCRIPTION
	" This table contains Phy-SAR Statis"
    ::= { hwMusaFrcPhyStatisGroup 2 }
    
       hwMusaFrcPhySARStatisEntry    OBJECT-TYPE
        SYNTAX   HwMusaFrcPhySARStatisEntry
        ACCESS   not-accessible
        STATUS   mandatory
        DESCRIPTION
        "This list contains Phy-SAR Statistic."
        INDEX { hwMusaFrameIndex,
                hwMusaSlotIndex
              }
      ::= { hwMusaFrcPhySARStatisTable  1}  
      
     HwMusaFrcPhySARStatisEntry     ::= SEQUENCE  {
            hwMusaFrcSarSendSucc         Counter,   
            hwMusaFrcSarRecvSucc         Counter,
            hwMusaFrcSarRxErrBSY         Counter,
            hwMusaFrcSarRxErrTBNR        Counter,
            hwMusaFrcSarRxErrGRLI        Counter,
            hwMusaFrcSarRxErrGBPB        Counter,
            hwMusaFrcSarRxErrINTO        Counter,
            hwMusaFrcSarRxErrABRT        Counter,
            hwMusaFrcSarRxErrLNE         Counter,
            hwMusaFrcSarRxErrCRE         Counter,
            hwMusaFrcSarRxErrCLP         Counter,
            hwMusaFrcSarRxErrCNG         Counter,
            hwMusaFrcSarRxErrCPUU        Counter,
            hwMusaFrcSarRxErrRedLine     Counter,
            hwMusaFrcSarRxErrNoBuff      Counter,
            hwMusaFrcSarTxErrTIRU        Counter,
            hwMusaFrcSarTxErrNoBD        Counter
            }  
            
      hwMusaFrcSarSendSucc       OBJECT-TYPE
		 SYNTAX	Counter
		 ACCESS	read-only
		 STATUS	mandatory
		 DESCRIPTION
		 "SAR发送成功."
	     ::= { hwMusaFrcPhySARStatisEntry 1 }  
	     
	   hwMusaFrcSarRecvSucc         OBJECT-TYPE
		 SYNTAX	Counter
		 ACCESS	read-only
		 STATUS	mandatory
		 DESCRIPTION
		 "SAR接收成功."
	     ::= { hwMusaFrcPhySARStatisEntry 2 } 
	     
       hwMusaFrcSarRxErrBSY         OBJECT-TYPE
		 SYNTAX	Counter
		 ACCESS	read-only
		 STATUS	mandatory
		 DESCRIPTION
		 "SAR接收数据帧时无空闲BD."
	     ::= { hwMusaFrcPhySARStatisEntry 3 } 
	     
       hwMusaFrcSarRxErrTBNR        OBJECT-TYPE
		 SYNTAX	Counter
		 ACCESS	read-only
		 STATUS	mandatory
		 DESCRIPTION
		 "SAR发送时BD Buffer未准备好."
	     ::= { hwMusaFrcPhySARStatisEntry 4 } 
	     
       hwMusaFrcSarRxErrGRLI        OBJECT-TYPE
		 SYNTAX	Counter
		 ACCESS	read-only
		 STATUS	mandatory
		 DESCRIPTION
		 "全局Buffer分配到达警告线(中断方式)."
	     ::= { hwMusaFrcPhySARStatisEntry 5 } 
	     
       hwMusaFrcSarRxErrGBPB        OBJECT-TYPE
		 SYNTAX	Counter
		 ACCESS	read-only
		 STATUS	mandatory
		 DESCRIPTION
		 "全局Buffer分配Busy."
	     ::= { hwMusaFrcPhySARStatisEntry 6 } 
	     
       hwMusaFrcSarRxErrINTO        OBJECT-TYPE
		 SYNTAX	Counter
		 ACCESS	read-only
		 STATUS	mandatory
		 DESCRIPTION
		 "中断队列溢出."
	     ::= { hwMusaFrcPhySARStatisEntry 7 } 
	     
       hwMusaFrcSarRxErrABRT        OBJECT-TYPE
		 SYNTAX	Counter
		 ACCESS	read-only
		 STATUS	mandatory
		 DESCRIPTION
		 "接收到数据长度为0的数据帧."
	     ::= { hwMusaFrcPhySARStatisEntry 8 } 
	     
       hwMusaFrcSarRxErrLNE         OBJECT-TYPE
		 SYNTAX	Counter
		 ACCESS	read-only
		 STATUS	mandatory
		 DESCRIPTION
		 "接收到的AAL5数据帧PDU长度非法."
	     ::= { hwMusaFrcPhySARStatisEntry 9 } 
	     
       hwMusaFrcSarRxErrCRE         OBJECT-TYPE
		 SYNTAX	Counter
		 ACCESS	read-only
		 STATUS	mandatory
		 DESCRIPTION
		 "接收到的数据帧CRC校验错."
	     ::= { hwMusaFrcPhySARStatisEntry 10 } 
	     
       hwMusaFrcSarRxErrCLP         OBJECT-TYPE
		 SYNTAX	Counter
		 ACCESS	read-only
		 STATUS	mandatory
		 DESCRIPTION
		 "接收到的置CLP位的数据帧."
	     ::= { hwMusaFrcPhySARStatisEntry 11 } 
	     
       hwMusaFrcSarRxErrCNG         OBJECT-TYPE
		 SYNTAX	Counter
		 ACCESS	read-only
		 STATUS	mandatory
		 DESCRIPTION
		 "接收到的置拥塞位的数据帧."
	     ::= { hwMusaFrcPhySARStatisEntry 12 } 
	     
       hwMusaFrcSarRxErrCPUU        OBJECT-TYPE
		 SYNTAX	Counter
		 ACCESS	read-only
		 STATUS	mandatory
		 DESCRIPTION
		 "接收到非0的CPCS-UU+CPI."
	     ::= { hwMusaFrcPhySARStatisEntry 13 } 
	     
       hwMusaFrcSarRxErrRedLine    OBJECT-TYPE
		 SYNTAX	Counter
		 ACCESS	read-only
		 STATUS	mandatory
		 DESCRIPTION
		 "全局Buffer分配到达警告线(非中断方式)."
	     ::= { hwMusaFrcPhySARStatisEntry 14 } 
	     
       hwMusaFrcSarRxErrNoBuff      OBJECT-TYPE
		 SYNTAX	Counter
		 ACCESS	read-only
		 STATUS	mandatory
		 DESCRIPTION
		 "接收数据帧时分配不到Buffer."
	     ::= { hwMusaFrcPhySARStatisEntry 15 } 
	     
       hwMusaFrcSarTxErrTIRU        OBJECT-TYPE
		 SYNTAX	Counter
		 ACCESS	read-only
		 STATUS	mandatory
		 DESCRIPTION
		 "内部调度模式下，发送速率低负荷."
	     ::= { hwMusaFrcPhySARStatisEntry 16 } 
	     
       hwMusaFrcSarTxErrNoBD        OBJECT-TYPE
		 SYNTAX	Counter
		 ACCESS	read-only
		 STATUS	mandatory
		 DESCRIPTION
		 "发送数据帧时无空闲BD."
	     ::= { hwMusaFrcPhySARStatisEntry 17 } 
    
END
