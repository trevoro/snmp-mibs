Nortel-MsCarrier-MscPassport-DisdnNI2MIB
DEFINITIONS ::= BEGIN



IMPORTS

      OBJECT-TYPE
   FROM RFC-1212

      mscPassportMIBs
   FROM Nortel-MsCarrier-MscPassport-UsefulDefinitionsMIB

      DisplayString,
      StorageType,
      RowStatus,
      Unsigned32
   FROM Nortel-MsCarrier-MscPassport-StandardTextualConventionsMIB

      NonReplicated,
      Link
   FROM Nortel-MsCarrier-MscPassport-TextualConventionsMIB

      mscDataSigChanIndex,
      mscDataSigChan
   FROM Nortel-MsCarrier-MscPassport-DataIsdnMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DisdnNI2 Enterprise MIB."

disdnNI2MIB OBJECT IDENTIFIER ::= { mscPassportMIBs 126 }










-- DataSigChan/n NationalIsdn2
-- The Ni2 component defines the operational characteristics of the 
-- signalling channel's connection to the external equipment.

mscDataSigChanNi2 OBJECT IDENTIFIER ::= { mscDataSigChan 12 }



mscDataSigChanNi2RowStatusTable OBJECT-TYPE
   SYNTAX     SEQUENCE OF MscDataSigChanNi2RowStatusEntry
   ACCESS     not-accessible
   STATUS     mandatory
   DESCRIPTION
     "This entry controls the addition and deletion of 
      mscDataSigChanNi2 components."
::= { mscDataSigChanNi2 1 }

mscDataSigChanNi2RowStatusEntry OBJECT-TYPE
   SYNTAX     MscDataSigChanNi2RowStatusEntry
   ACCESS     not-accessible
   STATUS     mandatory
   DESCRIPTION
     "A single entry in the table represents a single 
      mscDataSigChanNi2 component."
   INDEX {
      mscDataSigChanIndex,
      mscDataSigChanNi2Index }
::= { mscDataSigChanNi2RowStatusTable 1 }

MscDataSigChanNi2RowStatusEntry ::= SEQUENCE {
   mscDataSigChanNi2RowStatus
      RowStatus,
   mscDataSigChanNi2ComponentName
      DisplayString,
   mscDataSigChanNi2StorageType
      StorageType,
   mscDataSigChanNi2Index
      NonReplicated }

mscDataSigChanNi2RowStatus OBJECT-TYPE
   SYNTAX     RowStatus 
   ACCESS     read-write
   STATUS     mandatory
   DESCRIPTION
     "This variable is used as the basis for SNMP naming of
      mscDataSigChanNi2 components.
      These components can be added and deleted."
::= { mscDataSigChanNi2RowStatusEntry 1 }

mscDataSigChanNi2ComponentName OBJECT-TYPE
   SYNTAX     DisplayString 
   ACCESS     read-only
   STATUS     mandatory
   DESCRIPTION
     "This variable provides the component's string name for
      use with the ASCII Console Interface"
::= { mscDataSigChanNi2RowStatusEntry 2 }

mscDataSigChanNi2StorageType OBJECT-TYPE
   SYNTAX     StorageType 
   ACCESS     read-only
   STATUS     mandatory
   DESCRIPTION
     "This variable represents the storage type value for the
      mscDataSigChanNi2 tables."
::= { mscDataSigChanNi2RowStatusEntry 4 }

mscDataSigChanNi2Index OBJECT-TYPE
   SYNTAX     NonReplicated 
   ACCESS     not-accessible
   STATUS     mandatory
   DESCRIPTION
     "This variable represents the index for the mscDataSigChanNi2 tables."
::= { mscDataSigChanNi2RowStatusEntry 10 }

mscDataSigChanNi2L2Table OBJECT-TYPE
   SYNTAX     SEQUENCE OF MscDataSigChanNi2L2Entry
   ACCESS     not-accessible
   STATUS     mandatory
   DESCRIPTION
     "This group represents the provisionable Layer 2 attributes of the 
      Q931 CCITT protocol."
::= { mscDataSigChanNi2 11 }

mscDataSigChanNi2L2Entry OBJECT-TYPE
   SYNTAX     MscDataSigChanNi2L2Entry
   ACCESS     not-accessible
   STATUS     mandatory
   DESCRIPTION
     "An entry in the mscDataSigChanNi2L2Table."
   INDEX {
      mscDataSigChanIndex,
      mscDataSigChanNi2Index }
::= { mscDataSigChanNi2L2Table 1 }

MscDataSigChanNi2L2Entry ::= SEQUENCE {
   mscDataSigChanNi2T23
      Unsigned32,
   mscDataSigChanNi2T200
      Unsigned32,
   mscDataSigChanNi2N200
      Unsigned32,
   mscDataSigChanNi2T203
      Unsigned32,
   mscDataSigChanNi2N201
      Unsigned32,
   mscDataSigChanNi2CircuitSwitchedK
      Unsigned32 }

mscDataSigChanNi2T23 OBJECT-TYPE
   SYNTAX     Unsigned32 (1..15)
   ACCESS     read-write
   STATUS     mandatory
   DESCRIPTION
     "This attribute specifies the layer2 enable request timer."
   DEFVAL     { 10 }
::= { mscDataSigChanNi2L2Entry 1 }

mscDataSigChanNi2T200 OBJECT-TYPE
   SYNTAX     Unsigned32 (1..20)
   ACCESS     read-write
   STATUS     mandatory
   DESCRIPTION
     "This attribute specifies the maximum time between a layer 2 frame 
      and its acknowledgement"
   DEFVAL     { 2 }
::= { mscDataSigChanNi2L2Entry 2 }

mscDataSigChanNi2N200 OBJECT-TYPE
   SYNTAX     Unsigned32 (1..8)
   ACCESS     read-write
   STATUS     mandatory
   DESCRIPTION
     "This attribute specifies the maximum number of re-transmissions of 
      a layer2 frame."
   DEFVAL     { 3 }
::= { mscDataSigChanNi2L2Entry 3 }

mscDataSigChanNi2T203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { mscDataSigChanNi2L2Entry 4 }

mscDataSigChanNi2N201 OBJECT-TYPE
   SYNTAX     Unsigned32 (4..260)
   ACCESS     read-write
   STATUS     mandatory
   DESCRIPTION
     "This attribute specifies the maximum number of octets in an 
      information field."
   DEFVAL     { 260 }
::= { mscDataSigChanNi2L2Entry 5 }

mscDataSigChanNi2CircuitSwitchedK OBJECT-TYPE
   SYNTAX     Unsigned32 (1..632)
   ACCESS     read-write
   STATUS     mandatory
   DESCRIPTION
     "This attribute specifies the maximum number of frames for B 
      channel use."
   DEFVAL     { 7 }
::= { mscDataSigChanNi2L2Entry 6 }

mscDataSigChanNi2ProvTable OBJECT-TYPE
   SYNTAX     SEQUENCE OF MscDataSigChanNi2ProvEntry
   ACCESS     not-accessible
   STATUS     mandatory
   DESCRIPTION
     "This group defines the general options of the d-channel signalling 
      link."
::= { mscDataSigChanNi2 13 }

mscDataSigChanNi2ProvEntry OBJECT-TYPE
   SYNTAX     MscDataSigChanNi2ProvEntry
   ACCESS     not-accessible
   STATUS     mandatory
   DESCRIPTION
     "An entry in the mscDataSigChanNi2ProvTable."
   INDEX {
      mscDataSigChanIndex,
      mscDataSigChanNi2Index }
::= { mscDataSigChanNi2ProvTable 1 }

MscDataSigChanNi2ProvEntry ::= SEQUENCE {
   mscDataSigChanNi2Side
      INTEGER }

mscDataSigChanNi2Side OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { mscDataSigChanNi2ProvEntry 1 }

mscDataSigChanNi2OperTable OBJECT-TYPE
   SYNTAX     SEQUENCE OF MscDataSigChanNi2OperEntry
   ACCESS     not-accessible
   STATUS     mandatory
   DESCRIPTION
     "This group provides the operational attributes for the signalling 
      protocol."
::= { mscDataSigChanNi2 15 }

mscDataSigChanNi2OperEntry OBJECT-TYPE
   SYNTAX     MscDataSigChanNi2OperEntry
   ACCESS     not-accessible
   STATUS     mandatory
   DESCRIPTION
     "An entry in the mscDataSigChanNi2OperTable."
   INDEX {
      mscDataSigChanIndex,
      mscDataSigChanNi2Index }
::= { mscDataSigChanNi2OperTable 1 }

MscDataSigChanNi2OperEntry ::= SEQUENCE {
   mscDataSigChanNi2ActiveChannels
      Unsigned32,
   mscDataSigChanNi2PeakActiveChannels
      Unsigned32,
   mscDataSigChanNi2DChanStatus
      INTEGER }

mscDataSigChanNi2ActiveChannels OBJECT-TYPE
   SYNTAX     Unsigned32 (0..128)
   ACCESS     read-only
   STATUS     mandatory
   DESCRIPTION
     "This attribute indicates the number of currently active channels. 
      This includes data and voice channels."
   DEFVAL     { 0 }
::= { mscDataSigChanNi2OperEntry 1 }

mscDataSigChanNi2PeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { mscDataSigChanNi2OperEntry 4 }

mscDataSigChanNi2DChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { mscDataSigChanNi2OperEntry 7 }

mscDataSigChanNi2ToolsTable OBJECT-TYPE
   SYNTAX     SEQUENCE OF MscDataSigChanNi2ToolsEntry
   ACCESS     not-accessible
   STATUS     mandatory
   DESCRIPTION
     "This group contains a series of operational attributes which turn on 
      and off several kinds of tracing."
::= { mscDataSigChanNi2 16 }

mscDataSigChanNi2ToolsEntry OBJECT-TYPE
   SYNTAX     MscDataSigChanNi2ToolsEntry
   ACCESS     not-accessible
   STATUS     mandatory
   DESCRIPTION
     "An entry in the mscDataSigChanNi2ToolsTable."
   INDEX {
      mscDataSigChanIndex,
      mscDataSigChanNi2Index }
::= { mscDataSigChanNi2ToolsTable 1 }

MscDataSigChanNi2ToolsEntry ::= SEQUENCE {
   mscDataSigChanNi2Tracing
      OCTET STRING }

mscDataSigChanNi2Tracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { mscDataSigChanNi2ToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

mscDataSigChanNi2Framer OBJECT IDENTIFIER ::= { mscDataSigChanNi2 2 }



mscDataSigChanNi2FramerRowStatusTable OBJECT-TYPE
   SYNTAX     SEQUENCE OF MscDataSigChanNi2FramerRowStatusEntry
   ACCESS     not-accessible
   STATUS     mandatory
   DESCRIPTION
     "This entry controls the addition and deletion of 
      mscDataSigChanNi2Framer components."
::= { mscDataSigChanNi2Framer 1 }

mscDataSigChanNi2FramerRowStatusEntry OBJECT-TYPE
   SYNTAX     MscDataSigChanNi2FramerRowStatusEntry
   ACCESS     not-accessible
   STATUS     mandatory
   DESCRIPTION
     "A single entry in the table represents a single 
      mscDataSigChanNi2Framer component."
   INDEX {
      mscDataSigChanIndex,
      mscDataSigChanNi2Index,
      mscDataSigChanNi2FramerIndex }
::= { mscDataSigChanNi2FramerRowStatusTable 1 }

MscDataSigChanNi2FramerRowStatusEntry ::= SEQUENCE {
   mscDataSigChanNi2FramerRowStatus
      RowStatus,
   mscDataSigChanNi2FramerComponentName
      DisplayString,
   mscDataSigChanNi2FramerStorageType
      StorageType,
   mscDataSigChanNi2FramerIndex
      NonReplicated }

mscDataSigChanNi2FramerRowStatus OBJECT-TYPE
   SYNTAX     RowStatus 
   ACCESS     read-only
   STATUS     mandatory
   DESCRIPTION
     "This variable is used as the basis for SNMP naming of
      mscDataSigChanNi2Framer components.
      These components cannot be added nor deleted."
::= { mscDataSigChanNi2FramerRowStatusEntry 1 }

mscDataSigChanNi2FramerComponentName OBJECT-TYPE
   SYNTAX     DisplayString 
   ACCESS     read-only
   STATUS     mandatory
   DESCRIPTION
     "This variable provides the component's string name for
      use with the ASCII Console Interface"
::= { mscDataSigChanNi2FramerRowStatusEntry 2 }

mscDataSigChanNi2FramerStorageType OBJECT-TYPE
   SYNTAX     StorageType 
   ACCESS     read-only
   STATUS     mandatory
   DESCRIPTION
     "This variable represents the storage type value for the
      mscDataSigChanNi2Framer tables."
::= { mscDataSigChanNi2FramerRowStatusEntry 4 }

mscDataSigChanNi2FramerIndex OBJECT-TYPE
   SYNTAX     NonReplicated 
   ACCESS     not-accessible
   STATUS     mandatory
   DESCRIPTION
     "This variable represents the index for the mscDataSigChanNi2Framer tables."
::= { mscDataSigChanNi2FramerRowStatusEntry 10 }

mscDataSigChanNi2FramerProvTable OBJECT-TYPE
   SYNTAX     SEQUENCE OF MscDataSigChanNi2FramerProvEntry
   ACCESS     not-accessible
   STATUS     mandatory
   DESCRIPTION
     "This group contains the base provisioning data for the Framer 
      component. Application or hardware interface specific provisioning 
      data is contained in other provisionable Framer groups."
::= { mscDataSigChanNi2Framer 10 }

mscDataSigChanNi2FramerProvEntry OBJECT-TYPE
   SYNTAX     MscDataSigChanNi2FramerProvEntry
   ACCESS     not-accessible
   STATUS     mandatory
   DESCRIPTION
     "An entry in the mscDataSigChanNi2FramerProvTable."
   INDEX {
      mscDataSigChanIndex,
      mscDataSigChanNi2Index,
      mscDataSigChanNi2FramerIndex }
::= { mscDataSigChanNi2FramerProvTable 1 }

MscDataSigChanNi2FramerProvEntry ::= SEQUENCE {
   mscDataSigChanNi2FramerInterfaceName
      Link }

mscDataSigChanNi2FramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscDataSigChanNi2FramerProvEntry 1 }

mscDataSigChanNi2FramerStateTable OBJECT-TYPE
   SYNTAX     SEQUENCE OF MscDataSigChanNi2FramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDataSigChanNi2Framer 12 }

mscDataSigChanNi2FramerStateEntry OBJECT-TYPE
   SYNTAX     MscDataSigChanNi2FramerStateEntry
   ACCESS     not-accessible
   STATUS     mandatory
   DESCRIPTION
     "An entry in the mscDataSigChanNi2FramerStateTable."
   INDEX {
      mscDataSigChanIndex,
      mscDataSigChanNi2Index,
      mscDataSigChanNi2FramerIndex }
::= { mscDataSigChanNi2FramerStateTable 1 }

MscDataSigChanNi2FramerStateEntry ::= SEQUENCE {
   mscDataSigChanNi2FramerAdminState
      INTEGER,
   mscDataSigChanNi2FramerOperationalState
      INTEGER,
   mscDataSigChanNi2FramerUsageState
      INTEGER }

mscDataSigChanNi2FramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDataSigChanNi2FramerStateEntry 1 }

mscDataSigChanNi2FramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDataSigChanNi2FramerStateEntry 2 }

mscDataSigChanNi2FramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDataSigChanNi2FramerStateEntry 3 }

mscDataSigChanNi2FramerStatsTable OBJECT-TYPE
   SYNTAX     SEQUENCE OF MscDataSigChanNi2FramerStatsEntry
   ACCESS     not-accessible
   STATUS     mandatory
   DESCRIPTION
     "This group contains the operational statistics data for a Framer 
      component."
::= { mscDataSigChanNi2Framer 13 }

mscDataSigChanNi2FramerStatsEntry OBJECT-TYPE
   SYNTAX     MscDataSigChanNi2FramerStatsEntry
   ACCESS     not-accessible
   STATUS     mandatory
   DESCRIPTION
     "An entry in the mscDataSigChanNi2FramerStatsTable."
   INDEX {
      mscDataSigChanIndex,
      mscDataSigChanNi2Index,
      mscDataSigChanNi2FramerIndex }
::= { mscDataSigChanNi2FramerStatsTable 1 }

MscDataSigChanNi2FramerStatsEntry ::= SEQUENCE {
   mscDataSigChanNi2FramerFrmToIf
      Unsigned32,
   mscDataSigChanNi2FramerFrmFromIf
      Unsigned32,
   mscDataSigChanNi2FramerOctetFromIf
      Unsigned32,
   mscDataSigChanNi2FramerAborts
      Unsigned32,
   mscDataSigChanNi2FramerCrcErrors
      Unsigned32,
   mscDataSigChanNi2FramerLrcErrors
      Unsigned32,
   mscDataSigChanNi2FramerNonOctetErrors
      Unsigned32,
   mscDataSigChanNi2FramerOverruns
      Unsigned32,
   mscDataSigChanNi2FramerUnderruns
      Unsigned32,
   mscDataSigChanNi2FramerLargeFrmErrors
      Unsigned32 }

mscDataSigChanNi2FramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { mscDataSigChanNi2FramerStatsEntry 1 }

mscDataSigChanNi2FramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { mscDataSigChanNi2FramerStatsEntry 2 }

mscDataSigChanNi2FramerOctetFromIf OBJECT-TYPE
   SYNTAX     Unsigned32 (0..4294967295)
   ACCESS     read-only
   STATUS     mandatory
   DESCRIPTION
     "The number of bytes received from the link interface by Framer."
   DEFVAL     { 0 }
::= { mscDataSigChanNi2FramerStatsEntry 3 }

mscDataSigChanNi2FramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { mscDataSigChanNi2FramerStatsEntry 4 }

mscDataSigChanNi2FramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { mscDataSigChanNi2FramerStatsEntry 5 }

mscDataSigChanNi2FramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { mscDataSigChanNi2FramerStatsEntry 6 }

mscDataSigChanNi2FramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { mscDataSigChanNi2FramerStatsEntry 7 }

mscDataSigChanNi2FramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { mscDataSigChanNi2FramerStatsEntry 8 }

mscDataSigChanNi2FramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { mscDataSigChanNi2FramerStatsEntry 9 }

mscDataSigChanNi2FramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { mscDataSigChanNi2FramerStatsEntry 10 }




-- 
-- Version and Compliance statements
-- 



-- Object-Group Statement:
-- A list of all current accessible leaf objects.

-- OBJECTS { mscDataSigChanNi2DChanStatus,
--           mscDataSigChanNi2FramerAdminState,
--           mscDataSigChanNi2T203,
--           mscDataSigChanNi2FramerLrcErrors,
--           mscDataSigChanNi2CircuitSwitchedK,
--           mscDataSigChanNi2FramerLargeFrmErrors,
--           mscDataSigChanNi2FramerRowStatus,
--           mscDataSigChanNi2FramerStorageType,
--           mscDataSigChanNi2Tracing,
--           mscDataSigChanNi2RowStatus,
--           mscDataSigChanNi2N201,
--           mscDataSigChanNi2FramerFrmFromIf,
--           mscDataSigChanNi2FramerNonOctetErrors,
--           mscDataSigChanNi2PeakActiveChannels,
--           mscDataSigChanNi2FramerUsageState,
--           mscDataSigChanNi2ActiveChannels,
--           mscDataSigChanNi2FramerComponentName,
--           mscDataSigChanNi2FramerUnderruns,
--           mscDataSigChanNi2N200,
--           mscDataSigChanNi2Side,
--           mscDataSigChanNi2FramerInterfaceName,
--           mscDataSigChanNi2ComponentName,
--           mscDataSigChanNi2T23,
--           mscDataSigChanNi2FramerFrmToIf,
--           mscDataSigChanNi2FramerCrcErrors,
--           mscDataSigChanNi2StorageType,
--           mscDataSigChanNi2FramerOperationalState,
--           mscDataSigChanNi2T200,
--           mscDataSigChanNi2FramerOverruns,
--           mscDataSigChanNi2FramerOctetFromIf,
--           mscDataSigChanNi2FramerAborts }
-- STATUS  mandatory
-- DESCRIPTION
--   "A list of all current accessible leaf objects."

disdnNI2Group OBJECT IDENTIFIER ::= { disdnNI2MIB 1 }
disdnNI2GroupCA OBJECT IDENTIFIER ::= { disdnNI2Group 1 }
disdnNI2GroupCA02 OBJECT IDENTIFIER ::= { disdnNI2GroupCA 3 }
disdnNI2GroupCA02A OBJECT IDENTIFIER ::= { disdnNI2GroupCA02 2 }



-- Agent-Capabilities Statement:

-- PRODUCT-RELEASE "MscPassport Release 1.2 DisdnNI2."
-- STATUS          mandatory
-- DESCRIPTION     "Carrier Passport DisdnNI2 MIB: MIB Version CA02A,
--                  Software Version CA02S9C."
-- SUPPORTS        Nortel-MsCarrier-MscPassport-DisdnNI2MIB
--    INCLUDES     { disdnNI2GroupCA02A }

disdnNI2Capabilities OBJECT IDENTIFIER ::= { disdnNI2MIB 3 }
disdnNI2CapabilitiesCA OBJECT IDENTIFIER ::= { disdnNI2Capabilities 1 }
disdnNI2CapabilitiesCA02 OBJECT IDENTIFIER ::= { disdnNI2CapabilitiesCA 3 }
disdnNI2CapabilitiesCA02A OBJECT IDENTIFIER ::= { disdnNI2CapabilitiesCA02 2 }





END
