Nortel-MsCarrier-MscPassport-ModCommonMIB
DEFINITIONS ::= BEGIN



IMPORTS

      OBJECT-TYPE
   FROM RFC-1212

      mscPassportMIBs
   FROM Nortel-MsCarrier-MscPassport-UsefulDefinitionsMIB

      DisplayString,
      StorageType,
      RowStatus
   FROM Nortel-MsCarrier-MscPassport-StandardTextualConventionsMIB

      NonReplicated
   FROM Nortel-MsCarrier-MscPassport-TextualConventionsMIB

      mscMod,
      mscModIndex
   FROM Nortel-MsCarrier-MscPassport-BaseShelfMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     ModCommon Enterprise MIB."

modCommonMIB OBJECT IDENTIFIER ::= { mscPassportMIBs 74 }










-- Mod FrameRelaySystem
-- The Frs component defines the overall module wide data that is 
-- applicable to the Frame Relay system.

mscModFrs OBJECT IDENTIFIER ::= { mscMod 3 }



mscModFrsRowStatusTable OBJECT-TYPE
   SYNTAX     SEQUENCE OF MscModFrsRowStatusEntry
   ACCESS     not-accessible
   STATUS     mandatory
   DESCRIPTION
     "This entry controls the addition and deletion of 
      mscModFrs components."
::= { mscModFrs 1 }

mscModFrsRowStatusEntry OBJECT-TYPE
   SYNTAX     MscModFrsRowStatusEntry
   ACCESS     not-accessible
   STATUS     mandatory
   DESCRIPTION
     "A single entry in the table represents a single 
      mscModFrs component."
   INDEX {
      mscModIndex,
      mscModFrsIndex }
::= { mscModFrsRowStatusTable 1 }

MscModFrsRowStatusEntry ::= SEQUENCE {
   mscModFrsRowStatus
      RowStatus,
   mscModFrsComponentName
      DisplayString,
   mscModFrsStorageType
      StorageType,
   mscModFrsIndex
      NonReplicated }

mscModFrsRowStatus OBJECT-TYPE
   SYNTAX     RowStatus 
   ACCESS     read-only
   STATUS     mandatory
   DESCRIPTION
     "This variable is used as the basis for SNMP naming of
      mscModFrs components.
      These components cannot be added nor deleted."
::= { mscModFrsRowStatusEntry 1 }

mscModFrsComponentName OBJECT-TYPE
   SYNTAX     DisplayString 
   ACCESS     read-only
   STATUS     mandatory
   DESCRIPTION
     "This variable provides the component's string name for
      use with the ASCII Console Interface"
::= { mscModFrsRowStatusEntry 2 }

mscModFrsStorageType OBJECT-TYPE
   SYNTAX     StorageType 
   ACCESS     read-only
   STATUS     mandatory
   DESCRIPTION
     "This variable represents the storage type value for the
      mscModFrs tables."
::= { mscModFrsRowStatusEntry 4 }

mscModFrsIndex OBJECT-TYPE
   SYNTAX     NonReplicated 
   ACCESS     not-accessible
   STATUS     mandatory
   DESCRIPTION
     "This variable represents the index for the mscModFrs tables."
::= { mscModFrsRowStatusEntry 10 }




-- 
-- Version and Compliance statements
-- 



-- Object-Group Statement:
-- A list of all current accessible leaf objects.

-- OBJECTS { mscModFrsStorageType,
--           mscModFrsRowStatus,
--           mscModFrsComponentName }
-- STATUS  mandatory
-- DESCRIPTION
--   "A list of all current accessible leaf objects."

modCommonGroup OBJECT IDENTIFIER ::= { modCommonMIB 1 }
modCommonGroupCA OBJECT IDENTIFIER ::= { modCommonGroup 1 }
modCommonGroupCA02 OBJECT IDENTIFIER ::= { modCommonGroupCA 3 }
modCommonGroupCA02A OBJECT IDENTIFIER ::= { modCommonGroupCA02 2 }



-- Agent-Capabilities Statement:

-- PRODUCT-RELEASE "MscPassport Release 1.2 ModCommon."
-- STATUS          mandatory
-- DESCRIPTION     "Carrier Passport ModCommon MIB: MIB Version CA02A,
--                  Software Version CA02S9C."
-- SUPPORTS        Nortel-MsCarrier-MscPassport-ModCommonMIB
--    INCLUDES     { modCommonGroupCA02A }

modCommonCapabilities OBJECT IDENTIFIER ::= { modCommonMIB 3 }
modCommonCapabilitiesCA OBJECT IDENTIFIER ::= { modCommonCapabilities 1 }
modCommonCapabilitiesCA02 OBJECT IDENTIFIER ::= { modCommonCapabilitiesCA 3 }
modCommonCapabilitiesCA02A OBJECT IDENTIFIER ::= { modCommonCapabilitiesCA02 2 }





END
