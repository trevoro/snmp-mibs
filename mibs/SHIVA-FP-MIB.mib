-- 	$Id: shiva-fp.asn,v 1.7 1996/02/13 11:01:49 sdaigle Exp $

--
-- 	Copyright 1992, 1993, 1995, 1996 Shiva Corporation
--

--
--	Shiva FastPath MIB variables
--

SHIVA-FP-MIB DEFINITIONS ::= BEGIN

    IMPORTS
	Counter, TimeTicks
  		FROM RFC1155-SMI
	DisplayString
		FROM RFC1213-MIB
	OBJECT-TYPE
		FROM RFC-1212		-- Concise MIB Definitions
	fastpath
		FROM SHIVA-MIB;

    fpBuffer	OBJECT IDENTIFIER ::= { fastpath 1 }
    fpConf	OBJECT IDENTIFIER ::= { fastpath 2 }
    k-star	OBJECT IDENTIFIER ::= { fastpath 3 } -- for sysObjectID

	bufferSize OBJECT-TYPE
	    SYNTAX  INTEGER
	    ACCESS  read-only
	    STATUS  mandatory
	    DESCRIPTION
	    	"The size of the buffers in the buffer pool.
		All buffers are the same size."
	::= { fpBuffer 1 }

	bufferAvail OBJECT-TYPE
	    SYNTAX  INTEGER
	    ACCESS  read-only
	    STATUS  mandatory
	    DESCRIPTION
	    	"The total number of buffers initialized.  This does
	    	not indicate the number of currently free buffers.
	    	Rather it is the total number of buffers which were
	    	created and made free at boot time."
	    ::= { fpBuffer 2 }

	bufferDrops OBJECT-TYPE
	    SYNTAX  Counter
	    ACCESS  read-only
	    STATUS  mandatory
	    DESCRIPTION
	    	"The total number of times that a buffer was requested
	    	when none was available."
	    ::= { fpBuffer 3 }

	bufferTypeTable OBJECT-TYPE
	    SYNTAX  SEQUENCE OF BufferTypeEntry
	    ACCESS  not-accessible
	    STATUS  mandatory
	    DESCRIPTION
		"Each row of this table describes statistics on buffers
		allocated for a specific purpose. The sum of bufferTypeCount
		for all rows should always equal the bufferAvail count."
	    ::= { fpBuffer 4 }

	bufferTypeEntry OBJECT-TYPE
	    SYNTAX  BufferTypeEntry
	    ACCESS  not-accessible
	    STATUS  mandatory
	    DESCRIPTION
		"The object type of the rows in bufferTypeTable."
	    INDEX { bufferTypeIndex }
	::= { bufferTypeTable 1 }

	BufferTypeEntry ::= SEQUENCE {
	    bufferTypeIndex	INTEGER,
	    bufferTypeType	INTEGER,
	    bufferTypeDescr	DisplayString,
	    bufferTypeCount	INTEGER,
	    bufferTypeDrops	INTEGER,	-- should have been Counter
	    bufferTypeRequests	INTEGER,	-- should have been Counter
	    bufferTypeMaximum	INTEGER		-- should have been Gauge?
	}

	bufferTypeIndex OBJECT-TYPE
	    SYNTAX  INTEGER
	    ACCESS  read-only
	    STATUS  mandatory
	    DESCRIPTION
	    	"The enumeration of each buffer type row."
	    ::= { bufferTypeEntry 1 }

	bufferTypeType OBJECT-TYPE
	    SYNTAX  INTEGER {
		other(1),
		free(2),	-- free for anyone to use
		localtalk(3),	-- received localtalk data
		ethernet(4),	-- received ethernet data
		arp(5),		-- Address Resolution Protocol
		data(6),	-- general data (packets under construction)
		erbf(7),	-- available for ethernet receive
		etbf(8),	-- awaiting ethernet transmit complete
		malloc(9),	-- long-term storage
		serial(10),	-- received serial (SLIP/PPP) data
		tokenring(11)	-- received token ring data
	    }
	    ACCESS  read-only
	    STATUS  mandatory
	    DESCRIPTION
		"enumerated type of buffer type."
	    ::= { bufferTypeEntry 2 }

	bufferTypeDescr OBJECT-TYPE
	    SYNTAX  DisplayString
	    ACCESS  read-only
	    STATUS  mandatory
	    DESCRIPTION
		"Text description of buffer type."
	    ::= { bufferTypeEntry 3 }

	bufferTypeCount OBJECT-TYPE
	    SYNTAX  INTEGER
	    ACCESS  read-only
	    STATUS  mandatory
	    DESCRIPTION
		"The number of buffers of the type which is described by
		the value of bufferTypeType for this row."
	    ::= { bufferTypeEntry 4 }

	bufferTypeDrops OBJECT-TYPE
	    SYNTAX  INTEGER		-- should have been Counter
	    ACCESS  read-only
	    STATUS  mandatory
	    DESCRIPTION
		"The number of requests for buffers this type which were
		not fulfilled because no free buffers were available."
	    ::= { bufferTypeEntry 5 }

	bufferTypeRequests OBJECT-TYPE
	    SYNTAX  INTEGER			-- should have been Counter
	    ACCESS  read-only
	    STATUS  mandatory
	    DESCRIPTION
		"The number of times buffers of this type were requested."
	    ::= { bufferTypeEntry 6 }

	bufferTypeMaximum OBJECT-TYPE
	    SYNTAX  INTEGER		-- Should have been Gauge?
	    ACCESS  read-only
	    STATUS  mandatory
	    DESCRIPTION
		"A high water mark for buffers of this type.
		This number represents the greatest number of buffers
		of this type ever allocated concurrently."
	    ::= { bufferTypeEntry 7 }

-- The FastPath System Configuration Group.

-- The FastPath has other configuration variables in other parts of
-- this and other MIBS.  These variables are those which are
-- exclusivley associated with the FastPath architecture/OS, and not
-- with any specific protocol or function supported by the device.

	confReboot OBJECT-TYPE
	    SYNTAX  TimeTicks
	    ACCESS  read-write
	    STATUS  mandatory
	    DESCRIPTION
		"The amount of time, in hundredths of a second, until the
		device reboots itself."
	    ::= { fpConf 1 }

	confCheckSum OBJECT-TYPE
	    SYNTAX  INTEGER { valid(1), invalid(2) }
	    ACCESS  read-write
	    STATUS  mandatory
	    DESCRIPTION
		"Indicates the validity of the FastPath's configuration.  If
		written to, allows the management station to flush the
		configuration (by setting invalid), or to protect it (by
		setting valid)."
	    ::= { fpConf 2 }

	codeCheckSum OBJECT-TYPE
	    SYNTAX  INTEGER  { valid(1), invalid(2) }
	    ACCESS  read-write
	    STATUS  mandatory
	    DESCRIPTION
		"Indicates the validity of the FastPath's downloaded image.
		If written to, allows the management station to flush the
		downloaded image (by setting invalid), or to protect the
		it (by setting valid)."
	    ::= { fpConf 3 }

	promVersion OBJECT-TYPE
	    SYNTAX  INTEGER
	    ACCESS  read-only
	    STATUS  mandatory
	    DESCRIPTION
		"The version number of the PROM multiplied by 100, for
		instance, PROM version 4.1 would return 410."
	    ::= { fpConf 4 }

	hwStatus OBJECT-TYPE
	    SYNTAX  INTEGER
	    ACCESS  read-only
	    STATUS  mandatory
	    DESCRIPTION
	    	"This integer is a bit mask which holds the following flags:
		(not all bits are valid for all products)
			0x00000001 - LocalTalk failed tests
			0x00000002 - LAN controller failed tests
			0x00000004 - The battery is low
			0x00000008 - Expansion RAM is present
			0x00000010 - Ethernet 12V Fuse blown
			0x00000020 - Expansion RAM failed tests
			0x00000040 - Disable Enet CRS jumper installed
			0x00000080 - Disable Enet SQE jumper installed
			0x00000100 - Software Jumper 1 installed
			0x00000200 - Software Jumper 2 installed
			0x00000400 - Software Jumper 3 installed
			0x00000800 - Software Jumper 4 installed
			0x00007000 - EtherModule type field
			0x00008000 - EtherModule type field is valid
			0x00010000 - RAM Bank 3 is present
			0x00020000 - RAM Bank 3 failed tests
			0x00040000 - RAM Bank 4 is present
			0x00080000 - RAM Bank 4 failed tests
			0x00100000 - Downloader mode
			0x00200000 - Software Jumper 5 installed
			0x00400000 - Hardware has LocalTalk IOP
			0x00800000 - VROM on top of 'sam' PROM
			0x01000000 - Auxiliary memory board present
			0x02000000 - Auxiliary memory board failed tests."
	    ::= { fpConf 5 }

	confWhyReboot OBJECT-TYPE
	    SYNTAX  INTEGER {
	        other(1),		-- none of the following
	        hardware(2),		-- hardware maintenance
	        firmware(3),		-- firmware maintenance
		software(4),		-- software maintenance
		config(5)		-- configuration change
	}
	ACCESS  read-write
	STATUS  mandatory
	DESCRIPTION
		"Reason code for reboot scheduled by confReboot"
	    ::= { fpConf 6 }

    confWhoReboot OBJECT-TYPE
	SYNTAX  DisplayString
	ACCESS  read-write
	STATUS  mandatory
	DESCRIPTION
		"Person responsible for reboot scheduled by confReboot"
	::= { fpConf 7 }

    confRebootComment OBJECT-TYPE
	SYNTAX  DisplayString
	ACCESS  read-write
	STATUS  mandatory
	DESCRIPTION
		"Comment string for reboot scheduled by confReboot"
	::= { fpConf 8 }

    confHowReboot OBJECT-TYPE
	SYNTAX  INTEGER {
		cold(1),		-- reboot, checking conf and code sums
		warm(2),		-- immediate restart w/o checking sums
		ramdl(3),		-- stay in PROM/VROM mode
		reset(4),		-- reset code and configuration
		romdl(5),		-- reboot to BOOTPROM (FP5 only)
		dl(6),			-- download w/o clearing config
		bstrap(7)		-- jump to bootstrap (IBEAM only)
	}
	ACCESS  read-write
	STATUS  mandatory
	DESCRIPTION
		"Action taken when reboot scheduled by confReboot occurs"
	::= { fpConf 9 }

    confSerialNum OBJECT-TYPE
	SYNTAX  INTEGER
	ACCESS  read-write
	STATUS  mandatory
	DESCRIPTION
		"FastPath Serial Number"
	::= { fpConf 10 }

-- Add new variables to shiva-conf.asn, not here!!

END
