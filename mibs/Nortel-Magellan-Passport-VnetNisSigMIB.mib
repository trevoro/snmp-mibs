Nortel-Magellan-Passport-VnetNisSigMIB
DEFINITIONS ::= BEGIN



IMPORTS

      OBJECT-TYPE
   FROM RFC-1212

      passportMIBs
   FROM Nortel-Magellan-Passport-UsefulDefinitionsMIB

      DisplayString,
      StorageType,
      RowStatus,
      Unsigned32
   FROM Nortel-Magellan-Passport-StandardTextualConventionsMIB

      NonReplicated,
      Link
   FROM Nortel-Magellan-Passport-TextualConventionsMIB

      sigChanIndex,
      sigChan
   FROM Nortel-Magellan-Passport-VoiceNetworkingMIB;




-- LAST-UPDATED   "9904150000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     VnetNisSig Enterprise MIB."

vnetNisSigMIB OBJECT IDENTIFIER ::= { passportMIBs 112 }










-- SigChan/n NisSig
-- The NisSig component defines the operational characteristics of the 
-- signalling channel's connection to the external equipment.

sigChanNis OBJECT IDENTIFIER ::= { sigChan 8 }



sigChanNisRowStatusTable OBJECT-TYPE
   SYNTAX     SEQUENCE OF SigChanNisRowStatusEntry
   ACCESS     not-accessible
   STATUS     mandatory
   DESCRIPTION
     "This entry controls the addition and deletion of 
      sigChanNis components."
::= { sigChanNis 1 }

sigChanNisRowStatusEntry OBJECT-TYPE
   SYNTAX     SigChanNisRowStatusEntry
   ACCESS     not-accessible
   STATUS     mandatory
   DESCRIPTION
     "A single entry in the table represents a single 
      sigChanNis component."
   INDEX {
      sigChanIndex,
      sigChanNisIndex }
::= { sigChanNisRowStatusTable 1 }

SigChanNisRowStatusEntry ::= SEQUENCE {
   sigChanNisRowStatus
      RowStatus,
   sigChanNisComponentName
      DisplayString,
   sigChanNisStorageType
      StorageType,
   sigChanNisIndex
      NonReplicated }

sigChanNisRowStatus OBJECT-TYPE
   SYNTAX     RowStatus 
   ACCESS     read-write
   STATUS     mandatory
   DESCRIPTION
     "This variable is used as the basis for SNMP naming of
      sigChanNis components.
      These components can be added and deleted."
::= { sigChanNisRowStatusEntry 1 }

sigChanNisComponentName OBJECT-TYPE
   SYNTAX     DisplayString 
   ACCESS     read-only
   STATUS     mandatory
   DESCRIPTION
     "This variable provides the component's string name for
      use with the ASCII Console Interface"
::= { sigChanNisRowStatusEntry 2 }

sigChanNisStorageType OBJECT-TYPE
   SYNTAX     StorageType 
   ACCESS     read-only
   STATUS     mandatory
   DESCRIPTION
     "This variable represents the storage type value for the
      sigChanNis tables."
::= { sigChanNisRowStatusEntry 4 }

sigChanNisIndex OBJECT-TYPE
   SYNTAX     NonReplicated 
   ACCESS     not-accessible
   STATUS     mandatory
   DESCRIPTION
     "This variable represents the index for the sigChanNis tables."
::= { sigChanNisRowStatusEntry 10 }

sigChanNisL2Table OBJECT-TYPE
   SYNTAX     SEQUENCE OF SigChanNisL2Entry
   ACCESS     not-accessible
   STATUS     mandatory
   DESCRIPTION
     "This group specifies the provisionable layer 2 attributes of the 
      Q.931 ITU-T protocol."
::= { sigChanNis 11 }

sigChanNisL2Entry OBJECT-TYPE
   SYNTAX     SigChanNisL2Entry
   ACCESS     not-accessible
   STATUS     mandatory
   DESCRIPTION
     "An entry in the sigChanNisL2Table."
   INDEX {
      sigChanIndex,
      sigChanNisIndex }
::= { sigChanNisL2Table 1 }

SigChanNisL2Entry ::= SEQUENCE {
   sigChanNisT23
      Unsigned32,
   sigChanNisT200
      Unsigned32,
   sigChanNisN200
      Unsigned32,
   sigChanNisT203
      Unsigned32,
   sigChanNisCircuitSwitchedK
      Unsigned32 }

sigChanNisT23 OBJECT-TYPE
   SYNTAX     Unsigned32 (1..15)
   ACCESS     read-write
   STATUS     mandatory
   DESCRIPTION
     "This attribute specifies the layer 2 enable request timer."
   DEFVAL     { 10 }
::= { sigChanNisL2Entry 1 }

sigChanNisT200 OBJECT-TYPE
   SYNTAX     Unsigned32 (1..20)
   ACCESS     read-write
   STATUS     mandatory
   DESCRIPTION
     "This attribute specifies the maximum time between a layer 2 frame 
      and its acknowledgment."
   DEFVAL     { 1 }
::= { sigChanNisL2Entry 2 }

sigChanNisN200 OBJECT-TYPE
   SYNTAX     Unsigned32 (1..8)
   ACCESS     read-write
   STATUS     mandatory
   DESCRIPTION
     "This attribute specifies the maximum number of re-transmissions of 
      a layer 2 frame."
   DEFVAL     { 3 }
::= { sigChanNisL2Entry 3 }

sigChanNisT203 OBJECT-TYPE
   SYNTAX     Unsigned32 (2..40)
   ACCESS     read-write
   STATUS     mandatory
   DESCRIPTION
     "This attribute specifies the maximum time for which layer 2 frames 
      may be absent. Expiry triggers a check on whether the far end is 
      alive."
   DEFVAL     { 10 }
::= { sigChanNisL2Entry 4 }

sigChanNisCircuitSwitchedK OBJECT-TYPE
   SYNTAX     Unsigned32 (1..127)
   ACCESS     read-write
   STATUS     mandatory
   DESCRIPTION
     "This attribute specifies the maximum number of sequentially 
      numbered I frames (that is, window size (k)) that may be 
      unacknowledged at any given time for a SAP supporting primary 
      rate (64kbit/sec) signalling."
   DEFVAL     { 7 }
::= { sigChanNisL2Entry 6 }

sigChanNisL3Table OBJECT-TYPE
   SYNTAX     SEQUENCE OF SigChanNisL3Entry
   ACCESS     not-accessible
   STATUS     mandatory
   DESCRIPTION
     "This group represents the provisionable Layer 3 timer attributes of a 
      the Nis signalling protocol."
::= { sigChanNis 12 }

sigChanNisL3Entry OBJECT-TYPE
   SYNTAX     SigChanNisL3Entry
   ACCESS     not-accessible
   STATUS     mandatory
   DESCRIPTION
     "An entry in the sigChanNisL3Table."
   INDEX {
      sigChanIndex,
      sigChanNisIndex }
::= { sigChanNisL3Table 1 }

SigChanNisL3Entry ::= SEQUENCE {
   sigChanNisT309
      Unsigned32,
   sigChanNisT310
      Unsigned32 }

sigChanNisT309 OBJECT-TYPE
   SYNTAX     Unsigned32 (15..120)
   ACCESS     read-write
   STATUS     mandatory
   DESCRIPTION
     "This attribute specifies the data link failure timer; used to ride out 
      temporary failures."
   DEFVAL     { 90 }
::= { sigChanNisL3Entry 3 }

sigChanNisT310 OBJECT-TYPE
   SYNTAX     Unsigned32 (10..120)
   ACCESS     read-write
   STATUS     mandatory
   DESCRIPTION
     "This attribute specifies the call proceeding state timer."
   DEFVAL     { 10 }
::= { sigChanNisL3Entry 4 }

sigChanNisProvTable OBJECT-TYPE
   SYNTAX     SEQUENCE OF SigChanNisProvEntry
   ACCESS     not-accessible
   STATUS     mandatory
   DESCRIPTION
     "This group defines the general options of the D-channel signalling 
      link."
::= { sigChanNis 13 }

sigChanNisProvEntry OBJECT-TYPE
   SYNTAX     SigChanNisProvEntry
   ACCESS     not-accessible
   STATUS     mandatory
   DESCRIPTION
     "An entry in the sigChanNisProvTable."
   INDEX {
      sigChanIndex,
      sigChanNisIndex }
::= { sigChanNisProvTable 1 }

SigChanNisProvEntry ::= SEQUENCE {
   sigChanNisSide
      INTEGER,
   sigChanNisMaxNonCallConcurrent
      Unsigned32 }

sigChanNisSide OBJECT-TYPE
   SYNTAX     INTEGER  {
                 network(1),
                 user(2) }
   ACCESS     read-write
   STATUS     mandatory
   DESCRIPTION
     "This attribute specifies whether the interface is the network or user 
      side of the connection. The parameter applies to both the layer 2 
      and layer 3 of the interface. If this attribute is set to network, then 
      the interface is master during channel negotiation. If this attribute is 
      set to user, then the interface is slave during channel negotiation."
   DEFVAL     { network }
::= { sigChanNisProvEntry 1 }

sigChanNisMaxNonCallConcurrent OBJECT-TYPE
   SYNTAX     Unsigned32 (1..30)
   ACCESS     read-write
   STATUS     mandatory
   DESCRIPTION
     "This attribute specifies the maximum number of simultaneous active 
      non-call messages that are allowed."
   DEFVAL     { 30 }
::= { sigChanNisProvEntry 2 }

sigChanNisStateTable OBJECT-TYPE
   SYNTAX     SEQUENCE OF SigChanNisStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { sigChanNis 14 }

sigChanNisStateEntry OBJECT-TYPE
   SYNTAX     SigChanNisStateEntry
   ACCESS     not-accessible
   STATUS     mandatory
   DESCRIPTION
     "An entry in the sigChanNisStateTable."
   INDEX {
      sigChanIndex,
      sigChanNisIndex }
::= { sigChanNisStateTable 1 }

SigChanNisStateEntry ::= SEQUENCE {
   sigChanNisAdminState
      INTEGER,
   sigChanNisOperationalState
      INTEGER,
   sigChanNisUsageState
      INTEGER }

sigChanNisAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { sigChanNisStateEntry 1 }

sigChanNisOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { sigChanNisStateEntry 2 }

sigChanNisUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { sigChanNisStateEntry 3 }

sigChanNisStatsTable OBJECT-TYPE
   SYNTAX     SEQUENCE OF SigChanNisStatsEntry
   ACCESS     not-accessible
   STATUS     mandatory
   DESCRIPTION
     "This group provides the operational components for the NisSig 
      component."
::= { sigChanNis 15 }

sigChanNisStatsEntry OBJECT-TYPE
   SYNTAX     SigChanNisStatsEntry
   ACCESS     not-accessible
   STATUS     mandatory
   DESCRIPTION
     "An entry in the sigChanNisStatsTable."
   INDEX {
      sigChanIndex,
      sigChanNisIndex }
::= { sigChanNisStatsTable 1 }

SigChanNisStatsEntry ::= SEQUENCE {
   sigChanNisTotalCallsToIf
      Unsigned32,
   sigChanNisTotalCallsFromIf
      Unsigned32,
   sigChanNisNonCallAssocSessionsToIf
      Unsigned32,
   sigChanNisNonCallAssocSessionsFromIf
      Unsigned32 }

sigChanNisTotalCallsToIf OBJECT-TYPE
   SYNTAX     Unsigned32 (0..4294967295)
   ACCESS     read-only
   STATUS     mandatory
   DESCRIPTION
     "This attribute counts the total number of calls that have been made 
      to the interface. The value wraps when it reaches its maximum."
   DEFVAL     { 0 }
::= { sigChanNisStatsEntry 2 }

sigChanNisTotalCallsFromIf OBJECT-TYPE
   SYNTAX     Unsigned32 (0..4294967295)
   ACCESS     read-only
   STATUS     mandatory
   DESCRIPTION
     "This attribute counts the total number of calls from the interface. 
      The value wraps when it reaches its maximum."
   DEFVAL     { 0 }
::= { sigChanNisStatsEntry 3 }

sigChanNisNonCallAssocSessionsToIf OBJECT-TYPE
   SYNTAX     Unsigned32 (0..4294967295)
   ACCESS     read-only
   STATUS     mandatory
   DESCRIPTION
     "This attribute counts the total number of non-call associated 
      sessions to the interface. The value wraps when it reaches its 
      maximum."
   DEFVAL     { 0 }
::= { sigChanNisStatsEntry 4 }

sigChanNisNonCallAssocSessionsFromIf OBJECT-TYPE
   SYNTAX     Unsigned32 (0..4294967295)
   ACCESS     read-only
   STATUS     mandatory
   DESCRIPTION
     "This attribute counts the total number of non-call associated 
      sessions from the interface. The value wraps when it reaches its 
      maximum."
   DEFVAL     { 0 }
::= { sigChanNisStatsEntry 5 }

sigChanNisOperTable OBJECT-TYPE
   SYNTAX     SEQUENCE OF SigChanNisOperEntry
   ACCESS     not-accessible
   STATUS     mandatory
   DESCRIPTION
     "This group provides the operational attributes for the NisSig 
      protocol."
::= { sigChanNis 16 }

sigChanNisOperEntry OBJECT-TYPE
   SYNTAX     SigChanNisOperEntry
   ACCESS     not-accessible
   STATUS     mandatory
   DESCRIPTION
     "An entry in the sigChanNisOperTable."
   INDEX {
      sigChanIndex,
      sigChanNisIndex }
::= { sigChanNisOperTable 1 }

SigChanNisOperEntry ::= SEQUENCE {
   sigChanNisActiveChannels
      Unsigned32,
   sigChanNisActiveVoiceChannels
      Unsigned32,
   sigChanNisActiveDataChannels
      Unsigned32,
   sigChanNisPeakActiveChannels
      Unsigned32,
   sigChanNisPeakActiveVoiceChannels
      Unsigned32,
   sigChanNisPeakActiveDataChannels
      Unsigned32,
   sigChanNisDChanStatus
      INTEGER }

sigChanNisActiveChannels OBJECT-TYPE
   SYNTAX     Unsigned32 (0..128)
   ACCESS     read-only
   STATUS     mandatory
   DESCRIPTION
     "This attribute indicates the number of currently active channels. 
      This includes data and voice channels."
   DEFVAL     { 0 }
::= { sigChanNisOperEntry 1 }

sigChanNisActiveVoiceChannels OBJECT-TYPE
   SYNTAX     Unsigned32 (0..128)
   ACCESS     read-only
   STATUS     mandatory
   DESCRIPTION
     "This attribute indicates the number of channels that are currently 
      carrying voice."
   DEFVAL     { 0 }
::= { sigChanNisOperEntry 2 }

sigChanNisActiveDataChannels OBJECT-TYPE
   SYNTAX     Unsigned32 (0..128)
   ACCESS     read-only
   STATUS     mandatory
   DESCRIPTION
     "This attribute indicates the number of channels that are currently 
      carrying data. This does not include modem data."
   DEFVAL     { 0 }
::= { sigChanNisOperEntry 3 }

sigChanNisPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { sigChanNisOperEntry 4 }

sigChanNisPeakActiveVoiceChannels OBJECT-TYPE
   SYNTAX     Unsigned32 (0..128)
   ACCESS     read-only
   STATUS     mandatory
   DESCRIPTION
     "This attribute indicates the maximum number of voice channels that 
      have been active on this signalling channel during the last polling 
      period."
   DEFVAL     { 0 }
::= { sigChanNisOperEntry 5 }

sigChanNisPeakActiveDataChannels OBJECT-TYPE
   SYNTAX     Unsigned32 (0..128)
   ACCESS     read-only
   STATUS     mandatory
   DESCRIPTION
     "This attribute indicates the maximum number of data channels that 
      have been active on this signalling channel during the last polling 
      period."
   DEFVAL     { 0 }
::= { sigChanNisOperEntry 6 }

sigChanNisDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being 
      rei-initialized."
::= { sigChanNisOperEntry 7 }

sigChanNisToolsTable OBJECT-TYPE
   SYNTAX     SEQUENCE OF SigChanNisToolsEntry
   ACCESS     not-accessible
   STATUS     mandatory
   DESCRIPTION
     "This contains a series of operational attributes which turn on and off 
      several kinds of tracing."
::= { sigChanNis 17 }

sigChanNisToolsEntry OBJECT-TYPE
   SYNTAX     SigChanNisToolsEntry
   ACCESS     not-accessible
   STATUS     mandatory
   DESCRIPTION
     "An entry in the sigChanNisToolsTable."
   INDEX {
      sigChanIndex,
      sigChanNisIndex }
::= { sigChanNisToolsTable 1 }

SigChanNisToolsEntry ::= SEQUENCE {
   sigChanNisTracing
      OCTET STRING }

sigChanNisTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously.  
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { sigChanNisToolsEntry 1 }

sigChanNisNisSpecificProvTable OBJECT-TYPE
   SYNTAX     SEQUENCE OF SigChanNisNisSpecificProvEntry
   ACCESS     not-accessible
   STATUS     mandatory
   DESCRIPTION
     "This group provides NIS protocol specific provisioning."
::= { sigChanNis 18 }

sigChanNisNisSpecificProvEntry OBJECT-TYPE
   SYNTAX     SigChanNisNisSpecificProvEntry
   ACCESS     not-accessible
   STATUS     mandatory
   DESCRIPTION
     "An entry in the sigChanNisNisSpecificProvTable."
   INDEX {
      sigChanIndex,
      sigChanNisIndex }
::= { sigChanNisNisSpecificProvTable 1 }

SigChanNisNisSpecificProvEntry ::= SEQUENCE {
   sigChanNisChanMaintenanceHandling
      INTEGER }

sigChanNisChanMaintenanceHandling OBJECT-TYPE
   SYNTAX     INTEGER  {
                 globalOnStartup(0),
                 serviceMessage(1),
                 restartMessage(2) }
   ACCESS     read-write
   STATUS     mandatory
   DESCRIPTION
     "This attribute specifies how channel maintenance events should be 
      handled upon startup. Channel maintenance events include locking 
      and unlocking a channel or channel registration. The decision is 
      either to send individual channel RESTART messages, SERVICE 
      messages, or nothing. Note that channel registration only occurs 
      after the global interface restart at startup.
      
      Setting this attribute to enable SERVICE messages ensures that 
      SERVICE messages occur at startup and whenever a channel goes 
      into or out of service. If this attribute is not set to enable SERVICE 
      messaging, a RESTART is always sent on unlocking a channel.
      
      globalOnStartup provides the minimum required functionality at 
      startup, without any individual channel confirmation. Note that 
      when this is set, channel RESTART is still used for channel unlock. 
      globalOnStartup applies to SigChan startup only.
      
      serviceMessage enables sending and receiving SERVICE messages. 
      If this attribute is set to serviceMessage, SERVICE messages are 
      used for channel maintenance on channel lock, channel unlock, and 
      startup.
      
      restartMessage specifies that individual channel RESTARTs when 
      the SigChan starts up. If this attribute is set to restartMessage, a 
      RESTART message is used to send at startup and channel unlock."
   DEFVAL     { restartMessage }
::= { sigChanNisNisSpecificProvEntry 1 }


-- SigChan/n Nis Framer
-- 
-- The Framer component controls link layer framing for application 
-- components sending and receiving data on a link interface. It is also 
-- through Framer, that an application component is associated with a 
-- specific hardware link interface.
-- 
-- The Framer component provides provisionable attributes related to 
-- data path aspects of the hardware interface (such as crc and frame 
-- length). The Framer component also provides a provisionable 
-- attribute which binds the application component to a specific 
-- hardware component.
-- 
-- The Framer component contains operational attributes for link 
-- interface data path statistics (such as frame counts and aborts).
-- 

sigChanNisFramer OBJECT IDENTIFIER ::= { sigChanNis 2 }



sigChanNisFramerRowStatusTable OBJECT-TYPE
   SYNTAX     SEQUENCE OF SigChanNisFramerRowStatusEntry
   ACCESS     not-accessible
   STATUS     mandatory
   DESCRIPTION
     "This entry controls the addition and deletion of 
      sigChanNisFramer components."
::= { sigChanNisFramer 1 }

sigChanNisFramerRowStatusEntry OBJECT-TYPE
   SYNTAX     SigChanNisFramerRowStatusEntry
   ACCESS     not-accessible
   STATUS     mandatory
   DESCRIPTION
     "A single entry in the table represents a single 
      sigChanNisFramer component."
   INDEX {
      sigChanIndex,
      sigChanNisIndex,
      sigChanNisFramerIndex }
::= { sigChanNisFramerRowStatusTable 1 }

SigChanNisFramerRowStatusEntry ::= SEQUENCE {
   sigChanNisFramerRowStatus
      RowStatus,
   sigChanNisFramerComponentName
      DisplayString,
   sigChanNisFramerStorageType
      StorageType,
   sigChanNisFramerIndex
      NonReplicated }

sigChanNisFramerRowStatus OBJECT-TYPE
   SYNTAX     RowStatus 
   ACCESS     read-only
   STATUS     mandatory
   DESCRIPTION
     "This variable is used as the basis for SNMP naming of
      sigChanNisFramer components.
      These components cannot be added nor deleted."
::= { sigChanNisFramerRowStatusEntry 1 }

sigChanNisFramerComponentName OBJECT-TYPE
   SYNTAX     DisplayString 
   ACCESS     read-only
   STATUS     mandatory
   DESCRIPTION
     "This variable provides the component's string name for
      use with the ASCII Console Interface"
::= { sigChanNisFramerRowStatusEntry 2 }

sigChanNisFramerStorageType OBJECT-TYPE
   SYNTAX     StorageType 
   ACCESS     read-only
   STATUS     mandatory
   DESCRIPTION
     "This variable represents the storage type value for the
      sigChanNisFramer tables."
::= { sigChanNisFramerRowStatusEntry 4 }

sigChanNisFramerIndex OBJECT-TYPE
   SYNTAX     NonReplicated 
   ACCESS     not-accessible
   STATUS     mandatory
   DESCRIPTION
     "This variable represents the index for the sigChanNisFramer tables."
::= { sigChanNisFramerRowStatusEntry 10 }

sigChanNisFramerProvTable OBJECT-TYPE
   SYNTAX     SEQUENCE OF SigChanNisFramerProvEntry
   ACCESS     not-accessible
   STATUS     mandatory
   DESCRIPTION
     "This group contains the base provisioning data for the Framer 
      component. Application or hardware interface specific provisioning 
      data is contained in other provisionable Framer groups."
::= { sigChanNisFramer 10 }

sigChanNisFramerProvEntry OBJECT-TYPE
   SYNTAX     SigChanNisFramerProvEntry
   ACCESS     not-accessible
   STATUS     mandatory
   DESCRIPTION
     "An entry in the sigChanNisFramerProvTable."
   INDEX {
      sigChanIndex,
      sigChanNisIndex,
      sigChanNisFramerIndex }
::= { sigChanNisFramerProvTable 1 }

SigChanNisFramerProvEntry ::= SEQUENCE {
   sigChanNisFramerInterfaceName
      Link }

sigChanNisFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { sigChanNisFramerProvEntry 1 }

sigChanNisFramerStateTable OBJECT-TYPE
   SYNTAX     SEQUENCE OF SigChanNisFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { sigChanNisFramer 12 }

sigChanNisFramerStateEntry OBJECT-TYPE
   SYNTAX     SigChanNisFramerStateEntry
   ACCESS     not-accessible
   STATUS     mandatory
   DESCRIPTION
     "An entry in the sigChanNisFramerStateTable."
   INDEX {
      sigChanIndex,
      sigChanNisIndex,
      sigChanNisFramerIndex }
::= { sigChanNisFramerStateTable 1 }

SigChanNisFramerStateEntry ::= SEQUENCE {
   sigChanNisFramerAdminState
      INTEGER,
   sigChanNisFramerOperationalState
      INTEGER,
   sigChanNisFramerUsageState
      INTEGER }

sigChanNisFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { sigChanNisFramerStateEntry 1 }

sigChanNisFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { sigChanNisFramerStateEntry 2 }

sigChanNisFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { sigChanNisFramerStateEntry 3 }

sigChanNisFramerStatsTable OBJECT-TYPE
   SYNTAX     SEQUENCE OF SigChanNisFramerStatsEntry
   ACCESS     not-accessible
   STATUS     mandatory
   DESCRIPTION
     "This group contains the operational statistics data for a Framer 
      component."
::= { sigChanNisFramer 13 }

sigChanNisFramerStatsEntry OBJECT-TYPE
   SYNTAX     SigChanNisFramerStatsEntry
   ACCESS     not-accessible
   STATUS     mandatory
   DESCRIPTION
     "An entry in the sigChanNisFramerStatsTable."
   INDEX {
      sigChanIndex,
      sigChanNisIndex,
      sigChanNisFramerIndex }
::= { sigChanNisFramerStatsTable 1 }

SigChanNisFramerStatsEntry ::= SEQUENCE {
   sigChanNisFramerFrmToIf
      Unsigned32,
   sigChanNisFramerFrmFromIf
      Unsigned32,
   sigChanNisFramerOctetFromIf
      Unsigned32,
   sigChanNisFramerAborts
      Unsigned32,
   sigChanNisFramerCrcErrors
      Unsigned32,
   sigChanNisFramerLrcErrors
      Unsigned32,
   sigChanNisFramerNonOctetErrors
      Unsigned32,
   sigChanNisFramerOverruns
      Unsigned32,
   sigChanNisFramerUnderruns
      Unsigned32,
   sigChanNisFramerLargeFrmErrors
      Unsigned32 }

sigChanNisFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { sigChanNisFramerStatsEntry 1 }

sigChanNisFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { sigChanNisFramerStatsEntry 2 }

sigChanNisFramerOctetFromIf OBJECT-TYPE
   SYNTAX     Unsigned32 (0..4294967295)
   ACCESS     read-only
   STATUS     mandatory
   DESCRIPTION
     "The number of bytes received from the link interface by Framer."
   DEFVAL     { 0 }
::= { sigChanNisFramerStatsEntry 3 }

sigChanNisFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { sigChanNisFramerStatsEntry 4 }

sigChanNisFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { sigChanNisFramerStatsEntry 5 }

sigChanNisFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { sigChanNisFramerStatsEntry 6 }

sigChanNisFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { sigChanNisFramerStatsEntry 7 }

sigChanNisFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { sigChanNisFramerStatsEntry 8 }

sigChanNisFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { sigChanNisFramerStatsEntry 9 }

sigChanNisFramerLargeFrmErrors OBJECT-TYPE
   SYNTAX     Unsigned32 (0..4294967295)
   ACCESS     read-only
   STATUS     mandatory
   DESCRIPTION
     "This attribute counts the total number of frames received which 
      were too large (longer than 500 bytes).
      This count wraps to zero after reaching its maximum value."
   DEFVAL     { 0 }
::= { sigChanNisFramerStatsEntry 10 }




-- 
-- Version and Compliance statements
-- 



-- Object-Group Statement:
-- A list of all current accessible leaf objects.

-- OBJECTS { sigChanNisChanMaintenanceHandling,
--           sigChanNisActiveVoiceChannels,
--           sigChanNisT310,
--           sigChanNisFramerOctetFromIf,
--           sigChanNisRowStatus,
--           sigChanNisFramerOverruns,
--           sigChanNisDChanStatus,
--           sigChanNisMaxNonCallConcurrent,
--           sigChanNisNonCallAssocSessionsFromIf,
--           sigChanNisPeakActiveVoiceChannels,
--           sigChanNisSide,
--           sigChanNisNonCallAssocSessionsToIf,
--           sigChanNisActiveChannels,
--           sigChanNisFramerUsageState,
--           sigChanNisActiveDataChannels,
--           sigChanNisFramerInterfaceName,
--           sigChanNisFramerComponentName,
--           sigChanNisUsageState,
--           sigChanNisFramerLargeFrmErrors,
--           sigChanNisN200,
--           sigChanNisTotalCallsToIf,
--           sigChanNisFramerFrmToIf,
--           sigChanNisComponentName,
--           sigChanNisTotalCallsFromIf,
--           sigChanNisT23,
--           sigChanNisPeakActiveDataChannels,
--           sigChanNisCircuitSwitchedK,
--           sigChanNisFramerCrcErrors,
--           sigChanNisStorageType,
--           sigChanNisFramerOperationalState,
--           sigChanNisT200,
--           sigChanNisT309,
--           sigChanNisFramerAborts,
--           sigChanNisOperationalState,
--           sigChanNisFramerLrcErrors,
--           sigChanNisT203,
--           sigChanNisFramerFrmFromIf,
--           sigChanNisFramerNonOctetErrors,
--           sigChanNisPeakActiveChannels,
--           sigChanNisFramerAdminState,
--           sigChanNisFramerRowStatus,
--           sigChanNisTracing,
--           sigChanNisFramerUnderruns,
--           sigChanNisAdminState,
--           sigChanNisFramerStorageType }
-- STATUS  mandatory
-- DESCRIPTION
--   "A list of all current accessible leaf objects."

vnetNisSigGroup OBJECT IDENTIFIER ::= { vnetNisSigMIB 1 }
vnetNisSigGroupBE OBJECT IDENTIFIER ::= { vnetNisSigGroup 5 }
vnetNisSigGroupBE01 OBJECT IDENTIFIER ::= { vnetNisSigGroupBE 2 }
vnetNisSigGroupBE01A OBJECT IDENTIFIER ::= { vnetNisSigGroupBE01 2 }



-- Agent-Capabilities Statement:

-- PRODUCT-RELEASE "Passport Release 7.0 VnetNisSig."
-- STATUS          mandatory
-- DESCRIPTION     "VnetNisSig MIB: MIB Version BE01A,
--                  Software Version BG00S4C."
-- SUPPORTS        Nortel-Magellan-Passport-VnetNisSigMIB
--    INCLUDES     { vnetNisSigGroupBE01A }

vnetNisSigCapabilities OBJECT IDENTIFIER ::= { vnetNisSigMIB 3 }
vnetNisSigCapabilitiesBE OBJECT IDENTIFIER ::= { vnetNisSigCapabilities 5 }
vnetNisSigCapabilitiesBE01 OBJECT IDENTIFIER ::= { vnetNisSigCapabilitiesBE 2 }
vnetNisSigCapabilitiesBE01A OBJECT IDENTIFIER ::= { vnetNisSigCapabilitiesBE01 2 }





END
