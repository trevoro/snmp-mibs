-- $Header: avas.doc 1.0 95/06/07 $

-->#
--># Copyright (C) Siemens AG 1998
-->#               All rights reserved
-->#
-->#protocol specification
-->%PROTOCOL SNMP
-->#
-->#configuration
-->%REMCONFIG NO
-->%REMOPERATION NO
-->#
-- ###################################################################
-- Modification Record:
--
--   Date   | Version    | Description
-- ---------+------------+--------------------------------------------
-- 07.06.95 |       1    | Creation
-- 13.10.97 |       2    | globalData; Traps
--
-- ###################################################################

-- MIB-Version: 2

AVAS-MIB DEFINITIONS ::= BEGIN

--
-- Title:   MIB for AVAS
-- Date:    September, 1995
-- Authors: N.N,                 BS2000 DC144
--                               BS2000 DC144
--


IMPORTS
	TRAP-TYPE
	    FROM RFC-1215
	enterprises
	    FROM RFC1155-SMI
	DisplayString
	    FROM RFC1213-MIB
	OBJECT-TYPE
	    FROM RFC-1212;


sni                 OBJECT IDENTIFIER ::= { enterprises 231 }
sniProductMibs      OBJECT IDENTIFIER ::= { sni 2 }
sniAVAS             OBJECT IDENTIFIER ::= { sniProductMibs 24 }
avasProc            OBJECT IDENTIFIER ::= { sniAVAS 1 }
avasNet             OBJECT IDENTIFIER ::= { sniAVAS 2 }
avasElem            OBJECT IDENTIFIER ::= { sniAVAS 3 }
avasCond            OBJECT IDENTIFIER ::= { sniAVAS 4 }
avasGlobalData      OBJECT IDENTIFIER ::= { sniAVAS 10 }
avasTraps           OBJECT IDENTIFIER ::= { sniAVAS 11 }

-- AVAS Proc

avasPSumStat           OBJECT-TYPE
	SYNTAX  INTEGER {
			  missing       (1), -- (UPAMZD || PLAMZD) not ready
			  ready         (2), -- (UPAMZD && PLAMZD) ready
			  running       (3), -- min1 RCS (ready || running)
			  errorSystem   (4), -- (UPAMZD || PLAMZD) abended
			  errorNet      (5), -- min1 net in error
	--                errorElem     (6),    min1 element in error
	--                problemNet    (7),    min1 net in problem
			  errorSignon  (50), -- signon != ok
			  unknown      (99), -- rc != ok
			  undefined   (255)  -- nicht def. Wert
			}
	ACCESS  read-only
	STATUS  mandatory
	DESCRIPTION "Summary-State of Avas"
		    -- s. AHB S. 104/105
	::= {avasProc 1}

avasPUpamStat           OBJECT-TYPE
	SYNTAX  INTEGER {
			  started    (1),
			  ready      (2),  -- betriebsbereit, ZD gestartet
			  running    (3),  -- RCS hat sich angemeldet
			  ended      (4),
			  abended    (5),
			  stop       (6),
			  hold       (7),
			  shutdown   (8),
			  kill       (9),
			  unknown   (99),
			  undefined (255)  -- nicht def. Wert
			}
	ACCESS  read-write
	STATUS  mandatory
	DESCRIPTION "State of Process : UPAM-ZD"
		    -- s. AHB S. 104/105
	::= {avasProc 2}

avasPPlamStat           OBJECT-TYPE
	SYNTAX  INTEGER {
			  started    (1),
			  ready      (2),  -- betriebsbereit, ZD gestartet
			  running    (3),  -- RCS hat sich angemeldet
			  ended      (4),
			  abended    (5),
			  stop       (6),
			  hold       (7),
			  shutdown   (8),
			  kill       (9),
			  unknown   (99),
			  undefined (255)  -- nicht def. Wert
			}
	ACCESS  read-write
	STATUS  mandatory
	DESCRIPTION "State of Process PLAM-ZD"
		    -- s. AHB S. 104/105
	::= {avasProc 3}

avasPCentrStat          OBJECT-TYPE
	SYNTAX  INTEGER {
			  started    (1),
			  ready      (2),
			  running    (3),
			  ended      (4),
			  abended    (5),
			  stop       (6),
			  hold       (7),
			  shutdown   (8),
			  kill       (9),
			  unknown   (99),
			  undefined (255)  -- nicht def. Wert
			}
	ACCESS  read-write
	STATUS  mandatory
	DESCRIPTION "State of CENTRAL-Process"
		    -- s. AHB S. 104/105
	::= {avasProc 4}

avasPAvakNum            OBJECT-TYPE
	SYNTAX  INTEGER
	ACCESS  read-only
	STATUS  mandatory
	DESCRIPTION "The number of entries in the table avasPAvakTab"
	::= {avasProc 5}

avasPAvakTab            OBJECT-TYPE
	SYNTAX  SEQUENCE OF AvasPAvakTabEntry
	ACCESS  not-accessible
	STATUS  mandatory
	DESCRIPTION "The AVAS AVAK table"
	::= {avasProc 6}

avasPAvakTabEntry       OBJECT-TYPE
	SYNTAX  AvasPAvakTabEntry
	ACCESS  not-accessible
	STATUS  mandatory
	DESCRIPTION "An entry in the AVAS AVAK table"
	INDEX {avasPAvakTabIndex}
	::= {avasPAvakTab 1}

AvasPAvakTabEntry ::=
	SEQUENCE {
		avasPAvakTabIndex         INTEGER,
		avasPAvakJvName           DisplayString,
		avasPAvakState            INTEGER
	}

avasPAvakTabIndex       OBJECT-TYPE
	SYNTAX  INTEGER
	ACCESS  read-only
	STATUS  mandatory
	DESCRIPTION "A unique value for each entry, its value
		     ranges between 1 and the value of avasPAvakTabNum"
	::= {avasPAvakTabEntry 1}

avasPAvakJvName         OBJECT-TYPE
	SYNTAX  DisplayString
	ACCESS  read-only
	STATUS  mandatory
	DESCRIPTION "The Name of the Job-Variable for the AVAK"
	::= {avasPAvakTabEntry 2}

avasPAvakState          OBJECT-TYPE
	SYNTAX  INTEGER {
			  started    (1),
			  ready      (2),  -- RCS gestartet, kein Netz act.
			  running    (3),  -- >=1 Netz aktiv
			  ended      (4),
			  abended    (5),
			  stop       (6),
			  hold       (7),
			  shutdown   (8),
			  kill       (9),
			  unknown   (99),
			  undefined (255)  -- nicht def. Wert
			}
	ACCESS  read-only
	STATUS  mandatory
	DESCRIPTION "State of AVAK. It's the value of the Job-Variable "
		    -- s. AHB S. 104/105
	::= {avasPAvakTabEntry 3}


-- nicht in 1. Realisierungsstufe !!! , problematisch zu erfahren  !!!!
--
--avasPUserNum            OBJECT-TYPE
--        SYNTAX  INTEGER
--        ACCESS  read-only
--        STATUS  mandatory
--        DESCRIPTION "The number of entries in the table avasPuserTab"
--        ::= {avasProc 6}
--
--avasPUserTab            OBJECT-TYPE
--        SYNTAX  SEQUENCE OF AvasPUserTabEntry
--        ACCESS  not-accessible
--        STATUS  mandatory
--        DESCRIPTION "The AVAS User table"
--        ::= {avasProc 7}
--
--avasPUserTabEntry       OBJECT-TYPE
--        SYNTAX  AvasPUserTabEntry
--        ACCESS  not-accessible
--        STATUS  mandatory
--        DESCRIPTION "An entry in the AVAS User table"
--        INDEX {avasPUserTabIndex}
--        ::= {avasPUserTab 1}
--
--AvasPUserTabEntry ::=
--        SEQUENCE {
--                avasPUserTabIndex         INTEGER,
--                avasPUserName             DisplayString,
--                avasPUserGroup            DisplayString,
--                avasPUserState            INTEGER
--        }
--
--avasPUserTabIndex       OBJECT-TYPE
--        SYNTAX  INTEGER
--        ACCESS  read-only
--        STATUS  mandatory
--        DESCRIPTION "A unique value for each entry, its value
--                     ranges between 1 and the value of avasPUserTabNum"
--        ::= {avasPUserTabEntry 1}
--
--avasPUserName           OBJECT-TYPE
--        SYNTAX  DisplayString
--        ACCESS  read-only
--        STATUS  mandatory
--        DESCRIPTION "The User Name"
--        ::= {avasPUserTabEntry 2}
--
--avasPUserGroup          OBJECT-TYPE
--        SYNTAX  DisplayString
--        ACCESS  read-only
--        STATUS  mandatory
--        DESCRIPTION "The User Group"
--        ::= {avasPUserTabEntry 3}
--
--avasPUserState          OBJECT-TYPE
--        SYNTAX  INTEGER {
--                          up    (1),
--                          down  (2),
--                          test  (3)
--                        }
--        ACCESS  read-only
--        STATUS  mandatory
--        DESCRIPTION "State of User Dialog"
--        ::= {avasPUserTabEntry 4}


-- AVAS Netze

avasNStateF              OBJECT-TYPE
	SYNTAX  INTEGER {
			  problem      (1),
			  error        (5),   -- default
			  hold         (6),
			  running      (7),
			  waiting      (8),
			  condwait     (9),
			  all        (100)    -- wahrsch. nicht praktikabel
			}
	ACCESS  read-write
	STATUS  mandatory
	DESCRIPTION "State-Flag for restriction in Show Table"
		    -- s. BHB S.407, 415, 689
		    -- kann bei Auswahl angegeben werden
	::= {avasNet 1}

avasNPatF               OBJECT-TYPE
	SYNTAX  DisplayString
	ACCESS  read-write
	STATUS  mandatory
	DESCRIPTION "Name-Pattern for restriction in Show Table"
	::= {avasNet 2}


avasNNum                OBJECT-TYPE
	SYNTAX  INTEGER
	ACCESS  read-only
	STATUS  mandatory
	DESCRIPTION "The number of entries in the table avasNTab"
	::= {avasNet 3}

avasNTab                OBJECT-TYPE
	SYNTAX  SEQUENCE OF AvasNTabEntry
	ACCESS  not-accessible
	STATUS  mandatory
	DESCRIPTION "The AVAS Net table"
	::= {avasNet 4}

avasNTabEntry           OBJECT-TYPE
	SYNTAX  AvasNTabEntry
	ACCESS  not-accessible
	STATUS  mandatory
	DESCRIPTION "An entry in the AVAS Net table"
	INDEX {avasNTabIndex}
	::= {avasNTab 1}

AvasNTabEntry ::=
	SEQUENCE {
		avasNTabIndex         INTEGER,
		avasNName             DisplayString,
		avasNStart            DisplayString,  -- nicht in 1. Stufe
		avasNState            INTEGER,
		avasNStateOfError     INTEGER, -- net state switches AHBS.255
		avasNStateOfRestart   INTEGER, -- net state switches AHBS.255
		avasNStateOfCondwait  INTEGER, -- net state switches AHBS.255
		avasNStateOfHold      INTEGER, -- net state switches AHBS.255
		avasNStartedIndex     INTEGER,        -- nicht in 1. Stufe
		avasNAvak             DisplayString,
		avasNText             DisplayString   -- nicht in 1. Stufe
	}
-- s. BHB S.407, 415!, 689

avasNTabIndex           OBJECT-TYPE
	SYNTAX  INTEGER
	ACCESS  read-only
	STATUS  mandatory
	DESCRIPTION "A unique value for each entry, its value
		     ranges between 1 and the value of avasNTabNum"
	::= {avasNTabEntry 1}

avasNName               OBJECT-TYPE
	SYNTAX  DisplayString
	ACCESS  read-only
	STATUS  mandatory
	DESCRIPTION "The Name of the Net"
	::= {avasNTabEntry 2}

avasNStart              OBJECT-TYPE                   -- nicht in 1. Stufe
	SYNTAX  DisplayString
	ACCESS  read-only
	STATUS  mandatory
	DESCRIPTION "The Start-Time of the Net"
	::= {avasNTabEntry 3}

avasNState              OBJECT-TYPE
	SYNTAX  INTEGER {
			  abended     (3),
			  ended       (4),
			  error       (5),
			  hold        (6),
			  running     (7),
			  waiting     (8),
			  condwait    (9),
			  restarted  (10),
			  resumed    (11),
			  opwait     (12),
			  ignored    (14),
			  start      (17),
			  shifted    (21),
			  unknown    (99)
			}
	ACCESS  read-only
	STATUS  mandatory
	DESCRIPTION "The State of the Net"
	::= {avasNTabEntry 4}

avasNStateOfError       OBJECT-TYPE
	SYNTAX  INTEGER {
			  yes         (1),
			  no          (2),
			  unknown    (99)
			}
	ACCESS  read-only
	STATUS  mandatory
	DESCRIPTION "An Element is of state Error"
	::= {avasNTabEntry 5}

avasNStateOfRestart     OBJECT-TYPE
	SYNTAX  INTEGER {
			  yes         (1),
			  no          (2),
			  unknown    (99)
			}
	ACCESS  read-only
	STATUS  mandatory
	DESCRIPTION "An Element is of state Restart"
	::= {avasNTabEntry 6}

avasNStateOfCondwait    OBJECT-TYPE
	SYNTAX  INTEGER {
			  yes         (1),
			  no          (2),
			  unknown    (99)
			}
	ACCESS  read-only
	STATUS  mandatory
	DESCRIPTION "An Element is of state Condwait"
	::= {avasNTabEntry 7}

avasNStateOfHold        OBJECT-TYPE
	SYNTAX  INTEGER {
			  yes         (1),
			  no          (2),
			  unknown    (99)
			}
	ACCESS  read-only
	STATUS  mandatory
	DESCRIPTION "An Element is of state Hold"
	::= {avasNTabEntry 8}

avasNAvak               OBJECT-TYPE
	SYNTAX  DisplayString
	ACCESS  read-only
	STATUS  mandatory
	DESCRIPTION "The AVAK of the Net"
	::= {avasNTabEntry 9}
						      -- nicht in 1. Stufe
avasNStartedIndex       OBJECT-TYPE
	SYNTAX  INTEGER
	ACCESS  read-only
	STATUS  mandatory
	DESCRIPTION "The smallest index of the Net"
	::= {avasNTabEntry 10}

avasNText               OBJECT-TYPE                   -- nicht in 1. Stufe
	SYNTAX  DisplayString
	ACCESS  read-only
	STATUS  mandatory
	DESCRIPTION "A short description of the Net"
	::= {avasNTabEntry 11}


-- AVAS Netzstrukturelemente: Job,Procedure , Condition

avasEEStateF          OBJECT-TYPE
	SYNTAX  INTEGER {
			  all            (1),  -- default
			  abended        (3),  -- J/P , C
			  error          (5),  -- J/P , C
			  hold           (6),  -- J/P , C
			  running-exec   (7),  -- J/P , C
			  waiting        (8),  -- J/P , C
			  skipped       (13),  -- J/P , C
			  no-occure     (23)   --       C
			}
	ACCESS  read-write
	STATUS  mandatory
	DESCRIPTION "Element-State-Flag for restriction in Show Table"
		    -- s. BHB S.418
	::= {avasElem 1}

avasEETypeF          OBJECT-TYPE
	SYNTAX  INTEGER {
			  all           (1),  -- default
			  net           (2),      --      C
			  jva           (3),      --      C
			  ext           (4),      -- J/P
			  mod           (5),      -- J/P
			  std           (6),      -- J/P
			  job           (7),      --      C
			  res           (8),      --      C
			  val           (9),      --      C
			  tim          (10)       --      C
			}
	ACCESS  read-write
	STATUS  mandatory
	DESCRIPTION "Element-Type-Flag for restriction in Show Table"
		    -- s. BHB S.418
	::= {avasElem 2}

avasEEFuncF          OBJECT-TYPE
	SYNTAX  INTEGER {
			  all        (1),
			  job        (2),
			  proc       (3),
			  comp       (4),
			  add        (5),
			  delete     (6),
			  modify     (7),
			  net        (8),
			  wait       (9)
			}
	ACCESS  read-write
	STATUS  mandatory
	DESCRIPTION "Element-Function-Flag for restriction in Show Table"
		    -- s. BHB S.418
	::= {avasElem 3}


avasENStateF              OBJECT-TYPE
	SYNTAX  INTEGER {
			  problem      (1),   -- default
			  error        (5),
			  hold         (6),
			  running      (7),
			  waiting      (8),
			  condwait     (9),
			  all        (100)    -- wahrsch. nicht praktikabel
			}
	ACCESS  read-write
	STATUS  mandatory
	DESCRIPTION "State-Flag for restriction in Show Table"
		    -- s. BHB S.407, 415, 689
		    -- kann bei Auswahl angegeben werden
	::= {avasElem 4}

avasENPatF               OBJECT-TYPE
	SYNTAX  DisplayString
	ACCESS  read-write
	STATUS  mandatory
	DESCRIPTION "Name-Pattern for restriction in Show Table"
	::= {avasElem 5}

avasENum                OBJECT-TYPE
	SYNTAX  INTEGER
	ACCESS  read-only
	STATUS  mandatory
	DESCRIPTION "The number of entries in the table avasETab"
	::= {avasElem 6}

avasETab                OBJECT-TYPE
	SYNTAX  SEQUENCE OF AvasETabEntry
	ACCESS  not-accessible
	STATUS  mandatory
	DESCRIPTION "The AVAS Element table"
	::= {avasElem 7}

avasETabEntry           OBJECT-TYPE
	SYNTAX  AvasETabEntry
	ACCESS  not-accessible
	STATUS  mandatory
	DESCRIPTION "An entry in the AVAS Element table"
	INDEX {avasETabIndex}
	::= {avasETab 1}

AvasETabEntry ::=
	SEQUENCE {
		avasETabIndex         INTEGER,
		avasEName             DisplayString,
		avasEFu               INTEGER,
		avasEType             INTEGER,
		avasEInd              INTEGER,
		avasESynInd           INTEGER,
		avasEState            INTEGER,
		avasENet              DisplayString,
		avasEDelSolution      INTEGER,
		avasELatest           DisplayString,
		avasEJva              DisplayString,  -- nicht in 1. Stufe
		avasEJvaValue         DisplayString   -- nicht in 1. Stufe
	}
-- s. BHB S.417

avasETabIndex           OBJECT-TYPE
	SYNTAX  INTEGER
	ACCESS  read-only
	STATUS  mandatory
	DESCRIPTION "A unique value for each entry, its value
		     ranges between 1 and the value of avasETabNum"
	::= {avasETabEntry 1}

avasEName               OBJECT-TYPE
	SYNTAX  DisplayString
	ACCESS  read-only
	STATUS  mandatory
	DESCRIPTION "The Name of the Element"
	::= {avasETabEntry 2}

avasEFu                 OBJECT-TYPE
	SYNTAX  INTEGER {
			  job        (2),
			  proc       (3),
			  comp       (4),
			  add        (5),
			  delete     (6),
			  modify     (7),
			  net        (8),
			  wait       (9),
			  unknown   (99)
			}
	ACCESS  read-only
	STATUS  mandatory
	DESCRIPTION "The Function of the Element"
	::= {avasETabEntry 3}

avasEType               OBJECT-TYPE
	SYNTAX  INTEGER {
			  net   (2),       --      C
			  jva   (3),       --      C
			  ext   (4),       -- J/P
			  mod   (5),       -- J/P
			  std   (6),       -- J/P
			  job   (7),       --      C
			  res   (8),       --      C
			  val   (9),       --      C
			  tim  (10),       --      C
		      unknown  (99)
			}
	ACCESS  read-only
	STATUS  mandatory
	DESCRIPTION "The Type of the Element"
	::= {avasETabEntry 4}

avasEInd                OBJECT-TYPE
	SYNTAX  INTEGER   (1..999)
	ACCESS  read-only
	STATUS  mandatory
	DESCRIPTION "The Index of the Element"
	::= {avasETabEntry 5}

avasESynInd             OBJECT-TYPE
	SYNTAX  INTEGER   (1..999)
	ACCESS  read-only
	STATUS  mandatory
	DESCRIPTION "The Index of the Element"
	::= {avasETabEntry 6}

avasEState              OBJECT-TYPE
	SYNTAX  INTEGER {
			  created      (2),       -- J/P , C
			  abended      (3),       -- J/P
			  ended        (4),       -- J/P
			  error        (5),       -- J/P , C
			  hold         (6),       -- J/P , C
			  running      (7),       -- J/P
			  waiting      (8),       -- J/P , C
			  skipped     (13),       -- J/P , C
			  ignored     (14),       -- J/P , C
			  executed    (16),       --       C
			  no-plan     (18),       -- J/P , C
			  deleted     (19),       -- J/P , C
			  no-submit   (20),       -- J/P , C
			  occurred    (22),       --       C
			  no-occure   (23),       --       C
			  error-cat   (66),       -- J/P
			  unknown     (99)        -- J/P
			}
	ACCESS  read-only
	STATUS  mandatory
	DESCRIPTION "The State of the Element"
		    -- s. BHB S. 421, 425
	::= {avasETabEntry 7}

avasENet                OBJECT-TYPE
	SYNTAX  DisplayString
	ACCESS  read-only
	STATUS  mandatory
	DESCRIPTION "The Net of the Element"
	::= {avasETabEntry 8}

avasEDelSolution        OBJECT-TYPE
	SYNTAX  INTEGER {
			  start       (1),        -- J/P , C
			  ignore      (2),        -- J/P , C
			  cancel      (3),        -- J/P , C
			 unknown      (99)        -- J/P , C
			}
	ACCESS  read-only
	STATUS  mandatory
	DESCRIPTION "Delay-Solution for this element"
	::= {avasETabEntry 9}

avasELatest             OBJECT-TYPE
	SYNTAX  DisplayString
	ACCESS  read-only
	STATUS  mandatory
	DESCRIPTION "Latest Start/ Latest Occure"  -- time
	::= {avasETabEntry 10}

-- nur Conditions & Typ == jva
avasEJva                OBJECT-TYPE                   -- nicht in 1. Stufe
	SYNTAX  DisplayString
	ACCESS  read-only
	STATUS  mandatory
	DESCRIPTION "Name of the Condition-JV"
	::= {avasETabEntry 11}

-- nur Conditions & Typ == jva
avasEJvaValue           OBJECT-TYPE                   -- nicht in 1. Stufe
	SYNTAX  DisplayString
	ACCESS  read-only
	STATUS  mandatory
	DESCRIPTION "Value of the Condition-JV"
	::= {avasETabEntry 12}


-- AVAS Conditions Descritions

avasCFlag               OBJECT-TYPE
	SYNTAX  INTEGER {
			  all       (1),
			  free      (2),
			  error     (3),
			  share     (4),
			  exclusiv  (5)      -- weitere DRo ??
			}
	ACCESS  read-write
	STATUS  mandatory
	DESCRIPTION "Flag for restriction in Show Table"
		    -- s. BHB S.113
		    -- kann bei Auswahl angegeben werden
	::= {avasCond 1}

avasCNum                OBJECT-TYPE
	SYNTAX  INTEGER
	ACCESS  read-only
	STATUS  mandatory
	DESCRIPTION "The number of entries in the table avasCTab"
	::= {avasCond 2}

avasCTab                OBJECT-TYPE
	SYNTAX  SEQUENCE OF AvasCTabEntry
	ACCESS  not-accessible
	STATUS  mandatory
	DESCRIPTION "The AVAS Condition table"
	::= {avasCond 3}

avasCTabEntry           OBJECT-TYPE
	SYNTAX  AvasCTabEntry
	ACCESS  not-accessible
	STATUS  mandatory
	DESCRIPTION "An entry in the AVAS Condition table"
	INDEX {avasCTabIndex}
	::= {avasCTab 1}

AvasCTabEntry ::=
	SEQUENCE {
		avasCTabIndex         INTEGER,
		avasCName             DisplayString,
		avasCType             INTEGER,
		avasCInd              INTEGER,
		avasCState            INTEGER,
		avasCValue            INTEGER,
		avasCCreateBy         DisplayString,
		avasCCreateDate       DisplayString,
		avasCUpdate           DisplayString,
		avasCLifeTime         DisplayString
	}
-- s. BHB S.113

avasCTabIndex           OBJECT-TYPE
	SYNTAX  INTEGER
	ACCESS  read-only
	STATUS  mandatory
	DESCRIPTION "A unique value for each entry, its value
		     ranges between 1 and the value of avasCTabNum"
	::= {avasCTabEntry 1}

avasCName               OBJECT-TYPE
	SYNTAX  DisplayString
	ACCESS  read-only
	STATUS  mandatory
	DESCRIPTION "The Name of the Condition Description"
	::= {avasCTabEntry 2}

avasCType               OBJECT-TYPE
	SYNTAX  INTEGER {
			  net     (1),
			  job     (2),
			  res     (3),
			  val     (4)
			}
	ACCESS  read-only
	STATUS  mandatory
	DESCRIPTION "The Type of the Condition Description"
	::= {avasCTabEntry 3}

avasCInd                OBJECT-TYPE
	SYNTAX  INTEGER   (1..999)
	ACCESS  read-only
	STATUS  mandatory
	DESCRIPTION "The Index of the Element"   -- nur ... BHB S.115 DRo
	::= {avasCTabEntry 4}

avasCState              OBJECT-TYPE
	SYNTAX  INTEGER {
			  created      (1),
			  deleted      (2),
			  ended        (3),
			  abended      (4),
			  free         (5),
			  error        (6),
			  ignored      (7),
			  no-plan      (8),
			  no-submit    (9),
			  skipped     (10),
			  shared      (11),
			  exclusiv    (12)
			}
	ACCESS  read-only
	STATUS  mandatory
	DESCRIPTION "The State of the Condition"
	::= {avasCTabEntry 5}

avasCValue              OBJECT-TYPE
	SYNTAX  INTEGER {
			  created      (1),  -- net job res
			  ended        (2),  -- net job
			  abended      (3),  -- net job
			  ignored      (4),  -- net job
			  free         (5),  --         res
			  error        (6),  --     job res
			  deleted      (7),  --     job
			  no-plan      (8),  --     job
			  no-submit    (9),  --     job
			  skipped     (10),  --     job
			  shared      (11),  --         res
			  exclusiv    (12),  --         res
			  value       (13)   --              val
			}
	ACCESS  read-only
	STATUS  mandatory
	DESCRIPTION "The Value of the Condition"
	::= {avasCTabEntry 6}

avasCCreateBy           OBJECT-TYPE
	SYNTAX  DisplayString
	ACCESS  read-only
	STATUS  mandatory
	DESCRIPTION "The Condition Description was created by ..."
	::= {avasCTabEntry 7}

avasCCreateDate         OBJECT-TYPE
	SYNTAX  DisplayString
	ACCESS  read-only
	STATUS  mandatory
	DESCRIPTION "Date of the Creation of Condition Description"
	::= {avasCTabEntry 8}

avasCUpdate             OBJECT-TYPE
	SYNTAX  DisplayString
	ACCESS  read-only
	STATUS  mandatory
	DESCRIPTION "Last Update of Condition Description"
	::= {avasCTabEntry 9}

avasCLifeTime           OBJECT-TYPE
	SYNTAX  DisplayString
	ACCESS  read-only
	STATUS  mandatory
	DESCRIPTION "LifeTime of Condition Description"
	::= {avasCTabEntry 10}


-- AVAS GlobalData

avasagtVersion          OBJECT-TYPE
	SYNTAX  DisplayString
	ACCESS  read-only
	STATUS  mandatory
	DESCRIPTION "Version of Avas-Subagent"
	::= {avasGlobalData 1}

avasSystemID            OBJECT-TYPE
	SYNTAX  DisplayString
	ACCESS  read-only
	STATUS  mandatory
	DESCRIPTION "Avas-SystemID"
	::= {avasGlobalData 2}


-- AVAS Traps

avasTrapData            OBJECT IDENTIFIER ::= { avasTraps 1 }

avasLastMsg             OBJECT-TYPE
	SYNTAX  DisplayString
	ACCESS  read-only
	STATUS  mandatory
	DESCRIPTION "Last Trap Message"
	::= {avasTrapData 1}

avasStateTraps          OBJECT IDENTIFIER ::= { avasTraps 10 }

avasMissing            TRAP-TYPE
	ENTERPRISE avasStateTraps
	VARIABLES   { avasSystemID,
		      avasLastMsg   }
	DESCRIPTION "(UPAMZD || PLAMZD) not ready"
	::= 301

avasReady              TRAP-TYPE
	ENTERPRISE avasStateTraps
	VARIABLES   { avasSystemID,
		      avasLastMsg   }
	DESCRIPTION "(UPAMZD && PLAMZD) ready"
	::= 302

avasRunning            TRAP-TYPE
	ENTERPRISE avasStateTraps
	VARIABLES   { avasSystemID,
		      avasLastMsg   }
	DESCRIPTION "min1 RCS (ready || running)"
	::= 303

avasErrorSystem        TRAP-TYPE
	ENTERPRISE avasStateTraps
	VARIABLES   { avasSystemID,
		      avasLastMsg   }
	DESCRIPTION "(UPAMZD || PLAMZD) abended"
	::= 304

avasErrorNet           TRAP-TYPE
	ENTERPRISE avasStateTraps
	VARIABLES   { avasSystemID,
		      avasLastMsg   }
	DESCRIPTION "min1 net in error"
	::= 305

avasProblemNet         TRAP-TYPE
	ENTERPRISE avasStateTraps
	VARIABLES   { avasSystemID,
		      avasLastMsg   }
	DESCRIPTION "min1 net in problem"
	::= 307

avasErrorSignon        TRAP-TYPE
	ENTERPRISE avasStateTraps
	VARIABLES   { avasSystemID,
		      avasLastMsg   }
	DESCRIPTION "SIGNON != ok"
	::= 350

avasProblemTraps        OBJECT IDENTIFIER ::= { avasTraps 11 }

avasNetAbended         TRAP-TYPE
	ENTERPRISE avasProblemTraps
	VARIABLES   { avasSystemID,
		      avasLastMsg   }
	DESCRIPTION "Net abended"
	::= 311

avasNetError           TRAP-TYPE
	ENTERPRISE avasProblemTraps
	VARIABLES   { avasSystemID,
		      avasLastMsg   }
	DESCRIPTION "Net error"
	::= 312

avasNetRestarted       TRAP-TYPE
	ENTERPRISE avasProblemTraps
	VARIABLES   { avasSystemID,
		      avasLastMsg   }
	DESCRIPTION "Net Restarted"
	::= 313

avasNetCancelled       TRAP-TYPE
	ENTERPRISE avasProblemTraps
	VARIABLES   { avasSystemID,
		      avasLastMsg   }
	DESCRIPTION "Net Cancelled"
	::= 314

avasJobAbended         TRAP-TYPE
	ENTERPRISE avasProblemTraps
	VARIABLES   { avasSystemID,
		      avasLastMsg   }
	DESCRIPTION "Job abended"
	::= 321

avasJobError           TRAP-TYPE
	ENTERPRISE avasProblemTraps
	VARIABLES   { avasSystemID,
		      avasLastMsg   }
	DESCRIPTION "Job error"
	::= 322

avasJobRestarted       TRAP-TYPE
	ENTERPRISE avasProblemTraps
	VARIABLES   { avasSystemID,
		      avasLastMsg   }
	DESCRIPTION "Job restarted"
	::= 323

avasJobCancelled       TRAP-TYPE
	ENTERPRISE avasProblemTraps
	VARIABLES   { avasSystemID,
		      avasLastMsg   }
	DESCRIPTION "Job cancelled"
	::= 324

avasProcAbended        TRAP-TYPE
	ENTERPRISE avasProblemTraps
	VARIABLES   { avasSystemID,
		      avasLastMsg   }
	DESCRIPTION "Procedure abended"
	::= 331

avasProcError          TRAP-TYPE
	ENTERPRISE avasProblemTraps
	VARIABLES   { avasSystemID,
		      avasLastMsg   }
	DESCRIPTION "Procedure error"
	::= 332

avasProcRestarted      TRAP-TYPE
	ENTERPRISE avasProblemTraps
	VARIABLES   { avasSystemID,
		      avasLastMsg   }
	DESCRIPTION "Procedure restarted"
	::= 333

avasProcCancelled      TRAP-TYPE
	ENTERPRISE avasProblemTraps
	VARIABLES   { avasSystemID,
		      avasLastMsg   }
	DESCRIPTION "Procedure cancelled"
	::= 334

avasUJobAbended        TRAP-TYPE
	ENTERPRISE avasProblemTraps
	VARIABLES   { avasSystemID,
		      avasLastMsg   }
	DESCRIPTION "Unix or NT Job abended"
	::= 341

avasUJobError          TRAP-TYPE
	ENTERPRISE avasProblemTraps
	VARIABLES   { avasSystemID,
		      avasLastMsg   }
	DESCRIPTION "Unix or NT Job error"
	::= 342

avasUJobRestarted      TRAP-TYPE
	ENTERPRISE avasProblemTraps
	VARIABLES   { avasSystemID,
		      avasLastMsg   }
	DESCRIPTION "Unix or NT Job restarted"
	::= 343

avasUJobCancelled      TRAP-TYPE
	ENTERPRISE avasProblemTraps
	VARIABLES   { avasSystemID,
		      avasLastMsg   }
	DESCRIPTION "Unix or NT Job cancelled"
	::= 344


END
