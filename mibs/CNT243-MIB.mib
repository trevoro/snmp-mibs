--
--
--          Computer Network Technology, Corp.
--              6000 Nathan Lane North 
--              Plymouth, Minnesota  55442   
--
--                phone:  (763) 268-6000
--                  fax:  (763) 268-6800
--              support:  1-800-NET-TECH
--                email:  cnt.com
--
--	MIB Version:     TM1.1
--	Product Family:  CNT Zeus(2) Subagent(4) ATM Forum(3) 
--
-- +------------+ if you change this mib, you increment the version number.
-- | Attention! | Also, this MIB is supported by the escon subagent, and
-- +------------+ that agent must also be compiled with this mib version.
--

CNT243-MIB DEFINITIONS ::= BEGIN

	IMPORTS
		enterprises, Counter
			FROM RFC1065-SMI
		OBJECT-TYPE
			FROM RFC-1212
			DisplayString FROM RFC1213-MIB
		cnt2Subagent
			FROM CNT2-MIB;

---     cnt		OBJECT IDENTIFIER ::= { enterprises 333 }
---     cnt2		OBJECT IDENTIFIER ::= { cnt 2 }
---     cnt2Subagent	OBJECT IDENTIFIER ::= { cnt2 4 }


        cnt2Atmf   OBJECT IDENTIFIER ::= { cnt2Subagent 3 }

	-- the ATM Forum Aggregation Table
	
	cnt2AtmfTable OBJECT-TYPE
		SYNTAX  SEQUENCE OF Cnt2AtmfEntry
		ACCESS  not-accessible
		STATUS  mandatory
		DESCRIPTION
			"A list of entries describing the mapping
			of atm interfaces.  A specific atm object is
			terminated with the slot number."
		::= { cnt2Atmf 1 }

	cnt2AtmfEntry OBJECT-TYPE
		SYNTAX  Cnt2AtmfEntry
		ACCESS  not-accessible
		STATUS  mandatory
		DESCRIPTION
			"An individual atm port entry."
		INDEX { cnt2AtmfSlot, cnt2AtmfIndex }
		::= { cnt2AtmfTable 1 }

	Cnt2AtmfEntry ::= SEQUENCE {
		cnt2AtmfSlot
			INTEGER,
		cnt2AtmfIndex
			INTEGER,
		cnt2AtmfPort
			INTEGER
	}

	cnt2AtmfSlot OBJECT-TYPE
		SYNTAX  INTEGER
		ACCESS  read-only
		STATUS  mandatory
		DESCRIPTION
			"The slot index for this atm port."
		::= { cnt2AtmfEntry 1 }

	cnt2AtmfIndex OBJECT-TYPE
		SYNTAX  INTEGER
		ACCESS  read-only
		STATUS  mandatory
		DESCRIPTION
			"The local port index for this atm port."
		::= { cnt2AtmfEntry 2 }

	cnt2AtmfPort OBJECT-TYPE
		SYNTAX  INTEGER
		ACCESS  read-only
		STATUS  mandatory
		DESCRIPTION
			"The global port index for this atm port."
		::= { cnt2AtmfEntry 3 }

	END
