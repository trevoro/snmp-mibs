Centrum-MIB DEFINITIONS ::= BEGIN


IMPORTS
    enterprises, IpAddress, Counter FROM RFC1155-SMI
    DisplayString                   FROM RFC1213-MIB
    OBJECT-TYPE                     FROM RFC-1212
    TRAP-TYPE 			    FROM RFC-1215;


centrum OBJECT IDENTIFIER ::= { enterprises 327 }
mibDoc  OBJECT IDENTIFIER ::= { centrum 1 }

centrumRemote  OBJECT IDENTIFIER ::= { mibDoc 1 }

-- groups in CentrumRemote

port    OBJECT IDENTIFIER ::= { centrumRemote 1 }
path    OBJECT IDENTIFIER ::= { centrumRemote 2 }
crip    OBJECT IDENTIFIER ::= { centrumRemote 3 }
ipx     OBJECT IDENTIFIER ::= { centrumRemote 4 }
brg     OBJECT IDENTIFIER ::= { centrumRemote 5 }
admin   OBJECT IDENTIFIER ::= { centrumRemote 6 }
crat	OBJECT IDENTIFIER ::= { centrumRemote 7 }

-- textual conventions --

-- DisplayString ::=
-- OCTET STRING
-- This type is used to model textual information --

-- PhysAddress ::=
-- OCTET STRING
-- This data type is used to model media address --

-- port group --

-- port table --

portNumber OBJECT-TYPE
    SYNTAX  INTEGER
    ACCESS  read-only
    STATUS  mandatory
    DESCRIPTION
        "The number of communication ports (not including
        console port) on this system."
    ::= { port 1 }

portTable OBJECT-TYPE
    SYNTAX  SEQUENCE OF PortEntry
    ACCESS  not-accessible
    STATUS  mandatory
    DESCRIPTION
        "Remote PC access path table."
    ::= { port 2 }

portEntry OBJECT-TYPE
    SYNTAX  PortEntry
    ACCESS  not-accessible
    STATUS  mandatory
    DESCRIPTION
        "A path to a remote PC."
    INDEX   { portIndex }
    ::= { portTable 1 }

PortEntry ::=
    SEQUENCE {
        portIndex
            INTEGER,
        portId
            INTEGER,
        portSlot
            INTEGER,
        portScriptIdx
            INTEGER,
        portBaudrate 
            INTEGER,
        portParity 
            INTEGER,
        portStopBits 
            INTEGER,
        portDataBits 
            INTEGER,
        portCCSP 
            INTEGER,
        portPPPProbeInterval 
            INTEGER,
        portPPPMaxRcvPacketLength 
            INTEGER,
        portPPPAsyncCtrlChar 
            INTEGER,
        portPPPProtCompress 
            INTEGER,
        portPPPACCompress 
            INTEGER,
        portCRCErrors 
            Counter,
        portOversizes 
            Counter,
        portUndersizes 
            Counter,
        portCollisions 
            Counter,
        portInPackets 
            Counter,
        portOutPackets 
            Counter,
        portInBytes 
            Counter,
        portOutBytes 
            Counter,
        portResetPortCounters 
            INTEGER,
        portAsyncParityErrors
            Counter,
        portAsyncCharFrameErrors
            Counter,
        portAsyncOverrunErrors
            Counter,
        portAsyncPktCksumErrors
            Counter,
        portCTSState
            INTEGER,
        portDCDState
            INTEGER,
        portRIState
            INTEGER,
        portSyncFcsErrors
            Counter,
        portSyncMemoryErrors
            Counter,
        portSyncOverrunErrors
            Counter,
        portSyncUnderrunErrors
            Counter,
        portIPCPState
            INTEGER,
        portIPXCPState
            INTEGER,
        portBNCPState
            INTEGER,
        portDriverState
            INTEGER,
        portSpeed
            INTEGER,
        portTotalErrors
            Counter,
        portTransmitDiscards
            Counter,
        portReceiveCongestions	  
            Counter,
        portUnknownProtocols
            Counter,
        portAccessType
            INTEGER,
        portDialHangUp
            INTEGER,
        portPortDisabled
            INTEGER,
        portArapCompress
            INTEGER,
-- NANTUCKET 
		portInterFace
            INTEGER,
		portLEDLink
            INTEGER,
		portLEDActivity
            INTEGER,
		portLEDFault
            INTEGER,
-- ISDN BRI 
        portLinkType
            INTEGER,
        portSwitchType
            INTEGER,
        portSPID-1
            DisplayString,
        portSPID-2
            DisplayString,
        portDirectoryNo-1
            DisplayString,
        portDirectoryNo-2
            DisplayString,
        portLocalDialNo-1
            DisplayString,
        portLocalDialNo-2
            DisplayString,
        portLocalSubaddress-1
            DisplayString,
        portLocalSubaddress-2
            DisplayString,
        portProtocolMode
            INTEGER,
        portPortReset
            INTEGER,
        portIncomingCalls
            Counter,
        portOutgoingCalls
            Counter,
        portRemoteDialNo
            DisplayString,
        portRemoteSubaddress
            DisplayString,
        portISDNInterfaceType
            DisplayString,
-- AB6.0
        portPathName
            DisplayString,
	portILCCPState
            INTEGER,
	portCurISDNBChannel
            INTEGER,
	portLoginStatus
            INTEGER,
	portLastConnectBChannel
            INTEGER,
	portISDNPhyLineStatus
            INTEGER,
	portTEIState
            INTEGER,
	portLayer3Status
            INTEGER
    }

portIndex OBJECT-TYPE
    SYNTAX  INTEGER
    ACCESS  read-only
    STATUS  mandatory
    DESCRIPTION
        "A sequentially assigned index value for each 
        communication port on this system."
    ::= { portEntry 1 }

portId OBJECT-TYPE
    SYNTAX  INTEGER
        {
            msEthernet(1),
            s1Ethernet(2),
            s1Sync(3),
            s1Async1(4),
            s1Async2(5),
            s1Async3(6),
            s1Async4(7),
            s1Async5(8),
            s1Async6(9),
            s1Async7(10),
            s1Async8(11),
            s2Ethernet(12),
            s2Sync(13),
            s2Async1(14),
            s2Async2(15),
            s2Async3(16),
            s2Async4(17),
            s2Async5(18),
            s2Async6(19),
            s2Async7(20),
            s2Async8(21),
            msTokenRing(22),
--   NANTUCKET
	    port1(30),
	    port2(31),
	    port3(32),
	    port4(33),
	    port5(34),
	    port6(35),
	    port7(36),
	    port8(37),
-- ISDN BRI
            s1Br1B1(50),
            s1Br1B2(51),
            s1Br2B1(52),
            s1Br2B2(53),
            s1Br3B1(54),
            s1Br3B2(55),
            s1Br4B1(56),
            s1Br4B2(57),
            s2Br1B1(58),
            s2Br1B2(59),
            s2Br2B1(60),
            s2Br2B2(61),
            s2Br3B1(62),
            s2Br3B2(63),
            s2Br4B1(64),
            s2Br4B2(65)
        }
    ACCESS  read-only
    STATUS  mandatory
    DESCRIPTION
        "The type of port."
    ::= { portEntry 2 }

portSlot OBJECT-TYPE
    SYNTAX  INTEGER
    ACCESS  read-only
    STATUS  mandatory
    DESCRIPTION
        "The slot that this port is on."
    ::= { portEntry 3 }

-- Async port only --

portScriptIdx OBJECT-TYPE
    SYNTAX  INTEGER
    ACCESS  read-write
    STATUS  mandatory
    DESCRIPTION
        "This index identifies the modem dial in/out script to be used
        by this async port."
    ::= { portEntry 4 }

portBaudrate OBJECT-TYPE
    SYNTAX  INTEGER
        {
            baud-2400(24),
            baud-4800(48),
            baud-9600(96),
            baud-19200(192),
            baud-38400(384),
            baud-56000(560),
            baud-57600(576),
            baud-115200(1152)
        }
    ACCESS  read-write
    STATUS  mandatory
    DESCRIPTION
        "Baudrate of this async/sync port."
    ::= { portEntry 5 }

portParity OBJECT-TYPE
    SYNTAX  INTEGER
        {
            odd(1),
            even(2),
            zero(3),
            one(4),
            none(5)
        }
    ACCESS  read-write
    STATUS  mandatory
    DESCRIPTION
        "Parity of this async port."
    ::= { portEntry 6 }

portStopBits OBJECT-TYPE
    SYNTAX  INTEGER
        {
            bit-1(1),
            bit-15(2),
            bits-2(3)
        }
    ACCESS  read-write
    STATUS  mandatory
    DESCRIPTION
        "Number of stop bits for this async port."
    ::= { portEntry 7 }

portDataBits OBJECT-TYPE
    SYNTAX  INTEGER
        {
            bits-5(5),
            bits-6(6),
            bits-7(7),
            bits-8(8)
        }
    ACCESS  read-write
    STATUS  mandatory
    DESCRIPTION
        "Number of data bits for this async port."
    ::= { portEntry 8 }

portCCSP OBJECT-TYPE
    SYNTAX  INTEGER
         {
            disabled(1),
            enabled(2)
        }
    ACCESS  read-write
    STATUS  mandatory
    DESCRIPTION
        "Enable 3Com's proprietory data compression
        algorithm."
    ::= { portEntry 9 }

portPPPProbeInterval OBJECT-TYPE
    SYNTAX  INTEGER
    ACCESS  read-write
    STATUS  mandatory
    DESCRIPTION
        "Time duration in seconds in between two consecutive
        PPP probing packets."
    ::= { portEntry 10 }

portPPPMaxRcvPacketLength OBJECT-TYPE
    SYNTAX  INTEGER
    ACCESS  read-write
    STATUS  mandatory
    DESCRIPTION
        "Maximum data field length in bytes for PPP packets."
    ::= { portEntry 11 }

portPPPAsyncCtrlChar OBJECT-TYPE
    SYNTAX  INTEGER
    ACCESS  read-write
    STATUS  mandatory
    DESCRIPTION
        "Async control character bit-map for PPP link."
    ::= { portEntry 12 }

-- portPPPMagicNumber OBJECT-TYPE ::= { portEntry 13 }

portPPPProtCompress OBJECT-TYPE
    SYNTAX  INTEGER
         {
            disabled(1),
            enabled(2)
        }
    ACCESS  read-write
    STATUS  mandatory
    DESCRIPTION
        "Enable protocol field compression for PPP packets."
    ::= { portEntry 14 }

portPPPACCompress OBJECT-TYPE
    SYNTAX  INTEGER
         {
            disabled(1),
            enabled(2)
        }
    ACCESS  read-write
    STATUS  mandatory
    DESCRIPTION
        "Enable address and control field compression for 
        PPP packets."
    ::= { portEntry 15 }

-- Ethernet port only --

portCRCErrors OBJECT-TYPE
    SYNTAX  Counter
    ACCESS  read-only
    STATUS  mandatory
    DESCRIPTION
        "Ethernet packets received with CRC error."
    ::= { portEntry 16 }

portOversizes OBJECT-TYPE
    SYNTAX  Counter
    ACCESS  read-only
    STATUS  mandatory
    DESCRIPTION
        "Ethernet packets received with size bigger than 1500 bytes."
    ::= { portEntry 17 }

portUndersizes OBJECT-TYPE
    SYNTAX  Counter
    ACCESS  read-only
    STATUS  mandatory
    DESCRIPTION
        "Ethernet packets received with size smaller than 64 bytes."
    ::= { portEntry 18 }

portCollisions OBJECT-TYPE
    SYNTAX  Counter
    ACCESS  read-only
    STATUS  mandatory
    DESCRIPTION
        "Ethernet packet transmit failures due to collision."
    ::= { portEntry 19 }

-- Ethernet port only end --

portInPackets OBJECT-TYPE
    SYNTAX  Counter
    ACCESS  read-only
    STATUS  mandatory
    DESCRIPTION
        "Packets received with no error."
    ::= { portEntry 20 }

portOutPackets OBJECT-TYPE
    SYNTAX  Counter
    ACCESS  read-only
    STATUS  mandatory
    DESCRIPTION
        "Packets transmitted with no error."
    ::= { portEntry 21 }

portInBytes OBJECT-TYPE
    SYNTAX  Counter
    ACCESS  read-only
    STATUS  mandatory
    DESCRIPTION
        "Bytes received with no error."
    ::= { portEntry 22 }

portOutBytes OBJECT-TYPE
    SYNTAX  Counter
    ACCESS  read-only
    STATUS  mandatory
    DESCRIPTION
        "Bytes transmitted with no error."
    ::= { portEntry 23 }

portResetPortCounters OBJECT-TYPE
    SYNTAX  INTEGER
    ACCESS  read-write
    STATUS  mandatory
    DESCRIPTION
        "Writing any value to this variable will reset all port-related
        counters to zero."
    ::= { portEntry 24 }
    
portAsyncParityErrors OBJECT-TYPE
    SYNTAX  Counter
    ACCESS  read-only
    STATUS  mandatory
    DESCRIPTION
        "Number of async parity errors."
    ::= { portEntry 25 }

portAsyncCharFrameErrors OBJECT-TYPE
    SYNTAX  Counter
    ACCESS  read-only
    STATUS  mandatory
    DESCRIPTION
        "Number of async character framing errors."
    ::= { portEntry 26 }

portAsyncOverrunErrors OBJECT-TYPE
    SYNTAX  Counter
    ACCESS  read-only
    STATUS  mandatory
    DESCRIPTION
        "Number of async receive overrun errors."
    ::= { portEntry 27 }

portAsyncPktCksumErrors OBJECT-TYPE
    SYNTAX  Counter
    ACCESS  read-only
    STATUS  mandatory
    DESCRIPTION
        "Number of async packet checksum errors."
    ::= { portEntry 28 }
    
portCTSState OBJECT-TYPE
    SYNTAX  INTEGER
        {
            off(1),
            on(2)
        }
    ACCESS  read-only
    STATUS  mandatory
    DESCRIPTION
        "Current state CTS signal."
    ::= { portEntry 29 }
    
portDCDState OBJECT-TYPE
    SYNTAX  INTEGER
        {
            off(1),
            on(2)
        }
    ACCESS  read-only
    STATUS  mandatory
    DESCRIPTION
        "Current state DCD signal."
    ::= { portEntry 30 }
    
portRIState OBJECT-TYPE
    SYNTAX  INTEGER
        {
            off(1),
            on(2)
        }
    ACCESS  read-only
    STATUS  mandatory
    DESCRIPTION
        "Current state RI signal."
    ::= { portEntry 31 }
    

-- Sync port only --

portSyncFcsErrors OBJECT-TYPE
    SYNTAX  Counter
    ACCESS  read-only
    STATUS  mandatory
    DESCRIPTION
        "Number of sync packet FCS errors."
    ::= { portEntry 32 }

portSyncMemoryErrors OBJECT-TYPE
    SYNTAX  Counter
    ACCESS  read-only
    STATUS  mandatory
    DESCRIPTION
        "Number of sync memory errors."
    ::= { portEntry 33 }

portSyncOverrunErrors OBJECT-TYPE
    SYNTAX  Counter
    ACCESS  read-only
    STATUS  mandatory
    DESCRIPTION
        "Number of sync receive overrun errors."
    ::= { portEntry 34 }

portSyncUnderrunErrors OBJECT-TYPE
    SYNTAX  Counter
    ACCESS  read-only
    STATUS  mandatory
    DESCRIPTION
        "Number of sync transmit underrun errors."
    ::= { portEntry 35 }

-- Sync port only end --

portIPCPState OBJECT-TYPE
    SYNTAX  INTEGER
        {
            off(1),
            on(2)
        }
    ACCESS  read-only
    STATUS  mandatory
    DESCRIPTION
        "Current connection state of PPP IPCP."
    ::= { portEntry 36 }
    
portIPXCPState OBJECT-TYPE
    SYNTAX  INTEGER
        {
            off(1),
            on(2)
        }
    ACCESS  read-only
    STATUS  mandatory
    DESCRIPTION
        "Current connection state of PPP IPXCP."
    ::= { portEntry 37 }
    
portBNCPState OBJECT-TYPE
    SYNTAX  INTEGER
        {
            off(1),
            on(2)
        }
    ACCESS  read-only
    STATUS  mandatory
    DESCRIPTION
        "Current connection state of PPP BNCP."
    ::= { portEntry 38 }
    
-- Token Ring port only --

portDriverState OBJECT-TYPE
    SYNTAX  INTEGER
        {
            off(1),
            reset(2),
		    init(3),
	    	open(4),
		    online(5)
        }
    ACCESS  read-only
    STATUS  mandatory
    DESCRIPTION
        "Current Token Ring interface state."
    ::= { portEntry 39 }

portSpeed OBJECT-TYPE
    SYNTAX  INTEGER
        {
            megabyte-4(4),
            megabyte-16(16)
        }
    ACCESS  read-only
    STATUS  mandatory
    DESCRIPTION
        "Current Token Ring speed."
    ::= { portEntry 40 }

portTotalErrors OBJECT-TYPE
    SYNTAX  Counter
    ACCESS  read-only
    STATUS  mandatory
    DESCRIPTION
        "Number of total interface errors."
    ::= { portEntry 41 }

portTransmitDiscards OBJECT-TYPE
    SYNTAX  Counter
    ACCESS  read-only
    STATUS  mandatory
    DESCRIPTION
        "Number of packets dropped due to lack of buffers during transmit."
    ::= { portEntry 42 }

portReceiveCongestions OBJECT-TYPE
    SYNTAX  Counter
    ACCESS  read-only
    STATUS  mandatory
    DESCRIPTION
        "Number of packets dropped due to lack of buffers during receive."
    ::= { portEntry 43 }

portUnknownProtocols OBJECT-TYPE
    SYNTAX  Counter
    ACCESS  read-only
    STATUS  mandatory
    DESCRIPTION
        "Number of packets received with unknown DLC type."
    ::= { portEntry 44 }

-- Token Ring port only end --
    
portAccessType OBJECT-TYPE
    SYNTAX	INTEGER
        {
             auto(1),
             arap1-0(2),
	     router(4)
        }
    ACCESS  read-write
    STATUS  mandatory
    DESCRIPTION
        "Access Type for the corresponding port: ui for normal login sequence,
         arap for AppleTalk, and ppp for ppp's authentication (PAP/CHAP)"
    ::= { portEntry 45 }

portDialHangUp OBJECT-TYPE
    SYNTAX	INTEGER
    ACCESS  read-write
    STATUS  mandatory
    DESCRIPTION
        "Hang up current connection"
    ::= { portEntry 46 }

portPortDisabled OBJECT-TYPE
    SYNTAX  INTEGER
        {
            no(1),
            yes(2)
        }
    ACCESS  read-write
    STATUS  mandatory
    DESCRIPTION
        "The variable disables port for dialout function."
    ::= { portEntry 47 }
	
portArapCompress OBJECT-TYPE
    SYNTAX  INTEGER
        {
            v42bis(1),
            off(2)
        }
    ACCESS  read-write
    STATUS  mandatory
    DESCRIPTION
        "The variable for arap compression."
    ::= { portEntry 48 }
	
-- NANTUCKET
portInterFace OBJECT-TYPE
    SYNTAX  INTEGER
        {
            async(1),
            sync(2)
        }
    ACCESS  read-only
    STATUS  mandatory
    DESCRIPTION
        "The variable shows the port interface type."
	::= { portEntry 49 }
	
portLEDLink OBJECT-TYPE
    SYNTAX  INTEGER
        {
            on(1),
            off(2)
        }
    ACCESS  read-only
    STATUS  mandatory
    DESCRIPTION
        "The variable shows the port link LED."
	::= { portEntry 50 }
	
portLEDActivity OBJECT-TYPE
    SYNTAX  INTEGER
        {
            light(1),
            medium(2),
			heavy(3)
        }
    ACCESS  read-only
    STATUS  mandatory
    DESCRIPTION
        "The variable shows the port activity LED."
	::= { portEntry 51 }
	
portLEDFault OBJECT-TYPE
    SYNTAX  INTEGER
        {
            on(1),
            off(2)
        }
    ACCESS  read-only
    STATUS  mandatory
    DESCRIPTION
        "The variable shows the port fault LED."
	::= { portEntry 52 }

-- ISDN BRI

portLinkType OBJECT-TYPE
    SYNTAX  INTEGER
        {
            dial(0),
            permanent(1)
        }
    ACCESS  read-write
    STATUS  mandatory
    DESCRIPTION
        "The variable shows the ISDN port link type."
	::= { portEntry 53 }

portSwitchType OBJECT-TYPE
    SYNTAX  INTEGER
        {
            att5ess(1),
            dms100(2),
            ni1(3),
            ins64(4),
            vn3(5),
            net3(6)
        }
    ACCESS  read-write
    STATUS  mandatory
    DESCRIPTION
        "The variable shows the ISDN port country type."
	::= { portEntry 54 }

portSPID-1 OBJECT-TYPE
    SYNTAX  DisplayString (SIZE (0..20))
    ACCESS  read-write
    STATUS  mandatory
    DESCRIPTION
        "The variable shows the ISDN port SPID #1."
    ::= { portEntry 55 }

portSPID-2 OBJECT-TYPE
    SYNTAX  DisplayString (SIZE (0..20))
    ACCESS  read-write
    STATUS  mandatory
    DESCRIPTION
        "The variable shows the ISDN port SPID #2."
    ::= { portEntry 56 }

portDirectoryNo-1 OBJECT-TYPE
    SYNTAX  DisplayString (SIZE (0..20))
    ACCESS  read-write
    STATUS  mandatory
    DESCRIPTION
        "The variable shows the ISDN port DirectoryNo #1."
    ::= { portEntry 57 }

portDirectoryNo-2 OBJECT-TYPE
    SYNTAX  DisplayString (SIZE (0..20))
    ACCESS  read-write
    STATUS  mandatory
    DESCRIPTION
        "The variable shows the ISDN port DirectoryNo #2."
    ::= { portEntry 58 }

portLocalDialNo-1 OBJECT-TYPE
    SYNTAX  DisplayString (SIZE (0..20))
    ACCESS  read-write
    STATUS  mandatory
    DESCRIPTION
        "The variable shows the ISDN port LocalDialNo #1."
    ::= { portEntry 59 }

portLocalDialNo-2 OBJECT-TYPE
    SYNTAX  DisplayString (SIZE (0..20))
    ACCESS  read-write
    STATUS  mandatory
    DESCRIPTION
        "The variable shows the ISDN port LocalDialNo #2."
    ::= { portEntry 60 }

portLocalSubaddress-1 OBJECT-TYPE
    SYNTAX  DisplayString (SIZE (0..10))
    ACCESS  read-write
    STATUS  mandatory
    DESCRIPTION
        "The variable shows the ISDN port LocalSubaddress #1."
    ::= { portEntry 61 }

portLocalSubaddress-2 OBJECT-TYPE
    SYNTAX  DisplayString (SIZE (0..10))
    ACCESS  read-write
    STATUS  mandatory
    DESCRIPTION
        "The variable shows the ISDN port LocalSubaddress #2."
    ::= { portEntry 62 }

portProtocolMode OBJECT-TYPE
    SYNTAX  INTEGER
        {
            v-120(4),
            raw(5)
        }
    ACCESS  read-write
    STATUS  mandatory
    DESCRIPTION
        "The variable shows the ISDN port protocol mode."
	::= { portEntry 63 }

portPortReset OBJECT-TYPE
    SYNTAX  INTEGER
        {
            no(1),
            yes(2)
        }
    ACCESS  read-write
    STATUS  mandatory
    DESCRIPTION
        "The variable resets ISDN port."
    ::= { portEntry 64 }

portIncomingCalls OBJECT-TYPE
    SYNTAX  Counter
    ACCESS  read-only
    STATUS  mandatory
    DESCRIPTION
        "Number of ISDN incoming calls."
    ::= { portEntry 65 }

portOutgoingCalls OBJECT-TYPE
    SYNTAX  Counter
    ACCESS  read-only
    STATUS  mandatory
    DESCRIPTION
        "Number of ISDN outgoing calls."
    ::= { portEntry 66 }

portRemoteDialNo OBJECT-TYPE
    SYNTAX  DisplayString (SIZE (0..20))
    ACCESS  read-only
    STATUS  mandatory
    DESCRIPTION
        "The variable shows the ISDN port B channel remote dial no."
    ::= { portEntry 67 }

portRemoteSubaddress OBJECT-TYPE
    SYNTAX  DisplayString (SIZE (0..10))
    ACCESS  read-only
    STATUS  mandatory
    DESCRIPTION
        "The variable shows the ISDN port B channel remote subaddress."
    ::= { portEntry 68 }

portISDNInterfaceType OBJECT-TYPE
    SYNTAX  DisplayString (SIZE (0..3))
    ACCESS  read-only
    STATUS  mandatory
    DESCRIPTION
        "The variable shows the interface type of the ISDN card."
    ::= { portEntry 69 }
	
-- AB6.0

portPathName OBJECT-TYPE
    SYNTAX  DisplayString (SIZE (0..12))
    ACCESS  read-only
    STATUS  mandatory
    DESCRIPTION
        "The variable shows the path name on this port."
    ::= { portEntry 70 }
	
portILCCPState OBJECT-TYPE
    SYNTAX  INTEGER
        {
            off(1),
	    on(2)
        }
    ACCESS  read-only
    STATUS  mandatory
    DESCRIPTION
        "This parameter indicates the individual link CCP state."
    ::= { portEntry 71 }

portCurISDNBChannel OBJECT-TYPE
    SYNTAX  INTEGER
        {
            b-1(1),
	    b-2(2)
        }
    ACCESS  read-only
    STATUS  mandatory
    DESCRIPTION
        "This parameter indicates the physical binding channel number."
    ::= { portEntry 72 }

portLoginStatus OBJECT-TYPE
    SYNTAX  INTEGER
        {
            unused(1),
	    dial-in(2),
	    dial-out(3),
	    disabled(4),
	    router(5)
        }
    ACCESS  read-only
    STATUS  mandatory
    DESCRIPTION
        "This parameter indicates the login status for this port."
    ::= { portEntry 73 }

portLastConnectBChannel OBJECT-TYPE
    SYNTAX  INTEGER
        {
	    not-used(1),
            b-1(2),
	    b-2(3)
        }
    ACCESS  read-only
    STATUS  mandatory
    DESCRIPTION
        "This parameter indicates last connect B channel for this ISDN line."
    ::= { portEntry 74 }

portISDNPhyLineStatus OBJECT-TYPE
    SYNTAX  INTEGER
        {
            deactivated(1),
	    activated(2)
        }
    ACCESS  read-only
    STATUS  mandatory
    DESCRIPTION
        "This parameter indicates physical line status for this ISDN line."
    ::= { portEntry 75 }

portTEIState OBJECT-TYPE
    SYNTAX  INTEGER
        {
            unassigned(1),
	    assigned(2)
        }
    ACCESS  read-only
    STATUS  mandatory
    DESCRIPTION
        "This parameter indicates TEI state for this ISDN line."
    ::= { portEntry 76 }

portLayer3Status OBJECT-TYPE
    SYNTAX  INTEGER
        {
            uninitialized(1),
	    initialized(2)
        }
    ACCESS  read-only
    STATUS  mandatory
    DESCRIPTION
        "This parameter indicates lay 3 status for this ISDN line."
    ::= { portEntry 77 }

-- End of port table --

portResetAllCounters OBJECT-TYPE
    SYNTAX  INTEGER
    ACCESS  read-write
    STATUS  mandatory
    DESCRIPTION
        "Writing any value to this variable will reset all port-related
        counters to zero."
    ::= { port 3 }

portSourceRouteTable OBJECT-TYPE
    SYNTAX  SEQUENCE OF PortSourceRouteEntry
    ACCESS  not-accessible
    STATUS  mandatory
    DESCRIPTION
        "Source route information table for end stations."
    ::= { port 4 }

portSourceRouteEntry OBJECT-TYPE
    SYNTAX  PortSourceRouteEntry
    ACCESS  not-accessible
    STATUS  mandatory
    DESCRIPTION
        "A source route path to an end station."
    INDEX   { portSRMacAddress }
    ::= { portSourceRouteTable 1 }

PortSourceRouteEntry ::=
    SEQUENCE {
        portSRMacAddress
            OCTET STRING (SIZE (6)),
	portSRState	  
	    INTEGER,
	portSRTimeToLive
	    Counter,
	portSRLargestFrame
	    INTEGER,
	portSRDirection
	    INTEGER,
	portSRRouteDescrpt
            DisplayString (SIZE (0..70))
    }

portSRMacAddress OBJECT-TYPE
    SYNTAX  OCTET STRING (SIZE (6))
    ACCESS  read-only
    STATUS  mandatory
    DESCRIPTION
        "MAC address of the Source Route table entry."
    ::= { portSourceRouteEntry 1 }

portSRState OBJECT-TYPE
    SYNTAX  INTEGER
        {
            empty(0),
            pending(1),
	    new(2),
	    old(3)
        }
    ACCESS  read-only
    STATUS  mandatory
    DESCRIPTION
        "Source Route path state of the Source Route table entry."
    ::= { portSourceRouteEntry 2 }

portSRTimeToLive OBJECT-TYPE
    SYNTAX  Counter
    ACCESS  read-only
    STATUS  mandatory
    DESCRIPTION
        "Time to live information of the Source Route table entry."
    ::= { portSourceRouteEntry 3 }

portSRLargestFrame OBJECT-TYPE
    SYNTAX  INTEGER
    ACCESS  read-only
    STATUS  mandatory
    DESCRIPTION
        "Largest frame information of the Source Route table entry."
    ::= { portSourceRouteEntry 4 }

portSRDirection OBJECT-TYPE
    SYNTAX  INTEGER
        {
            forward(0),
            backword(1)
        }
    ACCESS  read-only
    STATUS  mandatory
    DESCRIPTION
        "Path direction of the Source Route table entry."
    ::= { portSourceRouteEntry 5 }

portSRRouteDescrpt OBJECT-TYPE
	SYNTAX	DisplayString (SIZE (0..70))
    ACCESS  read-only
    STATUS  mandatory
    DESCRIPTION
        "Path information of the Source Route table entry."
    ::= { portSourceRouteEntry 6 }

portAllLoginStatus OBJECT-TYPE
    SYNTAX  OCTET STRING (SIZE (0..256))
    ACCESS  read-only
    STATUS  mandatory
    DESCRIPTION
		"This parameter indicates the login status for all ports.
		 The format is the sequence of portID and login status."
    ::= { port 5 }


portTokenRingSpeed OBJECT-TYPE
    SYNTAX  INTEGER
        {
            megabyte-4(4),
            megabyte-16(16)
        }
    ACCESS  read-only
    STATUS  mandatory
    DESCRIPTION
        "Current Token Ring speed."
    ::= { port 6 }

-- NANTUCKET

portAllLEDStatus OBJECT-TYPE
    SYNTAX  OCTET STRING (SIZE (0..64))
    ACCESS  read-only
    STATUS  mandatory
    DESCRIPTION
		"This parameter indicates the led status for all ports.
		 The format is the sequence of portID, Link LED, Activity
		 LED and Fault LED."
    ::= { port 7 }

-- path group --

-- remote PC access path table --

prpaNumber OBJECT-TYPE
    SYNTAX  INTEGER
    ACCESS  read-only
    STATUS  mandatory
    DESCRIPTION
        "The number of remote PC access paths on this system."
    ::= { path 1 }

prpaTable OBJECT-TYPE
    SYNTAX  SEQUENCE OF PrpaEntry
    ACCESS  not-accessible
    STATUS  mandatory
    DESCRIPTION
        "Remote PC access path table."
    ::= { path 2 }

prpaEntry OBJECT-TYPE
    SYNTAX  PrpaEntry
    ACCESS  not-accessible
    STATUS  mandatory
    DESCRIPTION
        "A path to a remote PC."
    INDEX   { prpaIndex }
    ::= { prpaTable 1 }

PrpaEntry ::=
    SEQUENCE {
        prpaIndex
            INTEGER,
        prpaName
            DisplayString (SIZE (0..12)),
        prpaType
            INTEGER,
        prpaPortIdx
            INTEGER,
        prpaAutoHangUp
            INTEGER,
        prpaInPackets 
            Counter,
        prpaOutPackets
            Counter,
        prpaInBytes
            Counter,
        prpaOutBytes
            Counter,
        prpaResetPrpaCounters
            INTEGER,
        prpaLoginStatus
            INTEGER,
        prpaLoginUserName
            DisplayString (SIZE (0..10)),
        prpaLoginTime
            DisplayString (SIZE (0..8)),
        prpaLoginDuration
            DisplayString (SIZE (0..8)),
        prpaLoginAttempts
            Counter,
        prpaLoginInPackets
            Counter,
        prpaLoginOutPackets
            Counter,
        prpaLoginInBytes
            Counter,
        prpaLoginOutBytes
            Counter,
        prpaLoginParityErrors
            Counter,
        prpaLoginFrameErrors
            Counter,
        prpaLoginOverrunErrors
            Counter,
        prpaLoginCksumErrors
            Counter,
        prpaFilterAction
            INTEGER,
        prpaFilterMap
            INTEGER,
        prpaLoggerMap
            INTEGER,
        prpaFilterCount
            Counter,
        prpaLoggerCount
            Counter,
        prpaDiscardedPackets 
            Counter,
        prpaForwardedPackets
            Counter,
        prpaReceivedPackets
            Counter,
        prpaSmartFiltering
            INTEGER,
        prpaCurrentMacAddr
            OCTET STRING,
--  Ethernet only
	prpaIpEthernetII 
            INTEGER,
	prpaIpSnap 
            INTEGER,
	prpaRemotePcIpAddress
	    IpAddress,
	prpaIpxEn2WithNetBIOS 
            INTEGER,
	prpaIpx8023WithNetBIOS 
            INTEGER,
	prpaIpx8022WithNetBIOS 
            INTEGER,
	prpaIpxSnapWithNetBIOS 
            INTEGER,
	prpaXNS 
          INTEGER,
	prpaVinesEthernetII 
          INTEGER,
	prpaVinesSnap 
          INTEGER,
	prpaNetBIOS 
            INTEGER,
	prpaDECNet 
            INTEGER,
	prpaUnknowEthernetII 
            INTEGER,
	prpaUnknownSap 
            INTEGER,
	prpaUnknownSnap 
            INTEGER,
	prpaMulticastAddress 
            OCTET STRING,
-- Token-Ring only
	prpaXNSSap
            INTEGER,
	prpaXNSSnap
            INTEGER,
	prpaVinesSap
            INTEGER,
	prpaIpxEn2
            INTEGER,
	prpaIpx8023
            INTEGER,
	prpaIpx8022
            INTEGER,
	prpaIpxSnap
            INTEGER,
        prpaPortList
            DisplayString (SIZE (0..48)),
	prpaSpoofState
            INTEGER,
	prpaCCPState
            INTEGER,
	prpaIPCPState
            INTEGER,
	prpaIPXCPState
            INTEGER,
	prpaBNCPState
            INTEGER,
	prpaARAPState
            INTEGER,
	prpaLinkUtil
            INTEGER
    }

prpaIndex OBJECT-TYPE
    SYNTAX  INTEGER
    ACCESS  read-only
    STATUS  mandatory
    DESCRIPTION
        "A unique value for each remote PC access path.  
        The value for each path must remain constant at
        least from one re-initialization of the entity's
        network management system to the next re-
        initialization."
    ::= { prpaEntry 1 }

prpaName OBJECT-TYPE
    SYNTAX  DisplayString (SIZE (0..12))
    ACCESS  read-only
    STATUS  mandatory
    DESCRIPTION
        "A unique user-recognizable name for each remote 
        PC access path."
    ::= { prpaEntry 2 }

prpaType OBJECT-TYPE
    SYNTAX  INTEGER
         {
            invalid(1),
            valid(2)
        }
    ACCESS  read-only
    STATUS  mandatory
    DESCRIPTION
        "The type of path. Invalid means this path no longer
        exists."
    ::= { prpaEntry 3 }

prpaPortIdx OBJECT-TYPE
    SYNTAX  INTEGER
    ACCESS  read-only
    STATUS  mandatory
    DESCRIPTION
        "A number to uniquely identify a port for this remote 
        PC access path."
    ::= { prpaEntry 4 }

prpaAutoHangUp OBJECT-TYPE
    SYNTAX  INTEGER
         {
            disabled(1),
            enabled(2)
        }
    ACCESS  read-write
    STATUS  mandatory
    DESCRIPTION
        "This flag indicates whether Auto-hangup feature is
        enabled. If enabled, the line will be disconnected if
        no traffic activity has been detected for default time
        interval."
    ::= { prpaEntry 5 }

prpaInPackets OBJECT-TYPE
    SYNTAX  Counter
    ACCESS  read-only
    STATUS  mandatory
    DESCRIPTION
        "Packets received with no error."
    ::= { prpaEntry 6 }

prpaOutPackets OBJECT-TYPE
    SYNTAX  Counter
    ACCESS  read-only
    STATUS  mandatory
    DESCRIPTION
        "Packets transmitted with no error."
    ::= { prpaEntry 7 }

prpaInBytes OBJECT-TYPE
    SYNTAX  Counter
    ACCESS  read-only
    STATUS  mandatory
    DESCRIPTION
        "Bytes received with no error."
    ::= { prpaEntry 8 }

prpaOutBytes OBJECT-TYPE
    SYNTAX  Counter
    ACCESS  read-only
    STATUS  mandatory
    DESCRIPTION
        "Bytes transmitted with no error."
    ::= { prpaEntry 9 }

prpaResetPrpaCounters OBJECT-TYPE
    SYNTAX  INTEGER
    ACCESS  read-write
    STATUS  mandatory
    DESCRIPTION
        "Writing any value to this variable will reset all prpa-related
        counters to zero."
    ::= { prpaEntry 10 }
    
prpaLoginStatus OBJECT-TYPE
    SYNTAX  INTEGER
          {
              unused(0),
              dial-in(1),
              dial-out(2),
			  disabled(3)
          }
    ACCESS  read-only
    STATUS  mandatory
    DESCRIPTION
        "Login status of this RPA path."
    ::= { prpaEntry 11 }

prpaLoginUserName OBJECT-TYPE
    SYNTAX  DisplayString (SIZE (0..10))
    ACCESS  read-only
    STATUS  mandatory
    DESCRIPTION
        "The name of the currently logged-in user."
    ::= { prpaEntry 12 }

prpaLoginTime OBJECT-TYPE
    SYNTAX  DisplayString (SIZE (0..8))
    ACCESS  read-only
    STATUS  mandatory
    DESCRIPTION
        "The start time (in HH:MM:SS) of current session."
    ::= { prpaEntry 13 }

prpaLoginDuration OBJECT-TYPE
    SYNTAX  DisplayString (SIZE (0..8))
    ACCESS  read-only
    STATUS  mandatory
    DESCRIPTION
        "The elapsed time (in HH:MM:SS) of current session."
    ::= { prpaEntry 14 }

prpaLoginAttempts OBJECT-TYPE
    SYNTAX  Counter
    ACCESS  read-only
    STATUS  mandatory
    DESCRIPTION
        "Number of unsuccessful login attempts in this authentication
         process."
    ::= { prpaEntry 15 }

prpaLoginInPackets OBJECT-TYPE
    SYNTAX  Counter
    ACCESS  read-only
    STATUS  mandatory
    DESCRIPTION
        "Number of correctly received packets in this session."
    ::= { prpaEntry 16 }

prpaLoginOutPackets OBJECT-TYPE
    SYNTAX  Counter
    ACCESS  read-only
    STATUS  mandatory
    DESCRIPTION
        "Number of correctly transmitted packets in this session."
    ::= { prpaEntry 17 }

prpaLoginInBytes OBJECT-TYPE
    SYNTAX  Counter
    ACCESS  read-only
    STATUS  mandatory
    DESCRIPTION
        "Number of correctly received bytes in this session."
    ::= { prpaEntry 18 }

prpaLoginOutBytes OBJECT-TYPE
    SYNTAX  Counter
    ACCESS  read-only
    STATUS  mandatory
    DESCRIPTION
        "Number of correctly transmitted bytes in this session."
    ::= { prpaEntry 19 }

prpaLoginParityErrors OBJECT-TYPE
    SYNTAX  Counter
    ACCESS  read-only
    STATUS  mandatory
    DESCRIPTION
        "Number of characters received with parity error in this session."
    ::= { prpaEntry 20 }

prpaLoginFrameErrors OBJECT-TYPE
    SYNTAX  Counter
    ACCESS  read-only
    STATUS  mandatory
    DESCRIPTION
        "Number of characters received with framing error in this session."
    ::= { prpaEntry 21 }

prpaLoginOverrunErrors OBJECT-TYPE
    SYNTAX  Counter
    ACCESS  read-only
    STATUS  mandatory
    DESCRIPTION
        "Number of receive overrun errors in this session."
    ::= { prpaEntry 22 }

prpaLoginCksumErrors OBJECT-TYPE
    SYNTAX  Counter
    ACCESS  read-only
    STATUS  mandatory
    DESCRIPTION
        "Number of incoming pakets with bad checksum in this session."
    ::= { prpaEntry 23 }
 	
prpaFilterAction OBJECT-TYPE
    SYNTAX  INTEGER
        {
            discard(1),
            forward(2)
        }
    ACCESS  read-write
    STATUS  mandatory
    DESCRIPTION
        "The action to be taken by the configured this path's filters."
    ::= { prpaEntry 24 }

prpaFilterMap OBJECT-TYPE
    SYNTAX  INTEGER
    ACCESS  read-write
    STATUS  mandatory
    DESCRIPTION
        "This is a 16 bit bitmap corresponds to the bridge filter table."
    ::= { prpaEntry 25 }

prpaLoggerMap OBJECT-TYPE
    SYNTAX  INTEGER
    ACCESS  read-write
    STATUS  mandatory
    DESCRIPTION
        "This is a 16 bit bitmap corresponds to the bridge logger table."
    ::= { prpaEntry 26 }

prpaFilterCount OBJECT-TYPE
    SYNTAX  Counter
    ACCESS  read-only
    STATUS  mandatory
    DESCRIPTION
        "The number of packets that have been filtered."
    ::= { prpaEntry 27 }

prpaLoggerCount OBJECT-TYPE
    SYNTAX  Counter
    ACCESS  read-only
    STATUS  mandatory
    DESCRIPTION
        "The value gives the number of incoming packets that match
        this log description."
    ::= { prpaEntry 28 }

prpaDiscardedPackets OBJECT-TYPE
    SYNTAX  Counter
    ACCESS  read-only
    STATUS  mandatory
    DESCRIPTION
        "Packets discarded."
    ::= { prpaEntry 29 }

prpaForwardedPackets OBJECT-TYPE
    SYNTAX  Counter
    ACCESS  read-only
    STATUS  mandatory
    DESCRIPTION
        "Packets forwarded."
    ::= { prpaEntry 30 }

prpaReceivedPackets OBJECT-TYPE
    SYNTAX  Counter
    ACCESS  read-only
    STATUS  mandatory
    DESCRIPTION
        "Packets received."
    ::= { prpaEntry 31 }

prpaSmartFiltering OBJECT-TYPE
    SYNTAX  INTEGER
        {
            disabled(1),
            enabled(2)
        }
    ACCESS  read-write
    STATUS  mandatory
    DESCRIPTION
        "This enables/disables AccessBuilder's Smart Filtering feature."
    ::= { prpaEntry 32 }

prpaCurrentMacAddr OBJECT-TYPE
    SYNTAX  OCTET STRING
    ACCESS  read-only
    STATUS  mandatory
    DESCRIPTION
        "This parameter displays the remote client's MAC address."
    ::= { prpaEntry 33 }

prpaIpEthernetII OBJECT-TYPE
    SYNTAX  INTEGER
        {
            no(1),
            yes(2)
        }
    ACCESS  read-only
    STATUS  mandatory
    DESCRIPTION
        "This parameter indicates the protocol IP EthernetII running in 
         the remotepc client."
    ::= { prpaEntry 34 }

prpaIpSnap OBJECT-TYPE
    SYNTAX  INTEGER
        {
            no(1),
            yes(2)
        }
    ACCESS  read-only
    STATUS  mandatory
    DESCRIPTION
        "This parameter indicates the protocol IP Snap running in 
         the remotepc client."
    ::= { prpaEntry 35 }

prpaRemotePcIpAddress OBJECT-TYPE
    SYNTAX  IpAddress
    ACCESS  read-only
    STATUS  mandatory
    DESCRIPTION
        "This parameter indicates the IP address running in 
         the remotepc client."
    ::= { prpaEntry 36 }

prpaIpxEn2WithNetBIOS OBJECT-TYPE
    SYNTAX  INTEGER
        {
            no(1),
            yes(2)
        }
    ACCESS  read-only
    STATUS  mandatory
    DESCRIPTION
        "This parameter indicates the protocol IPX EthernetII with NetBIOS 
        running in the remotepc client."
    ::= { prpaEntry 37 }

prpaIpx8023WithNetBIOS OBJECT-TYPE
    SYNTAX  INTEGER
        {
            no(1),
            yes(2)
        }
    ACCESS  read-only
    STATUS  mandatory
    DESCRIPTION
        "This parameter indicates the protocol IPX 802.3 with NetBIOS 
         running in the remotepc client."
    ::= { prpaEntry 38 }

prpaIpx8022WithNetBIOS OBJECT-TYPE
    SYNTAX  INTEGER
        {
            no(1),
            yes(2)
        }
    ACCESS  read-only
    STATUS  mandatory
    DESCRIPTION
        "This parameter indicates the protocol IPX 802.2 with NetBIOS 
         running in the remotepc client."
    ::= { prpaEntry 39 }

prpaIpxSnapWithNetBIOS OBJECT-TYPE
    SYNTAX  INTEGER
        {
            no(1),
            yes(2)
        }
    ACCESS  read-only
    STATUS  mandatory
    DESCRIPTION
        "This parameter indicates the protocol IPX Snap with NetBIOS 
         running in the remotepc client."
    ::= { prpaEntry 40 }

 prpaXNS OBJECT-TYPE
   SYNTAX  INTEGER
        {
            no(1),
            yes(2)
        }
    ACCESS  read-only
    STATUS  mandatory
    DESCRIPTION
        "This parameter indicates the protocol XNS running in 
         the remotepc client."
    ::= { prpaEntry 41 }

prpaVinesEthernetII OBJECT-TYPE
   SYNTAX  INTEGER
        {
            no(1),
            yes(2)
        }
    ACCESS  read-only
    STATUS  mandatory
    DESCRIPTION
        "This parameter indicates the protocol Vines EthernetII running in 
         the remotepc client."
   ::= { prpaEntry 42 }

prpaVinesSnap OBJECT-TYPE
    SYNTAX  INTEGER
        {
            no(1),
            yes(2)
        }
    ACCESS  read-only
    STATUS  mandatory
    DESCRIPTION
        "This parameter indicates the protocol Vines Snap running in 
         the remotepc client."
    ::= { prpaEntry 43 }

prpaNetBIOS OBJECT-TYPE
    SYNTAX  INTEGER
        {
            no(1),
            yes(2)
        }
    ACCESS  read-only
    STATUS  mandatory
    DESCRIPTION
        "This parameter indicates the protocol NetBIOS running in 
         the remotepc client."
    ::= { prpaEntry 44 }

prpaDECNet OBJECT-TYPE
    SYNTAX  INTEGER
        {
            no(1),
            yes(2)
        }
    ACCESS  read-only
    STATUS  mandatory
    DESCRIPTION
        "This parameter indicates the protocol DECNET running in 
         the remotepc client."
    ::= { prpaEntry 45 }

prpaUnknowEthernetII OBJECT-TYPE
    SYNTAX  INTEGER
        {
            no(1),
            yes(2)
        }
    ACCESS  read-only
    STATUS  mandatory
    DESCRIPTION
        "This parameter indicates the protocol Unknown EthernetII running in 
         the remotepc client."
    ::= { prpaEntry 46 }

prpaUnknownSap OBJECT-TYPE
    SYNTAX  INTEGER
        {
            no(1),
            yes(2)
        }
    ACCESS  read-only
    STATUS  mandatory
    DESCRIPTION
        "This parameter indicates the protocol Unknown Sap running in 
         the remotepc client."
    ::= { prpaEntry 47 }

prpaUnknownSnap OBJECT-TYPE
    SYNTAX  INTEGER
        {
            no(1),
            yes(2)
        }
    ACCESS  read-only
    STATUS  mandatory
    DESCRIPTION
        "This parameter indicates the protocol Unknown Snap running in 
         the remotepc client."
    ::= { prpaEntry 48 }

prpaMulticastAddress OBJECT-TYPE
    SYNTAX  OCTET STRING
    ACCESS  read-only
    STATUS  mandatory
    DESCRIPTION
        "This parameter indicates the multicast address packets recongnized 
         by the remotepc client."
    ::= { prpaEntry 49 }

prpaXNSSap OBJECT-TYPE
    SYNTAX  INTEGER
        {
            no(1),
            yes(2)
        }
    ACCESS  read-only
    STATUS  mandatory
    DESCRIPTION
        "This parameter indicates the protocol XNS Sap running in 
         the remotepc client."
    ::= { prpaEntry 50 }

prpaXNSSnap OBJECT-TYPE
    SYNTAX  INTEGER
        {
            no(1),
            yes(2)
        }
    ACCESS  read-only
    STATUS  mandatory
    DESCRIPTION
        "This parameter indicates the protocol XNS Snap running in 
         the remotepc client."
    ::= { prpaEntry 51 }

prpaVinesSap OBJECT-TYPE
    SYNTAX  INTEGER
        {
            no(1),
            yes(2)
        }
    ACCESS  read-only
    STATUS  mandatory
    DESCRIPTION
        "This parameter indicates the protocol Vines Sap running in 
         the remotepc client."
    ::= { prpaEntry 52 }

 prpaIpxEn2 OBJECT-TYPE
     SYNTAX  INTEGER
         {
             no(1),
             yes(2)
         }
     ACCESS  read-only
     STATUS  mandatory
     DESCRIPTION
         "This parameter indicates the protocol IPX EthernetII 
         running in the remotepc client."
     ::= { prpaEntry 53 }

 prpaIpx8023 OBJECT-TYPE
     SYNTAX  INTEGER
         {
             no(1),
             yes(2)
         }
     ACCESS  read-only
     STATUS  mandatory
     DESCRIPTION
         "This parameter indicates the protocol IPX 802.3 
          running in the remotepc client."
     ::= { prpaEntry 54 }

prpaIpx8022 OBJECT-TYPE
    SYNTAX  INTEGER
        {
            no(1),
            yes(2)
        }
    ACCESS  read-only
    STATUS  mandatory
    DESCRIPTION
        "This parameter indicates the protocol IPX 802.2 
         running in the remotepc client."
    ::= { prpaEntry 55 }

prpaIpxSnap OBJECT-TYPE
    SYNTAX  INTEGER
        {
            no(1),
            yes(2)
        }
    ACCESS  read-only
    STATUS  mandatory
    DESCRIPTION
        "This parameter indicates the protocol IPX Snap 
         running in the remotepc client."
    ::= { prpaEntry 56 }

prpaPortList OBJECT-TYPE
    SYNTAX  DisplayString (SIZE (0..48))
    ACCESS  read-only
    STATUS  mandatory
    DESCRIPTION
        "This parameter indicates the port-id list for the binding
	 ports on this RPA path."
    ::= { prpaEntry 57 }

prpaSpoofState OBJECT-TYPE
    SYNTAX  INTEGER
        {
            off(1),
            connect(2),
	    spoofing(3),
	    disabled(4)
        }
    ACCESS  read-only
    STATUS  mandatory
    DESCRIPTION
        "This parameter indicates the spoofing state."
    ::= { prpaEntry 58 }

prpaCCPState OBJECT-TYPE
    SYNTAX  INTEGER
        {
            off(1),
	    on(2)
        }
    ACCESS  read-only
    STATUS  mandatory
    DESCRIPTION
        "This parameter indicates the CCP state."
    ::= { prpaEntry 59 }

prpaIPCPState OBJECT-TYPE
    SYNTAX  INTEGER
        {
            off(1),
	    on(2)
        }
    ACCESS  read-only
    STATUS  mandatory
    DESCRIPTION
        "This parameter indicates the IPCP state."
    ::= { prpaEntry 60 }

prpaIPXCPState OBJECT-TYPE
    SYNTAX  INTEGER
        {
            off(1),
	    on(2)
        }
    ACCESS  read-only
    STATUS  mandatory
    DESCRIPTION
        "This parameter indicates the IPXCP state."
    ::= { prpaEntry 61 }

prpaBNCPState OBJECT-TYPE
    SYNTAX  INTEGER
        {
            off(1),
	    on(2)
        }
    ACCESS  read-only
    STATUS  mandatory
    DESCRIPTION
        "This parameter indicates the BNCP state."
    ::= { prpaEntry 62 }

prpaARAPState OBJECT-TYPE
    SYNTAX  INTEGER
        {
            off(1),
	    on(2)
        }
    ACCESS  read-only
    STATUS  mandatory
    DESCRIPTION
        "This parameter indicates the ARAP state."
    ::= { prpaEntry 63 }

prpaLinkUtil OBJECT-TYPE
    SYNTAX  INTEGER
    ACCESS  read-only
    STATUS  mandatory
    DESCRIPTION
        "This parameter indicates the link utilization."
    ::= { prpaEntry 64 }

-- Local route path table --

plocalNumber OBJECT-TYPE
    SYNTAX  INTEGER
    ACCESS  read-only
    STATUS  mandatory
    DESCRIPTION
        "The number of local route paths on this system."
    ::= { path 3 }

plocalTable OBJECT-TYPE
    SYNTAX  SEQUENCE OF PlocalEntry
    ACCESS  not-accessible
    STATUS  mandatory
    DESCRIPTION
        "Local route path table."
    ::= { path 4 }

plocalEntry OBJECT-TYPE
    SYNTAX  PlocalEntry
    ACCESS  not-accessible
    STATUS  mandatory
    DESCRIPTION
        "A list of information for a local route path."
    INDEX   { plocalIndex }
    ::= { plocalTable 1 }

PlocalEntry ::=
    SEQUENCE {
        plocalIndex
            INTEGER,
        plocalName
            DisplayString (SIZE (0..12)),
        plocalType
            INTEGER,
        plocalPortIdx    
            INTEGER,
        plocalInPackets 
            Counter,
        plocalOutPackets
            Counter,
        plocalInBytes
            Counter,
        plocalOutBytes
            Counter,
        plocalResetPlocalCounters
            INTEGER,
        plocalFilterAction
            INTEGER,
        plocalFilterMap
            INTEGER,
        plocalLoggerMap
            INTEGER,
        plocalFilterCount
            Counter,
        plocalLoggerCount
            Counter,
        plocalDiscardedPackets 
            Counter,
        plocalForwardedPackets
            Counter,
        plocalReceivedPackets
            Counter
    }

plocalIndex OBJECT-TYPE
    SYNTAX  INTEGER
    ACCESS  read-only
    STATUS  mandatory
    DESCRIPTION
        "A unique value for each network route path.  
        The value for each path must remain constant at
        least from one re-initialization of the entity's
        network management system to the next re-
        initialization."
    ::= { plocalEntry 1 }

plocalName OBJECT-TYPE
    SYNTAX  DisplayString (SIZE (0..12))
    ACCESS  read-only
    STATUS  mandatory
    DESCRIPTION
        "A unique user-recognizable name for each local 
        route path."
    ::= { plocalEntry 2 }

plocalType OBJECT-TYPE
    SYNTAX  INTEGER
         {
            invalid(1),
            valid(2)
        }
    ACCESS  read-only
    STATUS  mandatory
    DESCRIPTION
        "The variable indicates whether this local route path
        entry is currently effective."
    ::= { plocalEntry 3 }

plocalPortIdx OBJECT-TYPE
    SYNTAX  INTEGER
    ACCESS  read-only
    STATUS  mandatory
    DESCRIPTION
        "A number to uniquely identify a port for this local 
        route path. The port that is identified by this index
        is the as the port identified by PortIndex in portTable."
    ::= { plocalEntry 4 }

plocalInPackets OBJECT-TYPE
    SYNTAX  Counter
    ACCESS  read-only
    STATUS  mandatory
    DESCRIPTION
        "Packets received with no error."
    ::= { plocalEntry 5 }

plocalOutPackets OBJECT-TYPE
    SYNTAX  Counter
    ACCESS  read-only
    STATUS  mandatory
    DESCRIPTION
        "Packets transmitted with no error."
    ::= { plocalEntry 6 }

plocalInBytes OBJECT-TYPE
    SYNTAX  Counter
    ACCESS  read-only
    STATUS  mandatory
    DESCRIPTION
        "Bytes received with no error."
    ::= { plocalEntry 7 }

plocalOutBytes OBJECT-TYPE
    SYNTAX  Counter
    ACCESS  read-only
    STATUS  mandatory
    DESCRIPTION
        "Bytes transmitted with no error."
    ::= { plocalEntry 8 }

plocalResetPlocalCounters OBJECT-TYPE
    SYNTAX  INTEGER
    ACCESS  read-write
    STATUS  mandatory
    DESCRIPTION
        "Writing any value to this variable will reset all plocal-related
        counters to zero."
    ::= { plocalEntry 9 }

plocalFilterAction OBJECT-TYPE
    SYNTAX  INTEGER
        {
            discard(1),
            forward(2)
        }
    ACCESS  read-write
    STATUS  mandatory
    DESCRIPTION
        "The action to be taken by the configured this path's filters."
    ::= { plocalEntry 10 }

plocalFilterMap OBJECT-TYPE
    SYNTAX  INTEGER
    ACCESS  read-write
    STATUS  mandatory
    DESCRIPTION
        "This is a 16 bit bitmap corresponds to the bridge filetr table."
    ::= { plocalEntry 11 }

plocalLoggerMap OBJECT-TYPE
    SYNTAX  INTEGER
    ACCESS  read-write
    STATUS  mandatory
    DESCRIPTION
        "This is a 16 bit bitmap corresponds to the bridge logger table."
    ::= { plocalEntry 12 }

plocalFilterCount OBJECT-TYPE
    SYNTAX  Counter
    ACCESS  read-only
    STATUS  mandatory
    DESCRIPTION
        "The number of packets that have been filtered."
    ::= { plocalEntry 13 }

plocalLoggerCount OBJECT-TYPE
    SYNTAX  Counter
    ACCESS  read-only
    STATUS  mandatory
    DESCRIPTION
        "The value gives the number of incoming packets that match
        this log description."
    ::= { plocalEntry 14 }

plocalDiscardedPackets OBJECT-TYPE
    SYNTAX  Counter
    ACCESS  read-only
    STATUS  mandatory
    DESCRIPTION
        "Packets discarded."
    ::= { plocalEntry 15 }

plocalForwardedPackets OBJECT-TYPE
    SYNTAX  Counter
    ACCESS  read-only
    STATUS  mandatory
    DESCRIPTION
        "Packets forwarded."
    ::= { plocalEntry 16 }

plocalReceivedPackets OBJECT-TYPE
    SYNTAX  Counter
    ACCESS  read-only
    STATUS  mandatory
    DESCRIPTION
        "Packets received."
    ::= { plocalEntry 17 }

-- Remote route path table --

prmtNumber OBJECT-TYPE
    SYNTAX  INTEGER
    ACCESS  read-only
    STATUS  mandatory
    DESCRIPTION
        "The number of route paths on this system."
    ::= { path 5 }

prmtTable OBJECT-TYPE
    SYNTAX  SEQUENCE OF PrmtEntry
    ACCESS  not-accessible
    STATUS  mandatory
    DESCRIPTION
        "Route path table."
    ::= { path 6 }

prmtEntry OBJECT-TYPE
    SYNTAX  PrmtEntry
    ACCESS  not-accessible
    STATUS  mandatory
    DESCRIPTION
        "A list of information for a route path."
    INDEX   { prmtIndex }
    ::= { prmtTable 1 }

PrmtEntry ::=
    SEQUENCE {
        prmtIndex
            INTEGER,
        prmtName
            DisplayString (SIZE (0..12)),
        prmtType
            INTEGER,
        prmtInitiator
            INTEGER,
        prmtCongestThreshold
            INTEGER,
        prmtScheduleType1
            INTEGER,
        prmtDaysScheduled1
            INTEGER,
        prmtStartTime1
            OCTET STRING,
        prmtHowLong1
            OCTET STRING,
        prmtScheduleType2
            INTEGER,
        prmtDaysScheduled2
            INTEGER,
        prmtStartTime2
            OCTET STRING,
        prmtHowLong2
            OCTET STRING,
        prmtInPackets 
            Counter,
        prmtOutPackets
            Counter,
        prmtInBytes
            Counter,
        prmtOutBytes
            Counter,
        prmtResetPrmtCounters
            INTEGER,
        prmtFilterAction
            INTEGER,
        prmtFilterMap
            INTEGER,
        prmtLoggerMap
            INTEGER,
        prmtFilterCount
            Counter,
        prmtLoggerCount
            Counter,
        prmtDiscardedPackets 
            Counter,
        prmtForwardedPackets
            Counter,
        prmtReceivedPackets
            Counter,
        prmtSmartFiltering
            INTEGER,
        prmtOutCongestions
            Counter,

-- AB6.0
	prmtRmtRouterName
            DisplayString (SIZE (0..32)),
	prmtTypeSelection
            INTEGER,
	prmtAsyncPortNo
            INTEGER,
	prmtISDNPortNo
            INTEGER,
	prmtISDNReqBaudRate
            INTEGER,
	prmtSpoofState
            INTEGER,
	prmtCCPState
            INTEGER,
	prmtIPCPState
            INTEGER,
	prmtIPXCPState
            INTEGER,
	prmtBNCPState
            INTEGER,
	prmtLinkUtil
            INTEGER,
	prmtPMPortList
            DisplayString (SIZE (0..48)),
	prmtBUPortList
            DisplayString (SIZE (0..48)),
	prmtODPortList
            DisplayString (SIZE (0..48)),
	prmtSCPortList
            DisplayString (SIZE (0..48))
    }

prmtIndex OBJECT-TYPE
    SYNTAX  INTEGER
    ACCESS  read-only
    STATUS  mandatory
    DESCRIPTION
        "A unique value for each network route path.  
        The value for each path must remain constant at
        least from one re-initialization of the entity's
        network management system to the next re-
        initialization."
    ::= { prmtEntry 1 }

prmtName OBJECT-TYPE
    SYNTAX  DisplayString (SIZE (0..12))
    ACCESS  read-write
    STATUS  mandatory
    DESCRIPTION
        "A unique user-recognizable name for each remote 
        PC access path."
    ::= { prmtEntry 2 }

prmtType OBJECT-TYPE
    SYNTAX  INTEGER
         {
            invalid(1),
            valid(2)
        }
    ACCESS  read-write
    STATUS  mandatory
    DESCRIPTION
        "The variable indicates whether this remote route path
        entry is currently effective."
    ::= { prmtEntry 3 }

prmtInitiator OBJECT-TYPE
    SYNTAX  INTEGER
         {
            auto(1),
            passive(2)
        }
    ACCESS  read-write
    STATUS  mandatory
    DESCRIPTION
        "Used on remote path only. This flag tells whether this
        side should initiate the connection."
    ::= { prmtEntry 4 }

prmtCongestThreshold OBJECT-TYPE
    SYNTAX  INTEGER
    ACCESS  read-write
    STATUS  mandatory
    DESCRIPTION
        "Used on remote paths with on-demand ports only. It is 
        used to determine when a on-demand port be started."
    ::= { prmtEntry 5 }

prmtScheduleType1 OBJECT-TYPE
    SYNTAX  INTEGER
        {
            invalid(1),
            daily(2),
            weekly(3),
            monthly(4)
        }
    ACCESS  read-write
    STATUS  mandatory
    DESCRIPTION
        "The variable is meaningful only on paths with schedule port.
        It described the port's schedule type - daily, weekly or
        monthly."
    ::= { prmtEntry 6 }

prmtDaysScheduled1 OBJECT-TYPE
    SYNTAX  INTEGER
    ACCESS  read-write
    STATUS  mandatory
    DESCRIPTION
        "The variable is meaningful only on paths with schedule port.
        A bit map of days on which each '1' bit represents
        a day that the port will be scheduled. The least
        significant bit indicates the 1st day in a period
        (for week, it's Monday; for month, it's the first
        day in a month.)"
    ::= { prmtEntry 7 }

prmtStartTime1 OBJECT-TYPE
    SYNTAX  OCTET STRING
    ACCESS  read-write
    STATUS  mandatory
    DESCRIPTION
        "The variable is meaningful only on paths with schedule port.
        This describes the scheduled port connection period
        in StartHour:StartMinute format."
    ::= { prmtEntry 8 }

prmtHowLong1 OBJECT-TYPE
    SYNTAX  OCTET STRING
    ACCESS  read-write
    STATUS  mandatory
    DESCRIPTION
        "The variable is meaningful only on paths with schedule port.
        This describes the scheduled port connection period
        in DurationHour:DurationMinute format."
    ::= { prmtEntry 9 }

prmtScheduleType2 OBJECT-TYPE
    SYNTAX  INTEGER
        {
            invalid(1),
            daily(2),
            weekly(3),
            monthly(4)
        }
    ACCESS  read-write
    STATUS  mandatory
    DESCRIPTION
        "The variable is meaningful only on paths with schedule port.
        It described the port's schedule type - daily, weekly or
        monthly."
    ::= { prmtEntry 10 }

prmtDaysScheduled2 OBJECT-TYPE
    SYNTAX  INTEGER
    ACCESS  read-write
    STATUS  mandatory
    DESCRIPTION
        "The variable is meaningful only on paths with schedule port.
        A bit map of days on which each '1' bit represents
        a day that the port will be scheduled. The least
        significant bit indicates the 1st day in a period
        (for week, it's Monday; for month, it's the first
        day in a month.)"
    ::= { prmtEntry 11 }

prmtStartTime2 OBJECT-TYPE
    SYNTAX  OCTET STRING
    ACCESS  read-write
    STATUS  mandatory
    DESCRIPTION
        "The variable is meaningful only on paths with schedule port.
        This describes the scheduled port connection period
        in StartHour:StartMinute format."
    ::= { prmtEntry 12 }

prmtHowLong2 OBJECT-TYPE
    SYNTAX  OCTET STRING
    ACCESS  read-write
    STATUS  mandatory
    DESCRIPTION
        "The variable is meaningful only on paths with schedule port.
        This describes the scheduled port connection period
        in DurationHour:DurationMinute format."
    ::= { prmtEntry 13 }

prmtInPackets OBJECT-TYPE
    SYNTAX  Counter
    ACCESS  read-only
    STATUS  mandatory
    DESCRIPTION
        "Packets received with no error."
    ::= { prmtEntry 14 }

prmtOutPackets OBJECT-TYPE
    SYNTAX  Counter
    ACCESS  read-only
    STATUS  mandatory
    DESCRIPTION
        "Packets transmitted with no error."
    ::= { prmtEntry 15 }

prmtInBytes OBJECT-TYPE
    SYNTAX  Counter
    ACCESS  read-only
    STATUS  mandatory
    DESCRIPTION
        "Bytes received with no error."
    ::= { prmtEntry 16 }

prmtOutBytes OBJECT-TYPE
    SYNTAX  Counter
    ACCESS  read-only
    STATUS  mandatory
    DESCRIPTION
        "Bytes transmitted with no error."
    ::= { prmtEntry 17 }

prmtResetPrmtCounters OBJECT-TYPE
    SYNTAX  INTEGER
    ACCESS  read-write
    STATUS  mandatory
    DESCRIPTION
        "Writing any value to this variable will reset all prmt-related
        counters to zero."
    ::= { prmtEntry 18 }

prmtFilterAction OBJECT-TYPE
    SYNTAX  INTEGER
        {
            discard(1),
            forward(2)
        }
    ACCESS  read-write
    STATUS  mandatory
    DESCRIPTION
        "The action to be taken by the configured this path's filters."
    ::= { prmtEntry 19 }

prmtFilterMap OBJECT-TYPE
    SYNTAX  INTEGER
    ACCESS  read-write
    STATUS  mandatory
    DESCRIPTION
        "This is a 16 bit bitmap corresponds to the bridge filetr table."
    ::= { prmtEntry 20 }

prmtLoggerMap OBJECT-TYPE
    SYNTAX  INTEGER
    ACCESS  read-write
    STATUS  mandatory
    DESCRIPTION
        "This is a 16 bit bitmap corresponds to the bridge logger table."
    ::= { prmtEntry 21 }

prmtFilterCount OBJECT-TYPE
    SYNTAX  Counter
    ACCESS  read-only
    STATUS  mandatory
    DESCRIPTION
        "The number of packets that have been filtered."
    ::= { prmtEntry 22 }

prmtLoggerCount OBJECT-TYPE
    SYNTAX  Counter
    ACCESS  read-only
    STATUS  mandatory
    DESCRIPTION
        "The value gives the number of incoming packets that match
        this log description."
    ::= { prmtEntry 23 }

prmtDiscardedPackets OBJECT-TYPE
    SYNTAX  Counter
    ACCESS  read-only
    STATUS  mandatory
    DESCRIPTION
        "Packets discarded."
    ::= { prmtEntry 24 }

prmtForwardedPackets OBJECT-TYPE
    SYNTAX  Counter
    ACCESS  read-only
    STATUS  mandatory
    DESCRIPTION
        "Packets forwarded."
    ::= { prmtEntry 25 }

prmtReceivedPackets OBJECT-TYPE
    SYNTAX  Counter
    ACCESS  read-only
    STATUS  mandatory
    DESCRIPTION
        "Packets received."
    ::= { prmtEntry 26 }

prmtSmartFiltering OBJECT-TYPE
    SYNTAX  INTEGER
        {
            disabled(1),
            enabled(2)
        }
    ACCESS  read-write
    STATUS  mandatory
    DESCRIPTION
        "This enables/disables AccessBuilder's Smart Filtering feature."
    ::= { prmtEntry 27 }

prmtOutCongestions OBJECT-TYPE
    SYNTAX  Counter
    ACCESS  read-only
    STATUS  mandatory
    DESCRIPTION
        "Number of packet transmit congestions."
    ::= { prmtEntry 28 }

-- AB6.0

prmtRmtRouterName OBJECT-TYPE
    SYNTAX  DisplayString (SIZE (0..32))
    ACCESS  read-write
    STATUS  mandatory
    DESCRIPTION
        "Remote router name."
    ::= { prmtEntry 29 }

prmtTypeSelection OBJECT-TYPE
    SYNTAX  INTEGER
        {
	    permanent-only(1),
	    permanent-with-backup(2),
	    on-demand-only(3),
	    schedule-only(4)
        }
    ACCESS  read-write
    STATUS  mandatory
    DESCRIPTION
        "Path type selection."
    ::= { prmtEntry 30 }

prmtAsyncPortNo OBJECT-TYPE
    SYNTAX  INTEGER
    ACCESS  read-write
    STATUS  mandatory
    DESCRIPTION
        "Number of async ports for Backup, On-demand and Schedule type."
    ::= { prmtEntry 31 }

prmtISDNPortNo OBJECT-TYPE
    SYNTAX  INTEGER
    ACCESS  read-write
    STATUS  mandatory
    DESCRIPTION
        "Number of ISDN ports for Backup, On-demand and Schedule type."
    ::= { prmtEntry 32 }

prmtISDNReqBaudRate OBJECT-TYPE
    SYNTAX  INTEGER
    	{
	    br-56000(1),
	    br-64000(2),
	    auto(3)
	}
    ACCESS  read-write
    STATUS  mandatory
    DESCRIPTION
        "ISDN required baudrate for satisfying all cases."
    ::= { prmtEntry 33 }

prmtSpoofState OBJECT-TYPE
    SYNTAX  INTEGER
        {
            off(1),
            connect(2),
	    spoofing(3),
	    disabled(4)
        }
    ACCESS  read-only
    STATUS  mandatory
    DESCRIPTION
        "This parameter indicates the spoofing state."
    ::= { prmtEntry 34 }

prmtCCPState OBJECT-TYPE
    SYNTAX  INTEGER
        {
            off(1),
	    on(2)
        }
    ACCESS  read-only
    STATUS  mandatory
    DESCRIPTION
        "This parameter indicates the CCP state."
    ::= { prmtEntry 35 }

prmtIPCPState OBJECT-TYPE
    SYNTAX  INTEGER
        {
            off(1),
	    on(2)
        }
    ACCESS  read-only
    STATUS  mandatory
    DESCRIPTION
        "This parameter indicates the IPCP state."
    ::= { prmtEntry 36 }

prmtIPXCPState OBJECT-TYPE
    SYNTAX  INTEGER
        {
            off(1),
	    on(2)
        }
    ACCESS  read-only
    STATUS  mandatory
    DESCRIPTION
        "This parameter indicates the IPXCP state."
    ::= { prmtEntry 37 }

prmtBNCPState OBJECT-TYPE
    SYNTAX  INTEGER
        {
            off(1),
	    on(2)
        }
    ACCESS  read-only
    STATUS  mandatory
    DESCRIPTION
        "This parameter indicates the BNCP state."
    ::= { prmtEntry 38 }

prmtLinkUtil OBJECT-TYPE
    SYNTAX  INTEGER
    ACCESS  read-only
    STATUS  mandatory
    DESCRIPTION
        "This parameter indicates the link utilization."
    ::= { prmtEntry 39 }

prmtPMPortList OBJECT-TYPE
    SYNTAX  DisplayString (SIZE (0..48))
    ACCESS  read-only
    STATUS  mandatory
    DESCRIPTION
        "This parameter indicates the port-id list for the binding
	 permenant ports on this Remote path."
    ::= { prmtEntry 40 }

prmtBUPortList OBJECT-TYPE
    SYNTAX  DisplayString (SIZE (0..48))
    ACCESS  read-only
    STATUS  mandatory
    DESCRIPTION
        "This parameter indicates the port-id list for the binding
	 backup ports on this Remote path."
    ::= { prmtEntry 41 }

prmtODPortList OBJECT-TYPE
    SYNTAX  DisplayString (SIZE (0..48))
    ACCESS  read-only
    STATUS  mandatory
    DESCRIPTION
        "This parameter indicates the port-id list for the binding
	 on-demand ports on this Remote path."
    ::= { prmtEntry 42 }

prmtSCPortList OBJECT-TYPE
    SYNTAX  DisplayString (SIZE (0..48))
    ACCESS  read-only
    STATUS  mandatory
    DESCRIPTION
        "This parameter indicates the port-id list for the binding
	 schedule ports on this Remote path."
    ::= { prmtEntry 43 }

-- Route path port table --

prmtPortTable OBJECT-TYPE
    SYNTAX  SEQUENCE OF PrmtPortEntry
    ACCESS  not-accessible
    STATUS  mandatory
    DESCRIPTION
        "Route path port table."
    ::= { path 7 }

prmtPortEntry OBJECT-TYPE
    SYNTAX  PrmtPortEntry
    ACCESS  not-accessible
    STATUS  mandatory
    DESCRIPTION
        "A list of information for each port associated with a
        route path."
    INDEX   { prmtPortPrmtIdx,
          prmtPortPortIdx }
    ::= { prmtPortTable 1 }

PrmtPortEntry ::=
    SEQUENCE {
        prmtPortPrmtIdx
            INTEGER,
        prmtPortPortIdx
            INTEGER,
        prmtPortType
            INTEGER,
        prmtPortPhoneNumber
            OCTET STRING (SIZE (0..15)),
        prmtPortDirectoryNo
            OCTET STRING (SIZE (0..20))
    }

prmtPortPrmtIdx OBJECT-TYPE
    SYNTAX  INTEGER
    ACCESS  read-only
    STATUS  mandatory
    DESCRIPTION
        "The route path on which this entry's equivalence is effective.
        The path identified by a particular value of this index
        is the same route path as identified by the same value
        of prmtIndex."
    ::= { prmtPortEntry 1 }

prmtPortPortIdx OBJECT-TYPE
    SYNTAX  INTEGER
    ACCESS  read-only
    STATUS  mandatory
    DESCRIPTION
        "The port on which the entry's equivalence is effective.
        The path identified by a particular value of this index
        is the same route path as identified by the same value
        of portIndex."
    ::= { prmtPortEntry 2 }

prmtPortType OBJECT-TYPE
    SYNTAX  INTEGER
        {
            invalid(1),
            on-demand(2),
            permanent(3),
            backup(4),
            scheduled(5)
        }
    ACCESS  read-write
    STATUS  mandatory
    DESCRIPTION
        "Used on remote path only. This vaiable tells the type of 
        port."
    ::= { prmtPortEntry 3 }

prmtPortPhoneNumber OBJECT-TYPE
    SYNTAX  OCTET STRING (SIZE (0..15))
    ACCESS  read-write
    STATUS  mandatory
    DESCRIPTION
        "Used on remote path only. The phone number to be used by 
        this type of port in the path." 
    ::= { prmtPortEntry 4 }

prmtPortDirectoryNo OBJECT-TYPE
    SYNTAX  OCTET STRING (SIZE (0..20))
    ACCESS  read-write
    STATUS  mandatory
    DESCRIPTION
        "Used on remote path only. The directory number to be used by 
        this type of port in the path." 
    ::= { prmtPortEntry 5 }

-- End of path tables --

pathResetAllCounters OBJECT-TYPE
    SYNTAX  INTEGER
    ACCESS  read-write
    STATUS  mandatory
    DESCRIPTION
        "Writing any value to this variable will reset all path-related
        counters to zero."
    ::= { path 8 }

-- AB6.0

prmtPhoneTable OBJECT-TYPE
    SYNTAX  SEQUENCE OF PrmtPhoneEntry
    ACCESS  not-accessible
    STATUS  mandatory
    DESCRIPTION
        "Router path phone table for Backup, On-demand and Schedule type."
    ::= { path 9 }

prmtPhoneEntry OBJECT-TYPE
    SYNTAX  PrmtPhoneEntry
    ACCESS  not-accessible
    STATUS  mandatory
    DESCRIPTION
        "A list of phone data for each port associated with a
        route path."
    INDEX   { prmtPhonePrmtIdx,
          prmtPhoneIdx }
    ::= { prmtPhoneTable 1 }

PrmtPhoneEntry ::=
    SEQUENCE {
        prmtPhonePrmtIdx
            INTEGER,
        prmtPhoneIdx
            INTEGER,
        prmtPhoneType
            INTEGER,
        prmtPhonePhoneNumber
            OCTET STRING (SIZE (0..15)),
        prmtPhoneDirectoryNo
            OCTET STRING (SIZE (0..20))
    }

prmtPhonePrmtIdx OBJECT-TYPE
    SYNTAX  INTEGER
    ACCESS  read-only
    STATUS  mandatory
    DESCRIPTION
	"Path index for phone table."
    ::= { prmtPhoneEntry 1 }

prmtPhoneIdx OBJECT-TYPE
    SYNTAX  INTEGER
    ACCESS  read-only
    STATUS  mandatory
    DESCRIPTION
	"Phone table index."
    ::= { prmtPhoneEntry 2 }

prmtPhoneType OBJECT-TYPE
    SYNTAX  INTEGER
        {
            invalid(1),
            on-demand-isdn(2),
            on-demand-async(3),
            backup-isdn(4),
            backup-async(5),
            scheduled-isdn(6),
            scheduled-async(7)
        }
    ACCESS  read-write
    STATUS  mandatory
    DESCRIPTION
	"Phone type for remote path."
    ::= { prmtPhoneEntry 3 }

prmtPhonePhoneNumber OBJECT-TYPE
    SYNTAX  OCTET STRING (SIZE (0..15))
    ACCESS  read-write
    STATUS  mandatory
    DESCRIPTION
	"Phone number in the phone table."
    ::= { prmtPhoneEntry 4 }

prmtPhoneDirectoryNo OBJECT-TYPE
    SYNTAX  OCTET STRING (SIZE (0..20))
    ACCESS  read-write
    STATUS  mandatory
    DESCRIPTION
	"Directory number in the phone table."
    ::= { prmtPhoneEntry 5 }

-- ip group --

ipRpa OBJECT IDENTIFIER ::= { crip 1 }

ipRt OBJECT IDENTIFIER ::= { crip 2 }

-- ip remote PC access path group --

ipRpaNumber OBJECT-TYPE
    SYNTAX  INTEGER
    ACCESS  read-only
    STATUS  mandatory
    DESCRIPTION
        "The number of IP remote PC paths on this system."
    ::= { ipRpa 1 }

-- ip route remote PC access table --

ipRpaTable OBJECT-TYPE
    SYNTAX  SEQUENCE OF IpRpaEntry
    ACCESS  not-accessible
    STATUS  mandatory
    DESCRIPTION
        "Remote PC access path table."
    ::= { ipRpa 2 }

ipRpaEntry OBJECT-TYPE
    SYNTAX  IpRpaEntry
    ACCESS  not-accessible
    STATUS  mandatory
    DESCRIPTION
        "A path to a remote PC."
    INDEX   { ipRpaIndex }
    ::= { ipRpaTable 1 }

IpRpaEntry ::=
    SEQUENCE {
        ipRpaIndex
            INTEGER,
        ipRpaCurrentClientIpAddress
            IpAddress,
        ipRpaConfigClientIpAddress
            IpAddress,
        ipRpaTcpHdrCompress
            INTEGER,
	ipRpaType
            INTEGER
    }

ipRpaIndex OBJECT-TYPE
    SYNTAX  INTEGER
    ACCESS  read-only
    STATUS  mandatory
    DESCRIPTION
        "The RPA path on which the entry's equivalence is effective.
        The path identified by a particular value of this index
        is the same RPA path as identified by the same value
        of prpaIndex."
    ::= { ipRpaEntry 1 }

ipRpaCurrentClientIpAddress OBJECT-TYPE
    SYNTAX  IpAddress
    ACCESS  read-only
    STATUS  mandatory
    DESCRIPTION
        "The current or last logged-in SLIP remote PC's IP address."
    ::= { ipRpaEntry 2 }

ipRpaConfigClientIpAddress OBJECT-TYPE
    SYNTAX  IpAddress
    ACCESS  read-write
    STATUS  mandatory
    DESCRIPTION
        "The administrator-assigned PPP remote PC's IP address. This is
        the IP address to be used by any PPP remote PC dial in to this port."
    ::= { ipRpaEntry 3 }

ipRpaTcpHdrCompress OBJECT-TYPE
    SYNTAX  INTEGER
        {
            no(1),
            yes(2)
        }
    ACCESS  read-write
    STATUS  mandatory
    DESCRIPTION
        "The VJ Compression (RFC 1144 TCP/IP Header Compression) of the PPP "
    ::= { ipRpaEntry 4 }

ipRpaType OBJECT-TYPE
    SYNTAX  INTEGER
         {
            invalid(1),
            valid(2)
        }
    ACCESS  read-only
    STATUS  mandatory
    DESCRIPTION
        "The type of iprpath. Invalid means this path no longer
        exists."
    ::= { ipRpaEntry 5 }

-- end of ip remote access table --

ipRpaBootpEnabled OBJECT-TYPE
    SYNTAX  INTEGER
        {
            no(1),
            yes(2)
        }
    ACCESS  read-write
    STATUS  mandatory
    DESCRIPTION
        "The variable enables BootP server on the AccessBuilder."
    ::= { ipRpa 3 }

ipRpaRarpEnabled OBJECT-TYPE
    SYNTAX  INTEGER
        {
            no(1),
            yes(2)
        }
    ACCESS  read-write
    STATUS  mandatory
    DESCRIPTION
        "The variable enables Reverse ARP server on the AccessBuilder."
    ::= { ipRpa 4 }

ipRpaBootpOrRarpRequired OBJECT-TYPE
    SYNTAX  INTEGER
        {
            no(1),
            yes(2)
        }
    ACCESS  read-write
    STATUS  mandatory
    DESCRIPTION
        "The variable forces remote clients to run BootP or Reverse ARP
		protocol before accessing IP hosts on the network."
    ::= { ipRpa 5 }

ipRpaBootpInPackets OBJECT-TYPE
    SYNTAX  Counter
    ACCESS  read-only
    STATUS  mandatory
    DESCRIPTION
        "BootP packets received with no error."
    ::= { ipRpa 6 }

ipRpaBootpOutPackets OBJECT-TYPE
    SYNTAX  Counter
    ACCESS  read-only
    STATUS  mandatory
    DESCRIPTION
        "BootP packets sent with no error."
    ::= { ipRpa 7 }

ipRpaRarpInPackets OBJECT-TYPE
    SYNTAX  Counter
    ACCESS  read-only
    STATUS  mandatory
    DESCRIPTION
        "Reverse ARP packets received with no error."
    ::= { ipRpa 8 }

ipRpaRarpOutPackets OBJECT-TYPE
    SYNTAX  Counter
    ACCESS  read-only
    STATUS  mandatory
    DESCRIPTION
        "Reverse ARP packets sent with no error."
    ::= { ipRpa 9 }

ipRpaResetAllRasCounters OBJECT-TYPE
    SYNTAX  INTEGER
    ACCESS  read-write
    STATUS  mandatory
    DESCRIPTION
        "Writing any value to this variable will reset all Bootp and
		Reverse ARP counters to zero."
    ::= { ipRpa 10 }

ipRpaPRPAIpHdrCompress OBJECT-TYPE
    SYNTAX  INTEGER
        {
            no(1),
            yes(2)
        }
    ACCESS  read-write
    STATUS  mandatory
    DESCRIPTION
        "Turn on/off IP header compression for remote access path."
    ::= { ipRpa 11 }

-- ip route group --

-- ip static route table --

ipSRouteNumber OBJECT-TYPE
    SYNTAX  INTEGER
    ACCESS  read-only
    STATUS  mandatory
    DESCRIPTION
        "The number of IP static routes on this system."
    ::= { ipRt 1 }

ipSRouteTable OBJECT-TYPE
    SYNTAX  SEQUENCE OF IpSRouteEntry
    ACCESS  not-accessible
    STATUS  mandatory
    DESCRIPTION
        "IP static route table."
    ::= { ipRt 2 }

ipSRouteEntry OBJECT-TYPE
    SYNTAX  IpSRouteEntry
    ACCESS  not-accessible
    STATUS  mandatory
    DESCRIPTION
        "A list of information for each static route."
    INDEX   { ipSRouteIndex }
    ::= { ipSRouteTable 1 }

IpSRouteEntry ::=
    SEQUENCE {
        ipSRouteIndex
            INTEGER,
        ipSRouteName
            DisplayString (SIZE (0..8)),
        ipSRouteType
            INTEGER,
        ipSRoutePathType
            INTEGER,
        ipSRoutePathIdx
            INTEGER,
        ipSRouteDestIpAddress
            IpAddress,
        ipSRouteNextRouter
            IpAddress,
        ipSRouteHopCount
            INTEGER

    }

ipSRouteIndex OBJECT-TYPE
    SYNTAX  INTEGER
    ACCESS  read-only
    STATUS  mandatory
    DESCRIPTION
        "A statics route number of the static route for which
        the entry contains the route's information."
    ::= { ipSRouteEntry 1 }

ipSRouteName OBJECT-TYPE
    SYNTAX  DisplayString (SIZE (0..8))
    ACCESS  read-write
    STATUS  mandatory
    DESCRIPTION
        "An user-defined name for the static route."
    ::= { ipSRouteEntry 2 }

ipSRouteType OBJECT-TYPE
    SYNTAX  INTEGER
        {
            invalid(1),
            valid(2)
        }
    ACCESS  read-write
    STATUS  mandatory
    DESCRIPTION
        "The variable indicates whether this static route 
        entry is currently effective."
    ::= { ipSRouteEntry 3 }

ipSRoutePathType OBJECT-TYPE
    SYNTAX  INTEGER
        {
            local(1),
            remote (2)
        }
    ACCESS  read-write
    STATUS  mandatory
    DESCRIPTION
        "The variable indicates which route path table (local or
        remote) this route uses."
    ::= { ipSRouteEntry 4 }

ipSRoutePathIdx OBJECT-TYPE
    SYNTAX  INTEGER
    ACCESS  read-write
    STATUS  mandatory
    DESCRIPTION
        "The route path on which the entry's equivalence is effective.
        The path identified by a particular value of this index
        is the same route path as identified by the same value
        of plocalIndex or prmtIndex depending on path type."
    ::= { ipSRouteEntry 5 }

ipSRouteDestIpAddress OBJECT-TYPE
    SYNTAX  IpAddress
    ACCESS  read-write
    STATUS  mandatory
    DESCRIPTION
        "The destination network's IP address."
    ::= { ipSRouteEntry 6 }

ipSRouteNextRouter OBJECT-TYPE
    SYNTAX  IpAddress
    ACCESS  read-write
    STATUS  mandatory
    DESCRIPTION
        "The next router's IP address in this route."
    ::= { ipSRouteEntry 7 }

ipSRouteHopCount OBJECT-TYPE
    SYNTAX  INTEGER
    ACCESS  read-write
    STATUS  mandatory
    DESCRIPTION
        "Number of hop needed to get to the destination network."
    ::= { ipSRouteEntry 8 }

-- ip local route path table --

ipPLocalNumber OBJECT-TYPE
    SYNTAX  INTEGER
    ACCESS  read-only
    STATUS  mandatory
    DESCRIPTION
        "The number of IP dynamic routes on this system."
    ::= { ipRt 3 }

ipPLocalTable OBJECT-TYPE
    SYNTAX  SEQUENCE OF IpPLocalEntry
    ACCESS  not-accessible
    STATUS  mandatory
    DESCRIPTION
        "IP dynamic route table."
    ::= { ipRt 4 }

ipPLocalEntry OBJECT-TYPE
    SYNTAX  IpPLocalEntry
    ACCESS  not-accessible
    STATUS  mandatory
    DESCRIPTION
        "A list of information for a IP dynamic route."
    INDEX   { ipPLocalIndex }
    ::= { ipPLocalTable 1 }

IpPLocalEntry ::=
    SEQUENCE {
        ipPLocalIndex
            INTEGER,
        ipPLocalIpAddress
            IpAddress,
        ipPLocalNetMask
            IpAddress,
        ipPLocalBcastAddr
            INTEGER
    }

ipPLocalIndex OBJECT-TYPE
    SYNTAX  INTEGER
    ACCESS  read-only
    STATUS  mandatory
    DESCRIPTION
        "The route path on which the entry's equivalence is effective.
        The path identified by a particular value of this index
        is the same route path as identified by the same value
        of plocalIndex."
    ::= { ipPLocalEntry 1 }

ipPLocalIpAddress OBJECT-TYPE
    SYNTAX  IpAddress
    ACCESS  read-write
    STATUS  mandatory
    DESCRIPTION
        "This path's IP address."
    ::= { ipPLocalEntry 2 }

ipPLocalNetMask OBJECT-TYPE
    SYNTAX  IpAddress
    ACCESS  read-write
    STATUS  mandatory
    DESCRIPTION
        "The netmask of the network that is attached to the path."
    ::= { ipPLocalEntry 3 }

ipPLocalBcastAddr OBJECT-TYPE
    SYNTAX  INTEGER
          {
              zero-based(0),
              one-based(1)
          }
    ACCESS  read-write
    STATUS  mandatory
    DESCRIPTION
        "The least significant bit of the IP broadcast address
        to network that is attached to the path."
    ::= { ipPLocalEntry 4 }

-- end of ip local route path table --

-- ip remote route path table --

ipPRmtNumber OBJECT-TYPE
    SYNTAX  INTEGER
    ACCESS  read-only
    STATUS  mandatory
    DESCRIPTION
        "The number of IP dynamic routes on this system."
    ::= { ipRt 5 }

ipPRmtTable OBJECT-TYPE
    SYNTAX  SEQUENCE OF IpPRmtEntry
    ACCESS  not-accessible
    STATUS  mandatory
    DESCRIPTION
        "IP dynamic route table."
    ::= { ipRt 6 }

ipPRmtEntry OBJECT-TYPE
    SYNTAX  IpPRmtEntry
    ACCESS  not-accessible
    STATUS  mandatory
    DESCRIPTION
        "A list of information for a IP dynamic route."
    INDEX   { ipPRmtIndex }
    ::= { ipPRmtTable 1 }

IpPRmtEntry ::=
    SEQUENCE {
        ipPRmtIndex
            INTEGER,
        ipPRmtIpAddress

            IpAddress,
        ipPRmtNetMask
            IpAddress,
        ipPRmtBcastAddr
            INTEGER,
        ipPRmtRipUpdate
            INTEGER,
        ipPRmtType
            INTEGER,
        ipPRmtTcpHdrCompress
            INTEGER
    }

ipPRmtIndex OBJECT-TYPE
    SYNTAX  INTEGER
    ACCESS  read-only
    STATUS  mandatory
    DESCRIPTION
        "The route path on which the entry's equivalence is effective.
        The path identified by a particular value of this index
        is the same route path as identified by the same value
        of prmtIndex."
    ::= { ipPRmtEntry 1 }

ipPRmtIpAddress OBJECT-TYPE
    SYNTAX  IpAddress
    ACCESS  read-write
    STATUS  mandatory
    DESCRIPTION
        "This path's IP address."
    ::= { ipPRmtEntry 2 }

ipPRmtNetMask OBJECT-TYPE
    SYNTAX  IpAddress
    ACCESS  read-write
    STATUS  mandatory
    DESCRIPTION
        "The netmask of the network that is attached to the path."
    ::= { ipPRmtEntry 3 }

ipPRmtBcastAddr OBJECT-TYPE
    SYNTAX  INTEGER
          {
              zero-based(0),
              one-based(1)
          }
    ACCESS  read-write
    STATUS  mandatory
    DESCRIPTION
        "The least significant bit of the IP broadcast address
        to network that is attached to the path."
    ::= { ipPRmtEntry 4 }

ipPRmtRipUpdate OBJECT-TYPE
    SYNTAX  INTEGER
        {
            disabled(1),
            trigger-update(2),
            periodic-update(3)
        }
    ACCESS  read-write
    STATUS  mandatory
    DESCRIPTION
        "The method of sending IP RIP packets and updating routing
        database for this path."
    ::= { ipPRmtEntry 5 }

ipPRmtType OBJECT-TYPE
    SYNTAX  INTEGER
        {
            invalid(1),
            valid(2)
        }
    ACCESS  read-only
    STATUS  mandatory
    DESCRIPTION
        "Indication of validity of this entry."
    ::= { ipPRmtEntry 6 }

ipPRmtTcpHdrCompress OBJECT-TYPE
    SYNTAX  INTEGER
        {
            no(1),
            yes(2)
        }
    ACCESS  read-write
    STATUS  mandatory
    DESCRIPTION
        "The VJ Compression (TCP/IP Header Compression) of the PPP "
    ::= { ipPRmtEntry 7 }

-- end of ip remote route path table --

ipRtUpdateTime OBJECT-TYPE
    SYNTAX  INTEGER
    ACCESS  read-write
    STATUS  mandatory
    DESCRIPTION
        "The time interval (in seconds) at which the routing information
        is being updated."
    ::= { ipRt 7 }

ipRtRipEnabled OBJECT-TYPE
    SYNTAX  INTEGER
        {
            no(1),
            yes(2)
        }
    ACCESS  read-write
    STATUS  mandatory
    DESCRIPTION
        "RIP protocol enable/disable flag."
    ::= { ipRt 8 }

ipRtEnabled OBJECT-TYPE
    SYNTAX  INTEGER
        {
            no(1),
            yes(2)
        }
    ACCESS  read-write
    STATUS  mandatory
    DESCRIPTION
        "Router function enable/disable flag."
    ::= { ipRt 9 }

ipRtDefaultTTL OBJECT-TYPE
    SYNTAX  INTEGER
    ACCESS  read-write
    STATUS  mandatory
    DESCRIPTION
        "The default time-to-live value for IP messages."
    ::= { ipRt 10 }

ipRtPoisonReverse OBJECT-TYPE
    SYNTAX  INTEGER
        {
            disabled(1),
            enabled(2)
        }
    ACCESS  read-write
    STATUS  mandatory
    DESCRIPTION
        "This flag tells whether to enable Poison-Reverse feature
        in RIP protocol."
    ::= { ipRt 11 }

ipRtResetAllCounters OBJECT-TYPE
    SYNTAX  INTEGER
    ACCESS  read-write
    STATUS  mandatory
    DESCRIPTION
        "Writing any value to this variable will reset all port-related
        counters to zero."
    ::= { ipRt 12 }

ipRtInPackets OBJECT-TYPE
    SYNTAX  Counter
    ACCESS  read-only
    STATUS  mandatory
    DESCRIPTION
        "IP packets received with no error."
    ::= { ipRt 13 }

ipRtOutPackets OBJECT-TYPE
    SYNTAX  Counter
    ACCESS  read-only
    STATUS  mandatory
    DESCRIPTION
        "IP packets transmitted with no error."
    ::= { ipRt 14 }


ipRtDefaultRouterAddress OBJECT-TYPE
    SYNTAX  IpAddress
    ACCESS  read-write
    STATUS  mandatory
    DESCRIPTION
        "The default router's IP address."
    ::= { ipRt 15 }

ipRtDefaultRouterPathType OBJECT-TYPE
    SYNTAX  INTEGER
        {
            local(1),
            remote (2)
        }
    ACCESS  read-write
    STATUS  mandatory
    DESCRIPTION
        "The variable indicates which route path table (local or
        remote) this route uses."
    ::= { ipRt 16 }

ipRtDefaultRouterPathIdx OBJECT-TYPE
    SYNTAX  INTEGER
    ACCESS  read-write
    STATUS  mandatory
    DESCRIPTION
        "The variable indicates the index to the path table (local or
        remote) this route uses."
    ::= { ipRt 17 }

ipRtDiscardNBBcastPkts OBJECT-TYPE
    SYNTAX  INTEGER
        {
            no(1),
            yes(2)
        }
    ACCESS  read-write
    STATUS  mandatory
    DESCRIPTION
        "The variable indicates to discard or forward the NETBIOS 
         broadcast packets to remote dial-in ports."
    ::= { ipRt 18 }

-- End of ipRt group --

-- ipx group --

ipxRpa OBJECT IDENTIFIER ::= { ipx 1 }

ipxRt OBJECT IDENTIFIER ::= { ipx 2 }

-- ipx RPA group --

ipxRpaNetNumber OBJECT-TYPE
    SYNTAX  OCTET STRING (SIZE (4))
    ACCESS  read-write
    STATUS  mandatory
    DESCRIPTION
        "The IPX network address for all RPA paths."
    ::= { ipxRpa 1 }

ipxRpaNumber OBJECT-TYPE
    SYNTAX  INTEGER
    ACCESS  read-only
    STATUS  mandatory
    DESCRIPTION
        "The number of IPX remote PC paths on this system."
    ::= { ipxRpa 2 }

-- ipx remote PC access table --

ipxRpaTable OBJECT-TYPE
    SYNTAX  SEQUENCE OF IpxRpaEntry
    ACCESS  not-accessible
    STATUS  mandatory
    DESCRIPTION
        "IPX Remote PC access path table."
    ::= { ipxRpa 3 }

ipxRpaEntry OBJECT-TYPE
    SYNTAX  IpxRpaEntry
    ACCESS  not-accessible
    STATUS  mandatory
    DESCRIPTION
        "A path to a IPX remote PC."
    INDEX   { ipxRpaIndex }
    ::= { ipxRpaTable 1 }

IpxRpaEntry ::=
    SEQUENCE {
        ipxRpaIndex
            INTEGER,
        ipxRpaCurrHostAddr
            OCTET STRING (SIZE (6))
    }

ipxRpaIndex OBJECT-TYPE
    SYNTAX  INTEGER
    ACCESS  read-only
    STATUS  mandatory
    DESCRIPTION
        "The RPA path on which the entry's equivalence is effective.
        The path identified by a particular value of this index
        is the same RPA path as identified by the same value
        of prpaIndex."
    ::= { ipxRpaEntry 1 }

ipxRpaCurrHostAddr OBJECT-TYPE
    SYNTAX  OCTET STRING (SIZE (6))
    ACCESS  read-only
    STATUS  mandatory
    DESCRIPTION
        "Current IPX Host Address"
    ::= { ipxRpaEntry 2 }

-- ipx route group --

-- ipx static route table --

ipxSRouteNumber OBJECT-TYPE
    SYNTAX  INTEGER
    ACCESS  read-only
    STATUS  mandatory
    DESCRIPTION
        "The number of IPX static routes on this system."
    ::= { ipxRt 1 }

ipxSRouteTable OBJECT-TYPE
    SYNTAX  SEQUENCE OF IpxSRouteEntry
    ACCESS  not-accessible
    STATUS  mandatory
    DESCRIPTION
        "IPX static route table."
    ::= { ipxRt 2 }

ipxSRouteEntry OBJECT-TYPE
    SYNTAX  IpxSRouteEntry
    ACCESS  not-accessible
    STATUS  mandatory
    DESCRIPTION
        "A list of information for a IPX static route."
    INDEX   { ipxSRouteIndex }
    ::= { ipxSRouteTable 1 }

IpxSRouteEntry ::=
    SEQUENCE {
        ipxSRouteIndex
            INTEGER,
        ipxSRouteName
            DisplayString (SIZE (0..8)),
        ipxSRouteType
            INTEGER,
        ipxSRoutePathType
            INTEGER,
        ipxSRoutePathIdx
            INTEGER,
        ipxSRouteDestNetNumber
    		OCTET STRING (SIZE (4)),
        ipxSRouteNextHostAddress
            OCTET STRING (SIZE (6)),
        ipxSRouteHopCount
            INTEGER
    }

ipxSRouteIndex OBJECT-TYPE
    SYNTAX  INTEGER
    ACCESS  read-only
    STATUS  mandatory
    DESCRIPTION
        "A statics route number of the IPX static route for which
        the entry contains the route's information."
    ::= { ipxSRouteEntry 1 }

ipxSRouteName OBJECT-TYPE
    SYNTAX  DisplayString (SIZE (0..8))
    ACCESS  read-write
    STATUS  mandatory
    DESCRIPTION
        "An user-defined name for the static route."
    ::= { ipxSRouteEntry 2 }

ipxSRouteType OBJECT-TYPE
    SYNTAX  INTEGER
        {
            invalid(1),
            valid(2)
        }
    ACCESS  read-write
    STATUS  mandatory
    DESCRIPTION
        "The variable indicates whether this static route 
        entry is currently effective."
    ::= { ipxSRouteEntry 3 }

ipxSRoutePathType OBJECT-TYPE
    SYNTAX  INTEGER
        {
            local(1),
            remote(2)
        }
    ACCESS  read-write
    STATUS  mandatory
    DESCRIPTION
        "The variable indicates which route path table (local or
        remote) this route uses."
    ::= { ipxSRouteEntry 4 }

ipxSRoutePathIdx OBJECT-TYPE
    SYNTAX  INTEGER
    ACCESS  read-write
    STATUS  mandatory
    DESCRIPTION
        "The route path on which the entry's equivalence is effective.
        The path identified by a particular value of this index
        is the same route path as identified by the same value
        of plocalIndex or prmtIndex depending on path type."
    ::= { ipxSRouteEntry 5 }

ipxSRouteDestNetNumber OBJECT-TYPE
    SYNTAX  OCTET STRING (SIZE (4))
    ACCESS  read-write
    STATUS  mandatory
    DESCRIPTION
        "The destination network's IPX network address."
    ::= { ipxSRouteEntry 6 }

ipxSRouteNextHostAddress OBJECT-TYPE
    SYNTAX  OCTET STRING (SIZE (6))
    ACCESS  read-write
    STATUS  mandatory
    DESCRIPTION
        "The host address of next IPX router in this route."
    ::= { ipxSRouteEntry 8 }

ipxSRouteHopCount OBJECT-TYPE
    SYNTAX  INTEGER
    ACCESS  read-write
    STATUS  mandatory
    DESCRIPTION
        "Number of hop needed to get to the destination network."
    ::= { ipxSRouteEntry 9 }

-- ipx local route path table --

ipxPLocalNumber OBJECT-TYPE
    SYNTAX  INTEGER
    ACCESS  read-only
    STATUS  mandatory
    DESCRIPTION
        "The number of IPX dynamic routes on this system."
    ::= { ipxRt 3 }

ipxPLocalTable OBJECT-TYPE
    SYNTAX  SEQUENCE OF IpxPLocalEntry
    ACCESS  not-accessible
    STATUS  mandatory
    DESCRIPTION
        "IPX dynamic routes table."
    ::= { ipxRt 4 }

ipxPLocalEntry OBJECT-TYPE
    SYNTAX  IpxPLocalEntry
    ACCESS  not-accessible
    STATUS  mandatory
    DESCRIPTION
        "A list of information for an IPX dynamic route."
    INDEX   { ipxPLocalIndex }
    ::= { ipxPLocalTable 1 }

IpxPLocalEntry ::=
    SEQUENCE {
        ipxPLocalIndex
            INTEGER,
        ipxPLocalNetNumber
            OCTET STRING (SIZE (4)),
        ipxPLocalDataLinkType
            INTEGER
    }

ipxPLocalIndex OBJECT-TYPE
    SYNTAX  INTEGER
    ACCESS  read-only
    STATUS  mandatory
    DESCRIPTION
        "The route path on which the entry's equivalence is effective.
        The path identified by a particular value of this index
        is the same route path as identified by the same value
        of plocalIndex."
    ::= { ipxPLocalEntry 1 }

ipxPLocalNetNumber OBJECT-TYPE
    SYNTAX  OCTET STRING (SIZE (4))
    ACCESS  read-write
    STATUS  mandatory
    DESCRIPTION
        "The network address of the network that is attached 
        to the path."
    ::= { ipxPLocalEntry 2 }

ipxPLocalDataLinkType OBJECT-TYPE
    SYNTAX  INTEGER
        {
            ieee8023(1),
            ethernet(2),
            snap(3),
            ieee8022(4),
            autolearn(5),
			trsnap(6),
			trsap(7)
        }
    ACCESS  read-write
    STATUS  mandatory
    DESCRIPTION
        "For local path only. The type data link header used in this path."
    ::= { ipxPLocalEntry 3 }

-- end of ipx local route path table --

-- ipx remote route path table --

ipxPRmtNumber OBJECT-TYPE
    SYNTAX  INTEGER
    ACCESS  read-only
    STATUS  mandatory
    DESCRIPTION
        "The number of IPX dynamic routes on this system."
    ::= { ipxRt 5 }

ipxPRmtTable OBJECT-TYPE
    SYNTAX  SEQUENCE OF IpxPRmtEntry
    ACCESS  not-accessible
    STATUS  mandatory
    DESCRIPTION
        "IPX dynamic routes table."
    ::= { ipxRt 6 }

ipxPRmtEntry OBJECT-TYPE
    SYNTAX  IpxPRmtEntry
    ACCESS  not-accessible
    STATUS  mandatory
    DESCRIPTION
        "A list of information for an IPX dynamic route."
    INDEX   { ipxPRmtIndex }
    ::= { ipxPRmtTable 1 }

IpxPRmtEntry ::=
    SEQUENCE {
        ipxPRmtIndex
            INTEGER,
        ipxPRmtNetNumber
            OCTET STRING (SIZE (4)),
        ipxPRmtNripUpdate
            INTEGER,
        ipxPRmtType
            INTEGER
    }

ipxPRmtIndex OBJECT-TYPE
    SYNTAX  INTEGER
    ACCESS  read-only
    STATUS  mandatory
    DESCRIPTION
        "The route path on which the entry's equivalence is effective.
        The path identified by a particular value of this index
        is the same route path as identified by the same value
        of prmtIndex."
    ::= { ipxPRmtEntry 1 }

ipxPRmtNetNumber OBJECT-TYPE
    SYNTAX  OCTET STRING (SIZE (4))
    ACCESS  read-write
    STATUS  mandatory
    DESCRIPTION
        "The network address of the network that is attached 
        to the path."
    ::= { ipxPRmtEntry 2 }

ipxPRmtNripUpdate OBJECT-TYPE
    SYNTAX  INTEGER
        {
            disabled(1),
            trigger-update(2),
            periodic-update(3)
        }
    ACCESS  read-write
    STATUS  mandatory
    DESCRIPTION
        "The method of sending NetWare RIP packets and updating
        routing database for this path."
    ::= { ipxPRmtEntry 3 }

ipxPRmtType OBJECT-TYPE
    SYNTAX  INTEGER
        {
            invalid(1),
            valid(2)
        }
    ACCESS  read-only
    STATUS  mandatory
    DESCRIPTION
        "Indication of validity of this entry."
    ::= { ipxPRmtEntry 4 }

-- end of ipx remote route path table --

ipxRtUpdateTime OBJECT-TYPE
    SYNTAX  INTEGER
    ACCESS  read-write
    STATUS  mandatory
    DESCRIPTION
        "The time interval (in seconds) at which the routing information
        is being updated."
    ::= { ipxRt 7 }

ipxRtEnabled OBJECT-TYPE
    SYNTAX  INTEGER
        {
            no(1),
            yes(2)
        }
    ACCESS  read-write
    STATUS  mandatory
    DESCRIPTION
        "IPX router function enable/disable flag."
    ::= { ipxRt 8 }

ipxRtRipEnabled OBJECT-TYPE
    SYNTAX  INTEGER
        {
            no(1),
            yes(2)
        }
    ACCESS  read-write
    STATUS  mandatory
    DESCRIPTION
        "IPX RIP protocol enable/disable flag."
    ::= { ipxRt 9 }

ipxRtResetAllCounters OBJECT-TYPE
    SYNTAX  INTEGER
    ACCESS  read-write
    STATUS  mandatory
    DESCRIPTION
        "Writing any value to this variable will reset all port-related
        counters to zero."
    ::= { ipxRt 11 }

ipxRtInPackets OBJECT-TYPE
    SYNTAX  Counter
    ACCESS  read-only
    STATUS  mandatory
    DESCRIPTION
        "IPX packets received with no error."
    ::= { ipxRt 12 }

ipxRtOutPackets OBJECT-TYPE
    SYNTAX  Counter
    ACCESS  read-only
    STATUS  mandatory
    DESCRIPTION
        "IPX packets transmitted with no error."
    ::= { ipxRt 13 }

-- ipx RIP table --

ipxRtRipNumber OBJECT-TYPE
    SYNTAX  INTEGER
    ACCESS  read-only
    STATUS  mandatory
    DESCRIPTION
        "The number of RIP entries on this system."
    ::= { ipxRt 14 }

ipxRtRipTable OBJECT-TYPE
    SYNTAX  SEQUENCE OF IpxRtRipEntry
    ACCESS  not-accessible
    STATUS  mandatory
    DESCRIPTION
        "This table contains IPX RIP information. Each entry
        corresponds to a route description."
    ::= { ipxRt 15 }

ipxRtRipEntry OBJECT-TYPE
    SYNTAX  IpxRtRipEntry
    ACCESS  not-accessible
    STATUS  mandatory
    DESCRIPTION

        "A list of information for an IPX RIP entry."
    INDEX   { ipxRtRipDestNetNumber }
    ::= { ipxRtRipTable 1 }

IpxRtRipEntry ::=
    SEQUENCE {
        ipxRtRipDestNetNumber
            OCTET STRING (SIZE (4)),
        ipxRtRipPathType
            INTEGER,
        ipxRtRipPathIdx
            INTEGER,
        ipxRtRipNextHostAddress
            OCTET STRING (SIZE (6)),
        ipxRtRipHopCount
            INTEGER,
        ipxRtRipTicks
            INTEGER,
        ipxRtRipRouteType
            INTEGER
        }

ipxRtRipDestNetNumber OBJECT-TYPE
    SYNTAX  OCTET STRING (SIZE (4))
    ACCESS  read-only
    STATUS  mandatory
    DESCRIPTION
        "The destination network's IPX network address."
    ::= { ipxRtRipEntry 1 }

ipxRtRipPathType    OBJECT-TYPE
    SYNTAX  INTEGER
        {
            local(1),
            remote(2),
            proxy(3)
        }
    ACCESS  read-only
    STATUS  mandatory
    DESCRIPTION
        "The variable indicates which route path table (local or
        remote) this route uses."
    ::= { ipxRtRipEntry 2 }

ipxRtRipPathIdx OBJECT-TYPE
    SYNTAX  INTEGER
    ACCESS  read-only
    STATUS  mandatory
    DESCRIPTION
        "The route path on which the entry's equivalence is effective.
        The path identified by a particular value of this index
        is the same route path as identified by the same value
        of plocalIndex or prmtIndex depending on path type."
    ::= { ipxRtRipEntry 3 }

ipxRtRipNextHostAddress OBJECT-TYPE
    SYNTAX  OCTET STRING (SIZE (6))
    ACCESS  read-only
    STATUS  mandatory
    DESCRIPTION
        "The host address of next IPX router in this route."
    ::= { ipxRtRipEntry 4 }

ipxRtRipHopCount OBJECT-TYPE
    SYNTAX  INTEGER
    ACCESS  read-only
    STATUS  mandatory
    DESCRIPTION
        "Number of hop needed to get to the destination network."
    ::= { ipxRtRipEntry 5 }

ipxRtRipTicks OBJECT-TYPE
    SYNTAX  INTEGER
    ACCESS  read-only
    STATUS  mandatory
    DESCRIPTION
        "Number of ticks needed to get to the destination network."
    ::= { ipxRtRipEntry 6 }

ipxRtRipRouteType OBJECT-TYPE
    SYNTAX  INTEGER
        {
            permanent(1),
            dynamic(2),
            static(3)
        }
    ACCESS  read-only
    STATUS  mandatory
    DESCRIPTION
        "Indication of how the route is entered."
    ::= { ipxRtRipEntry 7 }


ipxRtSapNumber OBJECT-TYPE
    SYNTAX  INTEGER
    ACCESS  read-only
    STATUS  mandatory
    DESCRIPTION
        "The number of SAP entries on this system."
    ::= { ipxRt 16 }

ipxRtSapTable OBJECT-TYPE
    SYNTAX  SEQUENCE OF IpxRtSapEntry
    ACCESS  not-accessible
    STATUS  mandatory
    DESCRIPTION
        "This table contains IPX SAP information. Each entry
        corresponds to a route description."
    ::= { ipxRt 17 }

ipxRtSapEntry OBJECT-TYPE
    SYNTAX  IpxRtSapEntry
    ACCESS  not-accessible
    STATUS  mandatory
    DESCRIPTION
        "A list of information for an IPX SAP entry."
    INDEX   { ipxRtSapIndex }
    ::= { ipxRtSapTable 1 }

IpxRtSapEntry ::=
    SEQUENCE {
        ipxRtSapIndex
            INTEGER,
        ipxRtSapServiceName
            OCTET STRING (SIZE (48)),
        ipxRtSapServiceType
            INTEGER,
        ipxRtSapServerNetNumber
            OCTET STRING (SIZE (4)),
        ipxRtSapServerHostAddress
            OCTET STRING (SIZE (6))
        }

ipxRtSapIndex    OBJECT-TYPE
    SYNTAX  INTEGER
    ACCESS  read-only
    STATUS  mandatory
    DESCRIPTION
        "A sequentially assigned index value for each entry."
    ::= { ipxRtSapEntry 1 }

ipxRtSapServiceName OBJECT-TYPE
    SYNTAX  OCTET STRING (SIZE (48))
    ACCESS  read-only
    STATUS  mandatory
    DESCRIPTION
        "The name of the service."
    ::= { ipxRtSapEntry 2 }

ipxRtSapServiceType    OBJECT-TYPE
    SYNTAX  INTEGER
    ACCESS  read-only
    STATUS  mandatory
    DESCRIPTION
        "The variable indicates which type of service this is."
    ::= { ipxRtSapEntry 3 }

ipxRtSapServerNetNumber OBJECT-TYPE
    SYNTAX  OCTET STRING (SIZE (4))
    ACCESS  read-only
    STATUS  mandatory
    DESCRIPTION
        "The network address of next IPX router in this route."
    ::= { ipxRtSapEntry 4 }

ipxRtSapServerHostAddress OBJECT-TYPE
    SYNTAX  OCTET STRING (SIZE (6))
    ACCESS  read-only
    STATUS  mandatory
    DESCRIPTION
        "The host address of next IPX router in this route."
    ::= { ipxRtSapEntry 5 }

ipxSpoofingTime OBJECT-TYPE
    SYNTAX  INTEGER
    ACCESS  read-write
    STATUS  mandatory
    DESCRIPTION
        "The time which centrum remote server acts as proxy"
    ::= { ipxRt 18 }

ipxRtDoNBPropagation OBJECT-TYPE
    SYNTAX  INTEGER
        {
            no(1),
            yes(2)
        }
    ACCESS  read-write
    STATUS  mandatory
    DESCRIPTION
        "The variable indicates to flood the NETBIOS IPX propagation 
		 packets (type 20) to LAN and remote router."
    ::= { ipxRt 19 }


-- bridge group --

-- bridge filter table --

brgFilterNumber OBJECT-TYPE
    SYNTAX  INTEGER
    ACCESS  read-only
    STATUS  mandatory
    DESCRIPTION
        "The number of bridge filters on this system."
    ::= { brg 1 }

brgFilterTable OBJECT-TYPE
    SYNTAX  SEQUENCE OF BrgFilterEntry
    ACCESS  not-accessible
    STATUS  mandatory
    DESCRIPTION
        "This table contains bridge filter information. Each entry
        corresponds to a filter description. Each filter description
        can consist of up to four conditions. When a incoming
        packet matches all the conditions, the packet is filtered."
    ::= { brg 2 }

brgFilterEntry OBJECT-TYPE
    SYNTAX  BrgFilterEntry
    ACCESS  not-accessible
    STATUS  mandatory
    DESCRIPTION
        "A list of information for a bridge filter."
    INDEX   { brgFilterIndex }
    ::= { brgFilterTable 1 }

BrgFilterEntry ::=
    SEQUENCE {
        brgFilterIndex
            INTEGER,
        brgFilterName
            DisplayString (SIZE (0..8)),
        brgFilterType
            INTEGER,
        brgFilterMask1Offset
            INTEGER,
        brgFilterMask1Value
            INTEGER,
        brgFilterMask1Type
            INTEGER,
        brgFilterMask1Size
            INTEGER,
        brgFilterMask2Offset
            INTEGER,
        brgFilterMask2Value
            INTEGER,
        brgFilterMask2Type
            INTEGER,
        brgFilterMask2Size
            INTEGER,
        brgFilterMask3Offset
            INTEGER,
        brgFilterMask3Value
            INTEGER,
        brgFilterMask3Type
            INTEGER,
        brgFilterMask3Size
            INTEGER,
        brgFilterMask4Offset
            INTEGER,
        brgFilterMask4Value
            INTEGER,
        brgFilterMask4Type
            INTEGER,
        brgFilterMask4Size
            INTEGER,
		brgFilterSkipRii
            INTEGER
    }

brgFilterIndex OBJECT-TYPE
    SYNTAX  INTEGER
    ACCESS  read-only
    STATUS  mandatory
    DESCRIPTION
        "A sequentally assigned index value for each entry."
    ::= { brgFilterEntry 1 }

brgFilterName OBJECT-TYPE
    SYNTAX  DisplayString (SIZE (0..8))
    ACCESS  read-write
    STATUS  mandatory
    DESCRIPTION
        "A unique user-recognizable name for each remote 
        bridge filter defined."
    ::= { brgFilterEntry 2 }

brgFilterType OBJECT-TYPE
    SYNTAX  INTEGER
        {
            invalid(1),
            valid(2)
        }
    ACCESS  read-write
    STATUS  mandatory
    DESCRIPTION
        "The indicates whether this filter is defined or not."
    ::= { brgFilterEntry 3 }

brgFilterMask1Offset OBJECT-TYPE
    SYNTAX  INTEGER (0..255)
    ACCESS  read-write
    STATUS  mandatory
    DESCRIPTION
        "The byte offset of the first mask of this filter."
    ::= { brgFilterEntry 4 }

brgFilterMask1Value OBJECT-TYPE
    SYNTAX  INTEGER
    ACCESS  read-write
    STATUS  mandatory
    DESCRIPTION
        "The value of the first mask of this filter. This can be 
        a byte, word or long value."
    ::= { brgFilterEntry 5 }

brgFilterMask1Type OBJECT-TYPE
    SYNTAX  INTEGER
        {
            invalid(1),
            equal(2),
            or(3),
            and(4),
            not(5)
        }
    ACCESS  read-write
    STATUS  mandatory
    DESCRIPTION
        "The type of the 1st mask of this filter."
    ::= { brgFilterEntry 6 }

brgFilterMask1Size OBJECT-TYPE
    SYNTAX  INTEGER
        {
            byte(1),
            half-word(2),
            word(3)
        }
    ACCESS  read-write
    STATUS  mandatory
    DESCRIPTION
        "The size (number of bytes covered by this mask) of the 1st 
        mask of this filter."
    ::= { brgFilterEntry 7 }

brgFilterMask2Offset OBJECT-TYPE
    SYNTAX  INTEGER (0..255)
    ACCESS  read-write
    STATUS  mandatory
    DESCRIPTION
        "The byte offset of the 2nd mask of this filter."
    ::= { brgFilterEntry 8 }

brgFilterMask2Value OBJECT-TYPE
    SYNTAX  INTEGER
    ACCESS  read-write
    STATUS  mandatory
    DESCRIPTION
        "The value of the 2nd mask of this filter. This can be 
        a byte, word or long value."
    ::= { brgFilterEntry 9 }

brgFilterMask2Type OBJECT-TYPE
    SYNTAX  INTEGER
        {
            invalid(1),
            equal(2),
            or(3),
            and(4),
            not(5)
        }
    ACCESS  read-write
    STATUS  mandatory
    DESCRIPTION
        "The type of the 2nd mask of this filter."
    ::= { brgFilterEntry 10 }

brgFilterMask2Size OBJECT-TYPE
    SYNTAX  INTEGER
        {
            byte(1),
            half-word(2),
            word(3)
        }
    ACCESS  read-write
    STATUS  mandatory
    DESCRIPTION
        "The size (number of bytes covered by this mask) of the 2nd 
        mask of this filter."
    ::= { brgFilterEntry 11 }

brgFilterMask3Offset OBJECT-TYPE
    SYNTAX  INTEGER (0..255)
    ACCESS  read-write
    STATUS  mandatory
    DESCRIPTION
        "The byte offset of the 3rd mask of this filter."
    ::= { brgFilterEntry 12 }

brgFilterMask3Value OBJECT-TYPE
    SYNTAX  INTEGER
    ACCESS  read-write
    STATUS  mandatory
    DESCRIPTION
        "The value of the 3rd mask of this filter. This can be 
        a byte, word or long value."
    ::= { brgFilterEntry 13 }

brgFilterMask3Type OBJECT-TYPE
    SYNTAX  INTEGER
        {
            invalid(1),
            equal(2),
            or(3),
            and(4),
            not(5)
        }
    ACCESS  read-write
    STATUS  mandatory
    DESCRIPTION
        "The type of the 3rd mask of this filter."
    ::= { brgFilterEntry 14 }

brgFilterMask3Size OBJECT-TYPE
    SYNTAX  INTEGER
        {
            byte(1),
            half-word(2),
            word(3)
        }
    ACCESS  read-write
    STATUS  mandatory
    DESCRIPTION
        "The size (number of bytes covered by this mask) of the 3rd 
        mask of this filter."
    ::= { brgFilterEntry 15 }

brgFilterMask4Offset OBJECT-TYPE
    SYNTAX  INTEGER (0..255)
    ACCESS  read-write
    STATUS  mandatory
    DESCRIPTION
        "The byte offset of the 4th mask of this filter."
    ::= { brgFilterEntry 16 }

brgFilterMask4Value OBJECT-TYPE
    SYNTAX  INTEGER
    ACCESS  read-write
    STATUS  mandatory
    DESCRIPTION
        "The value of the 4th mask of this filter. This can be 
        a byte, word or long value."
    ::= { brgFilterEntry 17 }

brgFilterMask4Type OBJECT-TYPE
    SYNTAX  INTEGER
        {
            invalid(1),
            equal(2),
            or(3),
            and(4),
            not(5)
        }
    ACCESS  read-write
    STATUS  mandatory
    DESCRIPTION
        "The type of the 4th mask of this filter."
    ::= { brgFilterEntry 18 }

brgFilterMask4Size OBJECT-TYPE
    SYNTAX  INTEGER
        {
            byte(1),
            half-word(2),
            word(3)
        }
    ACCESS  read-write
    STATUS  mandatory
    DESCRIPTION
        "The size (number of bytes covered by this mask) of the 4th 
        mask of this filter."
    ::= { brgFilterEntry 19 }

brgFilterSkipRii OBJECT-TYPE
    SYNTAX  INTEGER
        {
            no(1),
            yes(2)
        }
    ACCESS  read-write
    STATUS  mandatory
    DESCRIPTION
        "Specifying if source route field should be skipped for
        fitler offset."
    ::= { brgFilterEntry 20 }

-- bridge logger table --

brgLoggerNumber OBJECT-TYPE
    SYNTAX  INTEGER
    ACCESS  read-only
    STATUS  mandatory
    DESCRIPTION
        "The number of bridge logger on this system."
    ::= { brg 3 }

brgLoggerTable OBJECT-TYPE
    SYNTAX  SEQUENCE OF BrgLoggerEntry
    ACCESS  not-accessible
    STATUS  mandatory
    DESCRIPTION
        "This table contains bridge logger information. Each entry
        corresponds to a logging description. Each logging description
        can consist of up to four conditions. When a incoming
        packet matches all the conditions, the event is logged."
    ::= { brg 4 }

brgLoggerEntry OBJECT-TYPE
    SYNTAX  BrgLoggerEntry
    ACCESS  not-accessible
    STATUS  mandatory
    DESCRIPTION
        "A description of bridge logger."
    INDEX   { brgLoggerIndex }
    ::= { brgLoggerTable 1 }

BrgLoggerEntry ::=
    SEQUENCE {
        brgLoggerIndex
            INTEGER,
        brgLoggerName
            DisplayString (SIZE (0..8)),
        brgLoggerType
            INTEGER,
        brgLoggerMask1Offset
            INTEGER,
        brgLoggerMask1Value
            INTEGER,
        brgLoggerMask1Type
            INTEGER,
        brgLoggerMask1Size
            INTEGER,
        brgLoggerMask2Offset
            INTEGER,
        brgLoggerMask2Value
            INTEGER,
        brgLoggerMask2Type
            INTEGER,
        brgLoggerMask2Size
            INTEGER,
        brgLoggerMask3Offset
            INTEGER,
        brgLoggerMask3Value
            INTEGER,
        brgLoggerMask3Type
            INTEGER,
        brgLoggerMask3Size
            INTEGER,
        brgLoggerMask4Offset
            INTEGER,
        brgLoggerMask4Value
            INTEGER,
        brgLoggerMask4Type
            INTEGER,
        brgLoggerMask4Size
            INTEGER,
		brgLoggerSkipRii
		    INTEGER
    }

brgLoggerIndex OBJECT-TYPE
    SYNTAX  INTEGER
    ACCESS  read-only
    STATUS  mandatory
    DESCRIPTION
        "A sequentally assigned index value for each entry."
    ::= { brgLoggerEntry 1 }

brgLoggerName OBJECT-TYPE
    SYNTAX  DisplayString (SIZE (0..8))
    ACCESS  read-write
    STATUS  mandatory
    DESCRIPTION
        "A unique user-recognizable name for each remote 
        bridge logger defined."
    ::= { brgLoggerEntry 2 }

brgLoggerType OBJECT-TYPE
    SYNTAX  INTEGER
        {
            invalid(1),
            valid(2)
        }
    ACCESS  read-write
    STATUS  mandatory
    DESCRIPTION
        "The validity of this logger entry."
    ::= { brgLoggerEntry 3 }

brgLoggerMask1Offset OBJECT-TYPE
    SYNTAX  INTEGER (0..255)
    ACCESS  read-write
    STATUS  mandatory
    DESCRIPTION
        "The byte offset of the 4th mask of this logger."
    ::= { brgLoggerEntry 4 }

brgLoggerMask1Value OBJECT-TYPE
    SYNTAX  INTEGER
    ACCESS  read-write
    STATUS  mandatory
    DESCRIPTION
        "The value of the 4th mask of this logger. This can be 
        a byte, word or long value."
    ::= { brgLoggerEntry 5 }

brgLoggerMask1Type OBJECT-TYPE
    SYNTAX  INTEGER
        {
            invalid(1),
            equal(2),
            or(3),
            and(4),
            not(5)
        }
    ACCESS  read-write
    STATUS  mandatory
    DESCRIPTION
        "The type of the 4th mask of this logger."
    ::= { brgLoggerEntry 6 }

brgLoggerMask1Size OBJECT-TYPE
    SYNTAX  INTEGER
        {
            byte(1),
            half-word(2),
            word(3)
        }
    ACCESS  read-write
    STATUS  mandatory
    DESCRIPTION
        "The size (number of bytes covered by this mask) of the 1st 
        mask of this logger."
    ::= { brgLoggerEntry 7 }

brgLoggerMask2Offset OBJECT-TYPE
    SYNTAX  INTEGER (0..255)
    ACCESS  read-write
    STATUS  mandatory
    DESCRIPTION
        "The byte offset of the 4th mask of this logger."
    ::= { brgLoggerEntry 8 }

brgLoggerMask2Value OBJECT-TYPE
    SYNTAX  INTEGER
    ACCESS  read-write
    STATUS  mandatory
    DESCRIPTION
        "The value of the 4th mask of this logger. This can be 
        a byte, word or long value."
    ::= { brgLoggerEntry 9 }

brgLoggerMask2Type OBJECT-TYPE
    SYNTAX  INTEGER
        {
            invalid(1),
            equal(2),
            or(3),
            and(4),
            not(5)
        }
    ACCESS  read-write
    STATUS  mandatory
    DESCRIPTION
        "The type of the 4th mask of this logger."
    ::= { brgLoggerEntry 10 }

brgLoggerMask2Size OBJECT-TYPE
    SYNTAX  INTEGER
        {
            byte(1),
            half-word(2),
            word(3)
        }
    ACCESS  read-write
    STATUS  mandatory
    DESCRIPTION
        "The size (number of bytes covered by this mask) of the 2nd 
        mask of this logger."
    ::= { brgLoggerEntry 11 }

brgLoggerMask3Offset OBJECT-TYPE
    SYNTAX  INTEGER (0..255)
    ACCESS  read-write
    STATUS  mandatory
    DESCRIPTION
        "The byte offset of the 4th mask of this logger."
    ::= { brgLoggerEntry 12 }

brgLoggerMask3Value OBJECT-TYPE
    SYNTAX  INTEGER
    ACCESS  read-write
    STATUS  mandatory
    DESCRIPTION
        "The value of the 4th mask of this logger. This can be 
        a byte, word or long value."
    ::= { brgLoggerEntry 13 }

brgLoggerMask3Type OBJECT-TYPE
    SYNTAX  INTEGER
        {
            invalid(1),
            equal(2),
            or(3),
            and(4),
            not(5)
        }
    ACCESS  read-write
    STATUS  mandatory
    DESCRIPTION
        "The type of the 4th mask of this logger."
    ::= { brgLoggerEntry 14 }

brgLoggerMask3Size OBJECT-TYPE
    SYNTAX  INTEGER
        {
            byte(1),
            half-word(2),
            word(3)
        }
    ACCESS  read-write
    STATUS  mandatory
    DESCRIPTION
        "The size (number of bytes covered by this mask) of the 3rd 
        mask of this logger."
    ::= { brgLoggerEntry 15 }

brgLoggerMask4Offset OBJECT-TYPE
    SYNTAX  INTEGER (0..255)
    ACCESS  read-write
    STATUS  mandatory
    DESCRIPTION
        "The byte offset of the 4th mask of this logger."
    ::= { brgLoggerEntry 16 }

brgLoggerMask4Value OBJECT-TYPE
    SYNTAX  INTEGER
    ACCESS  read-write
    STATUS  mandatory
    DESCRIPTION
        "The value of the 4th mask of this logger. This can be 
        a byte, word or long value."
    ::= { brgLoggerEntry 17 }

brgLoggerMask4Type OBJECT-TYPE
    SYNTAX  INTEGER
        {
            invalid(1),
            equal(2),
            or(3),
            and(4),
            not(5)
        }
    ACCESS  read-write
    STATUS  mandatory
    DESCRIPTION
        "The type of the 4th mask of this logger."
    ::= { brgLoggerEntry 18 }

brgLoggerMask4Size OBJECT-TYPE
    SYNTAX  INTEGER
        {
            byte(1),
            half-word(2),
            word(3)
        }
    ACCESS  read-write
    STATUS  mandatory
    DESCRIPTION
        "The size (number of bytes covered by this mask) of the 4th 
        mask of this logger."
    ::= { brgLoggerEntry 19 }

brgLoggerSkipRii OBJECT-TYPE
    SYNTAX  INTEGER
        {
            no(1),
            yes(2)
        }
    ACCESS  read-write
    STATUS  mandatory
    DESCRIPTION
        "Specifying if source route field should be skipped for
        logger offset."
    ::= { brgLoggerEntry 20 }

-- bridge local path table --

brgPLocalNumber OBJECT-TYPE
    SYNTAX  INTEGER
    ACCESS  read-only
    STATUS  mandatory
    DESCRIPTION
        "The number of local bridge path on this system."
    ::= { brg 5 }

brgPLocalTable OBJECT-TYPE
    SYNTAX  SEQUENCE OF BrgPLocalEntry
    ACCESS  not-accessible
    STATUS  mandatory
    DESCRIPTION
        "This table contains bridge path (equivalent to port in 802.1d
        specification) information."
    ::= { brg 6 }

brgPLocalEntry OBJECT-TYPE
    SYNTAX  BrgPLocalEntry
    ACCESS  not-accessible
    STATUS  mandatory
    DESCRIPTION
        "A description of bridge path entry."
    INDEX   { brgPLocalIndex }
    ::= { brgPLocalTable 1 }

BrgPLocalEntry ::=
    SEQUENCE {
        brgPLocalIndex
            INTEGER,
        brgPLocalEnabled
            INTEGER,
        brgStpPLocalPriority
            INTEGER,
        brgStpPLocalCost
            INTEGER,
        brgStpPLocalDesigRoot
            OCTET STRING (SIZE (8)),
        brgStpPLocalDesigCost
            INTEGER,
        brgStpPLocalDesigBridge
            OCTET STRING (SIZE (8)),
        brgStpPLocalDesigPath
            INTEGER,
        brgStpPLocalPathState
            INTEGER
    }

brgPLocalIndex OBJECT-TYPE
    SYNTAX  INTEGER
    ACCESS  read-only
    STATUS  mandatory
    DESCRIPTION
        "The path on which the entry's equivalence is effective.
        The path identified by a particular value of this index
        is the same path as identified by the same value
        of plocalIndex."
    ::= { brgPLocalEntry 1 }

brgPLocalEnabled OBJECT-TYPE
    SYNTAX  INTEGER
        {
            no(1),
            yes(2)
        }
    ACCESS  read-write
    STATUS  mandatory
    DESCRIPTION
        "Enable this path as one of the bridge port."
    ::= { brgPLocalEntry 2 }

brgStpPLocalPriority OBJECT-TYPE
    SYNTAX  INTEGER
    ACCESS  read-write
    STATUS  mandatory
    DESCRIPTION
        "The value of the priority field which is contained in the
        first octet of the Port ID. The other octet of the Port ID
        is given by the value of brgPLocalIndex."
    ::= { brgPLocalEntry 3 }

brgStpPLocalCost OBJECT-TYPE
    SYNTAX  INTEGER
    ACCESS  read-write
    STATUS  mandatory
    DESCRIPTION
        "The contribution of this port to the path cost of paths
        towards the spanning tree root which include this port."
    ::= { brgPLocalEntry 4 }

brgStpPLocalDesigRoot OBJECT-TYPE
    SYNTAX  OCTET STRING (SIZE (8))
    ACCESS  read-only
    STATUS  mandatory
    DESCRIPTION
        "The unique Bridge Identifier of the Bridge recorded as the
        Root in the Configuration BPDUs transmitted by the Designated
        Bridge for the segment to which the port is attached."
    ::= { brgPLocalEntry 5 }

brgStpPLocalDesigCost OBJECT-TYPE
    SYNTAX  INTEGER
    ACCESS  read-only
    STATUS  mandatory
    DESCRIPTION
        "The path cost of the Designated Port of the segment
        connected to the port. This value is compared to the Root Path
        Cost field in received bridge PDUs."
    ::= { brgPLocalEntry 6 }

brgStpPLocalDesigBridge OBJECT-TYPE
    SYNTAX  OCTET STRING (SIZE (8))
    ACCESS  read-only
    STATUS  mandatory
    DESCRIPTION
        "The Bridge ID of the bridge which this port considers to be
        the Designated Bridge for this port's segment."
    ::= { brgPLocalEntry 7 }

brgStpPLocalDesigPath OBJECT-TYPE
    SYNTAX  INTEGER
    ACCESS  read-only
    STATUS  mandatory
    DESCRIPTION
        "The Port ID of the port on the Designated Bridge for this 
        port's segment."
    ::= { brgPLocalEntry 8 }

brgStpPLocalPathState OBJECT-TYPE
    SYNTAX  INTEGER
        {
            listening(1),
            blocking(2),
            learning(3),
            forwarding(4),
            disabled(255)
        }
    ACCESS  read-only
    STATUS  mandatory
    DESCRIPTION
        "The Spanning Tree state of the port."
    ::= { brgPLocalEntry 9 }

-- bridge remote path table --

brgPRmtNumber OBJECT-TYPE
    SYNTAX  INTEGER
    ACCESS  read-only
    STATUS  mandatory
    DESCRIPTION
        "The number of remote bridge path on this system."
    ::= { brg 7 }

brgPRmtTable OBJECT-TYPE
    SYNTAX  SEQUENCE OF BrgPRmtEntry
    ACCESS  not-accessible
    STATUS  mandatory
    DESCRIPTION
        "This table contains bridge path (equivalent to port in 802.1d
        specification) information."
    ::= { brg 8 }

brgPRmtEntry OBJECT-TYPE
    SYNTAX  BrgPRmtEntry
    ACCESS  not-accessible
    STATUS  mandatory
    DESCRIPTION
        "A description of bridge path entry."
    INDEX   { brgPRmtIndex }
    ::= { brgPRmtTable 1 }

BrgPRmtEntry ::=
    SEQUENCE {
        brgPRmtIndex
            INTEGER,
        brgPRmtEnabled
            INTEGER,
        brgStpPRmtPriority
            INTEGER,
        brgStpPRmtCost
            INTEGER,
        brgStpPRmtDesigRoot
            OCTET STRING (SIZE (8)),
        brgStpPRmtDesigCost
            INTEGER,
        brgStpPRmtDesigBridge
            OCTET STRING (SIZE (8)),
        brgStpPRmtDesigPath
            INTEGER,
        brgStpPRmtPathState
            INTEGER
    }

brgPRmtIndex OBJECT-TYPE
    SYNTAX  INTEGER
    ACCESS  read-only
    STATUS  mandatory
    DESCRIPTION
        "The path on which the entry's equivalence is effective.
        The path identified by a particular value of this index
        is the same path as identified by the same value
        of prmtIndex."
    ::= { brgPRmtEntry 1 }

brgPRmtEnabled OBJECT-TYPE
    SYNTAX  INTEGER
        {
            no(1),
            yes(2)
        }
    ACCESS  read-write
    STATUS  mandatory
    DESCRIPTION
        "Enable this path as one of the bridge port."
    ::= { brgPRmtEntry 2 }

brgStpPRmtPriority OBJECT-TYPE
    SYNTAX  INTEGER
    ACCESS  read-write
    STATUS  mandatory
    DESCRIPTION
        "The value of the priority field which is contained in the
        first octet of the Port ID. The other octet of the Port ID
        is given by the value of brgPRmtIndex."
    ::= { brgPRmtEntry 3 }

brgStpPRmtCost OBJECT-TYPE
    SYNTAX  INTEGER
    ACCESS  read-write
    STATUS  mandatory
    DESCRIPTION
        "The contribution of this port to the path cost of paths
        towards the spanning tree root which include this port."
    ::= { brgPRmtEntry 4 }

brgStpPRmtDesigRoot OBJECT-TYPE
    SYNTAX  OCTET STRING (SIZE (8))
    ACCESS  read-only
    STATUS  mandatory
    DESCRIPTION
        "The unique Bridge Identifier of the Bridge recorded as the
        Root in the Configuration BPDUs transmitted by the Designated
        Bridge for the segment to which the port is attached."
    ::= { brgPRmtEntry 5 }

brgStpPRmtDesigCost OBJECT-TYPE
    SYNTAX  INTEGER
    ACCESS  read-only
    STATUS  mandatory
    DESCRIPTION
        "The path cost of the Designated Port of the segment
        connected to the port. This value is compared to the Poot Path
        Cost field in received bridge PDUs."
    ::= { brgPRmtEntry 6 }

brgStpPRmtDesigBridge OBJECT-TYPE
    SYNTAX  OCTET STRING (SIZE (8))
    ACCESS  read-only
    STATUS  mandatory
    DESCRIPTION
        "The Bridge ID of the bridge which this port considers to be
        the Designated Bridge for this port's segment."
    ::= { brgPRmtEntry 7 }

brgStpPRmtDesigPath OBJECT-TYPE
    SYNTAX  INTEGER
    ACCESS  read-only
    STATUS  mandatory
    DESCRIPTION
        "The Port ID of the port on the Designated Bridge for this 
        port's segment."
    ::= { brgPRmtEntry 8 }

brgStpPRmtPathState OBJECT-TYPE
    SYNTAX  INTEGER
        {
            listening(1),
            blocking(2),
            learning(3),
            forwarding(4),
            disabled(255)
        }
    ACCESS  read-only
    STATUS  mandatory
    DESCRIPTION
        "The Spanning Tree state of the port."
    ::= { brgPRmtEntry 9 }

-- end of remote path table --


brgMisc    OBJECT IDENTIFIER ::= { brg 9 }

brgSpanningTreeProtocol OBJECT-TYPE
    SYNTAX  INTEGER
        {
            disabled(1),
            enable(2)
        }
    ACCESS  read-write
    STATUS  mandatory
    DESCRIPTION
        "This flag controls whether Spanning Tree protocol
        feature be enabled in this node."
    ::= { brgMisc 1 }

brgResetAllCounters OBJECT-TYPE
    SYNTAX  INTEGER
    ACCESS  read-write
    STATUS  mandatory
    DESCRIPTION
        "Writing any value to this variable will reset all brg-related
        counters to zero."
    ::= { brgMisc 2 }

brgAutoFtrEnabled OBJECT-TYPE
    SYNTAX  INTEGER
        {
            disabled(1),
            enable(2)
        }
    ACCESS  read-write
    STATUS  mandatory
    DESCRIPTION
        "This flag controls whether auto filter feature is enabled
         in this node."
    ::= { brgMisc 3 }

brgPRPASmartFiltering OBJECT-TYPE
    SYNTAX  INTEGER
        {
            disabled(1),
            enabled(2)
        }
    ACCESS  read-write
    STATUS  mandatory
    DESCRIPTION
        "This enables/disables AccessBuilder's Smart Filtering feature."
    ::= { brgMisc 4 }

brgPRPAFilterAction OBJECT-TYPE
    SYNTAX  INTEGER
        {
            discard(1),
            forward(2)
        }
    ACCESS  read-write
    STATUS  mandatory
    DESCRIPTION
        "The action to be taken for all remote access path's filters."
    ::= { brgMisc 5 }

brgPRPAFilterMap OBJECT-TYPE
    SYNTAX  INTEGER
        {
	     no(1),
	     yes(2)
        }
    ACCESS  read-write
    STATUS  mandatory
    DESCRIPTION
        "This is a 16 bit bitmap corresponds to the bridge filter table."
    ::= { brgMisc 6 }

brgPRPALoggerMap OBJECT-TYPE
    SYNTAX  INTEGER
        {
	     no(1),
	     yes(2)
        }
    ACCESS  read-write
    STATUS  mandatory
    DESCRIPTION
        "This is a 16 bit bitmap corresponds to the bridge logger table."
    ::= { brgMisc 7 }

brgMacHdrComp OBJECT-TYPE
    SYNTAX  INTEGER
        {
	     no(1),
	     yes(2)
        }
    ACCESS  read-write
    STATUS  mandatory
    DESCRIPTION
        "Turn on/off bridge MAC header compression."
    ::= { brgMisc 8 }

-- ** The following parameters will be supported with Spanning Tree
-- ** Protocol. **

-- brgStpPriority OBJECT-TYPE
--     SYNTAX  INTEGER
--     ACCESS  read-write
--     STATUS  mandatory
--     DESCRIPTION
--         "The value of the write-able portion of the Bridge ID, i.e.
--         the first two octets of the Bridge ID. The other 6 octets of
--         the Bridge ID are given by the mother board Ethernet port's
--         address."
--     ::= { brgMisc 4 }
-- 
-- brgStpBridgeMaxAge OBJECT-TYPE
--     SYNTAX  INTEGER
--     ACCESS  read-write
--     STATUS  mandatory
--     DESCRIPTION
--         "The value that all bridges use for MaxAge when this bridge
--         is acting as the root."
--     ::= { brgMisc 5 }
-- 
-- brgStpBridgeHelloTime OBJECT-TYPE
--     SYNTAX  INTEGER
--     ACCESS  read-write
--     STATUS  mandatory
--     DESCRIPTION
--         "The value that all bridges use for HelloTime when this bridge
--         is acting as the root."
--     ::= { brgMisc 6 }
-- 
-- brgStpBridgeForwardDelay OBJECT-TYPE
--     SYNTAX  INTEGER
--     ACCESS  read-write
--     STATUS  mandatory
--     DESCRIPTION
--         "The value that all bridges use for ForwardDelay when this 
--         bridge is acting as the root."
--     ::= { brgMisc 7 }
-- 
-- brgStpMaxAge OBJECT-TYPE
--     SYNTAX  INTEGER
--     ACCESS  read-only
--     STATUS  mandatory
--     DESCRIPTION
--         "The maximum age of Spanning Tree Protocol information
--         learned  from the network on any port before it is discarded,
--         in hundredth of a second. This is the actual value that this
--         bridge is currently using."
--     ::= { brgMisc 8 }
-- 
-- brgStpHelloTime OBJECT-TYPE
--     SYNTAX  INTEGER
--     ACCESS  read-only
--     STATUS  mandatory
--     DESCRIPTION
--         "The amount of time between the transmission of Configuration
--         BPDUs by this node on any port when it is the root,
--         in hundredths of a second. This is the actual value that this
--         bridge is currently using."
--     ::= { brgMisc 9 }
-- 
-- brgStpForwardDelay OBJECT-TYPE
--     SYNTAX  INTEGER
--     ACCESS  read-only
--     STATUS  mandatory
--     DESCRIPTION
--         "The time value, measured in hundredth of a second, controls
--         how fast a port changes its state toward Forwarding. This 
--         is the actual value that this bridge is currently using."
--     ::= { brgMisc 10 }
-- 
-- brgStpDesigRoot OBJECT-TYPE
--     SYNTAX  OCTET STRING (SIZE (8))
--     ACCESS  read-only
--     STATUS  mandatory
--     DESCRIPTION
--         "The Bridge Identifier of the root of the spanning tree as
--         determined by the Spanning Tree Protocol as executed by this
--         node."
--     ::= { brgMisc 11 }
-- 
-- brgStpRootPort OBJECT-TYPE
--     SYNTAX  INTEGER
--     ACCESS  read-only
--     STATUS  mandatory
--     DESCRIPTION
--         "The port number of the port which offers the lowest cost path
--         from this bridge to the root bridge."
--     ::= { brgMisc 12 }

-- bridge learned address table --

brgLearnedTable OBJECT-TYPE
    SYNTAX  SEQUENCE OF BrgLearnedEntry
    ACCESS  not-accessible
    STATUS  mandatory
    DESCRIPTION
        "Spanning tree bridge port table."
    ::= { brg 10 }

brgLearnedEntry OBJECT-TYPE
    SYNTAX  BrgLearnedEntry
    ACCESS  not-accessible
    STATUS  mandatory
    DESCRIPTION
        "A list of information for a learned address entry."
    INDEX   { brgLearnedAddress }
    ::= { brgLearnedTable 1 }

BrgLearnedEntry ::=
    SEQUENCE {
        brgLearnedAddress
            OCTET STRING (SIZE (6)),
        brgLearnedPathType
            INTEGER,
        brgLearnedPathIdx
            INTEGER,
        brgLearnedAge
            INTEGER
    }

brgLearnedAddress OBJECT-TYPE
    SYNTAX  OCTET STRING (SIZE (6))
    ACCESS  read-only
    STATUS  mandatory
    DESCRIPTION
        "A MAC address for the bridge has learned."
    ::= { brgLearnedEntry 1 }

brgLearnedPathType    OBJECT-TYPE
    SYNTAX  INTEGER
        {
            local(1),
            remote(2),
            permanent(3)
        }
    ACCESS  read-only
    STATUS  mandatory
    DESCRIPTION
        "The variable indicates from which path table (local or
        remote) this address is leaned."
    ::= { brgLearnedEntry 2 }

brgLearnedPathIdx OBJECT-TYPE
    SYNTAX  INTEGER
    ACCESS  read-only
    STATUS  mandatory
    DESCRIPTION
        "The path on which the entry's equivalence is effective.
        The path identified by a particular value of this index
        is the same route path as identified by the same value
        of plocalIndex or prmtIndex depending on path type."
    ::= { brgLearnedEntry 3 }

brgLearnedAge OBJECT-TYPE
    SYNTAX  INTEGER
        {
            young(1),
            middle(2),
            old(3),
            permanent(4)
        }
    ACCESS  read-only
    STATUS  mandatory
    DESCRIPTION
        "The relative newness of the learned address."
    ::= { brgLearnedEntry 4 }

-- Source Routing ring and bridge number --

brgTokenRing OBJECT IDENTIFIER ::= { brg 11 }

brgLocalRingNumber OBJECT-TYPE
    SYNTAX  INTEGER
    ACCESS  read-write
    STATUS  mandatory
    DESCRIPTION
        "The ring number on LAN side interface of the AccessBuilder."
    ::= { brgTokenRing 1 }

brgProxyRingNumber OBJECT-TYPE
    SYNTAX  INTEGER
    ACCESS  read-write
    STATUS  mandatory
    DESCRIPTION
        "The ring number on WAN side interface of the AccessBuilder."
    ::= { brgTokenRing 2 }

brgBridgeNumber OBJECT-TYPE
    SYNTAX  INTEGER
    ACCESS  read-write
    STATUS  mandatory
    DESCRIPTION
        "The bridge number assigned to AccessBuilder."
    ::= { brgTokenRing 3 }

-- admin group --

-- admin user table --

adminUserNumber OBJECT-TYPE
    SYNTAX  INTEGER
    ACCESS  read-only
    STATUS  mandatory
    DESCRIPTION
        "The number of users registered on this system."
    ::= { admin 1 }

adminUserTable OBJECT-TYPE
    SYNTAX  SEQUENCE OF AdminUserEntry
    ACCESS  not-accessible
    STATUS  mandatory
    DESCRIPTION
        "User table."
    ::= { admin 2 }

adminUserEntry OBJECT-TYPE
    SYNTAX  AdminUserEntry
    ACCESS  not-accessible
    STATUS  mandatory
    DESCRIPTION
        "A list of information for a user."
    INDEX   { adminUserIndex }
    ::= { adminUserTable 1 }

AdminUserEntry ::=
    SEQUENCE {
        adminUserIndex
            INTEGER,
        adminUserName
            DisplayString (SIZE (0..10)),
        adminUserType
            INTEGER,
        adminUserPassword
            OCTET STRING (SIZE (0..8)),
        adminUserCallBackPhone
            OCTET STRING (SIZE (0..15)),
        adminEncryptUserPassword
            OCTET STRING (SIZE (0..16)),
        adminEncryptCallBackPhone
            OCTET STRING (SIZE (0..24))
    }

adminUserIndex OBJECT-TYPE
    SYNTAX  INTEGER
    ACCESS  read-only
    STATUS  mandatory
    DESCRIPTION
        "A sequentally assigned index value for each entry."
    ::= { adminUserEntry 1 }

adminUserName OBJECT-TYPE
    SYNTAX  DisplayString (SIZE (0..10))
    ACCESS  read-write
    STATUS  mandatory
    DESCRIPTION
        "The user login name."
    ::= { adminUserEntry 2 }

adminUserType OBJECT-TYPE
    SYNTAX  INTEGER
        {
            invalid(1),
            user(2),
            admin(3),
            su(4)
        }
    ACCESS  read-write
    STATUS  mandatory
    DESCRIPTION
        "This value controls whether the user be given superuser, administrator
        or regular user priviledge while in User Interface session."
    ::= { adminUserEntry 3 }

adminUserPassword OBJECT-TYPE
    SYNTAX  OCTET STRING (SIZE (0..8))
    ACCESS  read-only
    STATUS  mandatory
    DESCRIPTION
        "The user login password."
    ::= { adminUserEntry 4 }

adminUserCallBackPhone OBJECT-TYPE
    SYNTAX  OCTET STRING (SIZE (0..15))
    ACCESS  read-only
    STATUS  mandatory
    DESCRIPTION
        "This string controls whether the system should disconnect
        the line and call back to the user for security reason. If
        this is a NULL string, the system does not call back. Otherwise,
        the system calls back with number given by this string."
    ::= { adminUserEntry 5 }

adminEncryptUserPassword OBJECT-TYPE
    SYNTAX  OCTET STRING (SIZE (0..16))
    ACCESS  read-write
    STATUS  mandatory
    DESCRIPTION
        "The encrypted user password is for configurator to change
		 user password by a authentication algorithm."
    ::= { adminUserEntry 6 }

adminEncryptCallBackPhone OBJECT-TYPE
    SYNTAX  OCTET STRING (SIZE (0..24))
    ACCESS  read-write
    STATUS  mandatory
    DESCRIPTION
        "The encrypted call back phone no. is for configurator to 
		 change user password by a authentication algorithm."
    ::= { adminUserEntry 7 }

-- admin community table --

adminCommNumber OBJECT-TYPE
    SYNTAX  INTEGER
    ACCESS  read-only
    STATUS  mandatory
    DESCRIPTION
        "The number of SNMP communities defined on this system."
    ::= { admin 3 }

adminCommTable OBJECT-TYPE
    SYNTAX  SEQUENCE OF AdminCommEntry
    ACCESS  not-accessible
    STATUS  mandatory
    DESCRIPTION
        "SNMP community table."
    ::= { admin 4 }

adminCommEntry OBJECT-TYPE
    SYNTAX  AdminCommEntry
    ACCESS  not-accessible
    STATUS  mandatory
    DESCRIPTION
        "A list of information for a SNMP community."
    INDEX   { adminCommIndex }
    ::= { adminCommTable 1 }

AdminCommEntry ::=
    SEQUENCE {
        adminCommIndex
            INTEGER,
        adminCommName
            DisplayString (SIZE (0..10)),
        adminCommType
            INTEGER,
        adminCommMgrIpAddress
            IpAddress,

-- NANTUCKET, AB6.0

        adminCommMgrIpxNetNumber
            OCTET STRING (SIZE (4)),
        adminCommMgrMacAddress
	        OCTET STRING (SIZE (6))
    }

adminCommIndex OBJECT-TYPE
    SYNTAX  INTEGER
    ACCESS  read-only
    STATUS  mandatory
    DESCRIPTION
        "A sequentally assigned index value for each entry."
    ::= { adminCommEntry 1 }

adminCommName OBJECT-TYPE
    SYNTAX  DisplayString (SIZE (0..10))
    ACCESS  read-write
    STATUS  mandatory
    DESCRIPTION
        "The community name."
    ::= { adminCommEntry 2 }

adminCommType OBJECT-TYPE
    SYNTAX  INTEGER
        {
            invalid(1),
            readOnly(2),
            readWrite(3)
        }
    ACCESS  read-write
    STATUS  mandatory
    DESCRIPTION
        "The community's access type."
    ::= { adminCommEntry 3 }

adminCommMgrIpAddress OBJECT-TYPE
    SYNTAX  IpAddress
    ACCESS  read-write
    STATUS  mandatory
    DESCRIPTION
        "The community network manager's IP address."
    ::= { adminCommEntry 4 }

-- NANTUCKET, AB6.0

adminCommMgrIpxNetNumber OBJECT-TYPE
    SYNTAX  OCTET STRING (SIZE (4))
    ACCESS  read-write
    STATUS  mandatory
    DESCRIPTION
        "The community network manager's IPX network ID."
    ::= { adminCommEntry 5 }

adminCommMgrMacAddress OBJECT-TYPE
    SYNTAX  OCTET STRING (SIZE (6))
    ACCESS  read-write
    STATUS  mandatory
    DESCRIPTION
        "The community network manager's MAC address"
    ::= { adminCommEntry 6 }

-- admin script table --

adminScriptNumber OBJECT-TYPE
    SYNTAX  INTEGER
    ACCESS  read-only
    STATUS  mandatory
    DESCRIPTION
        "The number of dialing scripts on this system."
    ::= { admin 5 }

adminScriptTable OBJECT-TYPE
    SYNTAX  SEQUENCE OF AdminScriptEntry
    ACCESS  not-accessible
    STATUS  mandatory
    DESCRIPTION
        "Dialing script table."
    ::= { admin 6 }

adminScriptEntry OBJECT-TYPE
    SYNTAX  AdminScriptEntry
    ACCESS  not-accessible
    STATUS  mandatory
    DESCRIPTION
        "A list of dialing script information."
    INDEX   { adminScriptIndex }
    ::= { adminScriptTable 1 }

AdminScriptEntry ::=
    SEQUENCE {
        adminScriptIndex
            INTEGER,
        adminScriptName
            DisplayString (SIZE (0..16)),
        adminScriptType
            INTEGER,
        adminScript
            OCTET STRING (SIZE (0..527))
    }

adminScriptIndex OBJECT-TYPE
    SYNTAX  INTEGER
    ACCESS  read-only
    STATUS  mandatory
    DESCRIPTION
        "A sequentally assigned index value for each entry."
    ::= { adminScriptEntry 1 }

adminScriptName OBJECT-TYPE
    SYNTAX  DisplayString (SIZE (0..16))
    ACCESS  read-only
    STATUS  mandatory
    DESCRIPTION
        "The name of the script."
    ::= { adminScriptEntry 2 }

adminScriptType OBJECT-TYPE
    SYNTAX  INTEGER
        {
            invalid(1),
            built-in(2),
            user-defined(3)
        }
    ACCESS  read-write
    STATUS  mandatory
    DESCRIPTION
        "The script's type. A built-in script's type can not be changed."
    ::= { adminScriptEntry 3 }

adminScript    OBJECT-TYPE
    SYNTAX  OCTET STRING (SIZE (0..527))
    ACCESS  read-write
    STATUS  mandatory
    DESCRIPTION
        "The connection control string."
    ::= { adminScriptEntry 4 }

-- end of tables --

-- admin RPA session log table --

adminRpaLogNumber OBJECT-TYPE
    SYNTAX  INTEGER
    ACCESS  read-only
    STATUS  mandatory
    DESCRIPTION
        "The number of remote PC access session log entries in this system."
    ::= { admin 7 }

adminRpaLogTable OBJECT-TYPE
    SYNTAX  SEQUENCE OF AdminRpaLogEntry
    ACCESS  not-accessible
    STATUS  mandatory
    DESCRIPTION
        "Remote PC access session log table."
    ::= { admin 8 }

adminRpaLogEntry OBJECT-TYPE
    SYNTAX  AdminRpaLogEntry
    ACCESS  not-accessible
    STATUS  mandatory
    DESCRIPTION
        "A list of logged remote PC access session information."
    INDEX   { adminRpaLogIndex }
    ::= { adminRpaLogTable 1 }

AdminRpaLogEntry ::=
    SEQUENCE {
        adminRpaLogIndex
            INTEGER,
        adminRpaLogUserName
            DisplayString (SIZE (0..10)),
        adminRpaLogTime
            DisplayString (SIZE (0..8)),
        adminRpaLogDuration
            DisplayString (SIZE (0..8)),
        adminRpaLogAttempts
            Counter,
        adminRpaLogInPackets
            Counter,
        adminRpaLogOutPackets
            Counter,
        adminRpaLogInBytes
            Counter,
        adminRpaLogOutBytes
            Counter,
        adminRpaLogParityErrors
            Counter,
        adminRpaLogFrameErrors
            Counter,
        adminRpaLogOverrunErrors
            Counter,
        adminRpaLogCksumErrors
            Counter,
	adminRpaLogDate
            DisplayString (SIZE (0..8)),
	adminRpaLogPortName
            DisplayString (SIZE (0..40)),
	adminRpaLogPathName
            DisplayString (SIZE (0..12))
    }

adminRpaLogIndex OBJECT-TYPE
    SYNTAX  INTEGER
    ACCESS  read-only
    STATUS  mandatory
    DESCRIPTION
        "A sequentally assigned index value for each entry. Index 32 always
        points to the most-recently completed remote PC access session."
    ::= { adminRpaLogEntry 1 }
    
adminRpaLogUserName OBJECT-TYPE
    SYNTAX  DisplayString (SIZE (0..10))
    ACCESS  read-only
    STATUS  mandatory
    DESCRIPTION
        "The name of the logged-in user."
    ::= { adminRpaLogEntry 2 }

adminRpaLogTime OBJECT-TYPE
    SYNTAX  DisplayString (SIZE (0..8))
    ACCESS  read-only
    STATUS  mandatory
    DESCRIPTION
        "The start time (in HH:MM:SS) of this session."
    ::= { adminRpaLogEntry 3 }

adminRpaLogDuration OBJECT-TYPE
    SYNTAX  DisplayString (SIZE (0..8))
    ACCESS  read-only
    STATUS  mandatory
    DESCRIPTION
        "The elapsed time (in HH:MM:SS) of this session."
    ::= { adminRpaLogEntry 4 }

adminRpaLogAttempts OBJECT-TYPE
    SYNTAX  Counter 
    ACCESS  read-only
    STATUS  mandatory
    DESCRIPTION
        "Number of unsuccessful login attempts in this authentication
         process."
    ::= { adminRpaLogEntry 5 }

adminRpaLogInPackets OBJECT-TYPE
    SYNTAX  Counter 
    ACCESS  read-only
    STATUS  mandatory
    DESCRIPTION
        "Number of correctly received packets in this session."
    ::= { adminRpaLogEntry 6 }

adminRpaLogOutPackets OBJECT-TYPE
    SYNTAX  Counter 
    ACCESS  read-only
    STATUS  mandatory
    DESCRIPTION
        "Number of correctly transmitted packets in this session."
    ::= { adminRpaLogEntry 7 }

adminRpaLogInBytes OBJECT-TYPE
    SYNTAX  Counter 
    ACCESS  read-only
    STATUS  mandatory
    DESCRIPTION
        "Number of correctly received bytes in this session."
    ::= { adminRpaLogEntry 8 }

adminRpaLogOutBytes OBJECT-TYPE
    SYNTAX  Counter 
    ACCESS  read-only
    STATUS  mandatory
    DESCRIPTION
        "Number of correctly transmitted bytes in this session."
    ::= { adminRpaLogEntry 9 }

adminRpaLogParityErrors OBJECT-TYPE
    SYNTAX  Counter 
    ACCESS  read-only
    STATUS  mandatory
    DESCRIPTION
        "Number of characters received with parity error in this session."
    ::= { adminRpaLogEntry 10 }

adminRpaLogFrameErrors OBJECT-TYPE
    SYNTAX  Counter 
    ACCESS  read-only
    STATUS  mandatory
    DESCRIPTION
        "Number of characters received with framing error in this session."
    ::= { adminRpaLogEntry 11 }

adminRpaLogOverrunErrors OBJECT-TYPE
    SYNTAX  Counter 
    ACCESS  read-only
    STATUS  mandatory
    DESCRIPTION
        "Number of receive overrun errors in this session."
    ::= { adminRpaLogEntry 12 }

adminRpaLogCksumErrors OBJECT-TYPE
    SYNTAX  Counter 
    ACCESS  read-only
    STATUS  mandatory
    DESCRIPTION
        "Number of receive checksum errors in this session."
    ::= { adminRpaLogEntry 13 }

adminRpaLogDate OBJECT-TYPE
    SYNTAX  DisplayString (SIZE (0..8))
    ACCESS  read-only
    STATUS  mandatory
    DESCRIPTION
        "The start date (in MM/DD/YY) of this session."
    ::= { adminRpaLogEntry 14 }

adminRpaLogPortName OBJECT-TYPE
    SYNTAX  DisplayString (SIZE (0..40))
    ACCESS  read-only
    STATUS  mandatory
    DESCRIPTION
        "The binding portname of this session."
    ::= { adminRpaLogEntry 15 }

adminRpaLogPathName OBJECT-TYPE
    SYNTAX  DisplayString (SIZE (0..12))
    ACCESS  read-only
    STATUS  mandatory
    DESCRIPTION
        "The binding pathname of this session."
    ::= { adminRpaLogEntry 16 }

-- end of tables --

adminMisc    OBJECT IDENTIFIER ::= { admin 9 }

adminSysDescr OBJECT-TYPE
    SYNTAX  DisplayString (SIZE (0..255))
    ACCESS  read-only
    STATUS  mandatory
    DESCRIPTION
        "Same as sysDescr in MIB II."
    ::= { adminMisc 1 }

adminNodeName OBJECT-TYPE
    SYNTAX  DisplayString (SIZE (0..10))
    ACCESS  read-write
    STATUS  mandatory
    DESCRIPTION
        "The login ID that is transmitted by this node to a remote
        router at connection establishing time. If the string is
        not what the remote router expects, the connection will be
        rejected."
    ::= { adminMisc 2 }

adminNodePassword OBJECT-TYPE
    SYNTAX  OCTET STRING (SIZE (0..8))
    ACCESS  read-only
    STATUS  mandatory
    DESCRIPTION
        "The password that is transmitted by this node to a remote
        router after login ID at connection establishing time. 
        If the string is not what the remote router expects, the 
        connection will be rejected."
    ::= { adminMisc 3 }

adminDate OBJECT-TYPE
    SYNTAX  DisplayString (SIZE (0..8))
    ACCESS  read-write
    STATUS  mandatory
    DESCRIPTION
        "Current date in mm/dd/yy format."
    ::= { adminMisc 4 }

adminTime OBJECT-TYPE
    SYNTAX  DisplayString (SIZE (0..8))
    ACCESS  read-write
    STATUS  mandatory
    DESCRIPTION
        "Current time in hh:mm:ss format."
    ::= { adminMisc 5 }

adminGreeting OBJECT-TYPE
    SYNTAX  DisplayString (SIZE (0..128))
    ACCESS  read-write
    STATUS  mandatory
    DESCRIPTION
        "A user-defined text that is displayed when a user logs
        into User Interface process."
    ::= { adminMisc 6 }

adminPrompt OBJECT-TYPE
    SYNTAX  DisplayString (SIZE (0..10))
    ACCESS  read-write
    STATUS  mandatory
    DESCRIPTION
        "An user-defined prompt string for this node's 
        User Interface process. Note: This one is obsoleted after version
	3.1 or later"
    ::= { adminMisc 7 }

adminSNMPGetFrom OBJECT-TYPE
    SYNTAX  INTEGER
        {
            current-value(1),
            config-value(2)
        }
    ACCESS  read-write
    STATUS  mandatory
    DESCRIPTION
        "The value controls the type value returned to an SNMP GET
        command. Setting this to '1' requests that the current
        operational value of this variable is returned. Setting it
        to '2' requests that the configured value (which will take
        effect after a re-boot) is returned. The default is '1'."
    ::= { adminMisc 8 }

adminDoIntegrity OBJECT-TYPE
    SYNTAX  INTEGER
        {
            integrity-check-OK(1),
            integrity-check-failed(2)
        }
    ACCESS  read-write
    STATUS  mandatory
    DESCRIPTION
        "A write to this variable (value don't care) cause an
        integrity check on all the configuration parameters. The
        result is given through a GET of this variable."
    ::= { adminMisc 9 }

adminDoFileload OBJECT-TYPE
    SYNTAX  INTEGER
        {
            fileload-OK(1),
            fileload-failed(2)
        }
    ACCESS  read-write
    STATUS  mandatory
    DESCRIPTION
        "A write to this variable (value don't care) cause a
        fileload (upload or download depending on LoadFileName)
        operation to start. The result is given through a 
        GET of this variable."
    ::= { adminMisc 10 }

adminLoadfileName OBJECT-TYPE
    SYNTAX  DisplayString (SIZE (0..12))
    ACCESS  read-write
    STATUS  mandatory
    DESCRIPTION
        "The name of the file upon which the file-load operation
        is to be operated."
    ::= { adminMisc 11 }

-- { adminMisc 12 } --

adminLastTrap OBJECT-TYPE
    SYNTAX  DisplayString (SIZE (0..255))
    ACCESS  read-only
    STATUS  mandatory
    DESCRIPTION
        "The last trap message contents."
    ::= { adminMisc 13 }

adminResetAllUserCounters OBJECT-TYPE
    SYNTAX  INTEGER
    ACCESS  read-write
    STATUS  mandatory
    DESCRIPTION
        "Writing any value to this variable will reset all User-related
        counters to zero."
    ::= { adminMisc 14 }

adminEraseConfig OBJECT-TYPE
    SYNTAX  INTEGER
    ACCESS  read-write
    STATUS  mandatory
    DESCRIPTION
        "Erase all configuration data in EEPROM."
    ::= { adminMisc 15 }

adminUIMsgLevel OBJECT-TYPE
    SYNTAX  INTEGER
        {
            panic-level(1),
            error-level(2),
            warning-level(3),
            status-level(4)
        }
    ACCESS  read-write
    STATUS  mandatory
    DESCRIPTION
        "This variable controls type of system messages to be displayed 
        on system console. Messages of priority equals or higher than the
        specified level are displayed."
    ::= { adminMisc 16 }

adminSNMPMsgLevel OBJECT-TYPE
    SYNTAX  INTEGER
        {
            none(1),
            error-level(2),
            warning-level(3),
            status-level(4)
        }
    ACCESS  read-write
    STATUS  mandatory
    DESCRIPTION
        "This variable controls type of system messages to be sent to SNMP 
        management stations. Messages of priority equals or higher than the
        specified level are sent."
    ::= { adminMisc 17 }

adminLoginOption OBJECT-TYPE
    SYNTAX  INTEGER
        {
            normal(1),
            nologin(2),
            nopassword(3)
        }
    ACCESS  read-write
    STATUS  mandatory
    DESCRIPTION
        "This variable enable the login sequence on async ports." 
    ::= { adminMisc 18 }

adminReboot OBJECT-TYPE
    SYNTAX  INTEGER
    ACCESS  read-write
    STATUS  mandatory
    DESCRIPTION
        "Reboot the AccessBuilder server."
    ::= { adminMisc 19 }

adminMajorVersion OBJECT-TYPE
    SYNTAX  INTEGER
    ACCESS  read-only
    STATUS  mandatory
    DESCRIPTION
        "AccessBuilder software Major version."
    ::= { adminMisc 20 }

adminMinorVersion OBJECT-TYPE
    SYNTAX  INTEGER
    ACCESS  read-only
    STATUS  mandatory
    DESCRIPTION
        "AccessBuilder software Minor version."
    ::= { adminMisc 21 }

adminMIBVersion OBJECT-TYPE
    SYNTAX  INTEGER
    ACCESS  read-only
    STATUS  mandatory
    DESCRIPTION
        "This MIB version."
    ::= { adminMisc 22 }

adminTimeZone OBJECT-TYPE
    SYNTAX  DisplayString (SIZE (1..4))
    ACCESS  read-write
    STATUS  mandatory
    DESCRIPTION
        "Time difference between local time zone and Greenwich time
		(in minutes)."
    ::= { adminMisc 23 }

adminSecurityServerType OBJECT-TYPE
    SYNTAX  INTEGER
        {
            internal(1),
            ab-nameserver(2),
	    	dce-server(3),
            ace-server(4),
			nw-bindery(5),
			nw-nds(6),
			generic(7),
			nt(8)
        }
    ACCESS  read-only
    STATUS  mandatory
    DESCRIPTION
        "Enables authentication through security helpers instead
		of local user database."
    ::= { adminMisc 24 }

adminSecPassword OBJECT-TYPE
    SYNTAX  OCTET STRING (SIZE (0..8))
    ACCESS  read-only
    STATUS  mandatory
    DESCRIPTION
        "The password is used to set up a session with security helpers."
    ::= { adminMisc 25 }

adminScrtyClntIpAddr OBJECT-TYPE
    SYNTAX  IpAddress
    ACCESS  read-only
    STATUS  mandatory
    DESCRIPTION
        "The primary security helper's IP address."
    ::= { adminMisc 26 }

adminSecondScrtyClntIpAddr OBJECT-TYPE
    SYNTAX  IpAddress
    ACCESS  read-only
    STATUS  mandatory
    DESCRIPTION
        "The secondary security helper's IP address."
    ::= { adminMisc 27 }

adminUdpPort OBJECT-TYPE
    SYNTAX  INTEGER
    ACCESS  read-only
    STATUS  mandatory
    DESCRIPTION
        "This is the UDP port for the security helper protocol."
    ::= { adminMisc 28 }

adminTelnetAdminPort OBJECT-TYPE
    SYNTAX  INTEGER
    ACCESS  read-write
    STATUS  mandatory
    DESCRIPTION
        "This is the telnet administration port for dialout function."
    ::= { adminMisc 29 }

adminTelnetDialOutAuth OBJECT-TYPE
    SYNTAX  INTEGER
        {
            no(1),
            yes(2)
        }
    ACCESS  read-write
    STATUS  mandatory
    DESCRIPTION
        "Enables authentication for dialout function."
    ::= { adminMisc 30 }

adminDialOutEnabled OBJECT-TYPE
    SYNTAX  INTEGER
        {
            no(1),
            yes(2)
        }
    ACCESS  read-write
    STATUS  mandatory
    DESCRIPTION
        "Enables dialout function."
    ::= { adminMisc 31 }

adminEncryptNodePassword OBJECT-TYPE
    SYNTAX  OCTET STRING (SIZE (0..16))
    ACCESS  read-write
    STATUS  mandatory
    DESCRIPTION
        "The encrypted node password is for configurator to change
		 node password by a authentication algorithm."
    ::= { adminMisc 32 }

adminEncryptSecurityServerType OBJECT-TYPE
    SYNTAX  OCTET STRING (SIZE (0..8))
    ACCESS  read-write
    STATUS  mandatory
    DESCRIPTION
        "The encrypted security server type is for configurator to 
		 change security server type by a authentication algorithm."
    ::= { adminMisc 33 }

adminEncryptSecPassword OBJECT-TYPE
    SYNTAX  OCTET STRING (SIZE (0..16))
    ACCESS  read-write
    STATUS  mandatory
    DESCRIPTION
        "The encrypted security password is for configurator to 
		 change security password by a authentication algorithm."
    ::= { adminMisc 34 }

adminEncryptScrtyClntIpAddr OBJECT-TYPE
    SYNTAX  OCTET STRING (SIZE (0..8))
    ACCESS  read-write
    STATUS  mandatory
    DESCRIPTION
        "The encrypted helper IP address is for configurator to 
		 change helper IP address by a authentication algorithm."
    ::= { adminMisc 35 }

adminEncryptSecondScrtyClntIpAddr OBJECT-TYPE
    SYNTAX  OCTET STRING (SIZE (0..8))
    ACCESS  read-write
    STATUS  mandatory
    DESCRIPTION
        "The encrypted secondary helper IP address is for configurator
		 to change secondary helper IP address by a authentication 
		 algorithm."
    ::= { adminMisc 36 }

adminEncryptUdpPort OBJECT-TYPE
    SYNTAX  OCTET STRING (SIZE (0..8))
    ACCESS  read-write
    STATUS  mandatory
    DESCRIPTION
        "The encrypted helper UDP port is for configurator to 
		 change helper UDP port by a authentication algorithm."
    ::= { adminMisc 37 }

adminEPromSize OBJECT-TYPE
    SYNTAX  INTEGER
    ACCESS  read-only
    STATUS  mandatory
    DESCRIPTION
        "This is the EProm size on the mother board."
    ::= { adminMisc 38 }

adminNVRamSize OBJECT-TYPE
    SYNTAX  INTEGER
    ACCESS  read-only
    STATUS  mandatory
    DESCRIPTION
        "This is the Non-Volatile Ram (EEProm) size on the mother board."
    ::= { adminMisc 39 }

adminFlashRomSize OBJECT-TYPE
    SYNTAX  INTEGER
    ACCESS  read-only
    STATUS  mandatory
    DESCRIPTION
        "This is the Flash Rom size on the mother board."
    ::= { adminMisc 40 }

adminLocalDRamSize OBJECT-TYPE
    SYNTAX  INTEGER
    ACCESS  read-only
    STATUS  mandatory
    DESCRIPTION
        "This is the Local DRam size on the mother board."
    ::= { adminMisc 41 }

adminSharedDRamSize OBJECT-TYPE
    SYNTAX  INTEGER
    ACCESS  read-only
    STATUS  mandatory
    DESCRIPTION
        "This is the Shared DRam size on the mother board."
    ::= { adminMisc 42 }

adminHWRev OBJECT-TYPE
    SYNTAX  INTEGER
    ACCESS  read-only
    STATUS  mandatory
    DESCRIPTION
        "This is the hardware revision on mother board."
    ::= { adminMisc 43 }

adminEncryptSuperUserPassword OBJECT-TYPE
    SYNTAX  OCTET STRING (SIZE (0..8))
    ACCESS  read-only
    STATUS  mandatory
    DESCRIPTION
        "The encrypted superuser password is for configurator to get
		 the superuser password."
    ::= { adminMisc 44 }

adminNewGreeting OBJECT-TYPE
    SYNTAX  DisplayString (SIZE (0..255))
    ACCESS  read-write
    STATUS  mandatory
    DESCRIPTION
        "A user-defined text that is displayed when a user logs
        into User Interface process."
    ::= { adminMisc 45 }

adminTFTPServerIpAddr OBJECT-TYPE
    SYNTAX  IpAddress
    ACCESS  read-write
    STATUS  mandatory
    DESCRIPTION
        "The TFTP server's IP address."
    ::= { adminMisc 46 }

-- NANTUCKET
adminSaveConfig OBJECT-TYPE
    SYNTAX  INTEGER
        {
            save-OK(1),
            save-failed(2)
        }
    ACCESS  read-write
    STATUS  mandatory
    DESCRIPTION
        "A write to this variable (value don't care) cause a
        save configuration operation to start. The result is 
		given through a GET of this variable."
    ::= { adminMisc 47 }

adminMaintenanceVersion OBJECT-TYPE
    SYNTAX  INTEGER
    ACCESS  read-only
    STATUS  mandatory
    DESCRIPTION
        "AccessBuilder software Maintenance version."
    ::= { adminMisc 48 }

adminCheckConsoleModem OBJECT-TYPE
    SYNTAX  INTEGER
    ACCESS  read-write
    STATUS  mandatory
    DESCRIPTION
        "Check the status of console modem."
    ::= { adminMisc 49 }

adminConsoleImageDownload OBJECT-TYPE
    SYNTAX  INTEGER
    ACCESS  read-write
    STATUS  mandatory
    DESCRIPTION
        "Download image by console port."
    ::= { adminMisc 50 }

adminConsoleConfigUpload OBJECT-TYPE
    SYNTAX  INTEGER
    ACCESS  read-write
    STATUS  mandatory
    DESCRIPTION
        "Upload configuration by console port."
    ::= { adminMisc 51 }

adminConsoleConfigDownload OBJECT-TYPE
    SYNTAX  INTEGER
    ACCESS  read-write
    STATUS  mandatory
    DESCRIPTION
        "Download configuration by console port."
    ::= { adminMisc 52 }

-- AB6.0
adminRasIdleTime OBJECT-TYPE
    SYNTAX  INTEGER
    ACCESS  read-write
    STATUS  mandatory
    DESCRIPTION
        "The idle time to start spoofing for ras port."
    ::= { adminMisc 53 }

adminRouterIdleTime OBJECT-TYPE
    SYNTAX  INTEGER
    ACCESS  read-write
    STATUS  mandatory
    DESCRIPTION
        "The idle time to start spoofing for router port."
    ::= { adminMisc 54 }

adminRasSpoofTime OBJECT-TYPE
    SYNTAX  INTEGER
    ACCESS  read-write
    STATUS  mandatory
    DESCRIPTION
        "The time to spoof for ras port."
    ::= { adminMisc 55 }

adminRouterSpoofTime OBJECT-TYPE
    SYNTAX  INTEGER
    ACCESS  read-write
    STATUS  mandatory
    DESCRIPTION
        "The time to spoof for router port."
    ::= { adminMisc 56 }

adminLnkUtilHighThld OBJECT-TYPE
    SYNTAX  INTEGER
    ACCESS  read-write
    STATUS  mandatory
    DESCRIPTION
        "Link utilization high threshold."
    ::= { adminMisc 57 }

adminLnkUtilLowThld OBJECT-TYPE
    SYNTAX  INTEGER
    ACCESS  read-write
    STATUS  mandatory
    DESCRIPTION
        "Link utilization low threshold."
    ::= { adminMisc 58 }

adminCallerIdCheck OBJECT-TYPE
    SYNTAX  INTEGER
	{
		no(1),
		yes(2)
	}
    ACCESS  read-write
    STATUS  mandatory
    DESCRIPTION
        "Indicate to check caller id or not."
    ::= { adminMisc 59 }

adminISDNRequiredBaudrate OBJECT-TYPE
    SYNTAX  INTEGER
    	{
	    br-56000(1),
	    br-64000(2),
	    auto(3)
	}
    ACCESS  read-write
    STATUS  mandatory
    DESCRIPTION
        "For baudrate adaption of ISDN call."
    ::= { adminMisc 60 }

adminRouterCCPEnabled OBJECT-TYPE
    SYNTAX  INTEGER
	{
		no(1),
		yes(2)
	}
    ACCESS  read-write
    STATUS  mandatory
    DESCRIPTION
        "Turn on/off CCP for remotepath."
    ::= { adminMisc 61 }


adminSuggestFlag OBJECT-TYPE
    SYNTAX  INTEGER
	{
		off(1),
		on(2)
	}
    ACCESS  read-write
    STATUS  mandatory
    DESCRIPTION
        "Turn on/off for ignoring some trivial error message."
    ::= { adminMisc 62 }

adminEEVersionNo OBJECT-TYPE
    SYNTAX  OCTET STRING (SIZE (4))
    ACCESS  read-only
    STATUS  mandatory
    DESCRIPTION
        "The EE version number, format is Major, Miror, Maintence and Patch"
    ::= { adminMisc 63 }

-- admin ModemSetup table --

adminMdSetupNumber OBJECT-TYPE
    SYNTAX  INTEGER
    ACCESS  read-only
    STATUS  mandatory
    DESCRIPTION
        "The number of dialing Modem Setups on this system; this table
        serves as a template to create 'real' modem script."
    ::= { admin 10 }

adminMdSetupTable OBJECT-TYPE
    SYNTAX  SEQUENCE OF AdminMdSetupEntry
    ACCESS  not-accessible
    STATUS  mandatory
    DESCRIPTION
        "Dialing Modem Setup table."
    ::= { admin 11 }

adminMdSetupEntry OBJECT-TYPE
    SYNTAX  AdminMdSetupEntry
    ACCESS  not-accessible
    STATUS  mandatory
    DESCRIPTION
        "A list of dialing Modem Setup information."
    INDEX   { adminMdSetupIndex }
    ::= { adminMdSetupTable 1 }

AdminMdSetupEntry ::=
    SEQUENCE {
        adminMdSetupIndex
            INTEGER,
        adminMdSetupType
            INTEGER,
        adminMdSetupName
            DisplayString (SIZE (0..16)),
        adminMdSetupATCmd
            DisplayString (SIZE (0..79)),
        adminMdSetupARAP1-0ATCmd
            DisplayString (SIZE (0..79)),
        adminMdSetupIncomingCall
            INTEGER,
        adminMdSetupConnIndication
            INTEGER,
        adminMdSetupCallTimeOut
            INTEGER,
        adminMdSetupCallDelay
            INTEGER
    }

adminMdSetupIndex OBJECT-TYPE
    SYNTAX  INTEGER
    ACCESS  read-only
    STATUS  mandatory
    DESCRIPTION
        "A sequentally assigned index value for each entry."
    ::= { adminMdSetupEntry 1 }

adminMdSetupType OBJECT-TYPE
    SYNTAX  INTEGER
        {
            invalid(1),
            built-in(2),
            user-defined(3)
        }
    ACCESS  read-write
    STATUS  mandatory
    DESCRIPTION
        "The Modem Setup's type. A built-in Modem Setup's type can not be changed.
	 This type has to be set to user-defined before set the following entries."
    ::= { adminMdSetupEntry 2 }

adminMdSetupName OBJECT-TYPE
    SYNTAX  DisplayString (SIZE (0..16))
    ACCESS  read-write
    STATUS  mandatory
    DESCRIPTION
        "The name of the Modem Setup. Once congifured, this name can not be
		 changed"
    ::= { adminMdSetupEntry 3 }

adminMdSetupATCmd    OBJECT-TYPE
    SYNTAX  DisplayString (SIZE (0..79))
    ACCESS  read-write
    STATUS  mandatory
    DESCRIPTION
        "The AT config command string."
    ::= { adminMdSetupEntry 4 }

adminMdSetupARAP1-0ATCmd    OBJECT-TYPE
    SYNTAX  DisplayString (SIZE (0..79))
    ACCESS  read-write
    STATUS  mandatory
    DESCRIPTION
        "The AT config command string for ARAP1.0."
    ::= { adminMdSetupEntry 5 }

adminMdSetupIncomingCall    OBJECT-TYPE
    SYNTAX  INTEGER
        {
            ri(1),
            ring(2)
        }
    ACCESS  read-write
    STATUS  mandatory
    DESCRIPTION
        "The In Coming call Indication: ri signal or 'ring' text"
    ::= { adminMdSetupEntry 6 }

adminMdSetupConnIndication    OBJECT-TYPE
    SYNTAX  INTEGER
        {
            connect(1),
            dcd(2)
        }
    ACCESS  read-write
    STATUS  mandatory
    DESCRIPTION
        "The In Connect Indication: DCD signal or 'connect' text"
    ::= { adminMdSetupEntry 7 }

adminMdSetupCallTimeOut    OBJECT-TYPE
    SYNTAX  INTEGER
    ACCESS  read-write
    STATUS  mandatory
    DESCRIPTION
        "The Call Time Out interval: 0 - 255 sec"
    ::= { adminMdSetupEntry 8 }

adminMdSetupCallDelay    OBJECT-TYPE
    SYNTAX  INTEGER
    ACCESS  read-write
    STATUS  mandatory
    DESCRIPTION
        "The Call Setup Delay interval: 0 - 120000 msec"
    ::= { adminMdSetupEntry 9 }

adminCallerIDNumber    OBJECT-TYPE
    SYNTAX  INTEGER
    ACCESS  read-only
    STATUS  mandatory
    DESCRIPTION
	"Caller Id Number."
    ::= { admin 12 }

adminCallerIDTable OBJECT-TYPE
    SYNTAX  SEQUENCE OF AdminCallerIDEntry
    ACCESS  not-accessible
    STATUS  mandatory
    DESCRIPTION
	""
    ::= { admin 13 }

adminCallerIDEntry OBJECT-TYPE
    SYNTAX  AdminCallerIDEntry
    ACCESS  not-accessible
    STATUS  mandatory
    DESCRIPTION
	""
    INDEX   { adminCallerIDIndex }
    ::= { adminCallerIDTable 1 }

AdminCallerIDEntry ::=
    SEQUENCE {
        adminCallerIDIndex
	    INTEGER,
        adminCallerIDName
            DisplayString (SIZE (0..20)),
        adminCallerIDType
	    INTEGER,
        adminCallerIDComment
            DisplayString (SIZE (0..10))
    }

adminCallerIDIndex OBJECT-TYPE
    SYNTAX  INTEGER
    ACCESS  read-only
    STATUS  mandatory
    DESCRIPTION
        "A sequentally assigned index value for each entry."
    ::= { adminCallerIDEntry 1 }

adminCallerIDName OBJECT-TYPE
    SYNTAX  DisplayString (SIZE (0..20))
    ACCESS  read-write
    STATUS  mandatory
    DESCRIPTION
	""
    ::= { adminCallerIDEntry 2 }

adminCallerIDType OBJECT-TYPE
    SYNTAX  INTEGER
    {
            invalid(1),
	    valid(2)
    }
    ACCESS  read-write
    STATUS  mandatory
    DESCRIPTION
	""
    ::= { adminCallerIDEntry 3 }

adminCallerIDComment OBJECT-TYPE
    SYNTAX  DisplayString (SIZE (0..10))
    ACCESS  read-write
    STATUS  mandatory
    DESCRIPTION
	""
    ::= { adminCallerIDEntry 4 }

-- appletalk group --

atRpa   OBJECT IDENTIFIER ::= { crat 1 }

atRt    OBJECT IDENTIFIER ::= { crat 2 }

-- at remote PC access path group --

atRpaNumber     OBJECT-TYPE
        SYNTAX  INTEGER
        ACCESS  read-only
        STATUS  mandatory
        DESCRIPTION
                "The number of AppleTalk (AT) remote PC paths on this system."
        ::= { atRpa 1 }

-- at route remote PC access table --

        atRpaTable      OBJECT-TYPE
        SYNTAX  SEQUENCE OF AtRpaEntry
        ACCESS  not-accessible
        STATUS  mandatory
        DESCRIPTION
                "Remote PC access path table."
        ::= { atRpa 2 }

        atRpaEntry OBJECT-TYPE
        SYNTAX  AtRpaEntry
        ACCESS  not-accessible
        STATUS  mandatory
        DESCRIPTION
                "A path to a remote PC."
        INDEX   { atRpaIndex }
        ::= { atRpaTable 1 }

AtRpaEntry ::=
SEQUENCE {
        atRpaIndex
                INTEGER,
        atRpaNetworkAddress
                OCTET STRING (SIZE (3)),
        atRpaState
                INTEGER
        }

atRpaIndex OBJECT-TYPE
        SYNTAX  INTEGER
        ACCESS  read-only
        STATUS  mandatory
        DESCRIPTION
	       "The RPA path on which the entry's equivalence is effective.
                The path identified by a particular value of this index
                is the same RPA path as identified by the same value
                of prpaIndex."
        ::= { atRpaEntry 1 }

atRpaNetworkAddress OBJECT-TYPE
        SYNTAX  OCTET STRING (SIZE (3))
        ACCESS  read-only
        STATUS  mandatory
        DESCRIPTION
                "The current or last logged-in remote PC's AT address."
        ::= { atRpaEntry 2 }

atRpaState OBJECT-TYPE
        SYNTAX  INTEGER
        ACCESS  read-only
        STATUS  mandatory
        DESCRIPTION
                "The state of ARA connection"
        ::= { atRpaEntry 3 }

atRpaDialInZone OBJECT-TYPE
        SYNTAX  OCTET STRING (SIZE (0..32))
        ACCESS  read-write
        STATUS  mandatory
        DESCRIPTION
                "The name of specific zone for the remote Mac Users; Note:
                 reboot to take effect"
        ::= { atRpa 3 }

atRpaMaxConnTime OBJECT-TYPE
        SYNTAX  INTEGER
        ACCESS  read-write
        STATUS  mandatory
        DESCRIPTION
                "The time interval of a seesion is allowed after login,
                 in minutes; 1 to 65,535; 0 = no limit"
        ::= { atRpa 4 }

atRpaNoNbpMulticast OBJECT-TYPE
        SYNTAX  INTEGER
                {
                        no(1),
                        yes(2)
                }
        ACCESS  read-write
        STATUS  mandatory
        DESCRIPTION
                "Whether to discard NBP multicast packets"
        ::= { atRpa 5 }

-- at route group --

-- at local route path table --

atPLocalNumber  OBJECT-TYPE
        SYNTAX  INTEGER
        ACCESS  read-only
        STATUS  mandatory
        DESCRIPTION
                "The number of AT dynamic routes on this system."
        ::= { atRt 1 }

atPLocalTable   OBJECT-TYPE
        SYNTAX  SEQUENCE OF AtPLocalEntry
        ACCESS  not-accessible
        STATUS  mandatory
        DESCRIPTION
                "AT dynamic route table."
        ::= { atRt 2 }

atPLocalEntry OBJECT-TYPE
        SYNTAX  AtPLocalEntry
        ACCESS  not-accessible
        STATUS  mandatory
        DESCRIPTION
                "A list of information for a AT dynamic route."
        INDEX   { atPLocalIndex }
        ::= { atPLocalTable 1 }

AtPLocalEntry ::=
        SEQUENCE {
                atPLocalIndex
                        INTEGER,
                atPLocalNetAddress
                        OCTET STRING (SIZE (3)),
                atPLocalNetStart
                        INTEGER,
                atPLocalNetEnd
                        INTEGER,
                atPLocalDefaultRouter
                        OCTET STRING (SIZE (3)),
                atPLocalLocalZone
                        OCTET STRING (SIZE (0..32))
        }

atPLocalIndex OBJECT-TYPE
        SYNTAX  INTEGER
        ACCESS  read-only
        STATUS  mandatory
        DESCRIPTION
                "The route path on which the entry's equivalence is effective.
                The path identified by a particular value of this index
                is the same route path as identified by the same value
                of plocalIndex."
        ::= { atPLocalEntry 1 }

atPLocalNetAddress OBJECT-TYPE
        SYNTAX  OCTET STRING (SIZE (3))
        ACCESS  read-only
        STATUS  mandatory
        DESCRIPTION
                "The current or last logged-in remote PC's AT address."
        ::= { atPLocalEntry 2 }

atPLocalNetStart OBJECT-TYPE
        SYNTAX  INTEGER
        ACCESS  read-only
        STATUS  mandatory
        DESCRIPTION
                "The current or last logged-in remote PC's AT address."
        ::= { atPLocalEntry 3 }

atPLocalNetEnd OBJECT-TYPE
        SYNTAX  INTEGER
        ACCESS  read-only
        STATUS  mandatory
        DESCRIPTION
                "The current or last logged-in remote PC's AT address."
        ::= { atPLocalEntry 4 }

atPLocalDefaultRouter OBJECT-TYPE
        SYNTAX  OCTET STRING (SIZE (3))
        ACCESS  read-only
        STATUS  mandatory
        DESCRIPTION
                "The current or last logged-in remote PC's AT address."
        ::= { atPLocalEntry 5 }



atPLocalLocalZone OBJECT-TYPE
        SYNTAX  OCTET STRING (SIZE (0..32))
        ACCESS  read-only
        STATUS  mandatory
        DESCRIPTION
                "The current or last logged-in remote PC's AT address."
        ::= { atPLocalEntry 6 }


atAarpTable OBJECT-TYPE
        SYNTAX  SEQUENCE OF AtAarpEntry
        ACCESS  not-accessible
        STATUS  mandatory
        DESCRIPTION
                "The AT Address Translation table used for mapping
                from AT addresses to physical addresses."
        ::= { atRt 3 }

atAarpEntry OBJECT-TYPE
        SYNTAX  AtAarpEntry
        ACCESS  not-accessible
        STATUS  mandatory
        DESCRIPTION
                "Each entry contains one AT Address to `physical'
                address equivalence."
        INDEX   { atAarpIfIndex,
                 atAarpNetAddress }
        ::= { atAarpTable 1 }

AtAarpEntry ::=
        SEQUENCE {
            atAarpIfIndex
                INTEGER,
            atAarpPhysAddress
              OCTET STRING (SIZE (6)),
            atAarpNetAddress
              OCTET STRING (SIZE (3))
        }

atAarpIfIndex OBJECT-TYPE
        SYNTAX  INTEGER
        ACCESS  read-only
        STATUS  mandatory
        DESCRIPTION
                "The interface on which this entry's equivalence
                is effective.  The interface identified by a
                particular value of this index is the same
                interface as identified by the same value of
                ifIndex."
        ::= { atAarpEntry 1 }

atAarpPhysAddress OBJECT-TYPE
        SYNTAX  OCTET STRING (SIZE (6))
        ACCESS  read-only
        STATUS  mandatory
        DESCRIPTION
                "The media-dependent `physical' address."
        ::= { atAarpEntry 2 }

atAarpNetAddress OBJECT-TYPE
        SYNTAX  OCTET STRING (SIZE (3))
        ACCESS  read-only
        STATUS  mandatory
        DESCRIPTION
                "The AtAddress corresponding to the media-
                dependent `physical' address."
        ::= { atAarpEntry 3 }


atBestRouterCacheTable OBJECT-TYPE
        SYNTAX  SEQUENCE OF AtBestRouterCacheEntry
        ACCESS  not-accessible
        STATUS  mandatory
        DESCRIPTION
                "The table for efficiently forwarding AT packets to 
                remote networks."
        ::= { atRt 4 }

atBestRouterCacheEntry OBJECT-TYPE
        SYNTAX  AtBestRouterCacheEntry
        ACCESS  not-accessible
        STATUS  mandatory
        DESCRIPTION
                "Each entry contains one AT Address and router physical
                address."
        INDEX   { atBestRouterCacheIfIndex,
                 atBestRouterCacheNetAddress}
        ::= { atBestRouterCacheTable 1 }

AtBestRouterCacheEntry ::=
        SEQUENCE {
            atBestRouterCacheIfIndex
                INTEGER,
            atBestRouterCachePhysAddress
              OCTET STRING (SIZE (6)),
            atBestRouterCacheNetAddress
              OCTET STRING (SIZE (3))
        }

atBestRouterCacheIfIndex OBJECT-TYPE
        SYNTAX  INTEGER
        ACCESS  read-only
        STATUS  mandatory
        DESCRIPTION
                "The interface on which this entry's equivalence
                is effective.  The interface identified by a
                particular value of this index is the same
                interface as identified by the same value of
                ifIndex."
        ::= { atBestRouterCacheEntry 1 }

atBestRouterCachePhysAddress OBJECT-TYPE
        SYNTAX  OCTET STRING (SIZE (6))
        ACCESS  read-only
        STATUS  mandatory
        DESCRIPTION
                "The host address of the next router a packet should go 
                 through to reach the specified AppleTalk."
        ::= { atBestRouterCacheEntry 2 }

atBestRouterCacheNetAddress OBJECT-TYPE
        SYNTAX  OCTET STRING (SIZE (3))
        ACCESS  read-only
        STATUS  mandatory
        DESCRIPTION
                "The At Address for recently learned routers on the same
                 network segment as the AccessBuilder."
        ::= { atBestRouterCacheEntry 3 }



atRtProtocolEnabled  OBJECT-TYPE
        SYNTAX  INTEGER
                {
                        no(1),
                        yes(2)
                }
        ACCESS        read-write
        STATUS        mandatory
        DESCRIPTION
                " ARAP protocol enable/disable flag."
        ::= { atRt 5 }

atRtInPackets OBJECT-TYPE
        SYNTAX  Counter
        ACCESS  read-only
        STATUS  mandatory
        DESCRIPTION
                "AT packets received with no error."
        ::= { atRt 6 }

atRtOutPackets OBJECT-TYPE
        SYNTAX  Counter
        ACCESS  read-only
        STATUS  mandatory
        DESCRIPTION
                "AT packets transmitted with no error."
        ::= { atRt 7 }

atRtResetAllCounters OBJECT-TYPE
        SYNTAX  INTEGER
        ACCESS  read-write
        STATUS  mandatory
        DESCRIPTION
                "Writing any value to this variable will reset all port-related
                counters to zero."
        ::= { atRt 8 }

atRtZoneFilterAction OBJECT-TYPE
    SYNTAX  INTEGER
        {
            discard(1),
            forward(2)
        }
    ACCESS  read-write
    STATUS  mandatory
    DESCRIPTION
        "This variable indicate the operation of zone filter." 
        ::= { atRt 9 }

atZoneFilterTable OBJECT-TYPE
    SYNTAX  SEQUENCE OF AtZoneFilterEntry
    ACCESS  not-accessible
    STATUS  mandatory
    DESCRIPTION
        "Zone Filter table."
        ::= { atRt 10 }


atZoneFilterEntry OBJECT-TYPE
    SYNTAX  AtZoneFilterEntry
    ACCESS  not-accessible
    STATUS  mandatory
    DESCRIPTION
        "A list of information for a zone filter."
    INDEX   { atZoneFilterIndex }
    ::= { atZoneFilterTable 1 }

AtZoneFilterEntry ::=
    SEQUENCE {

        atZoneFilterIndex
            INTEGER,
        atZoneFilterName
            DisplayString (SIZE (0..32)),
        atZoneFilterType
            INTEGER
    }

atZoneFilterIndex OBJECT-TYPE
    SYNTAX  INTEGER
    ACCESS  read-only
    STATUS  mandatory
    DESCRIPTION
        "A sequentally assigned index value for each entry."
    ::= { atZoneFilterEntry 1 }

atZoneFilterName OBJECT-TYPE
    SYNTAX  DisplayString (SIZE (0..32))
    ACCESS  read-write
    STATUS  mandatory
    DESCRIPTION
        "The zone filter name."
    ::= { atZoneFilterEntry 2 }

atZoneFilterType OBJECT-TYPE
    SYNTAX  INTEGER
        {
            invalid(1),
            valid(2)
        }
    ACCESS  read-write
    STATUS  mandatory
    DESCRIPTION
        "This value controls whether the zone filter name is valid or invalid.
		 It will be set valid while adding and set invalid while deleting."
    ::= { atZoneFilterEntry 3 }

--
--  The following three traps are added in by Stephen Tsai for ZEROX 08/03/95
--
userLogInTrap TRAP-TYPE
       ENTERPRISE  centrum
       VARIABLES   { adminLastTrap }
       DESCRIPTION
               " This trap is sent after the user logged in the AccessBuilder."
       ::= 16

userLogOutTrap TRAP-TYPE
       ENTERPRISE  centrum
       VARIABLES   { adminLastTrap }
       DESCRIPTION
               " This trap is sent after the user logged out the AccessBuilder."
       ::= 17

userSessionTimeOutTrap TRAP-TYPE
       ENTERPRISE  centrum
       VARIABLES   { adminLastTrap }
       DESCRIPTION
               " This trap is sent after the user logged out due to idle
	         time expired."
       ::= 18

END
