-------------------------------------------------------------------------------
-- file: ATMCongestionStatistics.mib 
--
-- description:
-- This file contains the SNMP definitions for the ATM Congestion Statistics 
-- area.
--
--  %%history-start%%
--  1998.07.21 munger 31A1185: Creation from V1.0 of MIBTemplate.mib. 
--  1998.07.30 munger 31A1185: Changed Low, Medium, Severe, Total seconds 
--    from NncExtCounter64 to Counter32. 
--  1998.08.26 munger 31A1185: Changed nncAtmCongStatsHardwareType to 
--    nncAtmCongPointHardwareType. 
--  1998.09.11 cgibson 31A1185: change the extension to 63 as allocated from 
--    Numbers Admin 
--  1998.09.30 gsusilo 31A1131: Added the intervalized congestion statistics 
--  %%history-end%%
--
-- Copyright 1998 Newbridge Networks Corporation.  All Rights Reserved
-------------------------------------------------------------------------------
NNC-ATM-CONGESTIONSTATISTICS-MIB DEFINITIONS ::= BEGIN

  IMPORTS
    MODULE-IDENTITY, OBJECT-TYPE, Counter32
      FROM SNMPv2-SMI
    TEXTUAL-CONVENTION
      FROM SNMPv2-TC
    MODULE-COMPLIANCE, OBJECT-GROUP
      FROM SNMPv2-CONF
    PhysicalIndex
      FROM ENTITY-MIB
    nncExtensions, NncExtCounter64
      FROM NNCGNI0001-SMI
    NncExtIntvlStateType
      FROM NNC-INTERVAL-STATISTICS-TC-MIB;

  nncAtmCongestionStatistics MODULE-IDENTITY
    LAST-UPDATED "9807141255Z"
    ORGANIZATION "Newbridge Networks Corporation"
    CONTACT-INFO
                 "Newbridge Networks Corporation
                  Postal: 600 March Road
                  Kanata, Ontario
                  Canada K2K 2E6

                  Phone:  +1 613 591 3600
                  Fax:    +1 613 591 3680"

    DESCRIPTION
      "This module contains the definitions for congestion statistics on ATM
       products.  Congestion statistics allow the user to monitor the 
       performance of a particular congestion point in order to alleviate future
       congestion problems.
      
       This MIB module contains the following tables:
         ATM Congestion Point Information Table
         ATM Raw Congestion Statistics Table.
         ATM Current Short Interval Congestion Statistics Table.
         ATM Short Interval Congestion Statistics Table.
         ATM Current Long Interval Congestion Statistics Table.
         ATM Long Interval Congestion Statistics Table.
         
         
       The following tables describe the mapping between a congestion point and
       the qualities of service available on the 36170.  Each card configuration
       is assigned a hardware type, which is then used to determine which 
       qualities of service are available for that particular card 
       configuration.
           
       Release 4.0 of the 36170 supports only OC12-1 hardware.
           
       Table 1 associates a number with each hardware type.  The hardware type 
       is a function of:
         - type of card,
         - queue and QOS configuration based on ASIC used on the card,
         - fabric type,
         - switch profile,
         - congestion point.
       The Congestion Point Index is to be used as nncAtmCongPointInfoIndex, 
       nncAtmCongPointRawIndex, nncAtmCongPointCurrentShortIntvlIndex,
       nncAtmCongPointShortIntvlIndex, nncAtmCongPointCurrentLongIntvlIndex,
       and nncAtmCongPointLongIntvlIndex.
             
       Table 2 consists of columns for each hardware type indicating which
       qualities of service are available for the particular hardware type.
       The Index column associates a number for each quality of service, which 
       is used as the nncAtmCongStatsQOSRawIndex, 
       nncAtmCongStatsQOSCurrentShortIntvlIndex, nncAtmCongStatsQOSShortIntvlIndex,
       nncAtmCongStatsQOSCurrentLongIntvlIndex, and nncAtmCongStatsQOSLongIntvlIndex.
           
        ________________________________________________________
       |           | SHub Diablo  |   SHub NSX   |  SHub Eagle  |
       |___________|______________|______________|______________|
       |Congestion |     |        |     |        |     |        |
       |  Point    | MUX | SWITCH | MUX | SWITCH | MUX | SWITCH |
       |___________|_____|________|_____|________|_____|________|
       |Congestion |     |        |     |        |     |        |
       |Point Index|1 , 2|  3 , 4 |1 , 2|  3 , 4 |1 , 2|  3 , 4 |
       |___________|_____|________|_____|________|_____|________|
       |________________________________________________________|
       |2K/12K     |              |              |              |
       |Profile 1  |  H/W Type 1  |  H/W Type 1  |  H/W Type 1  |
       |___________|______________|______________|______________|
       |2K/12K     |              |              |              |
       |Profile 2  |  H/W Type 2  |  H/W Type 2  |  H/W Type 2  |
       |___________|______________|______________|______________|
       |2K/12K     |              |              |              |
       |Profile 3  |  H/W Type 3  |  H/W Type 3  |  H/W Type 3  |
       |___________|______________|______________|______________|
       |2K/12K     |              |              |              |
       |Profile 4  |  H/W Type 4  |  H/W Type 4  |  H/W Type 4  |
       |___________|______________|______________|______________|
       |32K        |  H/W Type 3  |  H/W Type 3  |  5  |   3    |
       |___________|______________|______________|_____|________|

       Table 1: Fabric and linecard Hardware Type configurations

        ___________________________________________________________________
       |           |                    DSC NSX                            |
       |___________|_______________________________________________________|
       |Congestion |      |      |      |      |      |      |      |      |
       |  Point    | DRX1 | DRX2 | DRX3 | DRX4 | DRX5 | DRX6 | DRX7 | DRX8 |
       |___________|______|______|______|______|______|______|______|______|
       |Congestion |      |      |      |      |      |      |      |      |
       |Point Index|  1   |  2   |  3   |  4   |  5   |  6   |  7   |  8   |
       |___________|______|______|______|______|______|______|______|______|
       |___________________________________________________________________|
       |2K/12K     |                                                       |
       |Profile 1  |                   H/W Type 1                          |
       |___________|_______________________________________________________|
       |2K/12K     |                                                       |
       |Profile 2  |                   H/W Type 2                          |
       |___________|_______________________________________________________|
       |2K/12K     |                                                       |
       |Profile 3  |                   H/W Type 3                          |
       |___________|_______________________________________________________|
       |2K/12K     |                                                       |
       |Profile 4  |                   H/W Type 4                          |
       |___________|_______________________________________________________|
       |32K        |                   H/W Type 3                          |
       |___________|_______________________________________________________|
 
       Table 1: Continued

        ___________________________________________________________________
       |           |                   DSC Diablo                          |
       |___________|_______________________________________________________|
       |Congestion |      |      |      |      |      |      |      |      |
       |  Point    | DRX1 | DRX2 | DRX3 | DRX4 | DRX5 | DRX6 | DRX7 | DRX8 |
       |___________|______|______|______|______|______|______|______|______|
       |Congestion |      |      |      |      |      |      |      |      |
       |Point Index|  1   |  2   |  3   |  4   |  5   |  6   |  7   |  8   |
       |___________|______|______|______|______|______|______|______|______|
       |___________________________________________________________________|
       |2K/12K     |                                                       |
       |Profile 1  |                   H/W Type 1                          |
       |___________|_______________________________________________________|
       |2K/12K     |                                                       |
       |Profile 2  |                   H/W Type 2                          |
       |___________|_______________________________________________________|
       |2K/12K     |                                                       |
       |Profile 3  |                   H/W Type 3                          |
       |___________|_______________________________________________________|
       |2K/12K     |                                                       |
       |Profile 4  |                   H/W Type 4                          |
       |___________|_______________________________________________________|
       |32K        |                   H/W Type 3                          |
       |___________|_______________________________________________________|
 
       Table 1: Continued
 
        ____________________________________________________
       |           | DHub Diablo | DHub Eagle | LSHub Eagle |
       |___________|_____________|____________|_____________|
       |Congestion |             |            |             |
       |  Point    |     MUX     |     MUX    |     MUX     |
       |___________|_____________|____________|_____________|
       |Congestion |             |            |             |
       |Point Index|      1      |      1     |      1      |
       |___________|_____________|____________|_____________|
       |____________________________________________________|
       |2K/12K     |             |            |             |
       |Profile 1  | H/W Type 1  | H/W Type 1 | H/W Type 1  |
       |___________|_____________|____________|_____________|
       |2K/12K     |             |            |             |
       |Profile 2  | H/W Type 2  | H/W Type 2 | H/W Type 2  |
       |___________|_____________|____________|_____________|
       |2K/12K     |             |            |             |
       |Profile 3  | H/W Type 3  | H/W Type 3 | H/W Type 3  |
       |___________|_____________|____________|_____________|
       |2K/12K     |             |            |             |
       |Profile 4  | H/W Type 4  | H/W Type 4 | H/W Type 4  |
       |___________|_____________|____________|_____________|
       |32K        | H/W Type 3  | H/W Type 5 | H/W Type 5  |
       |___________|_____________|____________|_____________|
 
       Table 1: Continued
  
        _________________________________________________________
       |           | OC3-1  | OC3-2  | OC12-1 |      OC12-2      |
       |___________|________|________|________|__________________|
       |Congestion |        |        |        |         |        |
       |  Point    | Egress | Egress | Egress | Ingress | Egress |
       |___________|________|________|________|_________|________|
       |Congestion |        |        |        |         |        |
       |Point Index|   1    |   1    |   1    |    1    |   2    |
       |___________|________|________|________|_________|________|
       |_________________________________________________________|
       |2K/12K     |  H/W   |  H/W   |  H/W   |       H/W        |
       |Profile 1  | Type1  | Type1  | Type1  |      Type1       |
       |___________|________|________|________|__________________|
       |2K/12K     |  H/W   |  H/W   |  H/W   |       H/W        |
       |Profile 2  | Type2  | Type2  | Type2  |      Type2       |
       |___________|________|________|________|__________________|
       |2K/12K     |  H/W   |  H/W   |  H/W   |       H/W        |
       |Profile 3  | Type3  | Type3  | Type3  |      Type3       |
       |___________|________|________|________|__________________|
       |2K/12K     |  H/W   |  H/W   |  H/W   |       H/W        |
       |Profile 4  | Type4  | Type4  | Type4  |      Type4       |
       |___________|________|________|________|__________________|
       |32K        |  H/W   |  H/W   |  H/W   |       H/W        |
       |           | Type3  | Type5  | Type3  |      Type5       |
       |___________|________|________|________|__________________|
 
       Table 1: Continued
 
        _________________________________________________________________
       |           |          DS3-1           |          DS3-2           |
       |___________|__________________________|__________________________|
       |Congestion |        |        |        |        |        |        |
       |  Point    | Egress | Egress | Egress | Egress | Egress | Egress |
       |___________|________|________|________|________|________|________|
       |Congestion |        |        |        |        |        |        |
       |Point Index|   1    |   2    |   3    |   1    |   2    |   3    |
       |___________|________|________|________|________|________|________|
       |_________________________________________________________________|
       |2K/12K     |  H/W   |  H/W   |  H/W   |  H/W   |  H/W   |  H/W   |
       |Profile 1  | Type1  | Type1  | Type1  | Type1  | Type1  | Type1  |
       |___________|________|________|________|________|________|________|
       |2K/12K     |  H/W   |  H/W   |  H/W   |  H/W   |  H/W   |  H/W   |
       |Profile 2  | Type2  | Type2  | Type2  | Type2  | Type2  | Type2  |
       |___________|________|________|________|________|________|________|
       |2K/12K     |  H/W   |  H/W   |  H/W   |  H/W   |  H/W   |  H/W   |
       |Profile 3  | Type3  | Type3  | Type3  | Type3  | Type3  | Type3  |
       |___________|________|________|________|________|________|________|
       |2K/12K     |  H/W   |  H/W   |  H/W   |  H/W   |  H/W   |  H/W   |
       |Profile 4  | Type4  | Type4  | Type4  | Type4  | Type4  | Type4  |
       |___________|________|________|________|________|________|________|
       |32K        |  H/W   |  H/W   |  H/W   |  H/W   |  H/W   |  H/W   |
       |           | Type3  | Type3  | Type3  | Type5  | Type5  | Type5  |
       |___________|________|________|________|________|________|________|
 
       Table 1: Continued
 
        _________________________________________________________________
       |           |           E3-1           |           E3-2           |
       |___________|__________________________|__________________________|
       |Congestion |        |        |        |        |        |        |
       |  Point    | Egress | Egress | Egress | Egress | Egress | Egress |
       |___________|________|________|________|________|________|________|
       |Congestion |        |        |        |        |        |        |
       |Point Index|   1    |   2    |   3    |   1    |   2    |   3    |
       |___________|________|________|________|________|________|________|
       |_________________________________________________________________|
       |2K/12K     |  H/W   |  H/W   |  H/W   |  H/W   |  H/W   |  H/W   |
       |Profile 1  | Type1  | Type1  | Type1  | Type1  | Type1  | Type1  |
       |___________|________|________|________|________|________|________|
       |2K/12K     |  H/W   |  H/W   |  H/W   |  H/W   |  H/W   |  H/W   |
       |Profile 2  | Type2  | Type2  | Type2  | Type2  | Type2  | Type2  |
       |___________|________|________|________|________|________|________|
       |2K/12K     |  H/W   |  H/W   |  H/W   |  H/W   |  H/W   |  H/W   |
       |Profile 3  | Type3  | Type3  | Type3  | Type3  | Type3  | Type3  |
       |___________|________|________|________|________|________|________|
       |2K/12K     |  H/W   |  H/W   |  H/W   |  H/W   |  H/W   |  H/W   |
       |Profile 4  | Type4  | Type4  | Type4  | Type4  | Type4  | Type4  |
       |___________|________|________|________|________|________|________|
       |32K        |  H/W   |  H/W   |  H/W   |  H/W   |  H/W   |  H/W   |
       |           | Type3  | Type3  | Type3  | Type5  | Type5  | Type5  |
       |___________|________|________|________|________|________|________|
 
       Table 1: Continued
 
        _______________________________________________
       |           |  T1-1  |  T1-2  |  E1-1  |  E1-2  |
       |___________|________|________|________|________|
       |Congestion |        |        |        |        |
       |  Point    | Egress | Egress | Egress | Egress |
       |___________|________|________|________|________|
       |Congestion |        |        |        |        |
       |Point Index|   1    |   1    |   1    |   1    |
       |___________|________|________|________|________|
       |_______________________________________________|
       |2K/12K     |  H/W   |  H/W   |  H/W   |  H/W   |
       |Profile 1  | Type1  | Type1  | Type1  | Type1  |
       |___________|________|________|________|________|
       |2K/12K     |  H/W   |  H/W   |  H/W   |  H/W   |
       |Profile 2  | Type2  | Type2  | Type2  | Type2  |
       |___________|________|________|________|________|
       |2K/12K     |  H/W   |  H/W   |  H/W   |  H/W   |
       |Profile 3  | Type3  | Type3  | Type3  | Type3  |
       |___________|________|________|________|________|
       |2K/12K     |  H/W   |  H/W   |  H/W   |  H/W   |
       |Profile 4  | Type4  | Type4  | Type4  | Type4  |
       |___________|________|________|________|________|
       |32K        |  H/W   |  H/W   |  H/W   |  H/W   |
       |           | Type3  | Type5  | Type3  | Type5  |
       |___________|________|________|________|________|
 
       Table 1: Continued
  
        _____________________________________________________________
       |  Quality    |       |  H/W  |  H/W  |  H/W  |  H/W  |  H/W  |
       | of Service  | Index | Type1 | Type2 | Type3 | Type4 | Type5 |
       |_____________|_______|_______|_______|_______|_______|_______|
       |    CBR      |   1   |       |       |       |       |   X   |
       |_____________|_______|_______|_______|_______|_______|_______|
       |    UBR      |   2   |       |       |       |   X   |   X   |
       |_____________|_______|_______|_______|_______|_______|_______|
       |  rt_VBR1    |   3   |       |       |       |       |   X   |
       |_____________|_______|_______|_______|_______|_______|_______|
       |  rt_VBR2    |   4   |       |       |       |       |   X   |
       |_____________|_______|_______|_______|_______|_______|_______|
       | nrt_VBR1_2  |   5   |       |       |       |       |   X   |
       |_____________|_______|_______|_______|_______|_______|_______|
       |  nrt_VBR3   |   6   |       |       |       |       |   X   |
       |_____________|_______|_______|_______|_______|_______|_______|
       |    ABR      |   7   |       |       |       |       |   X   |
       |_____________|_______|_______|_______|_______|_______|_______|
       | CBR_rtVBR   |   8   |   X   |   X   |   X   |   X   |       |
       |_____________|_______|_______|_______|_______|_______|_______|
       | nrt_VBR/UBR |   9   |   X   |       |       |       |       |
       |_____________|_______|_______|_______|_______|_______|_______|
       |  ABR/UBR    |  10   |       |   X   |   X   |       |       |
       |_____________|_______|_______|_______|_______|_______|_______|
       |  nrt_VBR    |  11   |       |       |   X   |   X   |       |
       |_____________|_______|_______|_______|_______|_______|_______|
 
       Table 2: QOS supported by each Hardware Type
      "

  ::= { nncExtensions 63 }

  nncAtmCongStatsObjects 
    OBJECT IDENTIFIER ::= { nncAtmCongestionStatistics 1 }
  nncAtmCongStatsGroups 
    OBJECT IDENTIFIER ::= { nncAtmCongestionStatistics 2 }
  nncAtmCongStatsCompliances 
    OBJECT IDENTIFIER ::= { nncAtmCongestionStatistics 3 }


--------------------------------------------------------------------------------
-- Type Definitions
--------------------------------------------------------------------------------

--------------------------------------------------------------------------------
-- Object Definitions
--
-- This MIB module contains the following tables:
--   nncAtmCongPointInfoTable
--   nncAtmCongStatsRawTable
--   nncAtmCongStatsCurrentShortIntvlTable
--   nncAtmCongStatsShortIntvlTable
--   nncAtmCongStatsCurrentLongIntvlTable
--   nncAtmCongStatsLongIntvlTable
--------------------------------------------------------------------------------
-- nncAtmCongPointInfoTable
  nncAtmCongPointInfoTable OBJECT-TYPE 
        SYNTAX      SEQUENCE OF NncAtmCongPointInfoEntry 
        MAX-ACCESS  not-accessible
        STATUS      current
        DESCRIPTION 
          "The ATM Congestion Point Information table.  This table maintains
           various information for the congestion point specified."
  ::= { nncAtmCongStatsObjects 1 }
  
  nncAtmCongPointInfoEntry OBJECT-TYPE 
        SYNTAX      NncAtmCongPointInfoEntry 
        MAX-ACCESS  not-accessible
        STATUS      current
        DESCRIPTION 
          "An entry in the ATM Congestion Point Information table."
        INDEX       { 
          entPhysicalEntityInfoIndex,
          nncAtmCongPointInfoIndex 
        }
  ::= { nncAtmCongPointInfoTable 1 }
  
  NncAtmCongPointInfoEntry ::=
    SEQUENCE {
      entPhysicalEntityInfoIndex  PhysicalIndex,
      nncAtmCongPointInfoIndex    INTEGER,
      nncAtmCongPointHardwareType INTEGER
    }

  entPhysicalEntityInfoIndex OBJECT-TYPE
    SYNTAX      PhysicalIndex
    MAX-ACCESS  not-accessible
    STATUS      current
    DESCRIPTION
        "A unique value that identifies the physical entity, whether it supports
         Congestion Statistics or not.  This value is equivalent to the value
         of PhysicalIndex."
  ::= { nncAtmCongPointInfoEntry 1 }
    
  nncAtmCongPointInfoIndex OBJECT-TYPE
    SYNTAX      INTEGER (1..8)
    MAX-ACCESS  not-accessible
    STATUS      current
    DESCRIPTION
        "A unique value between 1 and 8 that identifies the congestion point on
         an entity which supports Congestion Statistics."
  ::= { nncAtmCongPointInfoEntry 2 }
    
  nncAtmCongPointHardwareType OBJECT-TYPE
        SYNTAX      INTEGER (1..99)
        MAX-ACCESS  read-only
        STATUS      current
        DESCRIPTION 
          "A unique value, 1 to 99, that identifies the current hardware type of
           the congestion point.  See Tables 1 and 2 for further details."
  ::= { nncAtmCongPointInfoEntry 3 }
  
  
-- nncAtmCongStatsRawTable
  nncAtmCongStatsRawTable OBJECT-TYPE 
        SYNTAX      SEQUENCE OF NncAtmCongStatsRawEntry 
        MAX-ACCESS  not-accessible
        STATUS      current
        DESCRIPTION 
          "The ATM Raw Congestion Statistics table.  This table maintains raw 
           per quality of service statistics since the interface was started."
  ::= { nncAtmCongStatsObjects 2 }
  
  nncAtmCongStatsRawEntry OBJECT-TYPE 
        SYNTAX      NncAtmCongStatsRawEntry 
        MAX-ACCESS  not-accessible
        STATUS      current
        DESCRIPTION 
          "An entry in the ATM Raw Congestion Statistics table."
        INDEX       { 
          entPhysicalEntityRawIndex, 
          nncAtmCongPointRawIndex, 
          nncAtmCongStatsQOSRawIndex 
        }
  ::= { nncAtmCongStatsRawTable 1 }
  
  NncAtmCongStatsRawEntry ::=
    SEQUENCE {
      entPhysicalEntityRawIndex             PhysicalIndex,
      nncAtmCongPointRawIndex               INTEGER,
      nncAtmCongStatsQOSRawIndex            INTEGER,
      nncAtmCongStatsTotalCellsArrived      NncExtCounter64,
      nncAtmCongStatsTotalCellsDiscarded    NncExtCounter64,
      nncAtmCongStatsClp0CellsDiscarded     NncExtCounter64,
      nncAtmCongStatsLowCongestedSeconds    Counter32,
      nncAtmCongStatsMediumCongestedSeconds Counter32,
      nncAtmCongStatsSevereCongestedSeconds Counter32,
      nncAtmCongStatsTotalSeconds           Counter32,
      nncAtmCongStatsCurrentCongestionState INTEGER,
      nncAtmCongStatsAlarmStatus            INTEGER,
      nncAtmCongStatsVirtualBandwidthAvail  Counter32
    }
    
  entPhysicalEntityRawIndex OBJECT-TYPE
    SYNTAX      PhysicalIndex
    MAX-ACCESS  not-accessible
    STATUS      current
    DESCRIPTION
        "A unique value that identifies the physical entity, whether it supports
         Congestion Statistics or not.  This value is equivalent to the value
         of PhysicalIndex."
  ::= { nncAtmCongStatsRawEntry 1 }
    
  nncAtmCongPointRawIndex OBJECT-TYPE
    SYNTAX      INTEGER (1..8)
    MAX-ACCESS  not-accessible
    STATUS      current
    DESCRIPTION
        "A unique value between 1 and 8 that identifies the congestion point on
         an entity which supports Congestion Statistics."
  ::= { nncAtmCongStatsRawEntry 2 }
    
  nncAtmCongStatsQOSRawIndex OBJECT-TYPE
        SYNTAX      INTEGER (1..11)
        MAX-ACCESS  not-accessible
        STATUS      current
        DESCRIPTION 
          "A number between 1 and 11 that identifies the quality of service on 
           which the set of statistics was collected for an entity.  The 
           following table describes the quality of service categories available
           and their corresponding index.
           
           Quality of Service   Quality of Service Index
           ------------------   ------------------------
                  CBR                      1
                  UBR                      2
                rt-VBR1                    3
                rt-VBR2                    4
               nrt-VBR1-2                  5
                nrt-VBR3                   6
                  ABR                      7
               CBR-rtVBR                   8
              nrt-VBR/UBR                  9
                ABR/UBR                   10
                nrt-VBR                   11
          "  
  ::= { nncAtmCongStatsRawEntry 3 }
 
  nncAtmCongStatsTotalCellsArrived OBJECT-TYPE
        SYNTAX      NncExtCounter64
        MAX-ACCESS  read-only
        STATUS      current
        DESCRIPTION 
          "Total number of cells received."
  ::= { nncAtmCongStatsRawEntry 4 }
  
  nncAtmCongStatsTotalCellsDiscarded OBJECT-TYPE
        SYNTAX      NncExtCounter64
        MAX-ACCESS  read-only
        STATUS      current
        DESCRIPTION 
          "Total number of cells discarded due to congestion."
  ::= { nncAtmCongStatsRawEntry 5 }
  
  nncAtmCongStatsClp0CellsDiscarded OBJECT-TYPE
        SYNTAX      NncExtCounter64
        MAX-ACCESS  read-only
        STATUS      current
        DESCRIPTION 
          "Number of CLP 0 cells discarded due to congestion."
  ::= { nncAtmCongStatsRawEntry 6 }
  
  nncAtmCongStatsLowCongestedSeconds OBJECT-TYPE
        SYNTAX      Counter32
        MAX-ACCESS  read-only
        STATUS      current
        DESCRIPTION 
          "Number of seconds the congestion point was in the Low Congestion
           State."
  ::= { nncAtmCongStatsRawEntry 7 }
  
  nncAtmCongStatsMediumCongestedSeconds OBJECT-TYPE
        SYNTAX      Counter32
        MAX-ACCESS  read-only
        STATUS      current
        DESCRIPTION 
          "Number of seconds the congestion point was in the Medium Congestion 
           State."
  ::= { nncAtmCongStatsRawEntry 8 }
  
  nncAtmCongStatsSevereCongestedSeconds OBJECT-TYPE
        SYNTAX      Counter32
        MAX-ACCESS  read-only
        STATUS      current
        DESCRIPTION 
          "Number of seconds the congestion point was in the Severe Congestion 
           State."
  ::= { nncAtmCongStatsRawEntry 9 }
  
  nncAtmCongStatsTotalSeconds OBJECT-TYPE
        SYNTAX      Counter32
        MAX-ACCESS  read-only
        STATUS      current
        DESCRIPTION 
          "Total number of seconds the congestion point was in the Normal, Low, 
           Medium, or Severe congestion states."
  ::= { nncAtmCongStatsRawEntry 10 }
  
  nncAtmCongStatsCurrentCongestionState OBJECT-TYPE
        SYNTAX INTEGER {
                 congStatsNormalState(1),
                 congStatsLowCongState(2),
                 congStatsMediumCongState(3),
                 congStatsSevereCongState(4)
               }
        MAX-ACCESS  read-only
        STATUS      current
        DESCRIPTION 
          "Current congestion state of the congestion point - one of Normal, 
           Low, Medium, or Severe.  When the current congestion state is 
           determined, the corresponding congestion time counter will 
           increment."
  ::= { nncAtmCongStatsRawEntry 11 }
  
  nncAtmCongStatsAlarmStatus OBJECT-TYPE
        SYNTAX INTEGER {
                 congStatsAlarmOn(1),
                 congStatsAlarmOff(2)
               }
        MAX-ACCESS  read-only
        STATUS      current
        DESCRIPTION 
          "Current alarm status - either ON or OFF.  When a congestion point has 
           been severely congested for longer than the allowable threshold time 
           the value of this object is set to congStatsAlarmOn.  When severe 
           congestion clears, the value of this object is set to 
           congStatsAlarmOff."
  ::= { nncAtmCongStatsRawEntry 12 }
  
  nncAtmCongStatsVirtualBandwidthAvail OBJECT-TYPE
        SYNTAX      Counter32
        MAX-ACCESS  read-only
        STATUS      current
        DESCRIPTION 
          "Percentage of virtual bandwidth that is available for use for each 
           quality of service."
  ::= { nncAtmCongStatsRawEntry 13 }
  
-------------------------------------------------------------------------------
-- Intervalized Congestion Statistics
-- The following tables cover Current Short Interval, Short Interval 
-- (96 intervals, 15 minute/per interval), Current Long Interval, and 
-- Long Interval (7 intervals, 1 day/per interval)  Congestion Statistics
-------------------------------------------------------------------------------
  
-------------------------------------------
-- nncAtmCongStatsCurrentShortIntvlTable --
-------------------------------------------
  nncAtmCongStatsCurrentShortIntvlTable OBJECT-TYPE 
        SYNTAX      SEQUENCE OF NncAtmCongStatsCurrentShortIntvlEntry 
        MAX-ACCESS  not-accessible
        STATUS      current
        DESCRIPTION 
          "The ATM Current Short Interval Congestion Statistics table.  
           This table maintains current-short interval statistics per quality of service 
           since the interface was started."
  ::= { nncAtmCongStatsObjects 3 }
  
  nncAtmCongStatsCurrentShortIntvlEntry OBJECT-TYPE 
        SYNTAX      NncAtmCongStatsCurrentShortIntvlEntry 
        MAX-ACCESS  not-accessible
        STATUS      current
        DESCRIPTION 
          "An entry in the ATM current-Short Interval Congestion Statistics table."
        INDEX       { 
          entPhysicalEntityCurrentShortIntvlIndex, 
          nncAtmCongPointCurrentShortIntvlIndex, 
          nncAtmCongStatsQOSCurrentShortIntvlIndex
        }
  ::= { nncAtmCongStatsCurrentShortIntvlTable 1 }
  
  NncAtmCongStatsCurrentShortIntvlEntry ::=
    SEQUENCE {
      entPhysicalEntityCurrentShortIntvlIndex                PhysicalIndex,
      nncAtmCongPointCurrentShortIntvlIndex                  INTEGER,
      nncAtmCongStatsQOSCurrentShortIntvlIndex               INTEGER,
      nncAtmCongStatsCurrentShortIntvlState                  NncExtIntvlStateType,
      nncAtmCongStatsCurrentShortIntvlAbsoluteIntervalNumber INTEGER,
      nncAtmCongStatsCurrentShortIntvlTotalCellsArrived      NncExtCounter64,
      nncAtmCongStatsCurrentShortIntvlTotalCellsDiscarded    NncExtCounter64,
      nncAtmCongStatsCurrentShortIntvlClp0CellsDiscarded     NncExtCounter64,
      nncAtmCongStatsCurrentShortIntvlLowCongestedSeconds    Counter32,
      nncAtmCongStatsCurrentShortIntvlMediumCongestedSeconds Counter32,
      nncAtmCongStatsCurrentShortIntvlSevereCongestedSeconds Counter32,
      nncAtmCongStatsCurrentShortIntvlTotalSeconds           Counter32,
      nncAtmCongStatsCurrentShortIntvlCongestionState        INTEGER,
      nncAtmCongStatsCurrentShortIntvlAlarmStatus            INTEGER
    }
    
  entPhysicalEntityCurrentShortIntvlIndex OBJECT-TYPE
    SYNTAX      PhysicalIndex
    MAX-ACCESS  not-accessible
    STATUS      current
    DESCRIPTION
        "A unique value that identifies the physical entity, whether it supports
         Congestion Statistics or not.  This value is equivalent to the value
         of PhysicalIndex."
  ::= { nncAtmCongStatsCurrentShortIntvlEntry 1 }
    
  nncAtmCongPointCurrentShortIntvlIndex OBJECT-TYPE
    SYNTAX      INTEGER (1..8)
    MAX-ACCESS  not-accessible
    STATUS      current
    DESCRIPTION
        "A unique value between 1 and 8 that identifies the congestion point on
         an entity which supports Congestion Statistics."
  ::= { nncAtmCongStatsCurrentShortIntvlEntry 2 }
    
  nncAtmCongStatsQOSCurrentShortIntvlIndex OBJECT-TYPE
        SYNTAX      INTEGER (1..11)
        MAX-ACCESS  not-accessible
        STATUS      current
        DESCRIPTION 
          "A number between 1 and 11 that identifies the quality of service on 
           which the set of statistics was collected for an entity.  The 
           following table describes the quality of service categories available
           and their corresponding index.
           
           Quality of Service   Quality of Service Index
           ------------------   ------------------------
                  CBR                      1
                  UBR                      2
                rt-VBR1                    3
                rt-VBR2                    4
               nrt-VBR1-2                  5
                nrt-VBR3                   6
                  ABR                      7
               CBR-rtVBR                   8
              nrt-VBR/UBR                  9
                ABR/UBR                   10
                nrt-VBR                   11
          "  
  ::= { nncAtmCongStatsCurrentShortIntvlEntry 3 }
  
  nncAtmCongStatsCurrentShortIntvlState OBJECT-TYPE
        SYNTAX      NncExtIntvlStateType
        MAX-ACCESS  read-only
        STATUS      current
        DESCRIPTION             
          "The state of the interval in the interval statistics interface.
           Possible states are:
           normal      (1) - normal interval; no change in time and no resets
           nonexistent (2) - statistics do not exist for this interval
           userReset   (3) - the user has reset statistics collection
                             during this interval
           start       (4) - this is the first interval
           timeChange  (5) - the system time has been changed during this
                             interval
          "
  ::= { nncAtmCongStatsCurrentShortIntvlEntry 4 }
 
  nncAtmCongStatsCurrentShortIntvlAbsoluteIntervalNumber OBJECT-TYPE
        SYNTAX        INTEGER (1..96)
        MAX-ACCESS    read-only
        STATUS        current
        DESCRIPTION 
          "The absolute interval number of the stats interval in the interval 
           statistics interface. If the interval is not defined yet, the absolute
           interval number will be -1.
 
           For the short, 15 minutes intervals the possible values are:
 
           absolute interval           interval
                index                start    end
           -----------------         ------------
                   1                 00:00  00:15
                   2                 00:15  00:30
                   3                 00:30  00:45
                  ...                 ...    ...
 
                  95                 23:30  23:45
                  96                 23:45  00:00
          "                 
  ::= { nncAtmCongStatsCurrentShortIntvlEntry 5 }
  
  nncAtmCongStatsCurrentShortIntvlTotalCellsArrived OBJECT-TYPE
        SYNTAX      NncExtCounter64
        MAX-ACCESS  read-only
        STATUS      current
        DESCRIPTION 
          "Total number of cells received."
  ::= { nncAtmCongStatsCurrentShortIntvlEntry 6 }
  
  nncAtmCongStatsCurrentShortIntvlTotalCellsDiscarded OBJECT-TYPE
        SYNTAX      NncExtCounter64
        MAX-ACCESS  read-only
        STATUS      current
        DESCRIPTION 
          "Total number of cells discarded due to congestion."
  ::= { nncAtmCongStatsCurrentShortIntvlEntry 7 }
  
  nncAtmCongStatsCurrentShortIntvlClp0CellsDiscarded OBJECT-TYPE
        SYNTAX      NncExtCounter64
        MAX-ACCESS  read-only
        STATUS      current
        DESCRIPTION 
          "Number of CLP 0 cells discarded due to congestion."
  ::= { nncAtmCongStatsCurrentShortIntvlEntry 8 }
  
  nncAtmCongStatsCurrentShortIntvlLowCongestedSeconds OBJECT-TYPE
        SYNTAX      Counter32
        MAX-ACCESS  read-only
        STATUS      current
        DESCRIPTION 
          "Number of seconds the congestion point was in the Low Congestion
           State."
  ::= { nncAtmCongStatsCurrentShortIntvlEntry 9 }
  
  nncAtmCongStatsCurrentShortIntvlMediumCongestedSeconds OBJECT-TYPE
        SYNTAX      Counter32
        MAX-ACCESS  read-only
        STATUS      current
        DESCRIPTION 
          "Number of seconds the congestion point was in the Medium Congestion 
           State."
  ::= { nncAtmCongStatsCurrentShortIntvlEntry 10 }
  
  nncAtmCongStatsCurrentShortIntvlSevereCongestedSeconds OBJECT-TYPE
        SYNTAX      Counter32
        MAX-ACCESS  read-only
        STATUS      current
        DESCRIPTION 
          "Number of seconds the congestion point was in the Severe Congestion 
           State."
  ::= { nncAtmCongStatsCurrentShortIntvlEntry 11 }
  
  nncAtmCongStatsCurrentShortIntvlTotalSeconds OBJECT-TYPE
        SYNTAX      Counter32
        MAX-ACCESS  read-only
        STATUS      current
        DESCRIPTION 
          "Total number of seconds the congestion point was in the Normal, Low, 
           Medium, or Severe congestion states."
  ::= { nncAtmCongStatsCurrentShortIntvlEntry 12 }
  
  nncAtmCongStatsCurrentShortIntvlCongestionState OBJECT-TYPE
        SYNTAX INTEGER {
                 congStatsNormalState(1),
                 congStatsLowCongState(2),
                 congStatsMediumCongState(3),
                 congStatsSevereCongState(4)
               }
        MAX-ACCESS  read-only
        STATUS      current
        DESCRIPTION 
          "Congestion state of the congestion point - one of Normal, 
           Low, Medium, or Severe.  When the current congestion state is 
           determined, the corresponding congestion time counter will 
           increment."
  ::= { nncAtmCongStatsCurrentShortIntvlEntry 13 }
  
  nncAtmCongStatsCurrentShortIntvlAlarmStatus OBJECT-TYPE
        SYNTAX INTEGER {
                 congStatsAlarmOn(1),
                 congStatsAlarmOff(2)
               }
        MAX-ACCESS  read-only
        STATUS      current
        DESCRIPTION 
          "Alarm status - either ON or OFF.  When a congestion point has 
           been severely congested for longer than the allowable threshold time 
           the value of this object is set to congStatsAlarmOn.  When severe 
           congestion clears, the value of this object is set to 
           congStatsAlarmOff."
  ::= { nncAtmCongStatsCurrentShortIntvlEntry 14 }
  
 
------------------------------------
-- nncAtmCongStatsShortIntvlTable --
------------------------------------
  
  nncAtmCongStatsShortIntvlTable OBJECT-TYPE 
        SYNTAX      SEQUENCE OF NncAtmCongStatsShortIntvlEntry 
        MAX-ACCESS  not-accessible
        STATUS      current
        DESCRIPTION 
          "The ATM Short Interval Congestion Statistics table.  
           This table maintains short interval statistics per quality of service 
           since the interface was started. There are 96 intervals, where the first
           interval (i.e., interval with index 1) is the most recently completed 
           interval and the length of each interval is 15 minutes."
  ::= { nncAtmCongStatsObjects 4 }
  
  nncAtmCongStatsShortIntvlEntry OBJECT-TYPE 
        SYNTAX      NncAtmCongStatsShortIntvlEntry 
        MAX-ACCESS  not-accessible
        STATUS      current
        DESCRIPTION 
          "An entry in the ATM Short Interval Congestion Statistics table."
        INDEX       { 
          entPhysicalEntityShortIntvlIndex, 
          nncAtmCongPointShortIntvlIndex, 
          nncAtmCongStatsQOSShortIntvlIndex, 
          nncAtmCongStatsShortIntvlIntervalIndex
        }
  ::= { nncAtmCongStatsShortIntvlTable 1 }
  
  NncAtmCongStatsShortIntvlEntry ::=
    SEQUENCE {
      entPhysicalEntityShortIntvlIndex                PhysicalIndex,
      nncAtmCongPointShortIntvlIndex                  INTEGER,
      nncAtmCongStatsQOSShortIntvlIndex               INTEGER,
      nncAtmCongStatsShortIntvlIntervalIndex          INTEGER,
      nncAtmCongStatsShortIntvlState                  NncExtIntvlStateType,
      nncAtmCongStatsShortIntvlAbsoluteIntervalNumber INTEGER,
      nncAtmCongStatsShortIntvlTotalCellsArrived      NncExtCounter64,
      nncAtmCongStatsShortIntvlTotalCellsDiscarded    NncExtCounter64,
      nncAtmCongStatsShortIntvlClp0CellsDiscarded     NncExtCounter64,
      nncAtmCongStatsShortIntvlLowCongestedSeconds    Counter32,
      nncAtmCongStatsShortIntvlMediumCongestedSeconds Counter32,
      nncAtmCongStatsShortIntvlSevereCongestedSeconds Counter32,
      nncAtmCongStatsShortIntvlTotalSeconds           Counter32,
      nncAtmCongStatsShortIntvlCongestionState        INTEGER,
      nncAtmCongStatsShortIntvlAlarmStatus            INTEGER
    }
    
  entPhysicalEntityShortIntvlIndex OBJECT-TYPE
    SYNTAX      PhysicalIndex
    MAX-ACCESS  not-accessible
    STATUS      current
    DESCRIPTION
        "A unique value that identifies the physical entity, whether it supports
         Congestion Statistics or not.  This value is equivalent to the value
         of PhysicalIndex."
  ::= { nncAtmCongStatsShortIntvlEntry 1 }
    
  nncAtmCongPointShortIntvlIndex OBJECT-TYPE
    SYNTAX      INTEGER (1..8)
    MAX-ACCESS  not-accessible
    STATUS      current
    DESCRIPTION
        "A unique value between 1 and 8 that identifies the congestion point on
         an entity which supports Congestion Statistics."
  ::= { nncAtmCongStatsShortIntvlEntry 2 }
    
  nncAtmCongStatsQOSShortIntvlIndex OBJECT-TYPE
        SYNTAX      INTEGER (1..11)
        MAX-ACCESS  not-accessible
        STATUS      current
        DESCRIPTION 
          "A number between 1 and 11 that identifies the quality of service on 
           which the set of statistics was collected for an entity.  The 
           following table describes the quality of service categories available
           and their corresponding index.
           
           Quality of Service   Quality of Service Index
           ------------------   ------------------------
                  CBR                      1
                  UBR                      2
                rt-VBR1                    3
                rt-VBR2                    4
               nrt-VBR1-2                  5
                nrt-VBR3                   6
                  ABR                      7
               CBR-rtVBR                   8
              nrt-VBR/UBR                  9
                ABR/UBR                   10
                nrt-VBR                   11
          "  
  ::= { nncAtmCongStatsShortIntvlEntry 3 }
 
   nncAtmCongStatsShortIntvlIntervalIndex OBJECT-TYPE
    SYNTAX      INTEGER(1..95)
    MAX-ACCESS  not-accessible
    STATUS      current
    DESCRIPTION
        "A unique value between 1 and 95 that identifies the interval index
         of the short interval statistics. Interval index 1 represents the most 
         recently completed interval of 15 minutes period and 
         interval index 2 represents the second most recently completed interval, 
         etc."
  ::= { nncAtmCongStatsShortIntvlEntry 4 }
  
  nncAtmCongStatsShortIntvlState OBJECT-TYPE
        SYNTAX      NncExtIntvlStateType
        MAX-ACCESS  read-only
        STATUS      current
        DESCRIPTION
          "The state of the interval in the interval statistics interface.
           Possible states are:
           normal      (1) - normal interval; no change in time and no resets
           nonexistent (2) - statistics do not exist for this interval
           userReset   (3) - the user has reset statistics collection
                             during this interval
           start       (4) - this is the first interval
           timeChange  (5) - the system time has been changed during this
                             interval
          "
  ::= { nncAtmCongStatsShortIntvlEntry 5 }
 
  nncAtmCongStatsShortIntvlAbsoluteIntervalNumber OBJECT-TYPE
        SYNTAX      INTEGER(1..96)
        MAX-ACCESS  read-only
        STATUS      current
        DESCRIPTION
          "The absolute interval number of the stats interval in the interval 
           statistics interface. If the interval is not defined yet, the absolute
           interval number will be -1.
 
           For the short, 15 minutes intervals the possible values are:
 
           absolute interval           interval
                index                start    end
           -----------------         ------------
                   1                 00:00  00:15
                   2                 00:15  00:30
                   3                 00:30  00:45
                  ...                 ...    ...
 
                  95                 23:30  23:45
                  96                 23:45  00:00
          "
  ::= { nncAtmCongStatsShortIntvlEntry 6 }
  
  nncAtmCongStatsShortIntvlTotalCellsArrived OBJECT-TYPE
        SYNTAX      NncExtCounter64
        MAX-ACCESS  read-only
        STATUS      current
        DESCRIPTION 
          "Total number of cells received."
  ::= { nncAtmCongStatsShortIntvlEntry 7 }
  
  nncAtmCongStatsShortIntvlTotalCellsDiscarded OBJECT-TYPE
        SYNTAX      NncExtCounter64
        MAX-ACCESS  read-only
        STATUS      current
        DESCRIPTION 
          "Total number of cells discarded due to congestion."
  ::= { nncAtmCongStatsShortIntvlEntry 8 }
  
  nncAtmCongStatsShortIntvlClp0CellsDiscarded OBJECT-TYPE
        SYNTAX      NncExtCounter64
        MAX-ACCESS  read-only
        STATUS      current
        DESCRIPTION 
          "Number of CLP 0 cells discarded due to congestion."
  ::= { nncAtmCongStatsShortIntvlEntry 9 }
  
  nncAtmCongStatsShortIntvlLowCongestedSeconds OBJECT-TYPE
        SYNTAX      Counter32
        MAX-ACCESS  read-only
        STATUS      current
        DESCRIPTION 
          "Number of seconds the congestion point was in the Low Congestion
           State."
  ::= { nncAtmCongStatsShortIntvlEntry 10 }
  
  nncAtmCongStatsShortIntvlMediumCongestedSeconds OBJECT-TYPE
        SYNTAX      Counter32
        MAX-ACCESS  read-only
        STATUS      current
        DESCRIPTION 
          "Number of seconds the congestion point was in the Medium Congestion 
           State."
  ::= { nncAtmCongStatsShortIntvlEntry 11 }
  
  nncAtmCongStatsShortIntvlSevereCongestedSeconds OBJECT-TYPE
        SYNTAX      Counter32
        MAX-ACCESS  read-only
        STATUS      current
        DESCRIPTION 
          "Number of seconds the congestion point was in the Severe Congestion 
           State."
  ::= { nncAtmCongStatsShortIntvlEntry 12 }
  
  nncAtmCongStatsShortIntvlTotalSeconds OBJECT-TYPE
        SYNTAX      Counter32
        MAX-ACCESS  read-only
        STATUS      current
        DESCRIPTION 
          "Total number of seconds the congestion point was in the Normal, Low, 
           Medium, or Severe congestion states."
  ::= { nncAtmCongStatsShortIntvlEntry 13 }
  
  nncAtmCongStatsShortIntvlCongestionState OBJECT-TYPE
        SYNTAX INTEGER {
                 congStatsNormalState(1),
                 congStatsLowCongState(2),
                 congStatsMediumCongState(3),
                 congStatsSevereCongState(4)
               }
        MAX-ACCESS  read-only
        STATUS      current
        DESCRIPTION 
          "Congestion state of the congestion point - one of Normal, 
           Low, Medium, or Severe.  When the current congestion state is 
           determined, the corresponding congestion time counter will 
           increment."
  ::= { nncAtmCongStatsShortIntvlEntry 14 }
  
  nncAtmCongStatsShortIntvlAlarmStatus OBJECT-TYPE
        SYNTAX INTEGER {
                 congStatsAlarmOn(1),
                 congStatsAlarmOff(2)
               }
        MAX-ACCESS  read-only
        STATUS      current
        DESCRIPTION 
          "Current alarm status - either ON or OFF.  When a congestion point has 
           been severely congested for longer than the allowable threshold time 
           the value of this object is set to congStatsAlarmOn.  When severe 
           congestion clears, the value of this object is set to 
           congStatsAlarmOff."
  ::= { nncAtmCongStatsShortIntvlEntry 15 }
  
 
------------------------------------------
-- nncAtmCongStatsCurrentLongIntvlTable --
------------------------------------------
  nncAtmCongStatsCurrentLongIntvlTable OBJECT-TYPE 
        SYNTAX      SEQUENCE OF NncAtmCongStatsCurrentLongIntvlEntry 
        MAX-ACCESS  not-accessible
        STATUS      current
        DESCRIPTION 
          "The ATM Current Long Interval Congestion Statistics table.  
           This table maintains current-long interval per quality of service statistics 
           since the interface was started. There are 7 intervals, where the first
           interval (i.e., interval with index 1) is the most recently completed 
           interval and the length of each interval is 1 day periode."
  ::= { nncAtmCongStatsObjects 5 }
  
  nncAtmCongStatsCurrentLongIntvlEntry OBJECT-TYPE 
        SYNTAX      NncAtmCongStatsCurrentLongIntvlEntry 
        MAX-ACCESS  not-accessible
        STATUS      current
        DESCRIPTION 
          "An entry in the ATM Current Long Interval Congestion Statistics table."
        INDEX       { 
          entPhysicalEntityCurrentLongIntvlIndex, 
          nncAtmCongPointCurrentLongIntvlIndex, 
          nncAtmCongStatsQOSCurrentLongIntvlIndex
        }
  ::= { nncAtmCongStatsCurrentLongIntvlTable 1 }
  
  NncAtmCongStatsCurrentLongIntvlEntry ::=
    SEQUENCE {
      entPhysicalEntityCurrentLongIntvlIndex                PhysicalIndex,
      nncAtmCongPointCurrentLongIntvlIndex                  INTEGER,
      nncAtmCongStatsQOSCurrentLongIntvlIndex               INTEGER,
      nncAtmCongStatsCurrentLongIntvlState                  NncExtIntvlStateType,
      nncAtmCongStatsCurrentLongIntvlAbsoluteIntervalNumber INTEGER,
      nncAtmCongStatsCurrentLongIntvlTotalCellsArrived      NncExtCounter64,
      nncAtmCongStatsCurrentLongIntvlTotalCellsDiscarded    NncExtCounter64,
      nncAtmCongStatsCurrentLongIntvlClp0CellsDiscarded     NncExtCounter64,
      nncAtmCongStatsCurrentLongIntvlLowCongestedSeconds    Counter32,
      nncAtmCongStatsCurrentLongIntvlMediumCongestedSeconds Counter32,
      nncAtmCongStatsCurrentLongIntvlSevereCongestedSeconds Counter32,
      nncAtmCongStatsCurrentLongIntvlTotalSeconds           Counter32,
      nncAtmCongStatsCurrentLongIntvlCongestionState        INTEGER,
      nncAtmCongStatsCurrentLongIntvlAlarmStatus            INTEGER
    }
    
  entPhysicalEntityCurrentLongIntvlIndex OBJECT-TYPE
    SYNTAX      PhysicalIndex
    MAX-ACCESS  not-accessible
    STATUS      current
    DESCRIPTION
        "A unique value that identifies the physical entity, whether it supports
         Congestion Statistics or not.  This value is equivalent to the value
         of PhysicalIndex."
  ::= { nncAtmCongStatsCurrentLongIntvlEntry 1 }
    
  nncAtmCongPointCurrentLongIntvlIndex OBJECT-TYPE
    SYNTAX      INTEGER (1..8)
    MAX-ACCESS  not-accessible
    STATUS      current
    DESCRIPTION
        "A unique value between 1 and 8 that identifies the congestion point on
         an entity which supports Congestion Statistics."
  ::= { nncAtmCongStatsCurrentLongIntvlEntry 2 }
    
  nncAtmCongStatsQOSCurrentLongIntvlIndex OBJECT-TYPE
        SYNTAX      INTEGER (1..11)
        MAX-ACCESS  not-accessible
        STATUS      current
        DESCRIPTION 
          "A number between 1 and 11 that identifies the quality of service on 
           which the set of statistics was collected for an entity.  The 
           following table describes the quality of service categories available
           and their corresponding index.
           
           Quality of Service   Quality of Service Index
           ------------------   ------------------------
                  CBR                      1
                  UBR                      2
                rt-VBR1                    3
                rt-VBR2                    4
               nrt-VBR1-2                  5
                nrt-VBR3                   6
                  ABR                      7
               CBR-rtVBR                   8
              nrt-VBR/UBR                  9
                ABR/UBR                   10
                nrt-VBR                   11
          "  
  ::= { nncAtmCongStatsCurrentLongIntvlEntry 3 }
  
  nncAtmCongStatsCurrentLongIntvlState OBJECT-TYPE
        SYNTAX      NncExtIntvlStateType
        MAX-ACCESS  read-only
        STATUS      current
        DESCRIPTION 
          "The state of the interval in the interval statistics interface.
           Possible states are:
           normal      (1) - normal interval; no change in time and no resets
           nonexistent (2) - statistics do not exist for this interval
           userReset   (3) - the user has reset statistics collection
                             during this interval
           start       (4) - this is the first interval
           timeChange  (5) - the system time has been changed during this
                             interval
          "
  ::= { nncAtmCongStatsCurrentLongIntvlEntry 4 }
 
  nncAtmCongStatsCurrentLongIntvlAbsoluteIntervalNumber OBJECT-TYPE
        SYNTAX      INTEGER(1..7)
        MAX-ACCESS  read-only
        STATUS      current
        DESCRIPTION 
          "The absolute interval number of the stats interval in 
           the interval statistics interface. If the interval is not defined yet, the absolute
           interval number will be -1.
           
           For the long, 1 day intervals the possible values are:
 
           absolute interval           interval  
                index                start    end
                                      day     day
           -----------------         ------------
                   1                   0       1 
                   2                   1       2 
                   3                   2       3
                   4                   3       4  
                   5                   4       5
                   6                   5       6
                   7                   6       7
          "
  ::= { nncAtmCongStatsCurrentLongIntvlEntry 5 }
 
  nncAtmCongStatsCurrentLongIntvlTotalCellsArrived OBJECT-TYPE
        SYNTAX      NncExtCounter64
        MAX-ACCESS  read-only
        STATUS      current
        DESCRIPTION 
          "Total number of cells received."
  ::= { nncAtmCongStatsCurrentLongIntvlEntry 6 }
  
  nncAtmCongStatsCurrentLongIntvlTotalCellsDiscarded OBJECT-TYPE
        SYNTAX      NncExtCounter64
        MAX-ACCESS  read-only
        STATUS      current
        DESCRIPTION 
          "Total number of cells discarded due to congestion."
  ::= { nncAtmCongStatsCurrentLongIntvlEntry 7 }
  
  nncAtmCongStatsCurrentLongIntvlClp0CellsDiscarded OBJECT-TYPE
        SYNTAX      NncExtCounter64
        MAX-ACCESS  read-only
        STATUS      current
        DESCRIPTION 
          "Number of CLP 0 cells discarded due to congestion."
  ::= { nncAtmCongStatsCurrentLongIntvlEntry 8 }
  
  nncAtmCongStatsCurrentLongIntvlLowCongestedSeconds OBJECT-TYPE
        SYNTAX      Counter32
        MAX-ACCESS  read-only
        STATUS      current
        DESCRIPTION 
          "Number of seconds the congestion point was in the Low Congestion
           State."
  ::= { nncAtmCongStatsCurrentLongIntvlEntry 9 }
  
  nncAtmCongStatsCurrentLongIntvlMediumCongestedSeconds OBJECT-TYPE
        SYNTAX      Counter32
        MAX-ACCESS  read-only
        STATUS      current
        DESCRIPTION 
          "Number of seconds the congestion point was in the Medium Congestion 
           State."
  ::= { nncAtmCongStatsCurrentLongIntvlEntry 10 }
  
  nncAtmCongStatsCurrentLongIntvlSevereCongestedSeconds OBJECT-TYPE
        SYNTAX      Counter32
        MAX-ACCESS  read-only
        STATUS      current
        DESCRIPTION 
          "Number of seconds the congestion point was in the Severe Congestion 
           State."
  ::= { nncAtmCongStatsCurrentLongIntvlEntry 11 }
  
  nncAtmCongStatsCurrentLongIntvlTotalSeconds OBJECT-TYPE
        SYNTAX      Counter32
        MAX-ACCESS  read-only
        STATUS      current
        DESCRIPTION 
          "Total number of seconds the congestion point was in the Normal, Low, 
           Medium, or Severe congestion states."
  ::= { nncAtmCongStatsCurrentLongIntvlEntry 12 }
  
  nncAtmCongStatsCurrentLongIntvlCongestionState OBJECT-TYPE
        SYNTAX INTEGER {
                 congStatsNormalState(1),
                 congStatsLowCongState(2),
                 congStatsMediumCongState(3),
                 congStatsSevereCongState(4)
               }
        MAX-ACCESS  read-only
        STATUS      current
        DESCRIPTION 
          "Congestion state of the congestion point - one of Normal, 
           Low, Medium, or Severe.  When the current congestion state is 
           determined, the corresponding congestion time counter will 
           increment."
  ::= { nncAtmCongStatsCurrentLongIntvlEntry 13 }
  
  nncAtmCongStatsCurrentLongIntvlAlarmStatus OBJECT-TYPE
        SYNTAX INTEGER {
                 congStatsAlarmOn(1),
                 congStatsAlarmOff(2)
               }
        MAX-ACCESS  read-only
        STATUS      current
        DESCRIPTION 
          "Current alarm status - either ON or OFF.  When a congestion point has 
           been severely congested for longer than the allowable threshold time 
           the value of this object is set to congStatsAlarmOn.  When severe 
           congestion clears, the value of this object is set to 
           congStatsAlarmOff."
  ::= { nncAtmCongStatsCurrentLongIntvlEntry 14 }
  
 
 
------------------------------------
-- nncAtmCongStatsLongIntvlTable --
------------------------------------
  
  nncAtmCongStatsLongIntvlTable OBJECT-TYPE 
        SYNTAX      SEQUENCE OF NncAtmCongStatsLongIntvlEntry 
        MAX-ACCESS  not-accessible
        STATUS      current
        DESCRIPTION 
          "The ATM Long Interval Congestion Statistics table.  
           This table maintains long interval per quality of service statistics 
           since the interface was started. There are 7 intervals, where the first
           interval (i.e., interval with index 1) is the most recently completed 
           interval and the length of each interval is 1 day periode."
  ::= { nncAtmCongStatsObjects 6 }
  
  nncAtmCongStatsLongIntvlEntry OBJECT-TYPE 
        SYNTAX      NncAtmCongStatsLongIntvlEntry 
        MAX-ACCESS  not-accessible
        STATUS      current
        DESCRIPTION 
          "An entry in the ATM Long Interval Congestion Statistics table."
        INDEX       { 
          entPhysicalEntityLongIntvlIndex, 
          nncAtmCongPointLongIntvlIndex, 
          nncAtmCongStatsQOSLongIntvlIndex,
          nncAtmCongStatsLongIntvlIntervalIndex
        }
  ::= { nncAtmCongStatsLongIntvlTable 1 }
  
  NncAtmCongStatsLongIntvlEntry ::=
    SEQUENCE {
      entPhysicalEntityLongIntvlIndex                PhysicalIndex,
      nncAtmCongPointLongIntvlIndex                  INTEGER,
      nncAtmCongStatsQOSLongIntvlIndex               INTEGER,
      nncAtmCongStatsLongIntvlIntervalIndex          INTEGER,
      nncAtmCongStatsLongIntvlState                  NncExtIntvlStateType,
      nncAtmCongStatsLongIntvlAbsoluteIntervalNumber INTEGER,
      nncAtmCongStatsLongIntvlTotalCellsArrived      NncExtCounter64,
      nncAtmCongStatsLongIntvlTotalCellsDiscarded    NncExtCounter64,
      nncAtmCongStatsLongIntvlClp0CellsDiscarded     NncExtCounter64,
      nncAtmCongStatsLongIntvlLowCongestedSeconds    Counter32,
      nncAtmCongStatsLongIntvlMediumCongestedSeconds Counter32,
      nncAtmCongStatsLongIntvlSevereCongestedSeconds Counter32,
      nncAtmCongStatsLongIntvlTotalSeconds           Counter32,
      nncAtmCongStatsLongIntvlCongestionState        INTEGER,
      nncAtmCongStatsLongIntvlAlarmStatus            INTEGER
    }
    
  entPhysicalEntityLongIntvlIndex OBJECT-TYPE
    SYNTAX      PhysicalIndex
    MAX-ACCESS  not-accessible
    STATUS      current
    DESCRIPTION
        "A unique value that identifies the physical entity, whether it supports
         Congestion Statistics or not.  This value is equivalent to the value
         of PhysicalIndex."
  ::= { nncAtmCongStatsLongIntvlEntry 1 }
    
  nncAtmCongPointLongIntvlIndex OBJECT-TYPE
    SYNTAX      INTEGER (1..8)
    MAX-ACCESS  not-accessible
    STATUS      current
    DESCRIPTION
        "A unique value between 1 and 8 that identifies the congestion point on
         an entity which supports Congestion Statistics."
  ::= { nncAtmCongStatsLongIntvlEntry 2 }
    
  nncAtmCongStatsQOSLongIntvlIndex OBJECT-TYPE
        SYNTAX      INTEGER (1..11)
        MAX-ACCESS  not-accessible
        STATUS      current
        DESCRIPTION 
          "A number between 1 and 11 that identifies the quality of service on 
           which the set of statistics was collected for an entity.  The 
           following table describes the quality of service categories available
           and their corresponding index.
           
           Quality of Service   Quality of Service Index
           ------------------   ------------------------
                  CBR                      1
                  UBR                      2
                rt-VBR1                    3
                rt-VBR2                    4
               nrt-VBR1-2                  5
                nrt-VBR3                   6
                  ABR                      7
               CBR-rtVBR                   8
              nrt-VBR/UBR                  9
                ABR/UBR                   10
                nrt-VBR                   11
          "  
  ::= { nncAtmCongStatsLongIntvlEntry 3 }
  
  nncAtmCongStatsLongIntvlIntervalIndex OBJECT-TYPE
    SYNTAX      INTEGER(1..6)
    MAX-ACCESS  not-accessible
    STATUS      current
    DESCRIPTION
        "A unique value between 1 and 6 that identifies the interval index
         of the long interval statistics. Interval index 1 represents the most 
         recently completed interval of 1 day period and interval index 2 
         represents the second most recently completed interval, etc.  "
  ::= { nncAtmCongStatsLongIntvlEntry 4 }
  
  nncAtmCongStatsLongIntvlState OBJECT-TYPE
        SYNTAX      NncExtIntvlStateType
        MAX-ACCESS  read-only
        STATUS      current
        DESCRIPTION 
          "The state of the interval in the interval statistics interface.
           Possible states are:
           normal      (1) - normal interval; no change in time and no resets
           nonexistent (2) - statistics do not exist for this interval
           userReset   (3) - the user has reset statistics collection
                             during this interval
           start       (4) - this is the first interval
           timeChange  (5) - the system time has been changed during this
                             interval"
  ::= { nncAtmCongStatsLongIntvlEntry 5 }
 
  nncAtmCongStatsLongIntvlAbsoluteIntervalNumber OBJECT-TYPE
        SYNTAX                  INTEGER(1..7)
        MAX-ACCESS              read-only
        STATUS                  current
        DESCRIPTION 
          "The absolute interval number of the stats interval in 
           the interval statistics interface. If the interval is not defined yet, the absolute
           interval number will be -1.
           
           For the long, 1 day intervals the possible values are:
 
           absolute interval           interval  
                index                start    end
                                      day     day
           -----------------         ------------
                   1                   0       1 
                   2                   1       2 
                   3                   2       3
                   4                   3       4  
                   5                   4       5
                   6                   5       6
                   7                   6       7
          "
  ::= { nncAtmCongStatsLongIntvlEntry 6 }
 
  nncAtmCongStatsLongIntvlTotalCellsArrived OBJECT-TYPE
        SYNTAX      NncExtCounter64
        MAX-ACCESS  read-only
        STATUS      current
        DESCRIPTION 
          "Total number of cells received."
  ::= { nncAtmCongStatsLongIntvlEntry 7 }
  
  nncAtmCongStatsLongIntvlTotalCellsDiscarded OBJECT-TYPE
        SYNTAX      NncExtCounter64
        MAX-ACCESS  read-only
        STATUS      current
        DESCRIPTION 
          "Total number of cells discarded due to congestion."
  ::= { nncAtmCongStatsLongIntvlEntry 8 }
  
  nncAtmCongStatsLongIntvlClp0CellsDiscarded OBJECT-TYPE
        SYNTAX      NncExtCounter64
        MAX-ACCESS  read-only
        STATUS      current
        DESCRIPTION 
          "Number of CLP 0 cells discarded due to congestion."
  ::= { nncAtmCongStatsLongIntvlEntry 9 }
  
  nncAtmCongStatsLongIntvlLowCongestedSeconds OBJECT-TYPE
        SYNTAX      Counter32
        MAX-ACCESS  read-only
        STATUS      current
        DESCRIPTION 
          "Number of seconds the congestion point was in the Low Congestion
           State."
  ::= { nncAtmCongStatsLongIntvlEntry 10 }
  
  nncAtmCongStatsLongIntvlMediumCongestedSeconds OBJECT-TYPE
        SYNTAX      Counter32
        MAX-ACCESS  read-only
        STATUS      current
        DESCRIPTION 
          "Number of seconds the congestion point was in the Medium Congestion 
           State."
  ::= { nncAtmCongStatsLongIntvlEntry 11 }
  
  nncAtmCongStatsLongIntvlSevereCongestedSeconds OBJECT-TYPE
        SYNTAX      Counter32
        MAX-ACCESS  read-only
        STATUS      current
        DESCRIPTION 
          "Number of seconds the congestion point was in the Severe Congestion 
           State."
  ::= { nncAtmCongStatsLongIntvlEntry 12 }
  
  nncAtmCongStatsLongIntvlTotalSeconds OBJECT-TYPE
        SYNTAX      Counter32
        MAX-ACCESS  read-only
        STATUS      current
        DESCRIPTION 
          "Total number of seconds the congestion point was in the Normal, Low, 
           Medium, or Severe congestion states."
  ::= { nncAtmCongStatsLongIntvlEntry 13 }
  
  nncAtmCongStatsLongIntvlCongestionState OBJECT-TYPE
        SYNTAX INTEGER {
                 congStatsNormalState(1),
                 congStatsLowCongState(2),
                 congStatsMediumCongState(3),
                 congStatsSevereCongState(4)
               }
        MAX-ACCESS  read-only
        STATUS      current
        DESCRIPTION 
          "Congestion state of the congestion point - one of Normal, 
           Low, Medium, or Severe.  When the current congestion state is 
           determined, the corresponding congestion time counter will 
           increment."
  ::= { nncAtmCongStatsLongIntvlEntry 14 }
  
  nncAtmCongStatsLongIntvlAlarmStatus OBJECT-TYPE
        SYNTAX INTEGER {
                 congStatsAlarmOn(1),
                 congStatsAlarmOff(2)
               }
        MAX-ACCESS  read-only
        STATUS      current
        DESCRIPTION 
          "Current alarm status - either ON or OFF.  When a congestion point has 
           been severely congested for longer than the allowable threshold time 
           the value of this object is set to congStatsAlarmOn.  When severe 
           congestion clears, the value of this object is set to 
           congStatsAlarmOff."
  ::= { nncAtmCongStatsLongIntvlEntry 15 }
  
 
-------------------------------------------------------------------------------
-- End of Intervalized Congestion Statistics
-------------------------------------------------------------------------------
 
--------------------------------------------------------------------------------
-- Trap Definitions
--------------------------------------------------------------------------------

--------------------------------------------------------------------------------
-- Conformance Group Definitions
--------------------------------------------------------------------------------
  nncAtmCongPointInfoGroup OBJECT-GROUP 
    OBJECTS {
      entPhysicalEntityInfoIndex,
      nncAtmCongPointInfoIndex,
      nncAtmCongPointHardwareType
    }
    STATUS      current
    DESCRIPTION 
      "An object providing various information for a congestion point."
  ::= { nncAtmCongStatsGroups 1 }
  
  nncAtmCongStatsRawGroup OBJECT-GROUP 
    OBJECTS {
      entPhysicalEntityRawIndex,
      nncAtmCongPointRawIndex,
      nncAtmCongStatsQOSRawIndex,
      nncAtmCongStatsTotalCellsArrived,
      nncAtmCongStatsTotalCellsDiscarded,
      nncAtmCongStatsClp0CellsDiscarded,
      nncAtmCongStatsLowCongestedSeconds,
      nncAtmCongStatsMediumCongestedSeconds,
      nncAtmCongStatsSevereCongestedSeconds,
      nncAtmCongStatsTotalSeconds,
      nncAtmCongStatsCurrentCongestionState,
      nncAtmCongStatsAlarmStatus,
      nncAtmCongStatsVirtualBandwidthAvail
    }
    STATUS      current
    DESCRIPTION 
      "A collection of objects providing raw congestion statistics per quality
       of service."
  ::= { nncAtmCongStatsGroups 2 }

  nncAtmCongStatsCurrentShortIntvlGroup OBJECT-GROUP 
    OBJECTS {
      entPhysicalEntityCurrentShortIntvlIndex,
      nncAtmCongPointCurrentShortIntvlIndex,
      nncAtmCongStatsQOSCurrentShortIntvlIndex,
      nncAtmCongStatsCurrentShortIntvlState,
      nncAtmCongStatsCurrentShortIntvlAbsoluteIntervalNumber,
      nncAtmCongStatsCurrentShortIntvlTotalCellsArrived,
      nncAtmCongStatsCurrentShortIntvlTotalCellsDiscarded,
      nncAtmCongStatsCurrentShortIntvlClp0CellsDiscarded,
      nncAtmCongStatsCurrentShortIntvlLowCongestedSeconds,
      nncAtmCongStatsCurrentShortIntvlMediumCongestedSeconds,
      nncAtmCongStatsCurrentShortIntvlSevereCongestedSeconds,
      nncAtmCongStatsCurrentShortIntvlTotalSeconds,
      nncAtmCongStatsCurrentShortIntvlCongestionState,
      nncAtmCongStatsCurrentShortIntvlAlarmStatus
    }
    STATUS      current
    DESCRIPTION 
      "A collection of objects providing current-short interval congestion statistics 
       per quality of service."
  ::= { nncAtmCongStatsGroups 3 }
  
  nncAtmCongStatsShortIntvlGroup OBJECT-GROUP 
    OBJECTS {
      entPhysicalEntityShortIntvlIndex,
      nncAtmCongPointShortIntvlIndex,
      nncAtmCongStatsQOSShortIntvlIndex,
      nncAtmCongStatsShortIntvlIntervalIndex,
      nncAtmCongStatsShortIntvlState,
      nncAtmCongStatsShortIntvlAbsoluteIntervalNumber,
      nncAtmCongStatsShortIntvlTotalCellsArrived,
      nncAtmCongStatsShortIntvlTotalCellsDiscarded,
      nncAtmCongStatsShortIntvlClp0CellsDiscarded,
      nncAtmCongStatsShortIntvlLowCongestedSeconds,
      nncAtmCongStatsShortIntvlMediumCongestedSeconds,
      nncAtmCongStatsShortIntvlSevereCongestedSeconds,
      nncAtmCongStatsShortIntvlTotalSeconds,
      nncAtmCongStatsShortIntvlCongestionState,
      nncAtmCongStatsShortIntvlAlarmStatus
    }
    STATUS      current
    DESCRIPTION 
      "A collection of objects providing short interval congestion statistics 
       per quality of service."
  ::= { nncAtmCongStatsGroups 4 }
 
 
  nncAtmCongStatsCurrentLongIntvlGroup OBJECT-GROUP 
    OBJECTS {
      entPhysicalEntityCurrentLongIntvlIndex,
      nncAtmCongPointCurrentLongIntvlIndex,
      nncAtmCongStatsQOSCurrentLongIntvlIndex,
      nncAtmCongStatsCurrentLongIntvlState,
      nncAtmCongStatsCurrentLongIntvlAbsoluteIntervalNumber,
      nncAtmCongStatsCurrentLongIntvlTotalCellsArrived,
      nncAtmCongStatsCurrentLongIntvlTotalCellsDiscarded,
      nncAtmCongStatsCurrentLongIntvlClp0CellsDiscarded,
      nncAtmCongStatsCurrentLongIntvlLowCongestedSeconds,
      nncAtmCongStatsCurrentLongIntvlMediumCongestedSeconds,
      nncAtmCongStatsCurrentLongIntvlSevereCongestedSeconds,
      nncAtmCongStatsCurrentLongIntvlTotalSeconds,
      nncAtmCongStatsCurrentLongIntvlCongestionState,
      nncAtmCongStatsCurrentLongIntvlAlarmStatus
    }
    STATUS      current
    DESCRIPTION 
      "A collection of objects providing current-long interval congestion statistics 
       per quality of service."
  ::= { nncAtmCongStatsGroups 5 }
  
  nncAtmCongStatsLongIntvlGroup OBJECT-GROUP 
    OBJECTS {
      entPhysicalEntityLongIntvlIndex,
      nncAtmCongPointLongIntvlIndex,
      nncAtmCongStatsQOSLongIntvlIndex,
      nncAtmCongStatsLongIntvlIntervalIndex,
      nncAtmCongStatsLongIntvlState,
      nncAtmCongStatsLongIntvlAbsoluteIntervalNumber,
      nncAtmCongStatsLongIntvlTotalCellsArrived,
      nncAtmCongStatsLongIntvlTotalCellsDiscarded,
      nncAtmCongStatsLongIntvlClp0CellsDiscarded,
      nncAtmCongStatsLongIntvlLowCongestedSeconds,
      nncAtmCongStatsLongIntvlMediumCongestedSeconds,
      nncAtmCongStatsLongIntvlSevereCongestedSeconds,
      nncAtmCongStatsLongIntvlTotalSeconds,
      nncAtmCongStatsLongIntvlCongestionState,
      nncAtmCongStatsLongIntvlAlarmStatus
    }
    STATUS      current
    DESCRIPTION 
      "A collection of objects providing long interval congestion statistics 
       per quality of service."
  ::= { nncAtmCongStatsGroups 6 }
  
--------------------------------------------------------------------------------
-- Compliance Statements (mandatory)
--------------------------------------------------------------------------------
  nncAtmCongStatsCompliance MODULE-COMPLIANCE
    STATUS      current
    DESCRIPTION 
      "The compliance statement for Newbridge SNMP entities which have ATM 
       congestion fabric statistics management."
    MODULE
      MANDATORY-GROUPS {
        nncAtmCongPointInfoGroup,
        nncAtmCongStatsRawGroup,
        nncAtmCongStatsCurrentShortIntvlGroup,
        nncAtmCongStatsShortIntvlGroup,
        nncAtmCongStatsCurrentLongIntvlGroup,
        nncAtmCongStatsLongIntvlGroup
      }
  ::= { nncAtmCongStatsCompliances 1 } 


-------------------------------------------------------------------------------
-- Review Minutes 
-------------------------------------------------------------------------------
--      MINUTES-BEGIN
--              REVIEW-DATE  "1998.06.10"
--              BODY  "
-- 
--      TO:     Chris Gibson*, Fernando Bello*, Franck Mainardis*, Frank Chen, 
--              Janice Wei*, Karl Toompuu, Keith Galway*, Randy Jones*, 
--              Raymond Allard*, Wendy Shuster*
--      CC:     Jim Ko, Suzanne Poulos
--      FROM:   Margaret Unger*
--
--      A meeting was held on June 6, 1998, to review 
--      ATMCongestionStatistics.mib.
--      Attendees are marked with * in the TO and CC lists above.
--
--      Outcome
--
--      It was the consensus of the review team that this file is acceptable 
--      with the indicated modifications.
--
--      Actions:
--      A1 -    Margaret Unger to update the file as indicated in D1 below.  
--              Response:  Status: CLOSED
--
--      Decisions:
--      D1 -    ATMCongestionStatistics.mib shall be updated as follows:
--      a)  Physical Entity index instead of IF index must be used to index 
--          objects,
--      b)  Additional Hardware Type table is necessary for interpretation of 
--          data based on card type and version, queue and QOS configuration 
--          on the card, fabric type, switch profile, and congestion point,
--      c)  Congestion Point and Congestion Point Index to be added to Table 1.
--    "
--
--      END-MINUTES
--
--
END -- DEFINITION OF NNC-ATM-CONGESTIONSTATISTICS-MIB
