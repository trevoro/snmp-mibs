MEDIAHAWK-MIB DEFINITIONS ::= BEGIN
IMPORTS enterprises, NetworkAddress, IpAddress, Counter, Gauge, TimeTicks
		FROM RFC1155-SMI
	OBJECT-TYPE FROM RFC-1212
	DisplayString, PhysAddress FROM RFC1213-MIB
	DateAndTime FROM SNMPv2-TC
	TRAP-TYPE FROM RFC-1215;
--
--	N.B. The mhvsVPStreamChangedStatus trap uses spsStreamInstState which
--	is defined in the Davic Server MIB.
--	If this MIB is available, uncomment the VARIABLES clause in
--	mhvsVPStreamChangedStatus and add the following IMPORTS clause:
-- 	spsStreamInstState FROM DAVIC-SERVER-MIB;
--
concurrentComputerCorporation	OBJECT IDENTIFIER ::= { enterprises 1457 }
mediaHawkVideoServer		OBJECT IDENTIFIER ::= { concurrentComputerCorporation 1 }
mediaHawkVSVP			OBJECT IDENTIFIER ::= { mediaHawkVideoServer 2 }
mhvsVPVideo			OBJECT IDENTIFIER ::= { mediaHawkVSVP 1 }
mhvsVPResources			OBJECT IDENTIFIER ::= { mediaHawkVSVP 2 }
mhvsVPStreams			OBJECT IDENTIFIER ::= { mediaHawkVSVP 3 }
mhvsVPMenu			OBJECT IDENTIFIER ::= { mediaHawkVSVP 4 }
mediaHawkVEMon			OBJECT IDENTIFIER ::= { mediaHawkVideoServer 3 }
mediaHawkDisk			OBJECT IDENTIFIER ::= { mediaHawkVEMon 3 }
mediaHawkEnvironment		OBJECT IDENTIFIER ::= { mediaHawkVEMon 4 }
mediaHawkVPMon			OBJECT IDENTIFIER ::= { mediaHawkVideoServer 4 }
--
-- GROUP mediaHawkVSVP
-- GROUP mhvsVPVideo
--
--  This group represents the Videos on the Video Server.
--  The mhvsVPVideoTable lists all the videos.
--  The mhvsVPVideoInstTable lists each instance of the videos.
-- 
mhvsVPVideoTable	OBJECT-TYPE
	SYNTAX	SEQUENCE OF MhvsVPVideoEntry
	ACCESS	not-accessible
	STATUS	mandatory
	DESCRIPTION
	" Table listing the Videos on the Video Server."
	::= { mhvsVPVideo 2 }
mhvsVPVideoEntry	OBJECT-TYPE
	SYNTAX	MhvsVPVideoEntry
	ACCESS	not-accessible
	STATUS	mandatory
	DESCRIPTION
	" Entry for table mhvsVPVideoTable"
	INDEX { mhvsVPVideoIndex		}
	::= { mhvsVPVideoTable 1 }
MhvsVPVideoEntry ::= SEQUENCE
	{
	mhvsVPVideoIndex	INTEGER,
	mhvsVPVideoName		DisplayString,
	mhvsVPVideoNumCopies	Gauge,
	mhvsVPVideoSize		INTEGER,
	mhvsVPVideoNumOpen	Gauge,
	mhvsVPVideoStatus	INTEGER,
	mhvsVPVideoContentSpace	INTEGER,
	mhvsVPVideoIndexSpace	INTEGER
	}
mhvsVPVideoIndex 	 OBJECT-TYPE
	SYNTAX 	 INTEGER (1..65536)
	ACCESS 	 read-only
	STATUS 	 mandatory
	DESCRIPTION
	" Unique identifier of this video"
	::= { mhvsVPVideoEntry 1 }
mhvsVPVideoName 	 OBJECT-TYPE
	SYNTAX 	 DisplayString
	ACCESS 	 read-only
	STATUS 	 mandatory
	DESCRIPTION
	" Name of this video"
	::= { mhvsVPVideoEntry 2 }
mhvsVPVideoNumCopies 	 OBJECT-TYPE
	SYNTAX 	 Gauge
	ACCESS 	 read-only
	STATUS 	 mandatory
	DESCRIPTION
	" Number of copies"
	::= { mhvsVPVideoEntry 3 }
mhvsVPVideoSize 	 OBJECT-TYPE
	SYNTAX 	 INTEGER
	ACCESS 	 read-only
	STATUS 	 mandatory
	DESCRIPTION
	" Size in KBytes of the video"
	::= { mhvsVPVideoEntry 4 }
mhvsVPVideoNumOpen 	 OBJECT-TYPE
	SYNTAX 	 Gauge
	ACCESS 	 read-only
	STATUS 	 mandatory
	DESCRIPTION
	" Current number of streams using this video"
	::= { mhvsVPVideoEntry 5 }
mhvsVPVideoStatus 	 OBJECT-TYPE
	SYNTAX 	 INTEGER
		{
		deleted		(1),
		disabled	(2),
		quiesce		(3),
		failed		(4),
		standby		(5),
		enabled		(6)
		}
	ACCESS 	 read-write
	STATUS 	 mandatory
	DESCRIPTION
	" Status of the video"
	::= { mhvsVPVideoEntry 6 }
mhvsVPVideoContentSpace	 OBJECT-TYPE
	SYNTAX 	 INTEGER
	ACCESS 	 read-only
	STATUS 	 mandatory
	DESCRIPTION
	" Space in KBytes of the content files belonging to the video"
	::= { mhvsVPVideoEntry 7 }
mhvsVPVideoIndexSpace	 OBJECT-TYPE
	SYNTAX 	 INTEGER
	ACCESS 	 read-only
	STATUS 	 mandatory
	DESCRIPTION
	" Space in KBytes of the index files belonging to the video"
	::= { mhvsVPVideoEntry 8 }

mhvsVPVideoInstTable	OBJECT-TYPE
	SYNTAX	SEQUENCE OF MhvsVPVideoInstEntry
	ACCESS	not-accessible
	STATUS	mandatory
	DESCRIPTION
	" Table listing each instance of the Videos on the Video Server"
	::= { mhvsVPVideo 3 }
mhvsVPVideoInstEntry	OBJECT-TYPE
	SYNTAX	MhvsVPVideoInstEntry
	ACCESS	not-accessible
	STATUS	mandatory
	DESCRIPTION
	" Entry for table mhvsVPVideoInstTable"
	INDEX { mhvsVPVideoInstVideoIndex,
		mhvsVPVideoInstIndex		}
	::= { mhvsVPVideoInstTable 1 }
MhvsVPVideoInstEntry ::= SEQUENCE
	{
	mhvsVPVideoInstVideoIndex	INTEGER,
	mhvsVPVideoInstDiskIndex	INTEGER,
	mhvsVPVideoInstNumOpen		Gauge,
	mhvsVPVideoInstStatus		INTEGER,
	mhvsVPVideoInstPath		DisplayString,
	mhvsVPVideoInstIndex		INTEGER,
	mhvsVPVideoInstSize		INTEGER
	}
mhvsVPVideoInstVideoIndex 	 OBJECT-TYPE
	SYNTAX 	 INTEGER (1..65536)
	ACCESS 	 read-only
	STATUS 	 mandatory
	DESCRIPTION
	" Unique identifier of this video. Set to mhvsVPVideoIndex."
	::= { mhvsVPVideoInstEntry 1 }
mhvsVPVideoInstDiskIndex 	 OBJECT-TYPE
	SYNTAX 	 INTEGER
	ACCESS 	 read-only
	STATUS 	 mandatory
	DESCRIPTION
	" The disk holding this instance. Set to mhvsVPResourcesDiskIndex."
	::= { mhvsVPVideoInstEntry 3 }
mhvsVPVideoInstNumOpen 	 OBJECT-TYPE
	SYNTAX 	 Gauge
	ACCESS 	 read-only
	STATUS 	 mandatory
	DESCRIPTION
	" Current number of streams using this video instance"
	::= { mhvsVPVideoInstEntry 4 }
mhvsVPVideoInstStatus 	 OBJECT-TYPE
	SYNTAX 	 INTEGER
		{
		deleted		(1),
		disabled	(2),
		quiesce		(3),
		failed		(4),
		standby		(5),
		enabled		(6)
		}
	ACCESS 	 read-write
	STATUS 	 mandatory
	DESCRIPTION
	" The status of this video instance"
	::= { mhvsVPVideoInstEntry 5 }
mhvsVPVideoInstPath 	 OBJECT-TYPE
	SYNTAX 	 DisplayString
	ACCESS 	 read-only
	STATUS 	 mandatory
	DESCRIPTION
	" Path to the video from the disk"
	::= { mhvsVPVideoInstEntry 6 }
mhvsVPVideoInstIndex 	 OBJECT-TYPE
	SYNTAX 	 INTEGER (1..65536)
	ACCESS 	 read-only
	STATUS 	 mandatory
	DESCRIPTION
	" The index for this video instance"
	::= { mhvsVPVideoInstEntry 7 }
mhvsVPVideoInstSize 	 OBJECT-TYPE
	SYNTAX 	 INTEGER
	ACCESS 	 read-only
	STATUS 	 mandatory
	DESCRIPTION
	" Size in KBytes of the video instance"
	::= { mhvsVPVideoInstEntry 8 }

mhvsVPVideoTrapGeneration 	 OBJECT-TYPE
	SYNTAX 	 INTEGER
		{
-- invalid	off	(0),
		on	(1)
		}
	ACCESS 	 read-write
	STATUS 	 mandatory
	DESCRIPTION
	" Controls when the mhvsVPVideoChangedStatus and
	mhvsVPVideoInstChangedStatus traps are generated.
	 off => no traps are generated,
	 on => video or video instance changes state"
	::= { mhvsVPVideo 4 }
mhvsVPVideoChangedStatus	
	TRAP-TYPE
	ENTERPRISE concurrentComputerCorporation
	VARIABLES
	    {
	    mhvsVPVideoStatus
	    }
	DESCRIPTION
	" Trap is issued when a video changes state
	 depending on the setting of mhvsVPVideoTrapGeneration.
	 The trap identifies the video and includes its new state"
	::= 57
mhvsVPVideoInstChangedStatus	
	TRAP-TYPE
	ENTERPRISE concurrentComputerCorporation
	VARIABLES
	    {
	    mhvsVPVideoInstStatus
	    }
	DESCRIPTION
	" Trap is issued when a video instance changes state
	 depending on the setting of mhvsVPVideoTrapGeneration.
	 The trap identifies the video instance and includes
	 its new state"
	::= 58
-- 
-- GROUP mhvsVPResources
--
--  This group represents the Resources available to the Video Server.
--
mhvsVPResourcesMaxStreams 	 OBJECT-TYPE
	SYNTAX 	 Gauge
	ACCESS 	 read-only
	STATUS 	 mandatory
	DESCRIPTION
	" The maximum number of streams supported by the Video Server "
	::= { mhvsVPResources 1 }
mhvsVPResourcesNumStreams 	 OBJECT-TYPE
	SYNTAX 	 Gauge
	ACCESS 	 read-only
	STATUS 	 mandatory
	DESCRIPTION
	" The number of streams running on the Video Server "
	::= { mhvsVPResources 2 }
mhvsVPResourcesMaxBandwidth 	 OBJECT-TYPE
	SYNTAX 	 Gauge
	ACCESS 	 read-only
	STATUS 	 mandatory
	DESCRIPTION
	" The maximum bandwidth in kbps supported by the Video Server "
	::= { mhvsVPResources 3 }
mhvsVPResourcesBandwidth 	 OBJECT-TYPE
	SYNTAX 	 Gauge
	ACCESS 	 read-only
	STATUS 	 mandatory
	DESCRIPTION
	" The currently allocated bandwidth in kbps on the Video Server "
	::= { mhvsVPResources 4 }

mhvsVPResourcesVPTable	OBJECT-TYPE
	SYNTAX	SEQUENCE OF MhvsVPResourcesVPEntry
	ACCESS	not-accessible
	STATUS	mandatory
	DESCRIPTION
	" Table listing the Video Pumps on the Video Server."
	::= { mhvsVPResources 5 }
mhvsVPResourcesVPEntry	OBJECT-TYPE
	SYNTAX	MhvsVPResourcesVPEntry
	ACCESS	not-accessible
	STATUS	mandatory
	DESCRIPTION
	" Entry for table mhvsVPResourcesVPTable"
	INDEX { mhvsVPResourcesVPIndex		}
	::= { mhvsVPResourcesVPTable 1 }
MhvsVPResourcesVPEntry ::= SEQUENCE
	{
	mhvsVPResourcesVPIndex		INTEGER,
	mhvsVPResourcesVPMax		Gauge,
	mhvsVPResourcesVPUsed		Gauge,
	mhvsVPResourcesVPNumStreams	Gauge,
	mhvsVPResourcesVPStatus		INTEGER,
	mhvsVPResourcesVPConnected	INTEGER,
	mhvsVPResourcesVPHostIndex	INTEGER
	}
mhvsVPResourcesVPIndex 	 OBJECT-TYPE
	SYNTAX 	 INTEGER (1..65536)
	ACCESS 	 read-only
	STATUS 	 mandatory
	DESCRIPTION
	" A unique number within the Video Server for the Video Pump"
	::= { mhvsVPResourcesVPEntry 1 }
mhvsVPResourcesVPMax 	 OBJECT-TYPE
	SYNTAX 	 Gauge
	ACCESS 	 read-only
	STATUS 	 mandatory
	DESCRIPTION
	" The maximum resources for this Video Pump"
	::= { mhvsVPResourcesVPEntry 2 }
mhvsVPResourcesVPUsed 	 OBJECT-TYPE
	SYNTAX 	 Gauge
	ACCESS 	 read-only
	STATUS 	 mandatory
	DESCRIPTION
	" The used resources for this Video Pump"
	::= { mhvsVPResourcesVPEntry 3 }
mhvsVPResourcesVPNumStreams 	 OBJECT-TYPE
	SYNTAX 	 Gauge
	ACCESS 	 read-only
	STATUS 	 mandatory
	DESCRIPTION
	" The number of streams using this Video Pump"
	::= { mhvsVPResourcesVPEntry 4 }
mhvsVPResourcesVPStatus 	OBJECT-TYPE
	SYNTAX 	 INTEGER
		{
		deleted		(1),
		disabled	(2),
		quiesce		(3),
		failed		(4),
		standby		(5),
		enabled		(6)
		}
	ACCESS 	 read-write
	STATUS 	 mandatory
	DESCRIPTION
	" The status of this Video Pump"
	::= { mhvsVPResourcesVPEntry 5 }
mhvsVPResourcesVPConnected 	 OBJECT-TYPE
	SYNTAX 	 INTEGER
		{
-- invalid	no	(0),
		yes	(1)
		}
	ACCESS 	 read-only
	STATUS 	 mandatory
	DESCRIPTION
	" Indicates whether this Video Pump is connected to the Video Server"
	::= { mhvsVPResourcesVPEntry 6 }
mhvsVPResourcesVPHostIndex 	 OBJECT-TYPE
	SYNTAX 	 INTEGER
	ACCESS 	 read-only
	STATUS 	 mandatory
	DESCRIPTION
	" Set to spsHostsindex in spsHostsTable"
	::= { mhvsVPResourcesVPEntry 7 }

mhvsVPResourcesDiskTable	OBJECT-TYPE
	SYNTAX	SEQUENCE OF MhvsVPResourcesDiskEntry
	ACCESS	not-accessible
	STATUS	mandatory
	DESCRIPTION
	" Table listing the Disk Resources on the Video Server."
	::= { mhvsVPResources 6 }
mhvsVPResourcesDiskEntry	OBJECT-TYPE
	SYNTAX	MhvsVPResourcesDiskEntry
	ACCESS	not-accessible
	STATUS	mandatory
	DESCRIPTION
	" Entry for table mhvsVPResourcesDiskTable"
	INDEX { mhvsVPResourcesDiskIndex		}
	::= { mhvsVPResourcesDiskTable 1 }
MhvsVPResourcesDiskEntry ::= SEQUENCE
	{
	mhvsVPResourcesDiskIndex	INTEGER,
	mhvsVPResourcesDiskName		DisplayString,
	mhvsVPResourcesDiskMax		Gauge,
	mhvsVPResourcesDiskUsed		Gauge,
	mhvsVPResourcesDiskNumStreams	Gauge,
	mhvsVPResourcesDiskStatus	INTEGER,
	mhvsVPResourcesDiskMaxCapacity		INTEGER,
	mhvsVPResourcesDiskUsedCapacity		INTEGER,
	mhvsVPResourcesDiskMaxSysCapacity	INTEGER,
	mhvsVPResourcesDiskUsedSysCapacity	INTEGER
	}
mhvsVPResourcesDiskIndex 	 OBJECT-TYPE
	SYNTAX 	 INTEGER (1..65536)
	ACCESS 	 read-only
	STATUS 	 mandatory
	DESCRIPTION
	" A unique number within the Video Server for the disk"
	::= { mhvsVPResourcesDiskEntry 1 }
mhvsVPResourcesDiskName 	 OBJECT-TYPE
	SYNTAX 	 DisplayString
	ACCESS 	 read-only
	STATUS 	 mandatory
	DESCRIPTION
	" The name of the disk"
	::= { mhvsVPResourcesDiskEntry 2 }
mhvsVPResourcesDiskMax 	 OBJECT-TYPE
	SYNTAX 	 Gauge
	ACCESS 	 read-write
	STATUS 	 mandatory
	DESCRIPTION
	" The maximum resources for this disk"
	::= { mhvsVPResourcesDiskEntry 3 }
mhvsVPResourcesDiskUsed 	 OBJECT-TYPE
	SYNTAX 	 Gauge
	ACCESS 	 read-only
	STATUS 	 mandatory
	DESCRIPTION
	" The used resources for this disk"
	::= { mhvsVPResourcesDiskEntry 4 }
mhvsVPResourcesDiskNumStreams 	 OBJECT-TYPE
	SYNTAX 	 Gauge
	ACCESS 	 read-only
	STATUS 	 mandatory
	DESCRIPTION
	" The number of streams using this disk"
	::= { mhvsVPResourcesDiskEntry 5 }
mhvsVPResourcesDiskStatus 	OBJECT-TYPE
	SYNTAX 	 INTEGER
		{
		deleted		(1),
		disabled	(2),
		quiesce		(3),
		failed		(4),
		standby		(5),
		enabled		(6)
		}
	ACCESS 	 read-write
	STATUS 	 mandatory
	DESCRIPTION
	" The status of this disk"
	::= { mhvsVPResourcesDiskEntry 6 }
mhvsVPResourcesDiskMaxCapacity	 OBJECT-TYPE
	SYNTAX 	 INTEGER
	ACCESS 	 read-only
	STATUS 	 mandatory
	DESCRIPTION
	" The maximum capacity in KBytes of the content partition of this disk"
	::= { mhvsVPResourcesDiskEntry 7 }
mhvsVPResourcesDiskUsedCapacity	 OBJECT-TYPE
	SYNTAX 	 INTEGER
	ACCESS 	 read-only
	STATUS 	 mandatory
	DESCRIPTION
	" The used capacity in KBytes of the content partition of this disk"
	::= { mhvsVPResourcesDiskEntry 8 }
mhvsVPResourcesDiskMaxSysCapacity	 OBJECT-TYPE
	SYNTAX 	 INTEGER
	ACCESS 	 read-only
	STATUS 	 mandatory
	DESCRIPTION
	" The maximum capacity in KBytes of the /sys partition of this disk"
	::= { mhvsVPResourcesDiskEntry 9 }
mhvsVPResourcesDiskUsedSysCapacity	 OBJECT-TYPE
	SYNTAX 	 INTEGER
	ACCESS 	 read-only
	STATUS 	 mandatory
	DESCRIPTION
	" The used capacity in KBytes of the /sys partition of this disk"
	::= { mhvsVPResourcesDiskEntry 10 }

mhvsVPResourcesNetwTable	OBJECT-TYPE
	SYNTAX	SEQUENCE OF MhvsVPResourcesNetwEntry
	ACCESS	not-accessible
	STATUS	mandatory
	DESCRIPTION
	" Table listing the Network Resources on the Video Server."
	::= { mhvsVPResources 7 }
mhvsVPResourcesNetwEntry	OBJECT-TYPE
	SYNTAX	MhvsVPResourcesNetwEntry
	ACCESS	not-accessible
	STATUS	mandatory
	DESCRIPTION
	" Entry for table mhvsVPResourcesNetwTable"
	INDEX { mhvsVPResourcesNetwType,
		mhvsVPResourcesNetwIndex		}
	::= { mhvsVPResourcesNetwTable 1 }
MhvsVPResourcesNetwEntry ::= SEQUENCE
	{
	mhvsVPResourcesNetwIndex	INTEGER,
	mhvsVPResourcesNetwMax		Gauge,
	mhvsVPResourcesNetwUsed		Gauge,
	mhvsVPResourcesNetwNumStreams	Gauge,
	mhvsVPResourcesNetwType		INTEGER,
	mhvsVPResourcesNetwId		DisplayString,
	mhvsVPResourcesNetwStatus	INTEGER
	}
mhvsVPResourcesNetwIndex 	 OBJECT-TYPE
	SYNTAX 	 INTEGER (1..65536)
	ACCESS 	 read-only
	STATUS 	 mandatory
	DESCRIPTION
	" A unique number within the Video Server for the network"
	::= { mhvsVPResourcesNetwEntry 1 }
mhvsVPResourcesNetwMax 	 OBJECT-TYPE
	SYNTAX 	 Gauge
	ACCESS 	 read-write
	STATUS 	 mandatory
	DESCRIPTION
	" The maximum resources for this network"
	::= { mhvsVPResourcesNetwEntry 3 }
mhvsVPResourcesNetwUsed 	 OBJECT-TYPE
	SYNTAX 	 Gauge
	ACCESS 	 read-only
	STATUS 	 mandatory
	DESCRIPTION
	" The used resources for this network"
	::= { mhvsVPResourcesNetwEntry 4 }
mhvsVPResourcesNetwNumStreams 	 OBJECT-TYPE
	SYNTAX 	 Gauge
	ACCESS 	 read-only
	STATUS 	 mandatory
	DESCRIPTION
	" The number of streams using this network"
	::= { mhvsVPResourcesNetwEntry 5 }
mhvsVPResourcesNetwType 	OBJECT-TYPE
	SYNTAX 	 INTEGER
		{
		dvb	(3),
		qam	(4),
		codec	(5),
		atm	(6),
		ip	(7)
		}
	ACCESS 	 read-only
	STATUS 	 mandatory
	DESCRIPTION
	" The type of this network"
	::= { mhvsVPResourcesNetwEntry 6 }
mhvsVPResourcesNetwId 	OBJECT-TYPE
	SYNTAX 	 DisplayString
	ACCESS 	 read-only
	STATUS 	 mandatory
	DESCRIPTION
	" The id. of this network
		For DVB or QAM, this is the TSID.
		For CODEC, this is the Codec port number.
		For ATM, this is the resource id..
		For IP, this is a user-defined identifier."
	::= { mhvsVPResourcesNetwEntry 7 }
mhvsVPResourcesNetwStatus 	OBJECT-TYPE
	SYNTAX 	 INTEGER
		{
		deleted		(1),
		disabled	(2),
		quiesce		(3),
		failed		(4),
		standby		(5),
		enabled		(6)
		}
	ACCESS 	 read-write
	STATUS 	 mandatory
	DESCRIPTION
	" The status of this network"
	::= { mhvsVPResourcesNetwEntry 8 }
 
mhvsVPResourcesSPTable	OBJECT-TYPE
	SYNTAX	SEQUENCE OF MhvsVPResourcesSPEntry
	ACCESS	not-accessible
	STATUS	mandatory
	DESCRIPTION
	" Table listing the Service Providers on the Video Server."
	::= { mhvsVPResources 8 }
mhvsVPResourcesSPEntry	OBJECT-TYPE
	SYNTAX	MhvsVPResourcesSPEntry
	ACCESS	not-accessible
	STATUS	mandatory
	DESCRIPTION
	" Entry for table mhvsVPResourcesSPTable"
	INDEX { mhvsVPResourcesSPIndex		}
	::= { mhvsVPResourcesSPTable 1 }
MhvsVPResourcesSPEntry ::= SEQUENCE
	{
	mhvsVPResourcesSPIndex		INTEGER,
	mhvsVPResourcesSPMax		Gauge,
	mhvsVPResourcesSPUsed		Gauge,
	mhvsVPResourcesSPStatus		INTEGER,
	mhvsVPResourcesSPConnected	INTEGER,
	mhvsVPResourcesSPHostIndex	INTEGER
	}
mhvsVPResourcesSPIndex 	 OBJECT-TYPE
	SYNTAX 	 INTEGER (1..65536)
	ACCESS 	 read-only
	STATUS 	 mandatory
	DESCRIPTION
	" A unique number within the Video Server for the Service Provider"
	::= { mhvsVPResourcesSPEntry 1 }
mhvsVPResourcesSPMax 	 OBJECT-TYPE
	SYNTAX 	 Gauge
	ACCESS 	 read-only
	STATUS 	 mandatory
	DESCRIPTION
	" The maximum resources (i.e. sessions) for this Service Provider "
	::= { mhvsVPResourcesSPEntry 2 }
mhvsVPResourcesSPUsed 	 OBJECT-TYPE
	SYNTAX 	 Gauge
	ACCESS 	 read-only
	STATUS 	 mandatory
	DESCRIPTION
	" The used resources (i.e. sessions) for this Service Provider "
	::= { mhvsVPResourcesSPEntry 3 }
mhvsVPResourcesSPStatus 	OBJECT-TYPE
	SYNTAX 	 INTEGER
		{
		deleted		(1),
		disabled	(2),
		quiesce		(3),
		failed		(4),
		standby		(5),
		enabled		(6)
		}
	ACCESS 	 read-write
	STATUS 	 mandatory
	DESCRIPTION
	" The status of this Service Provider "
	::= { mhvsVPResourcesSPEntry 4 }
mhvsVPResourcesSPConnected 	 OBJECT-TYPE
	SYNTAX 	 INTEGER
		{
-- invalid	no	(0),
		yes	(1)
		}
	ACCESS 	 read-only
	STATUS 	 mandatory
	DESCRIPTION
	" Indicates whether this Service Provider is connected to the Video Server"
	::= { mhvsVPResourcesSPEntry 5 }
mhvsVPResourcesSPHostIndex 	 OBJECT-TYPE
	SYNTAX 	 INTEGER
	ACCESS 	 read-only
	STATUS 	 mandatory
	DESCRIPTION
	" Set to spsHostsindex in spsHostsTable"
	::= { mhvsVPResourcesSPEntry 6 }

mhvsVPResourcesDiskAttTable	OBJECT-TYPE
	SYNTAX	SEQUENCE OF MhvsVPResourcesDiskAttEntry
	ACCESS	not-accessible
	STATUS	mandatory
	DESCRIPTION
	" Table listing the Disk Attachments on the Video Server."
	::= { mhvsVPResources 9 }
mhvsVPResourcesDiskAttEntry	OBJECT-TYPE
	SYNTAX	MhvsVPResourcesDiskAttEntry
	ACCESS	not-accessible
	STATUS	mandatory
	DESCRIPTION
	" Entry for table mhvsVPResourcesDiskAttTable"
	INDEX { mhvsVPResourcesDiskAttDiskIndex,
		mhvsVPResourcesDiskAttIndex }
	::= { mhvsVPResourcesDiskAttTable 1 }
MhvsVPResourcesDiskAttEntry ::= SEQUENCE
	{
	mhvsVPResourcesDiskAttDiskIndex	INTEGER,
	mhvsVPResourcesDiskAttVPIndex	INTEGER,
	mhvsVPResourcesDiskAttDir	DisplayString,
	mhvsVPResourcesDiskAttStatus	INTEGER,
	mhvsVPResourcesDiskAttIndex	INTEGER
	}
mhvsVPResourcesDiskAttDiskIndex 	 OBJECT-TYPE
	SYNTAX 	 INTEGER (1..65536)
	ACCESS 	 read-only
	STATUS 	 mandatory
	DESCRIPTION
	" Corresponds to mhvsVPResourcesDiskIndex in mhvsVPResourcesDiskTable"
	::= { mhvsVPResourcesDiskAttEntry 1 }
mhvsVPResourcesDiskAttVPIndex 	 OBJECT-TYPE
	SYNTAX 	 INTEGER
	ACCESS 	 read-only
	STATUS 	 mandatory
	DESCRIPTION
	" Corresponds to mhvsVPResourcesVPIndex in mhvsVPResourcesVPTable"
	::= { mhvsVPResourcesDiskAttEntry 2 }
mhvsVPResourcesDiskAttDir 	 OBJECT-TYPE
	SYNTAX 	 DisplayString
	ACCESS 	 read-only
	STATUS 	 mandatory
	DESCRIPTION
	" The mount-point of the disk on the host"
	::= { mhvsVPResourcesDiskAttEntry 3 }
mhvsVPResourcesDiskAttStatus 	OBJECT-TYPE
	SYNTAX 	 INTEGER
		{
		deleted		(1),
		disabled	(2),
		quiesce		(3),
		failed		(4),
		standby		(5),
		enabled		(6)
		}
	ACCESS 	 read-write
	STATUS 	 mandatory
	DESCRIPTION
	" The status of this disk to VP attachment"
	::= { mhvsVPResourcesDiskAttEntry 4 }
mhvsVPResourcesDiskAttIndex 	 OBJECT-TYPE
	SYNTAX 	 INTEGER (1..65536)
	ACCESS 	 read-only
	STATUS 	 mandatory
	DESCRIPTION
	" Index into list of attachments for this disk"
	::= { mhvsVPResourcesDiskAttEntry 5 }

mhvsVPResourcesNetwAttTable	OBJECT-TYPE
	SYNTAX	SEQUENCE OF MhvsVPResourcesNetwAttEntry
	ACCESS	not-accessible
	STATUS	mandatory
	DESCRIPTION
	" Table listing the NetwAttork Resource Attachments on the Video Server."
	::= { mhvsVPResources 10 }
mhvsVPResourcesNetwAttEntry	OBJECT-TYPE
	SYNTAX	MhvsVPResourcesNetwAttEntry
	ACCESS	not-accessible
	STATUS	mandatory
	DESCRIPTION
	" Entry for table mhvsVPResourcesNetwAttTable"
	INDEX { mhvsVPResourcesNetwAttFromType,
		mhvsVPResourcesNetwAttFromIndex,
		mhvsVPResourcesNetwAttIndex }
	::= { mhvsVPResourcesNetwAttTable 1 }
MhvsVPResourcesNetwAttEntry ::= SEQUENCE
	{
	mhvsVPResourcesNetwAttFromType	INTEGER,
	mhvsVPResourcesNetwAttFromIndex	INTEGER,
	mhvsVPResourcesNetwAttToType	INTEGER,
	mhvsVPResourcesNetwAttToIndex	INTEGER,
	mhvsVPResourcesNetwAttStatus	INTEGER,
	mhvsVPResourcesNetwAttIndex	INTEGER,
	mhvsVPResourcesNetwAttName	DisplayString
	}
mhvsVPResourcesNetwAttFromType 	OBJECT-TYPE
	SYNTAX 	 INTEGER
		{
		dvb	(3),
		qam	(4),
		codec	(5),
		atm	(6),
		ip	(7)
		}
	ACCESS 	 read-only
	STATUS 	 mandatory
	DESCRIPTION
	" Corresponds to mhvsVPResourcesNetwType in mhvsVPResourcesNetwTable"
	::= { mhvsVPResourcesNetwAttEntry 1 }
mhvsVPResourcesNetwAttFromIndex 	 OBJECT-TYPE
	SYNTAX 	 INTEGER (1..65536)
	ACCESS 	 read-only
	STATUS 	 mandatory
	DESCRIPTION
	" Corresponds to mhvsVPResourcesNetwIndex in mhvsVPResourcesNetwTable"
	::= { mhvsVPResourcesNetwAttEntry 2 }
mhvsVPResourcesNetwAttToType 	OBJECT-TYPE
	SYNTAX 	 INTEGER
		{
		vp	(1),
		disk	(2),
		dvb	(3),
		qam	(4),
		codec	(5),
		atm	(6),
		ip	(7)
		}
	ACCESS 	 read-only
	STATUS 	 mandatory
	DESCRIPTION
	" The type of resource to which the network resource is attached"
	::= { mhvsVPResourcesNetwAttEntry 3 }
mhvsVPResourcesNetwAttToIndex 	 OBJECT-TYPE
	SYNTAX 	 INTEGER
	ACCESS 	 read-only
	STATUS 	 mandatory
	DESCRIPTION
	" If mhvsVPResourcesNetwAttToType is vp, this corresponds to mhvsVPResourcesVpId in mhvsVPResourcesVPTable.
	  Otherwise, it corresponds to mhvsVPResourcesNetwIndex in mhvsVPResourcesNetwTable"
	::= { mhvsVPResourcesNetwAttEntry 4 }
mhvsVPResourcesNetwAttStatus 	OBJECT-TYPE
	SYNTAX 	 INTEGER
		{
		deleted		(1),
		disabled	(2),
		quiesce		(3),
		failed		(4),
		standby		(5),
		enabled		(6)
		}
	ACCESS 	 read-write
	STATUS 	 mandatory
	DESCRIPTION
	" The status of this network attachment"
	::= { mhvsVPResourcesNetwAttEntry 5 }
mhvsVPResourcesNetwAttIndex 	 OBJECT-TYPE
	SYNTAX 	 INTEGER (1..65536)
	ACCESS 	 read-only
	STATUS 	 mandatory
	DESCRIPTION
	" Index into list of attachments for this network resource"
	::= { mhvsVPResourcesNetwAttEntry 6 }
mhvsVPResourcesNetwAttName 	 OBJECT-TYPE
	SYNTAX 	 DisplayString
	ACCESS 	 read-only
	STATUS 	 mandatory
	DESCRIPTION
	" Name for this network attachment"
	::= { mhvsVPResourcesNetwAttEntry 7 }

mhvsVPResourcesTrapGeneration 	 OBJECT-TYPE
	SYNTAX 	 INTEGER
		{
-- invalid	off	(0),
		on	(1)
		}
	ACCESS 	 read-write
	STATUS 	 mandatory
	DESCRIPTION
	" Controls when the mhvsVPResources...ChangedStatus traps are generated.
	 off => no traps are generated,
	 on => resource changes state"
	::= { mhvsVPResources 11 }
mhvsVPResourcesSPChangedStatus	
	TRAP-TYPE
	ENTERPRISE concurrentComputerCorporation
	VARIABLES
	    {
	    mhvsVPResourcesSPStatus
	    }
	DESCRIPTION
	" Trap is issued when a Service Provider changes state
	 depending on the setting of mhvsVPResourcesTrapGeneration.
	 The trap identifies the SP and includes its new state"
	::= 51
mhvsVPResourcesVPChangedStatus	
	TRAP-TYPE
	ENTERPRISE concurrentComputerCorporation
	VARIABLES
	    {
	    mhvsVPResourcesVPStatus
	    }
	DESCRIPTION
	" Trap is issued when a Video Pump changes state
	 depending on the setting of mhvsVPResourcesTrapGeneration.
	 The trap identifies the VP and includes its new state"
	::= 52
mhvsVPResourcesDiskChangedStatus	
	TRAP-TYPE
	ENTERPRISE concurrentComputerCorporation
	VARIABLES
	    {
	    mhvsVPResourcesDiskStatus
	    }
	DESCRIPTION
	" Trap is issued when a Disk Resource changes state
	 depending on the setting of mhvsVPResourcesTrapGeneration.
	 The trap identifies the Disk and includes its new state"
	::= 53
mhvsVPResourcesDiskAttChangedStatus	
	TRAP-TYPE
	ENTERPRISE concurrentComputerCorporation
	VARIABLES
	    {
	    mhvsVPResourcesDiskAttStatus
	    }
	DESCRIPTION
	" Trap is issued when a Disk Attachment changes state
	 depending on the setting of mhvsVPResourcesTrapGeneration.
	 The trap identifies the Disk Attachment and includes its new state"
	::= 54
mhvsVPResourcesNetwChangedStatus	
	TRAP-TYPE
	ENTERPRISE concurrentComputerCorporation
	VARIABLES
	    {
	    mhvsVPResourcesNetwStatus
	    }
	DESCRIPTION
	" Trap is issued when a Network Resource changes state
	 depending on the setting of mhvsVPResourcesTrapGeneration.
	 The trap identifies the Network Resource and includes its new state"
	::= 55
mhvsVPResourcesNetwAttChangedStatus	
	TRAP-TYPE
	ENTERPRISE concurrentComputerCorporation
	VARIABLES
	    {
	    mhvsVPResourcesNetwAttStatus
	    }
	DESCRIPTION
	" Trap is issued when a Network Attachment changes state
	 depending on the setting of mhvsVPResourcesTrapGeneration.
	 The trap identifies the Network Attachment and includes its new state"
	::= 56
--
-- GROUP mhvsVPStreams
-- 
mhvsVPStreamsTrapGeneration 	 OBJECT-TYPE
	SYNTAX 	 INTEGER
		{
		none		(1),
		openClose	(2),
		stateChange	(3)
		}
	ACCESS 	 read-write
	STATUS 	 mandatory
	DESCRIPTION
	" Controls when the mhvsVPStreamChangedStatus trap is generated.
	 openClose => streams opened or closed,
	 stateChange => streams opened or closed or change state"
	::= { mhvsVPStreams 1 }
mhvsVPStreamsVideoTable	OBJECT-TYPE
	SYNTAX	SEQUENCE OF MhvsVPStreamsVideoEntry
	ACCESS	not-accessible
	STATUS	mandatory
	DESCRIPTION
	" Table relating Video Instances to Stream Instances"
	::= { mhvsVPStreams 2 }
mhvsVPStreamsVideoEntry	OBJECT-TYPE
	SYNTAX	MhvsVPStreamsVideoEntry
	ACCESS	not-accessible
	STATUS	mandatory
	DESCRIPTION
	" Entry for table mhvsVPStreamsVideoTable"
	INDEX { mhvsVPStreamsVideoSSEIndex,
		mhvsVPStreamsVideoSIIndex,
		mhvsVPStreamsVideoDiskIndex,
		mhvsVPStreamsVideoVideoIndex		}
	::= { mhvsVPStreamsVideoTable 1 }
MhvsVPStreamsVideoEntry ::= SEQUENCE
	{
	mhvsVPStreamsVideoSSEIndex	INTEGER,
	mhvsVPStreamsVideoSIIndex	INTEGER,
	mhvsVPStreamsVideoDiskIndex	INTEGER,
	mhvsVPStreamsVideoVideoIndex	INTEGER
	}
mhvsVPStreamsVideoSSEIndex 	 OBJECT-TYPE
	SYNTAX 	 INTEGER (1..2147483647)
	ACCESS 	 read-only
	STATUS 	 mandatory
	DESCRIPTION
	" Set to spsStreamInstStreamSEIndex."
	::= { mhvsVPStreamsVideoEntry 1 }
mhvsVPStreamsVideoSIIndex 	 OBJECT-TYPE
	SYNTAX 	 INTEGER (1..2147483647)
	ACCESS 	 read-only
	STATUS 	 mandatory
	DESCRIPTION
	" Set to spsStreamInstIndex."
	::= { mhvsVPStreamsVideoEntry 2 }
mhvsVPStreamsVideoDiskIndex 	 OBJECT-TYPE
	SYNTAX 	 INTEGER (1..65536)
	ACCESS 	 read-only
	STATUS 	 mandatory
	DESCRIPTION
	" Set to mhvsVPVideoInstDiskIndex."
	::= { mhvsVPStreamsVideoEntry 3 }
mhvsVPStreamsVideoVideoIndex 	 OBJECT-TYPE
	SYNTAX 	 INTEGER (1..65536)
	ACCESS 	 read-only
	STATUS 	 mandatory
	DESCRIPTION
	" Set to mhvsVPVideoInstVideoIndex."
	::= { mhvsVPStreamsVideoEntry 4 }
mhvsVPStreamsNetwTable	OBJECT-TYPE
	SYNTAX	SEQUENCE OF MhvsVPStreamsNetwEntry
	ACCESS	not-accessible
	STATUS	mandatory
	DESCRIPTION
	" Table relating Network Resources to Stream Instances."
	::= { mhvsVPStreams 3 }
mhvsVPStreamsNetwEntry	OBJECT-TYPE
	SYNTAX	MhvsVPStreamsNetwEntry
	ACCESS	not-accessible
	STATUS	mandatory
	DESCRIPTION
	" Entry for table mhvsVPStreamsNetwTable"
	INDEX { mhvsVPStreamsNetwSSEIndex,
			mhvsVPStreamsNetwSIIndex,
			mhvsVPStreamsNetwNetwType }
	::= { mhvsVPStreamsNetwTable 1 }
MhvsVPStreamsNetwEntry ::= SEQUENCE
	{
	mhvsVPStreamsNetwSSEIndex	INTEGER,
	mhvsVPStreamsNetwSIIndex	INTEGER,
	mhvsVPStreamsNetwNetwType	INTEGER,
	mhvsVPStreamsNetwNetwIndex	INTEGER
	}
mhvsVPStreamsNetwSSEIndex 	 OBJECT-TYPE
	SYNTAX 	 INTEGER (1..2147483647)
	ACCESS 	 read-only
	STATUS 	 mandatory
	DESCRIPTION
	" Corresponds to spsStreamInstStreamSEIndex in spsStreamInstTable"
	::= { mhvsVPStreamsNetwEntry 1 }
mhvsVPStreamsNetwSIIndex 	 OBJECT-TYPE
	SYNTAX 	 INTEGER (1..2147483647)
	ACCESS 	 read-only
	STATUS 	 mandatory
	DESCRIPTION
	" Corresponds to spsStreamInstIndex in spsStreamInstTable"
	::= { mhvsVPStreamsNetwEntry 2 }
mhvsVPStreamsNetwNetwType	OBJECT-TYPE
	SYNTAX 	 INTEGER
		{
		dvb	(3),
		qam	(4),
		codec	(5),
		atm	(6),
		ip	(7)
		}
	ACCESS 	 read-only
	STATUS 	 mandatory
	DESCRIPTION
	" Corresponds to mhvsVPResourcesNetwType in mhvsVPResourcesNetwTable"
	::= { mhvsVPStreamsNetwEntry 3 }
mhvsVPStreamsNetwNetwIndex 	 OBJECT-TYPE
	SYNTAX 	 INTEGER
	ACCESS 	 read-only
	STATUS 	 mandatory
	DESCRIPTION
	" Corresponds to mhvsVPResourcesNetwIndex in mhvsVPResourcesNetwTable"
	::= { mhvsVPStreamsNetwEntry 4 }
mhvsVPStreamChangedStatus	
	TRAP-TYPE
	ENTERPRISE concurrentComputerCorporation
-- 	VARIABLES
-- 	    {
-- 	    spsStreamInstState
-- 	    }
	DESCRIPTION
	" Trap is issued when a stream is opened or closed or changes state
	 depending on the setting of mhvsVPStreamsTrapGeneration.
	 The trap contains the new state of the stream ('unknown' if closed)"
	::= 50
--
-- GROUP mhvsVPMenu
--
--  This group represents the Menus on the Video Server.
--  The mhvsVPMenuTable lists all the menus.
--  The mhvsVPMenuInstTable lists each instance of the menus.
-- 
mhvsVPMenuTable	OBJECT-TYPE
	SYNTAX	SEQUENCE OF MhvsVPMenuEntry
	ACCESS	not-accessible
	STATUS	mandatory
	DESCRIPTION
	" Table listing the Menus on the Video Server."
	::= { mhvsVPMenu 2 }
mhvsVPMenuEntry	OBJECT-TYPE
	SYNTAX	MhvsVPMenuEntry
	ACCESS	not-accessible
	STATUS	mandatory
	DESCRIPTION
	" Entry for table mhvsVPMenuTable"
	INDEX { mhvsVPMenuIndex		}
	::= { mhvsVPMenuTable 1 }
MhvsVPMenuEntry ::= SEQUENCE
	{
	mhvsVPMenuIndex	INTEGER,
	mhvsVPMenuName		DisplayString,
	mhvsVPMenuNumCopies	Gauge,
	mhvsVPMenuNumOpen	Gauge,
	mhvsVPMenuStatus	INTEGER
	}
mhvsVPMenuIndex 	 OBJECT-TYPE
	SYNTAX 	 INTEGER (1..65536)
	ACCESS 	 read-only
	STATUS 	 mandatory
	DESCRIPTION
	" Unique identifier of this menu"
	::= { mhvsVPMenuEntry 1 }
mhvsVPMenuName 	 OBJECT-TYPE
	SYNTAX 	 DisplayString
	ACCESS 	 read-only
	STATUS 	 mandatory
	DESCRIPTION
	" Name of this menu"
	::= { mhvsVPMenuEntry 2 }
mhvsVPMenuNumCopies 	 OBJECT-TYPE
	SYNTAX 	 Gauge
	ACCESS 	 read-only
	STATUS 	 mandatory
	DESCRIPTION
	" Number of copies"
	::= { mhvsVPMenuEntry 3 }
mhvsVPMenuNumOpen 	 OBJECT-TYPE
	SYNTAX 	 Gauge
	ACCESS 	 read-only
	STATUS 	 mandatory
	DESCRIPTION
	" Current number of streams using this menu"
	::= { mhvsVPMenuEntry 5 }
mhvsVPMenuStatus 	 OBJECT-TYPE
	SYNTAX 	 INTEGER
		{
		deleted		(1),
		disabled	(2),
		quiesce		(3),
		failed		(4),
		standby		(5),
		enabled		(6)
		}
	ACCESS 	 read-write
	STATUS 	 mandatory
	DESCRIPTION
	" Status of the menu"
	::= { mhvsVPMenuEntry 6 }

mhvsVPMenuInstTable	OBJECT-TYPE
	SYNTAX	SEQUENCE OF MhvsVPMenuInstEntry
	ACCESS	not-accessible
	STATUS	mandatory
	DESCRIPTION
	" Table listing each instance of the Menus on the Video Server"
	::= { mhvsVPMenu 3 }
mhvsVPMenuInstEntry	OBJECT-TYPE
	SYNTAX	MhvsVPMenuInstEntry
	ACCESS	not-accessible
	STATUS	mandatory
	DESCRIPTION
	" Entry for table mhvsVPMenuInstTable"
	INDEX { mhvsVPMenuInstMenuIndex,
		mhvsVPMenuInstIndex		}
	::= { mhvsVPMenuInstTable 1 }
MhvsVPMenuInstEntry ::= SEQUENCE
	{
	mhvsVPMenuInstMenuIndex	INTEGER,
	mhvsVPMenuInstDiskIndex	INTEGER,
	mhvsVPMenuInstNumOpen		Gauge,
	mhvsVPMenuInstStatus		INTEGER,
	mhvsVPMenuInstPath		DisplayString,
	mhvsVPMenuInstIndex		INTEGER
	}
mhvsVPMenuInstMenuIndex 	 OBJECT-TYPE
	SYNTAX 	 INTEGER (1..65536)
	ACCESS 	 read-only
	STATUS 	 mandatory
	DESCRIPTION
	" Unique identifier of this menu. Set to mhvsVPMenuIndex."
	::= { mhvsVPMenuInstEntry 1 }
mhvsVPMenuInstDiskIndex 	 OBJECT-TYPE
	SYNTAX 	 INTEGER
	ACCESS 	 read-only
	STATUS 	 mandatory
	DESCRIPTION
	" The disk holding this instance. Set to mhvsVPResourcesDiskIndex."
	::= { mhvsVPMenuInstEntry 3 }
mhvsVPMenuInstNumOpen 	 OBJECT-TYPE
	SYNTAX 	 Gauge
	ACCESS 	 read-only
	STATUS 	 mandatory
	DESCRIPTION
	" Current number of streams using this menu instance"
	::= { mhvsVPMenuInstEntry 4 }
mhvsVPMenuInstStatus 	 OBJECT-TYPE
	SYNTAX 	 INTEGER
		{
		deleted		(1),
		disabled	(2),
		quiesce		(3),
		failed		(4),
		standby		(5),
		enabled		(6)
		}
	ACCESS 	 read-write
	STATUS 	 mandatory
	DESCRIPTION
	" The status of this menu instance"
	::= { mhvsVPMenuInstEntry 5 }
mhvsVPMenuInstPath 	 OBJECT-TYPE
	SYNTAX 	 DisplayString
	ACCESS 	 read-only
	STATUS 	 mandatory
	DESCRIPTION
	" Path to the menu from the disk"
	::= { mhvsVPMenuInstEntry 6 }
mhvsVPMenuInstIndex 	 OBJECT-TYPE
	SYNTAX 	 INTEGER (1..65536)
	ACCESS 	 read-only
	STATUS 	 mandatory
	DESCRIPTION
	" The index for this menu instance"
	::= { mhvsVPMenuInstEntry 7 }

mhvsVPMenuTrapGeneration 	 OBJECT-TYPE
	SYNTAX 	 INTEGER
		{
-- invalid	off	(0),
		on	(1)
		}
	ACCESS 	 read-write
	STATUS 	 mandatory
	DESCRIPTION
	" Controls when the mhvsVPMenuChangedStatus and
	mhvsVPMenuInstChangedStatus traps are generated.
	 off => no traps are generated,
	 on => menu or menu instance changes state"
	::= { mhvsVPMenu 4 }
mhvsVPMenuChangedStatus	
	TRAP-TYPE
	ENTERPRISE concurrentComputerCorporation
	VARIABLES
	    {
	    mhvsVPMenuStatus
	    }
	DESCRIPTION
	" Trap is issued when a menu changes state
	 depending on the setting of mhvsVPMenuTrapGeneration.
	 The trap identifies the menu and includes its new state"
	::= 59
mhvsVPMenuInstChangedStatus	
	TRAP-TYPE
	ENTERPRISE concurrentComputerCorporation
	VARIABLES
	    {
	    mhvsVPMenuInstStatus
	    }
	DESCRIPTION
	" Trap is issued when a menu instance changes state
	 depending on the setting of mhvsVPMenuTrapGeneration.
	 The trap identifies the menu instance and includes
	 its new state"
	::= 60
--
-- GROUP mediaHawkVEMon
-- 
mhProcessStart	
	TRAP-TYPE
	ENTERPRISE concurrentComputerCorporation
	VARIABLES
	    {
	    mediaHawkVEMonAlive
	    }
	DESCRIPTION
	" Trap is issued when VEMon successfully started"
	::= 101
mhProcessTermination	
	TRAP-TYPE
	ENTERPRISE concurrentComputerCorporation
	VARIABLES
	    {
	    mediaHawkVEMonAlive
	    }
	DESCRIPTION
	" Trap is issued when VEMon has terminated"
	::= 102
mhEnvironmentFanFailure	
	TRAP-TYPE
	ENTERPRISE concurrentComputerCorporation
	VARIABLES
	    {
	    mhEnvironmentFanStatus
	    }
	DESCRIPTION
	" Trap is issued when A Fan has failed"
	::= 106
mhEnvironmentPowerSupplyFailure	
	TRAP-TYPE
	ENTERPRISE concurrentComputerCorporation
	VARIABLES
	    {
	    mhEnvironmentPowerSupplyStatus
	    }
	DESCRIPTION
	" Trap is issued when A Power Supply has failed"
	::= 107
mhEnvironmentTemperatureAlarm	
	TRAP-TYPE
	ENTERPRISE concurrentComputerCorporation
	VARIABLES
	    {
	    mhEnvironmentTemperatureValue
	    }
	DESCRIPTION
	" Trap is issued when Over Temperature is detected"
	::= 108

mediaHawkVEMonAlive 	 OBJECT-TYPE
	SYNTAX 	 INTEGER
		{
-- invalid	no	(0),
		yes	(1)
		}
	ACCESS 	 read-only
	STATUS 	 mandatory
	DESCRIPTION
	" Always 1. If VEMon is not running on the target system, a snmp
	error or timeout will occur."
	::= { mediaHawkVEMon 1 }
--
-- GROUP mediaHawkDVB
--
mediaHawkDVBTable	OBJECT-TYPE
	SYNTAX	SEQUENCE OF MediaHawkDVBEntry
	ACCESS	not-accessible
	STATUS	mandatory
	DESCRIPTION
	" Table listing the DVBs on the IVM."
	::= { mediaHawkVEMon 2 }
mediaHawkDVBEntry	OBJECT-TYPE
	SYNTAX	MediaHawkDVBEntry
	ACCESS	not-accessible
	STATUS	mandatory
	DESCRIPTION
	" Entry for table mediaHawkDVBTable"
	INDEX { mhDVBName		}
	::= { mediaHawkDVBTable 1 }
MediaHawkDVBEntry ::= SEQUENCE
	{
	mhDVBStatus				INTEGER,
	mhDVBName				DisplayString,
	mhDVBMTU				INTEGER,
	mhDVBReceivePackets		INTEGER,
	mhDVBReceiveErrors		INTEGER,
	mhDVBTransmitPackets		INTEGER,
	mhDVBTransmitErrors		INTEGER,
	mhDVBTransmitKBytesPerSec	INTEGER
	}
mhDVBStatus 	 OBJECT-TYPE
	SYNTAX 	 INTEGER
		{
-- invalid	no	(0),
		yes	(1)
		}
	ACCESS 	 read-only
	STATUS 	 mandatory
	DESCRIPTION
	" '1' if the DVB-ASI card is on-line and operational, '0' if not."
	::= { mediaHawkDVBEntry 1 }
mhDVBName 	 OBJECT-TYPE
	SYNTAX 	 DisplayString (SIZE (1..255))
	ACCESS 	 read-only
	STATUS 	 mandatory
	DESCRIPTION
	" The device name of the DVB-ASI software device, currently either 'gi0' or 'mh0'."
	::= { mediaHawkDVBEntry 2 }
mhDVBMTU 	 OBJECT-TYPE
	SYNTAX 	 INTEGER
	ACCESS 	 read-only
	STATUS 	 mandatory
	DESCRIPTION
	" The MTU (maximum transmission unit) size for the DVB card Interface."
	::= { mediaHawkDVBEntry 3 }
mhDVBReceivePackets 	 OBJECT-TYPE
	SYNTAX 	 INTEGER
	ACCESS 	 read-only
	STATUS 	 mandatory
	DESCRIPTION
	" Total packets received by this DVB-ASI card.  Normally 0."
	::= { mediaHawkDVBEntry 4 }
mhDVBReceiveErrors 	 OBJECT-TYPE
	SYNTAX 	 INTEGER
	ACCESS 	 read-only
	STATUS 	 mandatory
	DESCRIPTION
	" Receive errors detected by this DVB-ASI card. Normally 0."
	::= { mediaHawkDVBEntry 5 }
mhDVBTransmitPackets 	 OBJECT-TYPE
	SYNTAX 	 INTEGER
	ACCESS 	 read-only
	STATUS 	 mandatory
	DESCRIPTION
	" Total packets transmitted by this DVB-ASI card since the system was
	last restarted.  Packets are 48128 bytes long."
	::= { mediaHawkDVBEntry 6 }
mhDVBTransmitErrors 	 OBJECT-TYPE
	SYNTAX 	 INTEGER
	ACCESS 	 read-only
	STATUS 	 mandatory
	DESCRIPTION
	" Total number of transmit errors detected by this DVB-ASI card since
	the system was last restarted."
	::= { mediaHawkDVBEntry 7 }
mhDVBTransmitKBytesPerSec 	 OBJECT-TYPE
	SYNTAX 	 INTEGER
	ACCESS 	 read-only
	STATUS 	 mandatory
	DESCRIPTION
	" Average number of 1K bytes transferred per second over the last 10
	seconds for this DVB-ASI card."
	::= { mediaHawkDVBEntry 8 }
--
-- GROUP mediaHawkDisk
--
mhDiskNumDisks 	 OBJECT-TYPE
	SYNTAX 	 INTEGER
	ACCESS 	 read-only
	STATUS 	 mandatory
	DESCRIPTION
" Total number of disk drives accessible to this CPU.
	Determines the number of entries in the following disk information variables."
	::= { mediaHawkDisk 1 }
mhDiskKBytesPerSec 	 OBJECT-TYPE
	SYNTAX 	 INTEGER
	ACCESS 	 read-only
	STATUS 	 mandatory
	DESCRIPTION
" Total number of Kilobytes per second of disk activity from this particular CPU
	from all drives connected to it.  Averaged over the last 10 seconds."
	::= { mediaHawkDisk 2 }
mhDiskDrivesTable	OBJECT-TYPE
	SYNTAX	SEQUENCE OF MhDiskDrivesEntry
	ACCESS	not-accessible
	STATUS	mandatory
	DESCRIPTION
	" Table listing the Disk Drives on the IVM."
	::= { mediaHawkDisk 3 }
mhDiskDrivesEntry	OBJECT-TYPE
	SYNTAX	MhDiskDrivesEntry
	ACCESS	not-accessible
	STATUS	mandatory
	DESCRIPTION
	" Entry for table mhDiskDrivesTable"
	INDEX { mhDiskDriveName		}
	::= { mhDiskDrivesTable 1 }
MhDiskDrivesEntry ::= SEQUENCE
	{
	mhDiskDriveName			DisplayString,
	mhDiskDriveReads			INTEGER,
	mhDiskDriveWrites			INTEGER,
	mhDiskDriveReadKBytes		INTEGER,
	mhDiskDriveWriteKBytes		INTEGER,
	mhDiskDriveReadKBytesPerSec	INTEGER,
	mhDiskDriveWriteKBytesPerSec	INTEGER
	}
mhDiskDriveName 	 OBJECT-TYPE
	SYNTAX 	 DisplayString (SIZE (1..255))
	ACCESS 	 read-only
	STATUS 	 mandatory
	DESCRIPTION
	" Returns a string identifying the particular drive.  The first 3 characters
	give the controller name, the next digit is the controller number.  This
	is followed by a logical drive number.  I.e.  fib0_12.  This drive number
	does not correspond to any other value in this MIB."
	::= { mhDiskDrivesEntry 1 }
mhDiskDriveReads 	 OBJECT-TYPE
	SYNTAX 	 INTEGER
	ACCESS 	 read-only
	STATUS 	 mandatory
	DESCRIPTION
	" The total number of read commands issued to the drive from this system
	since the system was booted."
	::= { mhDiskDrivesEntry 2 }
mhDiskDriveWrites 	 OBJECT-TYPE
	SYNTAX 	 INTEGER
	ACCESS 	 read-only
	STATUS 	 mandatory
	DESCRIPTION
	" The total number of write commands issued to the drive from this system
	since the system was booted."
	::= { mhDiskDrivesEntry 3 }
mhDiskDriveReadKBytes 	 OBJECT-TYPE
	SYNTAX 	 INTEGER
	ACCESS 	 read-only
	STATUS 	 mandatory
	DESCRIPTION
	" The total quantity of data read since the system was booted
	off of the specified drive.  Counted in units of 1024 bytes."
	::= { mhDiskDrivesEntry 4 }
mhDiskDriveWriteKBytes 	 OBJECT-TYPE
	SYNTAX 	 INTEGER
	ACCESS 	 read-only
	STATUS 	 mandatory
	DESCRIPTION
	" The total quantity of data written to the specified drive since
	the system was booted.  Counted in units of 1024 bytes."
	::= { mhDiskDrivesEntry 5 }
mhDiskDriveReadKBytesPerSec 	 OBJECT-TYPE
	SYNTAX 	 INTEGER
	ACCESS 	 read-only
	STATUS 	 mandatory
	DESCRIPTION
	" Average number of bytes read off of the specified drive from this system
	measured in units of 1024 bytes.  This average is over the last 5 seconds."
	::= { mhDiskDrivesEntry 6 }
mhDiskDriveWriteKBytesPerSec 	 OBJECT-TYPE
	SYNTAX 	 INTEGER
	ACCESS 	 read-only
	STATUS 	 mandatory
	DESCRIPTION
	" Average number of bytes written to the specified drive from this system
	measured in units of 1024 bytes.  This average is over the last 5 seconds."
	::= { mhDiskDrivesEntry 7 }
mhContentMounted 	 OBJECT-TYPE
	SYNTAX 	 INTEGER
		{
-- invalid	no	(0),
		yes	(1)
		}
	ACCESS 	 read-only
	STATUS 	 mandatory
	DESCRIPTION
" Returns an integer to indicate that the Video Content disk partition is mounted and on-line.
	A 1 indicates that the content is on-line, a 0 indicates it is not."
	::= { mediaHawkDisk 4 }
--
-- GROUP mediaHawkEnvironment
--
mhEnvironmentFanTable	OBJECT-TYPE
	SYNTAX	SEQUENCE OF MhEnvironmentFanEntry
	ACCESS	not-accessible
	STATUS	mandatory
	DESCRIPTION
	" Table listing the Fans on the IVM."
	::= { mediaHawkEnvironment 1 }
mhEnvironmentFanEntry	OBJECT-TYPE
	SYNTAX	MhEnvironmentFanEntry
	ACCESS	not-accessible
	STATUS	mandatory
	DESCRIPTION
	" Entry for table mhEnvironmentFanTable"
	INDEX { mhEnvironmentFanLocation		}
	::= { mhEnvironmentFanTable 1 }
MhEnvironmentFanEntry ::= SEQUENCE
	{
	mhEnvironmentFanLocation	DisplayString,
	mhEnvironmentFanStatus		INTEGER
	}
mhEnvironmentFanLocation 	 OBJECT-TYPE
	SYNTAX 	 DisplayString (SIZE (1..255))
	ACCESS 	 read-only
	STATUS 	 mandatory
	DESCRIPTION
	" Returns a string indicating the Video Array ID followed by the number, such
	As '1A,0' for the first fan, '1A,2' for the third fan, etc."
	::= { mhEnvironmentFanEntry 1 }
mhEnvironmentFanStatus 	 OBJECT-TYPE
	SYNTAX 	 INTEGER
		{
-- invalid	failed	(0),
		working	(1)
		}
	ACCESS 	 read-only
	STATUS 	 mandatory
	DESCRIPTION
" Returns an integer of either 0 if the fan has failed or 1 if the
	fan is working properly."
	::= { mhEnvironmentFanEntry 2 }

mhEnvironmentPowerSupplyTable	OBJECT-TYPE
	SYNTAX	SEQUENCE OF MhEnvironmentPowerSupplyEntry
	ACCESS	not-accessible
	STATUS	mandatory
	DESCRIPTION
	" Table listing the Power Supplies on the IVM."
	::= { mediaHawkEnvironment 2 }
mhEnvironmentPowerSupplyEntry	OBJECT-TYPE
	SYNTAX	MhEnvironmentPowerSupplyEntry
	ACCESS	not-accessible
	STATUS	mandatory
	DESCRIPTION
	" Entry for table mhEnvironmentPowerSupplyTable"
	INDEX { mhEnvironmentPowerSupplyLocation		}
	::= { mhEnvironmentPowerSupplyTable 1 }
MhEnvironmentPowerSupplyEntry ::= SEQUENCE
	{
	mhEnvironmentPowerSupplyLocation	DisplayString,
	mhEnvironmentPowerSupplyStatus	INTEGER
	}
mhEnvironmentPowerSupplyLocation 	 OBJECT-TYPE
	SYNTAX 	 DisplayString (SIZE (1..255))
	ACCESS 	 read-only
	STATUS 	 mandatory
	DESCRIPTION
	" Returns a string indicating the Video Array ID followed by the number, such
	as '1A,0' for the left supply, '1A,2' for the right supply, etc."
	::= { mhEnvironmentPowerSupplyEntry 1 }
mhEnvironmentPowerSupplyStatus 	 OBJECT-TYPE
	SYNTAX 	 INTEGER
		{
		mising	(-1),
-- invalid	failed	(0),
		working	(1)
		}
	ACCESS 	 read-only
	STATUS 	 mandatory
	DESCRIPTION
	" Returns an integer as follows: -1 if the power supply is missing or not
plugged in, 0 if the power supply has failed, or 1 if the power supply is
	working properly."
	::= { mhEnvironmentPowerSupplyEntry 2 }

mhEnvironmentTemperatureTable	OBJECT-TYPE
	SYNTAX	SEQUENCE OF MhEnvironmentTemperatureEntry
	ACCESS	not-accessible
	STATUS	mandatory
	DESCRIPTION
	" Table listing the Temperature sensors on the IVM."
	::= { mediaHawkEnvironment 3 }
mhEnvironmentTemperatureEntry	OBJECT-TYPE
	SYNTAX	MhEnvironmentTemperatureEntry
	ACCESS	not-accessible
	STATUS	mandatory
	DESCRIPTION
	" Entry for table mhEnvironmentTemperatureTable"
	INDEX { mhEnvironmentTemperatureLocation		}
	::= { mhEnvironmentTemperatureTable 1 }
MhEnvironmentTemperatureEntry ::= SEQUENCE
	{
	mhEnvironmentTemperatureLocation	DisplayString,
	mhEnvironmentTemperatureValue		INTEGER,
	mhEnvironmentTemperatureRedLine	INTEGER
	}
mhEnvironmentTemperatureLocation 	 OBJECT-TYPE
	SYNTAX 	 DisplayString (SIZE (1..255))
	ACCESS 	 read-only
	STATUS 	 mandatory
	DESCRIPTION
	" Returns a string indicating the location of the related temperature sensor,
	such as 'Inlet LR' for lower right air inlet sensor."
	::= { mhEnvironmentTemperatureEntry 1 }
mhEnvironmentTemperatureValue 	 OBJECT-TYPE
	SYNTAX 	 INTEGER
	ACCESS 	 read-only
	STATUS 	 mandatory
	DESCRIPTION
	" Returns the temperature of the related sensor, in degrees C."
	::= { mhEnvironmentTemperatureEntry 2 }
mhEnvironmentTemperatureRedLine 	 OBJECT-TYPE
	SYNTAX 	 INTEGER
	ACCESS 	 read-only
	STATUS 	 mandatory
	DESCRIPTION
	" Returns the maximum permissible temperature of the related sensor, in
	In degrees C.  Temperatures over this value may cause a system failure."
	::= { mhEnvironmentTemperatureEntry 3 }
--
-- GROUP mediaHawkVEMon (continued)
--
mediaHawkVideoEngineHealth 	 OBJECT-TYPE
	SYNTAX 	 INTEGER
		{
		red		(1),
		yellow	(2),
		green		(3)
		}
	ACCESS 	 read-only
	STATUS 	 mandatory
	DESCRIPTION
	" Returns a 1, 2, or 3 for the health of the addressed engine.  1 is red
	(something is down); 2 = yellow; 3 = green.  Checks status of DVB card, etc."
	::= { mediaHawkVEMon 5 }
mediaHawkArrayHealth 	 OBJECT-TYPE
	SYNTAX 	 INTEGER
		{
		red		(1),
		yellow	(2),
		green		(3)
		}
	ACCESS 	 read-only
	STATUS 	 mandatory
	DESCRIPTION
	" Returns a 1, 2, or 3 for the health of the overall video array.
	1 is red; (something is down); 2 = yellow; 3 = green.
	Checks particular engine to which the value is addressed, along with the health
	of the disks, power supplies, fans, etc."
	::= { mediaHawkVEMon 6 }
mediaHawkShutdown 	 OBJECT-TYPE
	SYNTAX 	 DisplayString
	ACCESS 	 read-write
	STATUS 	 mandatory
	DESCRIPTION
	"  A writable variable used to request a particular engine or full video array
	to shutdown or restart. Passes a string indicating the engine or array
	followed by a code indicating the function to perform."
	::= { mediaHawkVEMon 7 }
mediaHawkDiskDisable 	 OBJECT-TYPE
	SYNTAX 	 DisplayString
	ACCESS 	 read-write
	STATUS 	 mandatory
	DESCRIPTION
	"  A writable variable used to request a particular disk drive
	to be disabled and spun down.  Passes a string indicating the array
	followed by the drive position, such as 1A2.3.  Returns a string
	indicating status of the operation."
	::= { mediaHawkVEMon 8 } 
mediaHawkDiskEnable 	 OBJECT-TYPE
	SYNTAX 	 DisplayString
	ACCESS 	 read-write
	STATUS 	 mandatory
	DESCRIPTION
	"  A writable variable used to request a particular disk drive
	to be enabled and spun up.  Passes a string indicating the array
	followed by the drive position, such as 1A2.3.  Returns a string
	indicating status of the operation."
	::= { mediaHawkVEMon 9 }


--
-- GROUP mediaHawkVPMon
--
vpProcessStart	
	TRAP-TYPE
	ENTERPRISE concurrentComputerCorporation
	VARIABLES
	    {
	    mediaHawkVPMonAlive
	    }
	DESCRIPTION
	" Trap is issued when VPMon successfully started"
	::= 103
vpProcessTermination	
	TRAP-TYPE
	ENTERPRISE concurrentComputerCorporation
	VARIABLES
	    {
	    mediaHawkVPMonAlive
	    }
	DESCRIPTION
	" Trap is issued when VPMon has terminated"
	::= 104
vpPartitionStateChanged	
	TRAP-TYPE
	ENTERPRISE concurrentComputerCorporation
	VARIABLES
	    {
	    mhPartitionState
	    }
	DESCRIPTION
	" Trap is issued when the mirror state has changed"
	::= 105

mediaHawkVPMonAlive 	 OBJECT-TYPE
	SYNTAX 	 INTEGER
		{
-- invalid	no	(0),
		yes	(1)
		}
	ACCESS 	 read-only
	STATUS 	 mandatory
	DESCRIPTION
	" Always 1. If VPMon is not running on the target system, a snmp
	error or timeout will occur."
	::= { mediaHawkVPMon 1 }
mhPartitionLastUnit 	 OBJECT-TYPE
	SYNTAX 	 INTEGER
	ACCESS 	 read-only
	STATUS 	 mandatory
	DESCRIPTION
	" Returns last currently configured Virtual Partition number.  A
	value of -1 indicates that there are currently no configured
	virtual partitions in the target system."
	::= { mediaHawkVPMon 2 }
mhPartitionCount 	 OBJECT-TYPE
	SYNTAX 	 INTEGER
	ACCESS 	 read-only
	STATUS 	 mandatory
	DESCRIPTION
	" Returns the maximum number of virtual partitions that may be
	configured in the target system.  A value of 0 indicates that
	the Virtual Partition driver has not been configured into the
	kernel."
	::= { mediaHawkVPMon 3 }

mhPartitionsTable	OBJECT-TYPE
	SYNTAX	SEQUENCE OF MhPartitionsEntry
	ACCESS	not-accessible
	STATUS	mandatory
	DESCRIPTION
	" Table listing the Partitions on the IVM."
	::= { mediaHawkVPMon 4 }
mhPartitionsEntry	OBJECT-TYPE
	SYNTAX	MhPartitionsEntry
	ACCESS	not-accessible
	STATUS	mandatory
	DESCRIPTION
	" Entry for table mhPartitionsTable"
	INDEX { mhPartitionName		}
	::= { mhPartitionsTable 1 }
MhPartitionsEntry ::= SEQUENCE
	{
	mhPartitionName				DisplayString,
	mhPartitionType				DisplayString,
	mhPartitionState				DisplayString,
	mhPartitionActiveReadCount		INTEGER,
	mhPartitionActiveWriteCount		INTEGER,
	mhPartitionTotalErrors			INTEGER,
	mhPartitionSliceSize			INTEGER,
	mhPartitionSizeKbytes			INTEGER,
	mhPartitionReaderMode			DisplayString,
	mhPartitionWriterMode			INTEGER,
	mhPartitionRestoreThrottle		INTEGER,
	mhPartitionProgressMeter		DisplayString,
	mhPartitionMemberCount			INTEGER,
	mhPartitionMemberDevices		DisplayString,
	mhPartitionStartRestore			INTEGER,
	mhPartitionCancelRestore		INTEGER,
	mpPartitionErrorMask			INTEGER,
	mhPartitionHealth				DisplayString,
	mhPartitionRestoreStatus		DisplayString,
	mhPartitionRestoreDate			DateAndTime,
	mhPartitionMountPoint			DisplayString,
	mhPartitionFreeSpace			INTEGER
	}
mhPartitionName 	 OBJECT-TYPE
	SYNTAX 	 DisplayString (SIZE (1..255))
	ACCESS 	 read-only
	STATUS 	 mandatory
	DESCRIPTION
	" Returns the path name of the raw device associated with VP unit 'N'.
	Examples:
		mhPartitionName.0	Returns '/dev/rdsk/vp0'
		mhPartitionName.1	Returns '/dev/rdsk/vp1'."
	::= { mhPartitionsEntry 1 }
mhPartitionType	 OBJECT-TYPE
	SYNTAX 	 DisplayString
	ACCESS 	 read-only
	STATUS 	 mandatory
	DESCRIPTION
	" Returns current configuration of VP unit 'N'.
	Legal values are:
	    'unconfigured'	partition has not been configured
	    'mirror'		configured as a mirrored device
	    'stripe'		configured as a striped device."
	::= { mhPartitionsEntry 2 }
mhPartitionState 	 OBJECT-TYPE
	SYNTAX 	 DisplayString
	ACCESS 	 read-only
	STATUS 	 mandatory
	DESCRIPTION
	"
	Returns the current state of VP unit 'N'.
	Legal values are:
	    'unconfigured'	partition has not been configured
	    'striped'		configured as a striped device
	    'verifying'		mirror is currently synchronized and
				is executing a mirror integrity check.
	    'restoring'		mirror is currently being restored.
	    'synchronized	mirror is currently synchronized.
	    'primary disk failure'
				a primary disk failure has caused the
				mirror to loose synchronization.  The
				primary disk device requires maintenance.
	    'secondary disk failure'
				a secondary disk failure has caused the
				mirror to loose synchronization.  The
				secondary disk device requires maintenance.
	    'primary+secondary disk failure'
	    'tertiary disk failure'
	    'primary+tertiary disk failure'
	    'secondary+tertiary disk failure'
	    'triple disk failure'
	    'unsynchronized'	the mirror is not synchronized and needs
				to be restored.  This state occurs as a
				result of a system panic or hang, not as
				a result of a disk failure."
	::= { mhPartitionsEntry 3 }
mhPartitionActiveReadCount 	 OBJECT-TYPE
	SYNTAX 	 INTEGER
	ACCESS 	 read-only
	STATUS 	 mandatory
	DESCRIPTION
	" Returns the current number of outstanding read requests on VP unit 'N'."
	::= { mhPartitionsEntry 4 }
mhPartitionActiveWriteCount 	 OBJECT-TYPE
	SYNTAX 	 INTEGER
	ACCESS 	 read-only
	STATUS 	 mandatory
	DESCRIPTION
	" Returns the current number of outstanding write requests on VP unit 'N'."
	::= { mhPartitionsEntry 5 }
mhPartitionTotalErrors 	 OBJECT-TYPE
	SYNTAX 	 INTEGER
	ACCESS 	 read-only
	STATUS 	 mandatory
	DESCRIPTION
	" The total number of I/O errors on VP unit 'N' since system initialization."
	::= { mhPartitionsEntry 6 }
mhPartitionSliceSize 	 OBJECT-TYPE
	SYNTAX 	 INTEGER
	ACCESS 	 read-only
	STATUS 	 mandatory
	DESCRIPTION
	" If mhPartitionType='stripe', this is the stripe size as defined
	by vpinit(1m).  Otherwise, a 0 is returned."
	::= { mhPartitionsEntry 7 }
mhPartitionSizeKbytes 	 OBJECT-TYPE
	SYNTAX 	 INTEGER
	ACCESS 	 read-only
	STATUS 	 mandatory
	DESCRIPTION
	" The size, in kilobytes, of this VP is returned."
	::= { mhPartitionsEntry 8 }
mhPartitionReaderMode 	 OBJECT-TYPE
	SYNTAX 	 DisplayString
	ACCESS 	 read-write
	STATUS 	 mandatory
	DESCRIPTION
	" none	The VP is not a mirror.
	primary	When this mirror is synchronized, all
			read requests will be scheduled exclusively
			to the primary partition.
	secondary	When this mirror is synchronized, all
			read requests will be scheduled exclusively
			to the secondary partition.
	distributed	When this mirror is synchronized, all
			read requests will be distributed between
			the two partitions."
	::= { mhPartitionsEntry 9 }
mhPartitionWriterMode 	 OBJECT-TYPE
	SYNTAX 	 INTEGER
	ACCESS 	 read-write
	STATUS 	 mandatory
	DESCRIPTION
	" -1		The VP is not a mirror.
	0		When this mirror is synchronized, the first
			write to this device will result in the
			on-disk state of the mirror to be marked
			'dirty'.  The final close(2) of this VP
			will result in the VP being marked 'clean'.
			These on-disk states are used during system
			crash recover to maintain the integrity of
			the mirror.
	>0		When this mirror is synchronized, the first
			write to this VP."
	::= { mhPartitionsEntry 10 }
mhPartitionRestoreThrottle 	 OBJECT-TYPE
	SYNTAX 	 INTEGER
	ACCESS 	 read-write
	STATUS 	 mandatory
	DESCRIPTION
	" During a mirrored restore or verify operation, an artificial delay
	may be performed between each read/write (restore) or read/read
	(verify) sequence.   This value is the number of microseconds to
	delay.  Note that the VP driver converts this value into a number
	of clock 'ticks', so microsecond resolution is not actually possible.
	Specifying a delay between 1 and 16666 results in a 1 tick delay,
	between 16667 and 33333 results in a 2 tick delay, etc.
	    0		No delay is performed. This results in the fastest
			possible restoration/verification of the mirror
			at the expense of I/O bandwidth.
	    >0		The specified delay is performed.  This lengthens
			the restoration/verification process, but is more
			friendly to other transfers which are taking place
			on the same controller(s)."
	::= { mhPartitionsEntry 11 }
mhPartitionProgressMeter 	 OBJECT-TYPE
	SYNTAX 	 DisplayString
	ACCESS 	 read-only
	STATUS 	 mandatory
	DESCRIPTION
	" During a mirrored restore or verify operation, this value
	indicates the completion percentage.  This value is always
	between '0.0%' and  '100.0%'.  A synchronized mirror will
	report this value as '100.0%'."
	::= { mhPartitionsEntry 12 }
mhPartitionMemberCount 	 OBJECT-TYPE
	SYNTAX 	 INTEGER
	ACCESS 	 read-only
	STATUS 	 mandatory
	DESCRIPTION
	" Returns the number of sub-devices which comprise this VP unit.
	Unconfigured VPs return 0, mirror VPs return 2, and striped
	VP return the number of striped partitions."
	::= { mhPartitionsEntry 13 }
mhPartitionMemberDevices 	 OBJECT-TYPE
	SYNTAX 	 DisplayString
	ACCESS 	 read-only
	STATUS 	 mandatory
	DESCRIPTION
	" Returns the names of the sub-devices which comprise this VP unit.
	Normally, the named devices are the same as found in /dev/dsk.
	For example: 3s0 4s0.
	In the event that the device node for the configured device cannot
	be located, the major and minor number will be returned (this is
	very unlikely to happen).  For example: 101,57856."
	::= { mhPartitionsEntry 14 }
mhPartitionStartRestore 	 OBJECT-TYPE
	SYNTAX 	 INTEGER
	ACCESS 	 read-write
	STATUS 	 mandatory
	DESCRIPTION
	" Returns a 1 if a restore or verify operation is currently in
	progress, or a 0 if not.
	This option can be used to initiate a repair, restore, or verify
	operation as follows:
		1	Repair			(vpinit -R equivalent)
		2	Restore			(vpinit -r equivalent)
		3	Repair and Restore	(vpinit -Rr equivalent)
		4	Verify			(vpinit -t equivalent)
	All other set values are silently ignored."
	::= { mhPartitionsEntry 15 }
mhPartitionCancelRestore 	 OBJECT-TYPE
	SYNTAX 	 INTEGER
	ACCESS 	 read-write
	STATUS 	 mandatory
	DESCRIPTION
	" When read, returns a 0.
	When set to a value of 1, the currently executing restore or
	verify operation is terminated.  This operation is ignored
	if any value other than 1 is set, or if the specified VP
	device is not currently restoring or verifying the mirror."
	::= { mhPartitionsEntry 16 }
mpPartitionErrorMask 	 OBJECT-TYPE
	SYNTAX 	 INTEGER
	ACCESS 	 read-write
	STATUS 	 mandatory
	DESCRIPTION
	" Returns an integer value [0..7] which represents a bitmask
	of member devices which have reported an I/O error.  This
	value is a logical 'or' of all errant partition members.
	The bitmask is encoded as follows:

		0	No members have reported a failure (green).
		1	Primary member failure (yellow).
		2	Secondary member failure (yellow).
		3	Primary and secondary member failures (red).
		4	Tertiary member failure (yellow).
		5	Primary and tertiary member failures (red).
		6	Secondary and tertiary member failures (red).
		7	Primary, secondary and tertiary member failures (red)."
	::= { mhPartitionsEntry 17 }
mhPartitionHealth 	 OBJECT-TYPE
	SYNTAX 	 DisplayString
	ACCESS 	 read-only
	STATUS 	 mandatory
	DESCRIPTION
	" Returns a string which indicates the overall health
	of the VP subsystem:
	  none      This device is not a mirror.
	  red       A double or triple drive failure has occurred.
	  yellow    A single drive fault has occurred on the mirrored set.
	  green     All members of the mirror are synchronized."
	::= { mhPartitionsEntry 18 }
mhPartitionRestoreStatus 	 OBJECT-TYPE
	SYNTAX 	 DisplayString
	ACCESS 	 read-only
	STATUS 	 mandatory
	DESCRIPTION
	" Returns a string which indicates the restore/verify  status
	associated with either the current, or last, restore/verify
	operation performed.

	NOTE: This status does NOT reflect the current status of the
	      mirror.  This is simply a historical log of the last
	      restore or verify command which started execution on
	      the associated VP device.   For example, this status
	      may report a successfully executed restore operation
	      but the mirror may have lost synchronization in the
	      time period since the execution of the restore.

	The possible strings that can be returned are:

	restore/verify not run since reboot
		The restore/verify status is not persistent over
		kernel reboots.  This status is returned whenever
		the restore or verify commands have not been issued
		since the last reboot.

	restore successful
		The last command issued to this VP was a restore
		which was successful.

	verify successful
		The last command issued to this VP was a verify
		which was successful.

	restore cleared read errors
		The restore cleared the VP's read error counters.
		A physical restore operation was not performed.

	restore operation active
		A restore operation is currently active on this VP.

	verify operation active
		A verify operation is currently active on this VP.

	restore was canceled
		A restore operation was started but the canceled
		at the user's request.

	verify was canceled
		A verify operation was started but the canceled
		at the user's request.

	mirror needs repair
		A restore operation was attempted on a mirror that
		need to be repaired.

	memory allocation failure
		Buffer allocation necessary to perform a restore or
		verify operation were not available.

	cannot verify a 'forced' mirror
		A verify operation was attempted on a mirror that
		was created using the 'force' option.  Since the
		mirror was never synchronized on a block-by-block
		basis, the verify operation is expected to fail.

	synchronization was lost during verify
		The verify operation was aborted due to a loss of
		synchronization.  The error causing the loss of
		synchronization was not associated with the verify
		operation (an external event caused the loss).

	error reading primary device
		A restore or verify command aborted due to a read
		error on the primary device during the operation.

	error writing primary device
		A restore command aborted due to a write error on
		the primary device during the restore operation.

	error reading secondary device
		A restore or verify command aborted due to a read
		error on the secondary device during the operation.

	error writing secondary device
		A restore command aborted due to a write error on
		the secondary device during the restore operation.

	error accessing tertiary device
		A restore or verify command aborted due to failure
		either communicating with a Loop B client system or
		because of a read or write error on the tertiary
		device.

	verify error
		A verify error occured between the primary and secondary
		mirrored device.

	tertiary device verify error
		A verify error occured between the primary and tertiary
		mirrored device.

	status unavailable
		The restore status returned was invalid."
	::= { mhPartitionsEntry 19 }

mhPartitionRestoreDate	OBJECT-TYPE
	SYNTAX 	 DateAndTime
	ACCESS 	 read-only
	STATUS 	 mandatory
	DESCRIPTION
	" Returns the date and time of the last partition restore, in
    DateAndTime format of 11 octets."
	::= { mhPartitionsEntry 20 } 
	
mhPartitionMountPoint 	 OBJECT-TYPE
	SYNTAX 	 DisplayString
	ACCESS 	 read-only
	STATUS 	 mandatory
	DESCRIPTION
	" Returns a string denoting the mount-point name if this
	partition is the mount point for any file system.  A null string
	is returned if this partition is not a mount point. MediaHawk
	Model 2000 Systems only."
	::= { mhPartitionsEntry 21 }

mhPartitionFreeSpace 	 OBJECT-TYPE
	SYNTAX 	 INTEGER
	ACCESS 	 read-only
	STATUS 	 mandatory
	DESCRIPTION
	" Applicable only if previous entry (mount point) returns a
	non-null string. Returns an integer from 0 to 99 indicating
	the percentage of free space in this partition.  MediaHawk
	Model 2000 Systems only."
	::= { mhPartitionsEntry 22 }


mhVPSubsystemHealth 	 OBJECT-TYPE
	SYNTAX 	 DisplayString
	ACCESS 	 read-only
	STATUS 	 mandatory
	DESCRIPTION
	" Returns a string which indicates the overall health
	of the VP subsystem:

	  none      There are no mirrors confgiured.

	  red       At least one partition has reported a
			   double or triple drive failure.

	  yellow    At least one partition has reported a
			   single member fault.

	  green     All partitions are synchronized ."
	::= { mediaHawkVPMon 5 }
--
END
