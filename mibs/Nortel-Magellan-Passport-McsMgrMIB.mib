Nortel-Magellan-Passport-McsMgrMIB
DEFINITIONS ::= BEGIN



IMPORTS

      OBJECT-TYPE
   FROM RFC-1212

      components,
      passportMIBs
   FROM Nortel-Magellan-Passport-UsefulDefinitionsMIB

      RowPointer,
      DisplayString,
      StorageType,
      RowStatus,
      Unsigned32
   FROM Nortel-Magellan-Passport-StandardTextualConventionsMIB

      AsciiString,
      NonReplicated,
      Link
   FROM Nortel-Magellan-Passport-TextualConventionsMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     McsMgr Enterprise MIB."

mcsMgrMIB OBJECT IDENTIFIER ::= { passportMIBs 124 }










-- McsManager
-- There is at most one McsManager per module. The McsManager is 
-- required for FRF5 PVC and DPRS MCS functionality. The 
-- McsManager can run on one of a number of LPs. The LP of the 
-- active McsManager can be determined by looking at the currentLp 
-- operational attribute.

mcsMgr OBJECT IDENTIFIER ::= { components 122 }



mcsMgrRowStatusTable OBJECT-TYPE
   SYNTAX     SEQUENCE OF McsMgrRowStatusEntry
   ACCESS     not-accessible
   STATUS     mandatory
   DESCRIPTION
     "This entry controls the addition and deletion of 
      mcsMgr components."
::= { mcsMgr 1 }

mcsMgrRowStatusEntry OBJECT-TYPE
   SYNTAX     McsMgrRowStatusEntry
   ACCESS     not-accessible
   STATUS     mandatory
   DESCRIPTION
     "A single entry in the table represents a single 
      mcsMgr component."
   INDEX {
      mcsMgrIndex }
::= { mcsMgrRowStatusTable 1 }

McsMgrRowStatusEntry ::= SEQUENCE {
   mcsMgrRowStatus
      RowStatus,
   mcsMgrComponentName
      DisplayString,
   mcsMgrStorageType
      StorageType,
   mcsMgrIndex
      NonReplicated }

mcsMgrRowStatus OBJECT-TYPE
   SYNTAX     RowStatus 
   ACCESS     read-write
   STATUS     mandatory
   DESCRIPTION
     "This variable is used as the basis for SNMP naming of
      mcsMgr components.
      These components can be added and deleted."
::= { mcsMgrRowStatusEntry 1 }

mcsMgrComponentName OBJECT-TYPE
   SYNTAX     DisplayString 
   ACCESS     read-only
   STATUS     mandatory
   DESCRIPTION
     "This variable provides the component's string name for
      use with the ASCII Console Interface"
::= { mcsMgrRowStatusEntry 2 }

mcsMgrStorageType OBJECT-TYPE
   SYNTAX     StorageType 
   ACCESS     read-only
   STATUS     mandatory
   DESCRIPTION
     "This variable represents the storage type value for the
      mcsMgr tables."
::= { mcsMgrRowStatusEntry 4 }

mcsMgrIndex OBJECT-TYPE
   SYNTAX     NonReplicated 
   ACCESS     not-accessible
   STATUS     mandatory
   DESCRIPTION
     "This variable represents the index for the mcsMgr tables."
::= { mcsMgrRowStatusEntry 10 }

mcsMgrProvTable OBJECT-TYPE
   SYNTAX     SEQUENCE OF McsMgrProvEntry
   ACCESS     not-accessible
   STATUS     mandatory
   DESCRIPTION
     "This group contains the provisionable attributes of the 
      McsManager."
::= { mcsMgr 10 }

mcsMgrProvEntry OBJECT-TYPE
   SYNTAX     McsMgrProvEntry
   ACCESS     not-accessible
   STATUS     mandatory
   DESCRIPTION
     "An entry in the mcsMgrProvTable."
   INDEX {
      mcsMgrIndex }
::= { mcsMgrProvTable 1 }

McsMgrProvEntry ::= SEQUENCE {
   mcsMgrMaxEps
      INTEGER,
   mcsMgrEpAlarmThreshold
      INTEGER,
   mcsMgrOverrideNsapAddress
      AsciiString,
   mcsMgrLogicalProcessor
      Link,
   mcsMgrSecurity
      INTEGER }

mcsMgrMaxEps OBJECT-TYPE
   SYNTAX     INTEGER (1..16384)
   ACCESS     read-write
   STATUS     mandatory
   DESCRIPTION
     "This attribute specifies the number of end points that will be 
      allowed on the module.This includes end points originating from 
      and terminating on this module. When this limit is reached calls 
      requiring the creation of an end point are rejected. The current 
      number of EPs is indicated by the currentEps attribute."
   DEFVAL     { 512 }
::= { mcsMgrProvEntry 1 }

mcsMgrEpAlarmThreshold OBJECT-TYPE
   SYNTAX     INTEGER (1..16384)
   ACCESS     read-write
   STATUS     mandatory
   DESCRIPTION
     "This attribute specifies the maximum number of end points that can 
      exist before an alarm is raised. When currentEps exceeds this value 
      an alarm is generated. The alarm is cleared when currentEps falls 
      below this value."
   DEFVAL     { 128 }
::= { mcsMgrProvEntry 2 }

mcsMgrOverrideNsapAddress OBJECT-TYPE
   SYNTAX     AsciiString (SIZE (0..44))
   ACCESS     read-write
   STATUS     mandatory
   DESCRIPTION
     "This attribute specifies the NSAP address to use as the address of 
      the McsManager. If this attribute is left empty the default 
      McsManager NSAP address is used. The nsapAddress attribute 
      indicates the NSAP address used by the McsManager. 
      The default NSAP address for the McsManager takes the form:
      <26 byte module prefix>0020480d100100"
   DEFVAL     { ''H }  -- ""
::= { mcsMgrProvEntry 3 }

mcsMgrLogicalProcessor OBJECT-TYPE
   SYNTAX     Link 
   ACCESS     read-write
   STATUS     obsolete
   DESCRIPTION
     "This attribute specifies the LogicalProcessor on which the 
      DataShuntManager will be running."
::= { mcsMgrProvEntry 4 }

mcsMgrSecurity OBJECT-TYPE
   SYNTAX     INTEGER  {
                 off(0),
                 on(1) }
   ACCESS     read-write
   STATUS     mandatory
   DESCRIPTION
     "This attribute enables or disables security for the McsManager. 
      In the case of DPRS MCS Switched Paths, if security is set to on 
      this node must have a DprsMcsEpGroup with the nsapAddress of 
      the Addr subcomponent set to the same value as the node 
      originating the call setup for the call to be accepted.If this attribute 
      is set to off this node will accept DPRS MCS setup requests from 
      any other node in the network.
      This attribute has no effect on the setup of FRF5 switched paths 
      since an originating and terminating EP are required to establish an 
      FRF5 switched path."
   DEFVAL     { off }
::= { mcsMgrProvEntry 5 }

mcsMgrStateTable OBJECT-TYPE
   SYNTAX     SEQUENCE OF McsMgrStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mcsMgr 11 }

mcsMgrStateEntry OBJECT-TYPE
   SYNTAX     McsMgrStateEntry
   ACCESS     not-accessible
   STATUS     mandatory
   DESCRIPTION
     "An entry in the mcsMgrStateTable."
   INDEX {
      mcsMgrIndex }
::= { mcsMgrStateTable 1 }

McsMgrStateEntry ::= SEQUENCE {
   mcsMgrAdminState
      INTEGER,
   mcsMgrOperationalState
      INTEGER,
   mcsMgrUsageState
      INTEGER,
   mcsMgrAvailabilityStatus
      OCTET STRING,
   mcsMgrProceduralStatus
      OCTET STRING,
   mcsMgrControlStatus
      OCTET STRING,
   mcsMgrAlarmStatus
      OCTET STRING,
   mcsMgrStandbyStatus
      INTEGER,
   mcsMgrUnknownStatus
      INTEGER }

mcsMgrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mcsMgrStateEntry 1 }

mcsMgrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mcsMgrStateEntry 2 }

mcsMgrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mcsMgrStateEntry 3 }

mcsMgrAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mcsMgrStateEntry 4 }

mcsMgrProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mcsMgrStateEntry 5 }

mcsMgrControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mcsMgrStateEntry 6 }

mcsMgrAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mcsMgrStateEntry 7 }

mcsMgrStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mcsMgrStateEntry 8 }

mcsMgrUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mcsMgrStateEntry 9 }

mcsMgrOperTable OBJECT-TYPE
   SYNTAX     SEQUENCE OF McsMgrOperEntry
   ACCESS     not-accessible
   STATUS     mandatory
   DESCRIPTION
     "This group contains the operational attributes of the McsManager 
      component."
::= { mcsMgr 12 }

mcsMgrOperEntry OBJECT-TYPE
   SYNTAX     McsMgrOperEntry
   ACCESS     not-accessible
   STATUS     mandatory
   DESCRIPTION
     "An entry in the mcsMgrOperTable."
   INDEX {
      mcsMgrIndex }
::= { mcsMgrOperTable 1 }

McsMgrOperEntry ::= SEQUENCE {
   mcsMgrCurrentLp
      RowPointer,
   mcsMgrCurrentEps
      Unsigned32,
   mcsMgrNsapAddress
      AsciiString }

mcsMgrCurrentLp OBJECT-TYPE
   SYNTAX     RowPointer 
   ACCESS     read-only
   STATUS     mandatory
   DESCRIPTION
     "This attribute indicates the current LP on which the McsManager 
      resides. If this attribute is blank then no McsManager is available."
::= { mcsMgrOperEntry 1 }

mcsMgrCurrentEps OBJECT-TYPE
   SYNTAX     Unsigned32 (0..16384)
   ACCESS     read-only
   STATUS     mandatory
   DESCRIPTION
     "The indicates the number of EPs both originating and terminating 
      on this module."
::= { mcsMgrOperEntry 3 }

mcsMgrNsapAddress OBJECT-TYPE
   SYNTAX     AsciiString (SIZE (0..44))
   ACCESS     read-only
   STATUS     mandatory
   DESCRIPTION
     "This attribute indicates the NSAP address of the McsManager on 
      this node. The value of this attributed depends on how the 
      overrideNsapAddress attribute is set. All DPRS MCS and FRF5 
      switched paths that are to terminate on this node must specify this 
      NSAP address as their destination."
::= { mcsMgrOperEntry 4 }

mcsMgrCanLpsTable OBJECT-TYPE
   SYNTAX     SEQUENCE OF McsMgrCanLpsEntry
   ACCESS     not-accessible
   STATUS     mandatory
   DESCRIPTION
     "This attribute indicates the set of LPs capable of running the 
      McsManager. If this attribute is blank then there are no candidate 
      LPs."
::= { mcsMgr 418 }

mcsMgrCanLpsEntry OBJECT-TYPE
   SYNTAX     McsMgrCanLpsEntry
   ACCESS     not-accessible
   STATUS     mandatory
   DESCRIPTION
     "An entry in the mcsMgrCanLpsTable."
   INDEX {
      mcsMgrIndex,
      mcsMgrCanLpsValue }
::= { mcsMgrCanLpsTable 1 }

McsMgrCanLpsEntry ::= SEQUENCE {
   mcsMgrCanLpsValue
      RowPointer }

mcsMgrCanLpsValue OBJECT-TYPE
   SYNTAX     RowPointer 
   ACCESS     read-only
   STATUS     mandatory
   DESCRIPTION
     "This variable represents both the value and the index for the
      mcsMgrCanLpsTable."
::= { mcsMgrCanLpsEntry 1 }




-- 
-- Version and Compliance statements
-- 



-- Object-Group Statement:
-- A list of all current accessible leaf objects.

-- OBJECTS { mcsMgrStorageType,
--           mcsMgrRowStatus,
--           mcsMgrCurrentEps,
--           mcsMgrProceduralStatus,
--           mcsMgrAvailabilityStatus,
--           mcsMgrOperationalState,
--           mcsMgrCurrentLp,
--           mcsMgrMaxEps,
--           mcsMgrOverrideNsapAddress,
--           mcsMgrUnknownStatus,
--           mcsMgrAlarmStatus,
--           mcsMgrUsageState,
--           mcsMgrSecurity,
--           mcsMgrControlStatus,
--           mcsMgrAdminState,
--           mcsMgrEpAlarmThreshold,
--           mcsMgrComponentName,
--           mcsMgrStandbyStatus,
--           mcsMgrCanLpsValue,
--           mcsMgrNsapAddress }
-- STATUS  mandatory
-- DESCRIPTION
--   "A list of all current accessible leaf objects."

mcsMgrGroup OBJECT IDENTIFIER ::= { mcsMgrMIB 1 }
mcsMgrGroupBE OBJECT IDENTIFIER ::= { mcsMgrGroup 5 }
mcsMgrGroupBE00 OBJECT IDENTIFIER ::= { mcsMgrGroupBE 1 }
mcsMgrGroupBE00A OBJECT IDENTIFIER ::= { mcsMgrGroupBE00 2 }



-- Agent-Capabilities Statement:

-- PRODUCT-RELEASE "Passport Release 7.0 McsMgr."
-- STATUS          mandatory
-- DESCRIPTION     "McsMgr MIB: MIB Version BE00A,
--                  Software Version BG00S4C."
-- SUPPORTS        Nortel-Magellan-Passport-McsMgrMIB
--    INCLUDES     { mcsMgrGroupBE00A }

mcsMgrCapabilities OBJECT IDENTIFIER ::= { mcsMgrMIB 3 }
mcsMgrCapabilitiesBE OBJECT IDENTIFIER ::= { mcsMgrCapabilities 5 }
mcsMgrCapabilitiesBE00 OBJECT IDENTIFIER ::= { mcsMgrCapabilitiesBE 1 }
mcsMgrCapabilitiesBE00A OBJECT IDENTIFIER ::= { mcsMgrCapabilitiesBE00 2 }





END
