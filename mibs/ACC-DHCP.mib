ACC-DHCP DEFINITIONS ::= BEGIN

    IMPORTS
      OBJECT-TYPE, IpAddress, TimeTicks, Gauge, Counter FROM RFC1155-SMI
		accTrapLogSeqNum FROM ACC-SYSTEM
 accBRG, DisplayString, RowStatus, IfIndex, SmdsAddress
             FROM ACC-MIB;

-- DHCP Group
accDHCP            OBJECT IDENTIFIER ::= { accBRG 55 }
	accDHCPSrvTable		OBJECT-TYPE
		SYNTAX	SEQUENCE OF AccDHCPSrvEntry
		ACCESS	not-accessible
		STATUS	mandatory
		DESCRIPTION
		" A table of DHCP server parameters for IP interfaces."
		::= { accDHCP 1 }
	accDHCPSrvEntry		OBJECT-TYPE
		SYNTAX	AccDHCPSrvEntry
		ACCESS	not-accessible
		STATUS	mandatory
		DESCRIPTION
		" An entry of parameters for a DHCP server interface."
		INDEX	{ accDhcpSrvIfIndex }
		::= { accDHCPSrvTable 1 }
	AccDHCPSrvEntry ::=	SEQUENCE {
					accDhcpSrvIfIndex		INTEGER,
					accDhcpSrvAdmStatus		INTEGER,
					accDhcpSrvOpStatus		INTEGER,
					accDhcpSrvStartIpAddr		IpAddress,
					accDhcpSrvEndIpAddr		IpAddress,
					accDhcpSrvLeaseLen		TimeTicks,
					accDhcpSrvLeaseCnt		Gauge,
					accDhcpSrvRenewals		Counter,
					accDhcpSrvRefusals		Counter,
					accDhcpSrvUnknowns		Counter,
					accDhcpSrvInforms		Counter,
					accDhcpSrvDiscovers		Counter,
					accDhcpSrvRequests		Counter,
					accDhcpSrvReleases		Counter,
					accDhcpSrvDeclines		Counter,
					accDhcpSrvReclaimeds		Counter,
					accDhcpSrvExpireds		Counter,
					accDhcpSrvAcks			Counter,
					accDhcpSrvNacks			Counter,
					accDhcpSrvOffers		Counter,
					accDhcpSrvDomainName		OCTET STRING,
					accDhcpSrvDomainServer		IpAddress,
					accDhcpSrvMessageLevel		INTEGER,
					accDhcpSrvDomainServer1		IpAddress,
					accDhcpSrvDomainServer2		IpAddress,
					accDhcpSrvDomainServer3		IpAddress,
					accDhcpSrvDomainServer4		IpAddress,
					accDhcpSrvNetBiosServer1	IpAddress,
					accDhcpSrvNetBiosServer2	IpAddress,
					accDhcpSrvNetBiosServer3	IpAddress,
					accDhcpSrvNetBiosServer4	IpAddress,
					accDhcpSrvAutoDialPort		INTEGER,
					accDhcpSrvAutoDns1		IpAddress,
					accDhcpSrvAutoDns2		IpAddress,
					accDhcpSrvAutoNbns1		IpAddress,
					accDhcpSrvAutoNbns2		IpAddress
				}
	accDhcpSrvIfIndex		OBJECT-TYPE
		SYNTAX	INTEGER
		ACCESS	read-only
		STATUS	mandatory
		DESCRIPTION
		" The ifIndex of the interface hosting the DHCP server."
		::= { accDHCPSrvEntry 1 }
	accDhcpSrvAdmStatus	OBJECT-TYPE
		SYNTAX	INTEGER {
				enabled(1),
				disabled(2)
			}
		ACCESS	read-write
		STATUS	mandatory
		DESCRIPTION
		" The administrative status of the DHCP server on this interface."
		::= { accDHCPSrvEntry 2 }
	accDhcpSrvOpStatus		OBJECT-TYPE
		SYNTAX	INTEGER {
				enabled(1),
				disabled(2)
			}
		ACCESS	read-only
		STATUS	mandatory
		DESCRIPTION
		" The operational status of the DHCP server on this interface."
		::= { accDHCPSrvEntry 3 }
	accDhcpSrvStartIpAddr	OBJECT-TYPE
		SYNTAX	IpAddress
		ACCESS	read-write
		STATUS	mandatory
		DESCRIPTION
		" The first address in the DHCP server lease range."
		::= { accDHCPSrvEntry 4 }
	accDhcpSrvEndIpAddr	OBJECT-TYPE
		SYNTAX	IpAddress
		ACCESS	read-write
		STATUS	mandatory
		DESCRIPTION
		" The last address in the DHCP server lease range."
		::= { accDHCPSrvEntry 5 }
	accDhcpSrvLeaseLen		OBJECT-TYPE
		SYNTAX	TimeTicks
		ACCESS	read-write
		STATUS	mandatory
		DESCRIPTION
		" The DHCP server current default lease length."
		::= { accDHCPSrvEntry 6 }
	accDhcpSrvLeaseCnt		OBJECT-TYPE
		SYNTAX	Gauge
		ACCESS	read-only
		STATUS	mandatory
		DESCRIPTION
		" The DHCP server current lease count."
		::= { accDHCPSrvEntry 7 }
	accDhcpSrvRenewals		OBJECT-TYPE
		SYNTAX	Counter
		ACCESS	read-only
		STATUS	mandatory
		DESCRIPTION
		" The number of lease renewals by this DHCP server."
		::= { accDHCPSrvEntry 8 }
	accDhcpSrvRefusals		OBJECT-TYPE
		SYNTAX	Counter
		ACCESS	read-only
		STATUS	mandatory
		DESCRIPTION
		" The number of leases refused by this DHCP server."
		::= { accDHCPSrvEntry 9 }
	accDhcpSrvUnknowns		OBJECT-TYPE
		SYNTAX	Counter
		ACCESS	read-only
		STATUS	mandatory
		DESCRIPTION
		" The number of unrecognized requests received by this DHCP server."
		::= { accDHCPSrvEntry 10 }
	accDhcpSrvInforms		OBJECT-TYPE
		SYNTAX	Counter
		ACCESS	read-only
		STATUS	mandatory
		DESCRIPTION
		" The number of inform packets received by this DHCP server."
		::= { accDHCPSrvEntry 11 }
	accDhcpSrvDiscovers	OBJECT-TYPE
		SYNTAX	Counter
		ACCESS	read-only
		STATUS	mandatory
		DESCRIPTION
		" The number of discover packets received by this DHCP server."
		::= { accDHCPSrvEntry 12 }
	accDhcpSrvRequests		OBJECT-TYPE
		SYNTAX	Counter
		ACCESS	read-only
		STATUS	mandatory
		DESCRIPTION
		" The number of request packets received by this DHCP server."
		::= { accDHCPSrvEntry 13 }
	accDhcpSrvReleases		OBJECT-TYPE
		SYNTAX	Counter
		ACCESS	read-only
		STATUS	mandatory
		DESCRIPTION
		" The number of release packets received by this DHCP server."
		::= { accDHCPSrvEntry 14 }
	accDhcpSrvDeclines		OBJECT-TYPE
		SYNTAX	Counter
		ACCESS	read-only
		STATUS	mandatory
		DESCRIPTION
		" The number of decline packets received by this DHCP server."
		::= { accDHCPSrvEntry 15 }
	accDhcpSrvReclaimeds	OBJECT-TYPE
		SYNTAX	Counter
		ACCESS	read-only
		STATUS	mandatory
		DESCRIPTION
		" The number of reclaimed leases on this DHCP server."
		::= { accDHCPSrvEntry 16 }
	accDhcpSrvExpireds		OBJECT-TYPE
		SYNTAX	Counter
		ACCESS	read-only
		STATUS	mandatory
		DESCRIPTION
		" The number of expired leases on this DHCP server."
		::= { accDHCPSrvEntry 17 }
	accDhcpSrvAcks		OBJECT-TYPE
		SYNTAX	Counter
		ACCESS	read-only
		STATUS	mandatory
		DESCRIPTION
		" The number of acknowledge packets sent by this DHCP server."
		::= { accDHCPSrvEntry 18 }
	accDhcpSrvNacks		OBJECT-TYPE
		SYNTAX	Counter
		ACCESS	read-only
		STATUS	mandatory
		DESCRIPTION
		" The number of negative acknowledge packets sent by this DHCP server."
		::= { accDHCPSrvEntry 19 }
	accDhcpSrvOffers		OBJECT-TYPE
		SYNTAX	Counter
		ACCESS	read-only
		STATUS	mandatory
		DESCRIPTION
		" The number of lease offers made by this DHCP server."
		::= { accDHCPSrvEntry 20 }
	accDhcpSrvDomainName	OBJECT-TYPE
		SYNTAX	OCTET STRING
		ACCESS	read-write
		STATUS	mandatory
		DESCRIPTION
		" The domain name provided by this DHCP server."
		::= { accDHCPSrvEntry 21 }
	accDhcpSrvDomainServer	OBJECT-TYPE
		SYNTAX	IpAddress
		ACCESS	read-write
		STATUS	mandatory
		DESCRIPTION
		" The primary domain server address provided by this 
		  DHCP server."
		::= { accDHCPSrvEntry 22 }
	accDhcpSrvMessageLevel	OBJECT-TYPE
		SYNTAX	INTEGER (1..7)
		ACCESS	read-write
		STATUS	mandatory
		DESCRIPTION
		" The current message level set for this DHCP server."
		::= { accDHCPSrvEntry 23 }
	accDhcpSrvDomainServer1	OBJECT-TYPE
		SYNTAX	IpAddress
		ACCESS	read-write
		STATUS	mandatory
		DESCRIPTION
		" The primary domain server address provided by this 
		  DHCP server."
		::= { accDHCPSrvEntry 24 }
	accDhcpSrvDomainServer2	OBJECT-TYPE
		SYNTAX	IpAddress
		ACCESS	read-write
		STATUS	mandatory
		DESCRIPTION
		" The secondary domain server address provided by this 
		  DHCP server."
		::= { accDHCPSrvEntry 25 }
	accDhcpSrvDomainServer3	OBJECT-TYPE
		SYNTAX	IpAddress
		ACCESS	read-write
		STATUS	mandatory
		DESCRIPTION
		" The third domain server address provided by this 
		  DHCP server."
		::= { accDHCPSrvEntry 26 }
	accDhcpSrvDomainServer4	OBJECT-TYPE
		SYNTAX	IpAddress
		ACCESS	read-write
		STATUS	mandatory
		DESCRIPTION
		" The fourth domain server address provided by this 
		  DHCP server."
		::= { accDHCPSrvEntry 27 }
	accDhcpSrvNetBiosServer1	OBJECT-TYPE
		SYNTAX	IpAddress
		ACCESS	read-write
		STATUS	mandatory
		DESCRIPTION
		" The primary NetBios name server address provided by this 
		  DHCP server."
		::= { accDHCPSrvEntry 28 }
	accDhcpSrvNetBiosServer2	OBJECT-TYPE
		SYNTAX	IpAddress
		ACCESS	read-write
		STATUS	mandatory
		DESCRIPTION
		" The secondary NetBios name server address provided by this 
		  DHCP server."
		::= { accDHCPSrvEntry 29 }
	accDhcpSrvNetBiosServer3	OBJECT-TYPE
		SYNTAX	IpAddress
		ACCESS	read-write
		STATUS	mandatory
		DESCRIPTION
		" The third NetBios name server address provided by this 
		  DHCP server."
		::= { accDHCPSrvEntry 30 }
	accDhcpSrvNetBiosServer4	OBJECT-TYPE
		SYNTAX	IpAddress
		ACCESS	read-write
		STATUS	mandatory
		DESCRIPTION
		" The fourth NetBios name server address provided by this 
		  DHCP server."
		::= { accDHCPSrvEntry 31 }
	accDhcpSrvAutoDialPort	OBJECT-TYPE
		SYNTAX	INTEGER 
		ACCESS	read-write
		STATUS	mandatory
		DESCRIPTION
		" The ifIndex of the Dial Port used for automatic 
		  DHCP Server configuration"
		::= { accDHCPSrvEntry 32 }
	accDhcpSrvAutoDns1	OBJECT-TYPE
		SYNTAX	IpAddress
		ACCESS	read-only
		STATUS	mandatory
		DESCRIPTION
		" The primary domain server address automatically obtained
		by this DHCP server."
		::= { accDHCPSrvEntry 33 }
	accDhcpSrvAutoDns2	OBJECT-TYPE
		SYNTAX	IpAddress
		ACCESS	read-only
		STATUS	mandatory
		DESCRIPTION
		" The secondary domain server address automatically obtained
		by this DHCP server."
		::= { accDHCPSrvEntry 34 }
	accDhcpSrvAutoNbns1	OBJECT-TYPE
		SYNTAX	IpAddress
		ACCESS	read-only
		STATUS	mandatory
		DESCRIPTION
		" The primary NetBios name server address automatically 
		obtained by this DHCP server."
		::= { accDHCPSrvEntry 35 }
	accDhcpSrvAutoNbns2	OBJECT-TYPE
		SYNTAX	IpAddress
		ACCESS	read-only
		STATUS	mandatory
		DESCRIPTION
		" The secondary NetBios name server address automatically 
		obtained by this DHCP server."
		::= { accDHCPSrvEntry 36 }
	accDHCPSrvLeaseTable	OBJECT-TYPE
 		SYNTAX	SEQUENCE OF AccDHCPSrvLeaseEntry
 		ACCESS	not-accessible
 		STATUS	mandatory
 		DESCRIPTION
 		" A table of DHCP server leases."
 		::= { accDHCP 2 }
	accDHCPSrvLeaseEntry	OBJECT-TYPE
		SYNTAX	AccDHCPSrvLeaseEntry
		ACCESS	not-accessible
		STATUS	mandatory
		DESCRIPTION
		" An entry for a DHCP server lease."
		INDEX	{ accDhcpSrvLeaseTblIndex }
		::= { accDHCPSrvLeaseTable 1 }
	AccDHCPSrvLeaseEntry ::= SEQUENCE {
				accDhcpSrvLeaseTblAddr		IpAddress,
				accDhcpSrvLeaseTblIndex		INTEGER,
				accDhcpSrvLeaseTblClient	OCTET STRING,
				accDhcpSrvLeaseTblTime		TimeTicks
				}
	accDhcpSrvLeaseTblAddr	OBJECT-TYPE
		SYNTAX	IpAddress
		ACCESS	read-only
		STATUS	mandatory
		DESCRIPTION
		" A current leased address on this DHCP server."
		::= { accDHCPSrvLeaseEntry 1 }
	accDhcpSrvLeaseTblIndex	OBJECT-TYPE
		SYNTAX	INTEGER
		ACCESS	read-only
		STATUS	mandatory
		DESCRIPTION
		" The index of this leased address on this DHCP server."
		::= { accDHCPSrvLeaseEntry 2 }
	accDhcpSrvLeaseTblClient	OBJECT-TYPE
		SYNTAX	OCTET STRING
		ACCESS	read-only
		STATUS	mandatory
		DESCRIPTION
		" The client ID of this leased address on this DHCP server."
		::= { accDHCPSrvLeaseEntry 3 }
	accDhcpSrvLeaseTblTime	OBJECT-TYPE
		SYNTAX	TimeTicks
		ACCESS	read-only
		STATUS	mandatory
		DESCRIPTION
		" The current lease time remaining for this address on this DHCP server."
		::= { accDHCPSrvLeaseEntry 4 }

END
