NETGEAR-QOS-MIB DEFINITIONS ::= BEGIN

-- NETGEAR Quality of Service Package MIB
-- Copyright LVL7 Systems (2001-2005) All rights reserved.

-- This SNMP Management Information Specification
-- embodies LVL7 System's confidential and proprietary
-- intellectual property.  LVL7 Systems retains all title
-- and ownership in the Specification including any revisions.

-- This Specification is supplied "AS IS", LVL7 Systems
-- makes no warranty, either expressed or implied,
-- as to the use, operation, condition, or performance of the
-- Specification.


IMPORTS
    MODULE-IDENTITY, OBJECT-TYPE, NOTIFICATION-TYPE, Integer32, Gauge32        
                                        FROM SNMPv2-SMI
    RowStatus                           FROM SNMPv2-TC
    ng7000Switch                        FROM NETGEAR-REF-MIB
    DisplayString                       FROM RFC1213-MIB;
                
    agentQOS MODULE-IDENTITY
    LAST-UPDATED "200502231200Z" -- 23 Feb 2005 12:00:00 GMT
    ORGANIZATION "Netgear"
    CONTACT-INFO
       ""
        
    DESCRIPTION
       "The MIB definitaions for Quality of Service Flex package."
       
    -- revision history
    REVISION
       "200502231200Z" -- 23 Feb 2005 12:00:00 GMT
   	DESCRIPTION
       "Initial revision."
       
    ::= { ng7000Switch 3 }
      
END
