-- 
-- Copyright 1999 by Fore Systems, Inc. 
-- Converted to SMIv2 rfc 2578,2579,2580 - STD 58
--
--
--
-- Copyright (c) 1993-1999 FORE Systems, Inc., as an unpublished work.
-- This notice does not imply unrestricted or public access to these
-- materials which are a trade secret of FORE Systems, Inc. or its
-- subsidiaries or affiliates (together referred to as "FORE"), and
-- which may not be reproduced, used, sold or transferred to any third
-- party without FORE's prior written consent.
--
-- All rights reserved.
--
-- U.S. Government Restricted Rights.  If you are licensing the
-- Software on behalf of the U.S. Government ("Government"), the
-- following provisions apply to you.  If the Software is supplied to
-- the Department of Defense ("DoD"), it is classified as "Commercial
-- Computer Software" under paragraph 252.227-7014 of the DoD Supplement
-- to the Federal Acquisition Regulations ("DFARS") (or any successor
-- regulations) and the Government is acquiring only the license
-- rights granted herein (the license rights customarily provided to
-- non-Government users).  If the Software is supplied to any unit
-- or agency of the Government other than DoD, it is classified as
-- "Restricted Computer Software" and the Government's rights in the
-- Software are defined in paragraph 52.227-19 of the Federal Acquisition
-- Regulations ("FAR") (or any successor regulations) or, in the cases
-- of NASA, in paragraph 18.52.227-86 of the NASA Supplement to the FAR
-- (or any successor regulations).
--

Fore-Asxethernet-MIB DEFINITIONS ::= BEGIN

IMPORTS
        MODULE-IDENTITY,
        OBJECT-TYPE         FROM SNMPv2-SMI
	software	    FROM Fore-Common-MIB
	ifIndex             FROM IF-MIB;

asxEthernetAutoNegotiate  MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "Fore Switch ASX extensions to the etherlike mib."
	  ::= { software 5 }

---------------------------------------------------------------
-- MIB Types Definitions

-- AsxEthernetModes ::= TEXTUAL-CONVENTION
--	STATUS current
--	DESCRIPTION
--		"The different modes of an ethernet port on an Alchemy blade.
--		Auto stands for values derived from auto negotiation"
--    SYNTAX  INTEGER{ tenHalfDuplex(1),
--		     tenFullDuplex(2),
--		     hundredHalfDuplex(3),
--		     hundredFullDuplex(4),
--		     auto(5)}

AsxEthernetModes ::= INTEGER {
		    tenHalfDuplex(1),
		    tenFullDuplex(2),
		    hundredHalfDuplex(3),
		    hundredFullDuplex(4),
		    auto(5)
		}

---------------------------------------------------------------
-- MIB Groups

-----------------------------------------------------------------------
-- The Auto Negotiation Table
asxEthernetAutoNegotiationTable OBJECT-TYPE
	SYNTAX  SEQUENCE OF AsxEthernetAutoNegotiationEntry
	MAX-ACCESS  not-accessible
	STATUS  current
	DESCRIPTION
		"A table that contains the auto negotiation informtion about
		every port of a given alchemy blade."
	::= { asxEthernetAutoNegotiate 1 }

asxEthernetAutoNegotiationEntry OBJECT-TYPE
	SYNTAX  AsxEthernetAutoNegotiationEntry
	MAX-ACCESS  not-accessible
	STATUS  current
	DESCRIPTION
		"A list of auto negotiation information  that is maintained
		per port per blade. The configuration information of the port
		is also mainatained."
	INDEX   { ifIndex }
	::= { asxEthernetAutoNegotiationTable 1 }

AsxEthernetAutoNegotiationEntry ::=
	SEQUENCE {
		asxEthernetConfigModes          AsxEthernetModes,
		asxEthernetOperStatus           AsxEthernetModes,
		asxEthernetLinkState            INTEGER,
		asxEthernetRemoteAutoNeg    INTEGER,
		asxEthernetRemoteOperStatus INTEGER
		}

asxEthernetConfigModes OBJECT-TYPE
    SYNTAX  AsxEthernetModes
    MAX-ACCESS  read-write
    STATUS  current
    DESCRIPTION
		"The mode which the port should be configured to.
		The default mode is auto."
	::= { asxEthernetAutoNegotiationEntry 1 }

asxEthernetOperStatus OBJECT-TYPE
    SYNTAX  AsxEthernetModes
    MAX-ACCESS  read-only
    STATUS  current
    DESCRIPTION
		"The actual operational mode of this port. Note that the
		values for this object are invalid if the asxEthernetLinkState
		is link-down."
	::= { asxEthernetAutoNegotiationEntry 2 }

asxEthernetLinkState OBJECT-TYPE
    SYNTAX  INTEGER {
			link-up(1),
			link-down(2)
		    }
    MAX-ACCESS  read-only
    STATUS  current
    DESCRIPTION
		"This object signifies if the link on the specified port is
		actually up or down"
	::= { asxEthernetAutoNegotiationEntry 3 }

asxEthernetRemoteAutoNeg OBJECT-TYPE
    SYNTAX  INTEGER {
			detected(1),
			not-detected(2)
		    }
    MAX-ACCESS  read-only
    STATUS  current
    DESCRIPTION
		"This object signifies whether the remote end of the link is
		using auto-negotiation."
	::= { asxEthernetAutoNegotiationEntry 4 }

asxEthernetRemoteOperStatus OBJECT-TYPE
    SYNTAX  INTEGER {
			other(0),               -- other or unknown
			tenHalfDuplex(1),       -- 10BASE-T  half duplex mode
			tenFullDuplex(2),       -- 10BASE-T  full duplex mode
			hundredHalfDuplex(3),   -- 100BASE-TX half duplex mode
			hundredFullDuplex(4)    -- 100BASE-TX full duplex mode
		    }
    MAX-ACCESS  read-only
    STATUS  current
    DESCRIPTION
		"The actual operational mode of the remote end of this
		link. The value of this object is invalid if the
		asxEthernetRemoteAutoNeg is not-detected."
	::= { asxEthernetAutoNegotiationEntry 5 }

END
