SVCEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32, IpAddress
			FROM SNMPv2-SMI
		DisplayString, RowStatus
			FROM SNMPv2-TC
		TRAP-TYPE
			FROM RFC-1215
		svcExt
			FROM APENT-MIB;


--SVCEXT MIB

    apSvcExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  content services table"
      ::= { svcExt 1}


apSvcTable OBJECT-TYPE
	SYNTAX          SEQUENCE OF APSvcEntry
	MAX-ACCESS      not-accessible
	STATUS          current
	DESCRIPTION
		"A list of content service entries."
	::= { svcExt 2 }

apSvcEntry OBJECT-TYPE
	SYNTAX          APSvcEntry
	MAX-ACCESS      not-accessible
	STATUS          current
	DESCRIPTION
		"A group of information to uniquely identify a content providing 
		service."
	INDEX   { apSvcName }
	--DEFAULT apjam-group apServicesGroupInst, apSvcName
	--DEFAULT apjam-popup-def apServicesGroupInst, Properties, local, Advanced
	--DEFAULT apjam-popup-def apServicesGroupInst, Delete, special, apSvcStatus
	--DEFAULT apjam-wizard	Service Wizard, 1, images/arrowlogo.gif, "Service provide the content for a website."
	--DEFAULT apjam-wizard	Service Wizard, 2, images/arrowlogo.gif, ""
	--DEFAULT apjam-group-code  // add define of delete message.
	--DEFAULT apjam-group-code  public String getDeleteMessage()
	--DEFAULT apjam-group-code  {
	--DEFAULT apjam-group-code      return( new String("Please make sure that the service is not referenced by a content rule."));
	--DEFAULT apjam-group-code  }
	::= { apSvcTable 1 }

APSvcEntry ::= SEQUENCE {
		apSvcName                    DisplayString,
		apSvcIndex                   Integer32,
		apSvcIPAddress               IpAddress,
		apSvcIPProtocol              INTEGER,
		apSvcPort                    Integer32,
		apSvcKALType                 INTEGER,
		apSvcKALFrequency            Integer32,
		apSvcKALMaxFailure           Integer32,
		apSvcKALRetryPeriod          Integer32,
		apSvcKALUri	                 DisplayString,
		apSvcKALMethod               INTEGER,
		apSvcEnable                  INTEGER,
		apSvcType                    INTEGER,
		apSvcQOSMinRate              Integer32,
		apSvcQOSMinBW                Integer32,
		apSvcWeight                  Integer32,
		apSvcState                   INTEGER,
		apSvcShortLoad               Integer32,
        apSvcMaxConnections          Integer32,
		apSvcConnections             Integer32,
		apSvcTransitions             Integer32,
		apSvcMaxContent              Integer32,
		apSvcMaxUsage                Integer32,
		apSvcMaxAge                  Integer32,
		apSvcAccessRecordName        DisplayString,
		apSvcStatus                  RowStatus,
		apSvcCookie                  DisplayString,
		apSvcKALPersistence          INTEGER,
        apSvcKALName                 DisplayString,
		apSvcLongLoad                Integer32,
		apSvcKALPort                 Integer32,
        apSvcPublishName             DisplayString,
        apSvcPublishState            INTEGER,
		apSvcPublishInterval		 Integer32,
		apSvcAccessType              INTEGER,
		apSvcKALHash                 DisplayString,
		apSvcKALFTPRecord            DisplayString,
		apSvcPublishFile             DisplayString,
		apSvcRedirectDomain          DisplayString,
		apSvcAvgLoad                 Integer32,
		apSvcIPAddressRange          INTEGER,
		apSvcPortRange               INTEGER,
		apSvcKALScriptName	     	 DisplayString,	
		apSvcKALScriptArgs	     	 DisplayString,
	    apSvcKALScriptLog            DisplayString,
		apSvcCacheByPass		INTEGER
}

apSvcName OBJECT-TYPE
	SYNTAX          DisplayString (SIZE(1..31))
	MAX-ACCESS      read-create
	STATUS          current
	DESCRIPTION     
			"The name of the content providing service."
	--DEFAULT ap-display-name	Name
	--DEFAULT apjam-popup-ref apServicesGroupInst, Properties
	--DEFAULT ap-create-requires Yes
	--DEFAULT apjam-noedit-dlg	True
	--DEFAULT apjam-wizard-field	1, normal
	::= {apSvcEntry 1}

apSvcIndex OBJECT-TYPE
	SYNTAX          Integer32
	MAX-ACCESS      read-only
	STATUS  		current
	DESCRIPTION     
		"The unique service index assigned to the name by the SCM."
	::= {apSvcEntry 2}

apSvcIPAddress OBJECT-TYPE
	SYNTAX          IpAddress
	MAX-ACCESS      read-create
	STATUS  		current
	DESCRIPTION     
		"The IP Address the of the content providing service."
	--DEFAULT ap-display-name	IP Address
	--DEFAULT apjam-popup-ref apServicesGroupInst, Properties
	--DEFAULT apjam-wizard-field	1, normal
	::= {apSvcEntry 3}

apSvcIPProtocol OBJECT-TYPE
	SYNTAX          INTEGER {
							any (0),
							tcp (6),
							udp (17)
							}
	MAX-ACCESS      read-create
	STATUS  		current
	DESCRIPTION     
		"The IP Protocol the of the content providing service."
	DEFVAL { any }
	--DEFAULT ap-display-name	Protocol
	--DEFAULT apjam-popup-ref apServicesGroupInst, Properties
	--DEFAULT apjam-wizard-field	1, normal
	::= {apSvcEntry 4}

apSvcPort OBJECT-TYPE
	SYNTAX          Integer32 (0..65535)
	MAX-ACCESS      read-create
	STATUS  		current
	DESCRIPTION     
		"The UDP or TCP port of the content providing service."
	--DEFAULT ap-display-name	Port
	--DEFAULT apjam-popup-ref apServicesGroupInst, Properties
	--DEFAULT apjam-wizard-field	1, normal
	::= {apSvcEntry 5}

apSvcKALType OBJECT-TYPE
	SYNTAX  INTEGER {
	                none(0)                           ,
					icmp(1)                                         ,
					http(2)                            ,
					ftp(3)                           ,
				    tcp(4)                           ,
					named(5)                             ,
					script(6)                              
					}
	MAX-ACCESS      read-create
	STATUS 			current
	DESCRIPTION     
		"The Keepalive detection method."
	DEFVAL { icmp }
	--DEFAULT ap-display-name	Keepalive Method
	--DEFAULT apjam-popup-ref apServicesGroupInst, Properties
	--DEFAULT apjam-wizard-field	2, normal
	::= {apSvcEntry  6}

apSvcKALFrequency OBJECT-TYPE
	SYNTAX          Integer32 (2..255)
	MAX-ACCESS      read-create
	STATUS  		current
	DESCRIPTION     
		"The Keepalive frequency of doing keepalive probes in units of seconds."
	DEFVAL { 5 }
	--DEFAULT ap-display-name	Keepalive Frequency
	--DEFAULT apjam-popup-ref apServicesGroupInst, Properties, Advanced
	::= {apSvcEntry 7}

apSvcKALMaxFailure OBJECT-TYPE
	SYNTAX          Integer32 (1..10)
	MAX-ACCESS      read-create
	STATUS  		current
	DESCRIPTION     
		"The Keepalive maximum number of failures before the service is 
		transitioned to failed state."
	DEFVAL { 3 }
	--DEFAULT ap-display-name	Keepalive Max Failures
	--DEFAULT apjam-popup-ref apServicesGroupInst, Properties, Advanced
	::= {apSvcEntry 8}

apSvcKALRetryPeriod OBJECT-TYPE
	SYNTAX          Integer32 (2..255)
	MAX-ACCESS      read-create
	STATUS  		current
	DESCRIPTION     
		"The Keepalive frequency of probes to the service after it has been
		transitioned to failed state."
	DEFVAL { 5 }
	--DEFAULT ap-display-name	Keepalive Retry Period
	--DEFAULT apjam-popup-ref apServicesGroupInst, Properties, Advanced
	::= {apSvcEntry 9}

apSvcKALUri OBJECT-TYPE
	SYNTAX          DisplayString (SIZE(0..64))
	MAX-ACCESS      read-create
	STATUS          current
	DESCRIPTION     
			"The URI which be checked during an HTTP keepalive."
	--DEFAULT ap-display-name	Keepalive HTTP Uri
	--DEFAULT apjam-popup-ref apServicesGroupInst, Properties
	--DEFAULT apjam-wizard-field	2, normal
	::= {apSvcEntry 10}

apSvcKALMethod  OBJECT-TYPE
	SYNTAX  INTEGER {
					head(0)                   ,
					get(1)                                 ,
					post(2)                                  
 					}
	MAX-ACCESS      read-create
	STATUS 			current
	DESCRIPTION     
		"The HTTP method used for the HTTP keepalive type.  The 
         methods operate in the following manner:
         HEAD -- HTTP HEAD generated.  200 response code required
         GET  -- HTTP GET generated.  MD5 Hash of entify body performed.
                 First successful GET (200 response code) becomes reference 
                 hash.  Deviation from rererence hash result, or non-200
                 response code, results in service state transition.
         POST -- Same as GET with substituation of POST method."
	DEFVAL { head }
	--DEFAULT ap-display-name	HTTP Keepalive Method
	--DEFAULT apjam-popup-ref apServicesGroupInst, Properties
	--DEFAULT apjam-wizard-field	2, normal
	::= {apSvcEntry  11}

apSvcEnable  OBJECT-TYPE
	SYNTAX  INTEGER {
					disable(0),
					enable(1)
 					}
	MAX-ACCESS      read-create
	STATUS 			current
	DESCRIPTION     
		"The state of the service, either enable or disabled"
	DEFVAL { disable }
	--DEFAULT ap-display-name	Status
	--DEFAULT apjam-popup-ref apServicesGroupInst, Properties
	--DEFAULT apjam-wizard-field	2, normal
	::= {apSvcEntry  12}

apSvcType  OBJECT-TYPE
	SYNTAX  INTEGER {
					local(1),
					redirect(2),
					proxyCache(4),
					transparentCache(8),
					automaticRedirect(16),
					replicationStore(32),
					replicationCache(64),
					smashCache(128),
					redundancyUp(256),
					nciInfoOnly(512),
					nciDirectReturn(1024),
					replicationStoreRedirect(2048),
					replicationCacheRedirect(4096)
					}
	MAX-ACCESS      read-create
	STATUS 			current
	DESCRIPTION     
		"The type of this server"
	DEFVAL { local }
	--DEFAULT ap-display-name	Service Type
	--DEFAULT apjam-popup-ref apServicesGroupInst, Properties
	--DEFAULT apjam-wizard-field	2, normal
	::= {apSvcEntry  13}

apSvcQOSMinRate OBJECT-TYPE
	SYNTAX          Integer32
	MAX-ACCESS      read-create
	STATUS  		current
	DESCRIPTION     
		"The Average Minimum Bandwidth Rate for this service"
	DEFVAL { 14400 }
	--DEFAULT ap-display-name	Avg Bandwidth Rate
	--DEFAULT apjam-popup-ref apServicesGroupInst, Properties, Advanced
	::= {apSvcEntry 14}

apSvcQOSMinBW OBJECT-TYPE
	SYNTAX          Integer32
	MAX-ACCESS      read-create
	STATUS  		current
	DESCRIPTION     
		"The Total Bandwidth of this service"
	DEFVAL { 100000000 }
	--DEFAULT ap-display-name	Min Bandwidth
	--DEFAULT apjam-popup-ref apServicesGroupInst, Properties, Advanced
	::= {apSvcEntry 15}

apSvcWeight OBJECT-TYPE
	SYNTAX          Integer32 (1..10)
	MAX-ACCESS      read-create
	STATUS  		current
	DESCRIPTION     
		"The Service weight which is used in conjunction with load metrics when
		 making load allocation decisions.  The weight may be used to bias flows 
		 towards the specified service ."
	DEFVAL { 1 }
	--DEFAULT ap-display-name	Service Weight
	--DEFAULT apjam-popup-ref apServicesGroupInst, Properties, Advanced
	--DEFAULT apjam-wizard-field	2, normal
	::= {apSvcEntry 16}

apSvcState  OBJECT-TYPE
	SYNTAX  INTEGER {
					suspended(1),
					down(2),
					alive(4),
					dying(5)
 					}
	MAX-ACCESS      read-only
	STATUS 			current
	DESCRIPTION     
		"The current service state"
	DEFVAL { suspended }
	::= {apSvcEntry 17}

apSvcShortLoad OBJECT-TYPE
	SYNTAX          Integer32 (2..255)
	MAX-ACCESS      read-only
	STATUS  		current
	DESCRIPTION     
		"The Service currently sensed load for Short Lived Flows"
	DEFVAL { 2 }
	--DEFAULT ap-display-name	Service Load
	::= {apSvcEntry 18}

apSvcMaxConnections OBJECT-TYPE
	SYNTAX          Integer32 (0..65535)
	MAX-ACCESS      read-create
	STATUS  		current
	DESCRIPTION     
		"The maximum concurrent number of TCP connections allowed to this service"
	DEFVAL { 0 }
	--DEFAULT ap-display-name	Max Service Connections
	::= {apSvcEntry 19}

apSvcConnections OBJECT-TYPE
	SYNTAX          Integer32
	MAX-ACCESS      read-only
	STATUS  		current
	DESCRIPTION     
		"The current number of TCP connections to this service"
	DEFVAL { 0 }
	--DEFAULT ap-display-name	Service Connections
	::= {apSvcEntry 20}

apSvcTransitions OBJECT-TYPE
	SYNTAX          Integer32
	MAX-ACCESS      read-only
	STATUS  		current
	DESCRIPTION     
		"The number of service state transitions that have occurred"
	DEFVAL { 0 }
	--DEFAULT ap-display-name	Service Transitions
	::= {apSvcEntry 21}

apSvcMaxContent OBJECT-TYPE
	SYNTAX          Integer32 (1..65535)
	MAX-ACCESS      read-create
	STATUS  		current
	DESCRIPTION     
		"Maximum pieces of content permitted to be replicated upon this
         service.  This object only has validity when this service is 
         configured to have type replication.  The pieces of content
         replicated may by limited by apSvcMaxUsage prior to this object,
         where the limiting is the min(apSvcMaxContent,apSvcMaxUsage)."
	DEFVAL { 100 }
	::= {apSvcEntry 22}

apSvcMaxUsage OBJECT-TYPE
	SYNTAX          Integer32 (1..1000)
	MAX-ACCESS      read-create
	STATUS  		current
	DESCRIPTION     
		"Maximum storage space in MB which may be replicated upon this
         service.  This object only has validity when the this service
         is configured to have type replication.  The storage space usage
         may be limited by apSvcMaxContent prior to this object,
         where the limiting is the min(apSvcMaxUsage,apSvcMaxContent)."
	DEFVAL { 1 }
	::= {apSvcEntry 23}

apSvcMaxAge OBJECT-TYPE
	SYNTAX          Integer32 (1..1440)
	MAX-ACCESS      read-create
	STATUS  		current
	DESCRIPTION     
		"The time in minutes replicated content may exist upon this service
         before it is aged out.  This age out time is applied on a per-
         replicated-content basis."
	DEFVAL { 120 }
	::= {apSvcEntry 24}

apSvcAccessRecordName OBJECT-TYPE
	SYNTAX          DisplayString (SIZE(0..16))
	MAX-ACCESS      read-create
	STATUS  		current
	DESCRIPTION     
		"An access record name, present in apFtpTable or apHttpTable, 
         used for replication access when this service is configured to be 
         of type replicationStore, publisher or subscriber"
	::= {apSvcEntry 25}

apSvcStatus OBJECT-TYPE
	SYNTAX          RowStatus
	MAX-ACCESS      read-create
	STATUS          current
	DESCRIPTION      
		"Status entry for this row "
	::= {apSvcEntry 26}

apSvcCookie OBJECT-TYPE
	SYNTAX          DisplayString (SIZE(0..15))
	MAX-ACCESS      read-create
	STATUS          current
	DESCRIPTION     
			"The unique server cookie for this service."
	::= {apSvcEntry 27 }

apSvcKALPersistence  OBJECT-TYPE
	SYNTAX  INTEGER {
					non-persistent(0)                                              ,
					persistent(1)                                        
 					}
	MAX-ACCESS      read-create
	STATUS 			current
	DESCRIPTION     
		"This object controls whether the Keepalive will be attempted over
         a persistent connection.  Persistent connections are supported 
         through HTTP 1.1, and HTTP 1.0 with Connection-KeepAlive"
	DEFVAL { persistent }
	::= {apSvcEntry  28}

apSvcKALName  OBJECT-TYPE
	SYNTAX          DisplayString (SIZE(0..31))
	MAX-ACCESS      read-create
	STATUS          current
	DESCRIPTION     
		"The name of the keepalive that this service will use."
	::= {apSvcEntry  29}

apSvcLongLoad OBJECT-TYPE
	SYNTAX          Integer32 (2..255)
	MAX-ACCESS      read-only
	STATUS  		current
	DESCRIPTION     
		"The Service currently sensed load for Long Lived Flows"
	DEFVAL { 2 }
	::= {apSvcEntry 30}

apSvcKALPort OBJECT-TYPE
	SYNTAX          Integer32 (0..65535)
	MAX-ACCESS      read-create
	STATUS  		current
	DESCRIPTION     
		"The port to use, for TCP & HTTP keepalives.
         This KAL port designation does not impact 'named' keep-
         alive configurations.  If this object is not configured, keep-
         alive configurations will utilize the apSvcPort object if present,
         or default to 80"
	DEFVAL { 0 }
	::= {apSvcEntry 31}

apSvcPublishName OBJECT-TYPE
	SYNTAX          DisplayString (SIZE(0..32))
	MAX-ACCESS      read-create
	STATUS  		current
	DESCRIPTION
      "The name used to identify the service which publishes for this
       subscriber.  This object is used in conjunction with 
       apSvcPublishState."     
	::= {apSvcEntry 32}

apSvcPublishState OBJECT-TYPE
	SYNTAX          INTEGER {
                              none(0),
                              publisher(1),
                              subscriber(2)
                            }
	MAX-ACCESS      read-create
	STATUS  		current
	DESCRIPTION
      "The state of this service in relation to publish/subscribe activity."
	DEFVAL { none }	
	::= {apSvcEntry 33}

apSvcPublishInterval OBJECT-TYPE
	SYNTAX          Integer32 (0..3600)
	MAX-ACCESS      read-create
	STATUS  		current
	DESCRIPTION     
		"When this service is configured as a publisher, controls when
         the publisher will attempt to update the subscribers. When this
         object contains the value 0, it is interpreted as OFF."
	DEFVAL { 0 }
	::= {apSvcEntry 34}

apSvcAccessType OBJECT-TYPE
	SYNTAX          INTEGER {
                             ftp-access(0),
                             http-access(1),
                             no-access(2)
                            }
	MAX-ACCESS      read-create
	STATUS  		current
	DESCRIPTION     
		"Specifies whether the access mechanism associated with this service
         is of type HTTP or FTP"
	DEFVAL { 0 }
	::= {apSvcEntry 35}

apSvcKALHash OBJECT-TYPE
	SYNTAX          DisplayString(SIZE(0..32))
	MAX-ACCESS      read-create
	STATUS  		current
	DESCRIPTION     
		"This object contains the MD5 hash which will be compared for
         HTTP keepalives which use the GET method."
	::= {apSvcEntry 36}

apSvcKALFTPRecord OBJECT-TYPE
	SYNTAX          DisplayString(SIZE(0..16))
	MAX-ACCESS      read-create
	STATUS  		current
	DESCRIPTION     
		"This object contains the name of the ftp-record used for a FTP 
         keepalive"
	::= {apSvcEntry 37}

apSvcPublishFile OBJECT-TYPE
	SYNTAX          DisplayString(SIZE(0..64))
	MAX-ACCESS      read-create
	STATUS  		current
	DESCRIPTION     
		"This object contains the name of the file which the publisher will
         check for modification on to commence a publish operation.  This 
         object is used in conjunction with apSvcPublishInterval"
	::= {apSvcEntry 38}


apSvcRedirectDomain OBJECT-TYPE
	SYNTAX          DisplayString (SIZE(0..64))
	MAX-ACCESS      read-create
	STATUS          current
	DESCRIPTION     
			"The domain name used when a redirect service generates an 
             object moved redirect instead of the service address."
	::= {apSvcEntry 39 }

apSvcAvgLoad OBJECT-TYPE
	SYNTAX          Integer32 (2..255)
	MAX-ACCESS      read-only
	STATUS  		current
	DESCRIPTION     
		"The Service currently sensed average load"
	DEFVAL { 2 }
	::= {apSvcEntry 40}

apSvcIPAddressRange OBJECT-TYPE
	SYNTAX          INTEGER (1..65535)
	MAX-ACCESS      read-create
	STATUS  		current
	DESCRIPTION     
		"The range of IP Addresses of the content providing service."
	DEFVAL { 1 }
	--DEFAULT ap-display-name	IP Address Range
	--DEFAULT apjam-popup-ref apServicesGroupInst, Properties
	--DEFAULT apjam-wizard-field	1, normal
	::= {apSvcEntry 41}

apSvcPortRange OBJECT-TYPE
	SYNTAX          INTEGER (1..65535)
	MAX-ACCESS      read-create
	STATUS  		current
	DESCRIPTION     
		"The range of UDP or TCP ports of the content providing service."
	DEFVAL { 1 }
	--DEFAULT ap-display-name	Port Range
	--DEFAULT apjam-popup-ref apServicesGroupInst, Properties
	--DEFAULT apjam-wizard-field	1, normal
	::= {apSvcEntry 42}

apSvcKALScriptName  OBJECT-TYPE
	SYNTAX          DisplayString (SIZE(0..32))
	MAX-ACCESS      read-create
	STATUS          current
	DESCRIPTION     
		"This name represents the script that will be used in conjunction with
        the keepalive type script.  The script will be played everytime the keepalive
        is issued."
	::= {apSvcEntry  43}


apSvcKALScriptArgs OBJECT-TYPE
	SYNTAX          DisplayString(SIZE(0..128))
	MAX-ACCESS      read-create
	STATUS  		current
	DESCRIPTION     
		"This name represents the script arguments that will be used in conjunction
        with the keepalive type script."
	::= {apSvcEntry 44}


apSvcKALScriptLog OBJECT-TYPE
	SYNTAX          DisplayString(SIZE(0..32))
	MAX-ACCESS      read-create
	STATUS  		current
	DESCRIPTION     
		"This name represents the script log that can be used to capture output
        from a keepalive script."
	::= {apSvcEntry 45}


apSvcCacheByPass  OBJECT-TYPE
	SYNTAX  INTEGER {
				disable(0),
				enable(1)
 			}
	MAX-ACCESS      read-create
	STATUS 		current
	DESCRIPTION     
		"Controls whether a chache type of services implicit by-pass
	feature is enabled or disabled"
	DEFVAL { enable }
	::= {apSvcEntry 46}

apSvcTransitionTrap TRAP-TYPE
	ENTERPRISE svcExt
	VARIABLES { apSvcName, apSvcState }
	DESCRIPTION
			"A service transition trap is generated whenever the 
             the service state transitions from ACTIVE -> DEAD, or
             DEAD -> ACTIVE."
	::= 1


apSvcLoadThreshold OBJECT-TYPE
	SYNTAX      INTEGER    ( 2..254 )
	MAX-ACCESS  read-write
	STATUS      current
	DESCRIPTION
	       "Global load threshold, maximum Load Number for service eligibility "
	DEFVAL {254}
	::= {svcExt 3}


apSvcLoadStepSize OBJECT-TYPE
	SYNTAX      INTEGER    ( 1..1000000000 )
	MAX-ACCESS  read-write
	STATUS      current
	DESCRIPTION
	       "The granularity of Load Numbers, expressed in msec."
	DEFVAL {10}
	::= {svcExt 4}

apSvcLoadStepStatic OBJECT-TYPE
	SYNTAX      INTEGER {
                             disable(0),
                             enable(1)
                            }
	MAX-ACCESS  read-write
	STATUS      current
	DESCRIPTION
	       "Disables system dynamic Load Step Size calculation"
	DEFVAL {disable}
	::= {svcExt 5}

apSvcLoadDecayInterval OBJECT-TYPE
	SYNTAX      INTEGER    ( 1..1000000000 )
	MAX-ACCESS  read-write
	STATUS      current
	DESCRIPTION
	       "The frequency which an ineligible service, becomes eligible, expressed in teardown report cycles."
	DEFVAL {10}
	::= {svcExt 6}

apSvcLoadEnable OBJECT-TYPE
	SYNTAX      INTEGER {
                             disable(0),
                             enable(1)
                            }
	MAX-ACCESS  read-write
	STATUS      current
	DESCRIPTION
	       "Controls system service Load calculation"
	DEFVAL {enable}
	::= {svcExt 7}

apSvcLoadSvcStatRptTimeout OBJECT-TYPE
	SYNTAX      INTEGER    ( 0..1000000000 )
	MAX-ACCESS  read-write
	STATUS      current
	DESCRIPTION
	       "The maximum time period the system will wait to send a teardown report. (in seconds)"
	DEFVAL {20}
	::= {svcExt 8}

apSvcLoadInfoTimeout OBJECT-TYPE
	SYNTAX      INTEGER    ( 0..1000000000 )
	MAX-ACCESS  read-write
	STATUS      current
	DESCRIPTION
	       "The amount of time (in seconds), which stale load information will be aged out."
	DEFVAL {60}
	::= {svcExt 9}
END
