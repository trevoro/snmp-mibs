-- $Id: ir-appletalk-mib.mib,v 1.1 2002/06/27 15:47:22 sse Exp $
            MRV-IN-REACH-APPLETALK-MIB DEFINITIONS ::= BEGIN

                    IMPORTS
                            Counter, TimeTicks
                                    FROM RFC1155-SMI
                            DdpAddress
                                    FROM RFC1243-MIB
                            DisplayString
                                    FROM RFC1213-MIB
                            OBJECT-TYPE
                                    FROM RFC-1212
                            charPortIndex
                                    FROM RFC1316-MIB
	                    mrvInReachProductDivision
                               FROM MRV-IN-REACH-PRODUCT-DIVISION-MIB;

            xApple          OBJECT IDENTIFIER ::= { mrvInReachProductDivision 21 }

            -- MRV In-Reach AppleTalk subgroups

            xAppleSystem        OBJECT IDENTIFIER ::= { xApple 1 }
            xApplePort          OBJECT IDENTIFIER ::= { xApple 2 }
            xApplePolicy        OBJECT IDENTIFIER ::= { xApple 3 }
            xAppleNbp           OBJECT IDENTIFIER ::= { xApple 4 }
            xAppleTraffic       OBJECT IDENTIFIER ::= { xApple 5 }
            xAppleRemoteAccess  OBJECT IDENTIFIER ::= { xApple 6 }

            -- This is a MIB module for all MRV In-Reach systems that
            -- implement Appletalk.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the AppleTalk System group

            appleState OBJECT-TYPE
                SYNTAX INTEGER { disabled(1), enabled(2) }
                ACCESS read-write
                STATUS mandatory
                DESCRIPTION
                    "Controls whether the router will perform AppleTalk 
                    routing."
                ::= { xAppleSystem 1 }

            appleStatus OBJECT-TYPE
                SYNTAX INTEGER { disabled(1), active(2), noInterface(3),
                                 badConfig(4), noInterfaceActive (5) }
                ACCESS read-only
                STATUS mandatory
                DESCRIPTION
                    "Indicates whether the router is performing 
                    AppleTalk routing."
                ::= { xAppleSystem 2 }

            appleStatusIf OBJECT-TYPE
                SYNTAX INTEGER
                ACCESS read-only
                STATUS mandatory
                DESCRIPTION
                    "The ifIndex of the bad interface if appleStatus is 
                    'badConfig'."
                ::= { xAppleSystem 3 }


            -- the AppleTalk Port group

            applePortTable OBJECT-TYPE
                SYNTAX SEQUENCE OF ApplePortEntry
                ACCESS not-accessible
                STATUS mandatory
                DESCRIPTION
                    "Table of fields indexed by interface."
                ::= { xApplePort 1 }

            applePortEntry OBJECT-TYPE
                SYNTAX ApplePortEntry
                ACCESS not-accessible
                STATUS mandatory
                DESCRIPTION
                    "A particular entry."
                INDEX { applePortIndex }
                ::= { applePortTable 1 }

            ApplePortEntry ::=
                SEQUENCE {
                    applePortIndex
                        INTEGER,
                    applePortProtocolPriority
                        INTEGER,
                    applePortArpInterval
                        INTEGER,
                    applePortArpRetransmitCount
                        INTEGER,
                    applePortChecksum
                        INTEGER,
                    applePortPacketsIn
                        Counter,
                    applePortPacketsOut
                        Counter,
                    applePortForwardsIn
                        Counter,
                    applePortForwardsOut
                        Counter,
                    applePortNetAddress
                        DdpAddress,
                    applePortNetStart
                        OCTET STRING,
                    applePortNetEnd
                        OCTET STRING,
                    applePortErrors
                        Counter,
                    applePortLastError
                        INTEGER,
                    applePortLastErrorTime
                        TimeTicks,
                    applePortLastErrorData
                        OCTET STRING,
                    applePortBringBackTime
                        INTEGER,
                    applePortUseNeighborNotify
                        INTEGER,
                    applePortRouterType
                        INTEGER
                }

            applePortIndex OBJECT-TYPE
                SYNTAX INTEGER
                ACCESS read-only
                STATUS mandatory
                DESCRIPTION
                    "The index of the interface; same as IfIndex."
                ::= { applePortEntry 1 }

            applePortProtocolPriority OBJECT-TYPE
                SYNTAX INTEGER { low(1), medium(3), high(5) }
                ACCESS read-write
                STATUS mandatory
                DESCRIPTION
                    "This value defines the priority at which all Apple 
                    routed packets will be placed on the WAN output 
                    queue."
                DEFVAL { medium }
                ::= { applePortEntry 2 }

            applePortArpInterval OBJECT-TYPE
                SYNTAX INTEGER (33..65535)
                ACCESS read-write
                STATUS mandatory
                DESCRIPTION
                    "The interval at which ARP messages should be sent 
                    during the process of selecting a network address."
                DEFVAL { 33 }
                ::= { applePortEntry 3 }

            applePortArpRetransmitCount OBJECT-TYPE
                SYNTAX INTEGER (1..65535)
                ACCESS read-write
                STATUS mandatory
                DESCRIPTION
                    "The number of ARP messages that should be sent 
                    during the process of selecting a network address."
                DEFVAL { 20 }
                ::= { applePortEntry 4 }

            applePortChecksum OBJECT-TYPE
                SYNTAX INTEGER { disabled(1), enabled(2) }
                ACCESS read-write
                STATUS mandatory
                DESCRIPTION
                    "Controls whether checksums are generated on all DDP 
                    packets sent out the interface."
                DEFVAL { disabled }
                ::= { applePortEntry 5 }

            applePortPacketsIn OBJECT-TYPE
                SYNTAX Counter
                ACCESS read-only
                STATUS mandatory
                DESCRIPTION
                    "The number of AppleTalk packets received on this 
                    interface."
                ::= { applePortEntry 6 }

            applePortPacketsOut OBJECT-TYPE
                SYNTAX Counter
                ACCESS read-only
                STATUS mandatory
                DESCRIPTION
                    "The number of AppleTalk packets transmitted on this 
                    interface."
                ::= { applePortEntry 7 }

            applePortForwardsIn OBJECT-TYPE
                SYNTAX Counter
                ACCESS read-only
                STATUS mandatory
                DESCRIPTION
                    "The number of AppleTalk packets received on this 
                    interface which were not addressed to this router."
                ::= { applePortEntry 8 }

            applePortForwardsOut OBJECT-TYPE
                SYNTAX Counter
                ACCESS read-only
                STATUS mandatory
                DESCRIPTION
                    "The number of AppleTalk packets transmitted on this 
                    interface which were not originated by this 
                    router."
                ::= { applePortEntry 9 }

            applePortNetAddress OBJECT-TYPE
                SYNTAX DdpAddress
                ACCESS read-only
                STATUS mandatory
                DESCRIPTION
                    "The actual address used by this port."
                ::= { applePortEntry 10 }

            applePortNetStart OBJECT-TYPE
                SYNTAX OCTET STRING ( SIZE(2) )
                ACCESS read-only
                STATUS mandatory
                DESCRIPTION
                    "The start of the actual network range used by this 
                    port."
                ::= { applePortEntry 11 }

            applePortNetEnd OBJECT-TYPE
                SYNTAX OCTET STRING ( SIZE(2) )
                ACCESS read-only
                STATUS mandatory
                DESCRIPTION
                    "The end of the actual network range used by this 
                    port."
                ::= { applePortEntry 12 }

            applePortErrors OBJECT-TYPE
                SYNTAX Counter
                ACCESS read-only
                STATUS mandatory
                DESCRIPTION
                    "The number of AppleTalk packets received in 
                    error."
                ::= { applePortEntry 13 }

            applePortLastError OBJECT-TYPE
                SYNTAX INTEGER { broadcast(1), checksum(2), hopCount(3),
                                 noProtocol(4), noRoute(5), shortDDP(6),
                                 tooLong(7), tooShort(8) }
                ACCESS read-only
                STATUS mandatory
                DESCRIPTION
                    "The type of the most recent error counted in 
                    applePortErrors.  A value of zero means no error."
                ::= { applePortEntry 14 }

            applePortLastErrorTime OBJECT-TYPE
                SYNTAX TimeTicks
                ACCESS read-only
                STATUS mandatory
                DESCRIPTION
                    "The value of sysUptime when applePortLastError last 
                    occured."
                ::= { applePortEntry 15 }

            applePortLastErrorData OBJECT-TYPE
                SYNTAX OCTET STRING ( SIZE(22) )
                ACCESS read-only
                STATUS mandatory
                DESCRIPTION
                    "The first 22 bytes of the packet from 
                    applePortLastError."
                ::= { applePortEntry 16 }

            applePortBringBackTime OBJECT-TYPE
                SYNTAX INTEGER (0..65535)
                ACCESS read-write
                STATUS mandatory
                DESCRIPTION
                    "The number of seconds to shut down an interface 
                    while waiting for a manager-initiated configuration 
                    change to propagate."
                ::= { applePortEntry 17 }

            applePortUseNeighborNotify OBJECT-TYPE
                SYNTAX INTEGER { disabled(1), enabled(2) }
                ACCESS read-write
                STATUS mandatory
                DESCRIPTION
                    "Controls generation of neighbor notify messages 
                    when an interface is disabled or system is shut 
                    down."
                ::= { applePortEntry 18 }

            applePortRouterType OBJECT-TYPE
                SYNTAX INTEGER { full(1), half(2) }
                ACCESS read-write
                STATUS mandatory
                DESCRIPTION
                    "Type of router operation over this port."
                ::= { applePortEntry 19 }


            -- the Port Zone table

            applePortZoneTable OBJECT-TYPE
                SYNTAX SEQUENCE OF ApplePortZoneEntry
                ACCESS not-accessible
                STATUS mandatory
                DESCRIPTION
                    "Table of fields indexed by interface and zone."
                ::= { xApplePort 2 }

            applePortZoneEntry OBJECT-TYPE
                SYNTAX ApplePortZoneEntry
                ACCESS not-accessible
                STATUS mandatory
                DESCRIPTION
                    "A particular entry."
                INDEX { applePortZoneIndex, applePortZoneName }
                ::= { applePortZoneTable 1 }

            ApplePortZoneEntry ::=
                SEQUENCE {
                    applePortZoneIndex
                        INTEGER,
                    applePortZoneName
                        OCTET STRING,
                    applePortZoneStatus
                        INTEGER
                }

            applePortZoneIndex OBJECT-TYPE
                SYNTAX INTEGER
                ACCESS read-only
                STATUS mandatory
                DESCRIPTION
                    "The index of the interface; same as IfIndex."
                ::= { applePortZoneEntry 1 }

            applePortZoneName OBJECT-TYPE
                SYNTAX OCTET STRING ( SIZE(32) )
                ACCESS read-only
                STATUS mandatory
                DESCRIPTION
                    "The name of the zone."
                ::= { applePortZoneEntry 2 }

            applePortZoneStatus OBJECT-TYPE
                SYNTAX INTEGER { invalid(1), valid(2) }
                ACCESS read-write
                STATUS mandatory
                DESCRIPTION
                    "The status of the entry.  Set to 'invalid' to 
                    remove the entry."
                DEFVAL { valid }
                ::= { applePortZoneEntry 3 }


            -- the AppleTalk Port Policy group

            applePortExportTable OBJECT-TYPE
                SYNTAX SEQUENCE OF ApplePortExportEntry
                ACCESS not-accessible
                STATUS mandatory
                DESCRIPTION
                    "Table of fields indexed by interface and zone."
                ::= { xApplePolicy 1 }

            applePortExportEntry OBJECT-TYPE
                SYNTAX ApplePortExportEntry
                ACCESS not-accessible
                STATUS mandatory
                DESCRIPTION
                    "A particular entry."
                INDEX { applePortExportIndex, applePortExportZone,
                        applePortExportName, applePortExportType }
                ::= { applePortExportTable 1 }

            ApplePortExportEntry ::=
                SEQUENCE {
                    applePortExportIndex
                        INTEGER,
                    applePortExportZone
                        OCTET STRING,
                    applePortExportName
                        OCTET STRING,
                    applePortExportType
                        OCTET STRING,
                    applePortExportAction
                        INTEGER,
                    applePortExportStatus
                        INTEGER
                }

            applePortExportIndex OBJECT-TYPE
                SYNTAX INTEGER
                ACCESS read-only
                STATUS mandatory
                DESCRIPTION
                    "The index of the interface; same as IfIndex."
                ::= { applePortExportEntry 1 }

            applePortExportZone OBJECT-TYPE
                SYNTAX OCTET STRING ( SIZE(0..32) )
                ACCESS read-only
                STATUS mandatory
                DESCRIPTION
                    "The name of the zone."
                ::= { applePortExportEntry 2 }

            applePortExportName OBJECT-TYPE
                SYNTAX OCTET STRING ( SIZE(0..32) )
                ACCESS read-only
                STATUS mandatory
                DESCRIPTION
                    "The name of the name."
                ::= { applePortExportEntry 3 }

            applePortExportType OBJECT-TYPE
                SYNTAX OCTET STRING ( SIZE(0..32) )
                ACCESS read-only
                STATUS mandatory
                DESCRIPTION
                    "The name of the type."
                ::= { applePortExportEntry 4 }

            applePortExportAction OBJECT-TYPE
                SYNTAX INTEGER { hide(1), advertise(2) }
                ACCESS read-write
                STATUS mandatory
                DESCRIPTION
                    "Control whether the data will be hidden or 
                    advertised."
                DEFVAL { advertise }
                ::= { applePortExportEntry 5 }

            applePortExportStatus OBJECT-TYPE
                SYNTAX INTEGER { invalid(1), valid(2) }
                ACCESS read-write
                STATUS mandatory
                DESCRIPTION
                    "The status of the entry.  Set to 'invalid' to 
                    remove the entry."
                DEFVAL { valid }
                ::= { applePortExportEntry 6 }

            applePortImportTable OBJECT-TYPE
                SYNTAX SEQUENCE OF ApplePortImportEntry
                ACCESS not-accessible
                STATUS mandatory
                DESCRIPTION
                    "Table of fields indexed by interface and zone."
                ::= { xApplePolicy 2 }

            applePortImportEntry OBJECT-TYPE
                SYNTAX ApplePortImportEntry
                ACCESS not-accessible
                STATUS mandatory
                DESCRIPTION
                    "A particular entry."
                INDEX { applePortImportIndex, applePortImportZone,
                        applePortImportName, applePortImportType }
                ::= { applePortImportTable 1 }

            ApplePortImportEntry ::=
                SEQUENCE {
                    applePortImportIndex
                        INTEGER,
                    applePortImportZone
                        OCTET STRING,
                    applePortImportName
                        OCTET STRING,
                    applePortImportType
                        OCTET STRING,
                    applePortImportAction
                        INTEGER,
                    applePortImportStatus
                        INTEGER
                }

            applePortImportIndex OBJECT-TYPE
                SYNTAX INTEGER
                ACCESS read-only
                STATUS mandatory
                DESCRIPTION
                    "The index of the interface; same as IfIndex."
                ::= { applePortImportEntry 1 }

            applePortImportZone OBJECT-TYPE
                SYNTAX OCTET STRING ( SIZE(0..32) )
                ACCESS read-only
                STATUS mandatory
                DESCRIPTION
                    "The name of the zone."
                ::= { applePortImportEntry 2 }

            applePortImportName OBJECT-TYPE
                SYNTAX OCTET STRING ( SIZE(0..32) )
                ACCESS read-only
                STATUS mandatory
                DESCRIPTION
                    "The name of the name."
                ::= { applePortImportEntry 3 }

            applePortImportType OBJECT-TYPE
                SYNTAX OCTET STRING ( SIZE(0..32) )
                ACCESS read-only
                STATUS mandatory
                DESCRIPTION
                    "The name of the type."
                ::= { applePortImportEntry 4 }

            applePortImportAction OBJECT-TYPE
                SYNTAX INTEGER { discard(1), accept(2) }
                ACCESS read-write
                STATUS mandatory
                DESCRIPTION
                    "Control whether the data will be discarded or 
                    accepted."
                DEFVAL { accept }
                ::= { applePortImportEntry 5 }

            applePortImportStatus OBJECT-TYPE
                SYNTAX INTEGER { invalid(1), valid(2) }
                ACCESS read-write
                STATUS mandatory
                DESCRIPTION
                    "The status of the entry.  Set to 'invalid' to 
                    remove the entry."
                DEFVAL { valid }
                ::= { applePortImportEntry 6 }


            -- the AppleTalk Name group

            appleNbpTable OBJECT-TYPE
                SYNTAX SEQUENCE OF AppleNbpEntry
                ACCESS not-accessible
                STATUS mandatory
                DESCRIPTION
                    "Table of fields indexed by interface and zone."
                ::= { xAppleNbp 1 }

            appleNbpEntry OBJECT-TYPE
                SYNTAX AppleNbpEntry
                ACCESS not-accessible
                STATUS mandatory
                DESCRIPTION
                    "A particular entry."
                INDEX { appleNbpZone, appleNbpName, appleNbpType }
                ::= { appleNbpTable 1 }

            AppleNbpEntry ::=
                SEQUENCE {
                    appleNbpZone
                        OCTET STRING,
                    appleNbpName
                        OCTET STRING,
                    appleNbpType
                        OCTET STRING,
                    appleNbpNode
                        DdpAddress,
                    appleNbpSocket
                        INTEGER
                }

            appleNbpZone OBJECT-TYPE
                SYNTAX OCTET STRING ( SIZE(0..32) )
                ACCESS read-only
                STATUS mandatory
                DESCRIPTION
                    "The name of the zone."
                ::= { appleNbpEntry 1 }

            appleNbpName OBJECT-TYPE
                SYNTAX OCTET STRING ( SIZE(0..32) )
                ACCESS read-only
                STATUS mandatory
                DESCRIPTION
                    "The name of the name."
                ::= { appleNbpEntry 2 }

            appleNbpType OBJECT-TYPE
                SYNTAX OCTET STRING ( SIZE(0..32) )
                ACCESS read-only
                STATUS mandatory
                DESCRIPTION
                    "The name of the type."
                ::= { appleNbpEntry 3 }

            appleNbpNode OBJECT-TYPE
                SYNTAX DdpAddress
                ACCESS read-only
                STATUS mandatory
                DESCRIPTION
                    "The address of the node who offers the service 
                    associated with this entry."
                ::= { appleNbpEntry 4 }

            appleNbpSocket OBJECT-TYPE
                SYNTAX INTEGER
                ACCESS read-only
                STATUS mandatory
                DESCRIPTION
                    "The socket of the service associated with this 
                    entry.  The value 0 means no socket."
                ::= { appleNbpEntry 5 }


            -- the AppleTalk Traffic group

            appleTrafficSort OBJECT-TYPE
                SYNTAX INTEGER { ready(1), execute(2) }
                ACCESS read-write
                STATUS mandatory
                DESCRIPTION
                    "Setting to EXECUTE causes the most recent traffic 
                    information to be sorted into the appleTrafficTable.  
                    The sorting precedence is: decreasing percentage, 
                    increasing destination address, increasing source 
                    address, and increasing interface number.  Setting 
                    to READY has no effect."
                ::= { xAppleTraffic 1 }

            -- Additional single objects follow the Traffic table

            -- the Traffic table

            appleTrafficTable OBJECT-TYPE
                SYNTAX SEQUENCE OF AppleTrafficEntry
                ACCESS not-accessible
                STATUS mandatory
                DESCRIPTION
                    "A list of traffic entries, sorted in the order 
                    specified by appleTrafficSort."
                ::= { xAppleTraffic 2 }

            appleTrafficEntry OBJECT-TYPE
                SYNTAX AppleTrafficEntry
                ACCESS not-accessible
                STATUS mandatory
                DESCRIPTION
                    "Parameter values for an Filter filter."
                INDEX { appleTrafficIndex }
                ::= { appleTrafficTable 1 }

            AppleTrafficEntry ::=
                SEQUENCE {
                    appleTrafficIndex
                        INTEGER,
                    appleTrafficPercent
                        INTEGER,
                    appleTrafficDst
                        DdpAddress,
                    appleTrafficSrc
                        DdpAddress,
                    appleTrafficIntf
                        INTEGER
                }

            appleTrafficIndex OBJECT-TYPE
                SYNTAX INTEGER
                ACCESS read-only
                STATUS mandatory
                DESCRIPTION
                    "Identification of a traffic entry."
                ::= { appleTrafficEntry 1 }

            appleTrafficPercent OBJECT-TYPE
                SYNTAX INTEGER ( 0..1000 )
                ACCESS read-only
                STATUS mandatory
                DESCRIPTION
                    "The percent of total traffic that this traffic 
                    entryrepresents, in tenths of a percent."
                ::= { appleTrafficEntry 2 }

            appleTrafficDst OBJECT-TYPE
                SYNTAX DdpAddress
                ACCESS read-only
                STATUS mandatory
                DESCRIPTION
                    "The destination to which the traffic entry 
                    applies."
                ::= { appleTrafficEntry 3 }

            appleTrafficSrc OBJECT-TYPE
                SYNTAX DdpAddress
                ACCESS read-only
                STATUS mandatory
                DESCRIPTION
                    "The source to which the traffic entry applies."
                ::= { appleTrafficEntry 4 }

            appleTrafficIntf OBJECT-TYPE
                SYNTAX INTEGER
                ACCESS read-only
                STATUS mandatory
                DESCRIPTION
                    "The inbound interface to which the traffic entry 
                    applies."
                ::= { appleTrafficEntry 5 }

            -- Additional individual objects

            appleTrafficMonitoring OBJECT-TYPE
                SYNTAX INTEGER { disable(1), enable(2) }
                ACCESS read-write
                STATUS mandatory
                DESCRIPTION
                    "Controls whether internet traffic information will 
                    be recorded."
                ::= { xAppleTraffic 3 }

            -- The MRV In-Reach ARAP MIB branch

            arapPassword OBJECT-TYPE
                SYNTAX DisplayString (SIZE (0..8))
                ACCESS read-write
                STATUS mandatory
                DESCRIPTION
                    "The server's ARAP password.  To increase security, Gets
                    of this object return the NULL string."
                ::= { xAppleRemoteAccess 1 }

            arapDefaultZoneName OBJECT-TYPE
                SYNTAX DisplayString (SIZE (0..32))
                ACCESS read-write
                STATUS mandatory
                DESCRIPTION
                    "The name of the AppleTalk zone that the server should
                    try to choose at boot time."
                ::= { xAppleRemoteAccess 2 }

            -- the ARAP Port table

            arapPortTable OBJECT-TYPE
                SYNTAX SEQUENCE OF ArapPortEntry
                ACCESS not-accessible
                STATUS mandatory
                DESCRIPTION
                    "A list of ARAP port entries."
                ::= { xAppleRemoteAccess 3 }

            arapPortEntry OBJECT-TYPE
                SYNTAX ArapPortEntry
                ACCESS not-accessible
                STATUS mandatory
                DESCRIPTION
                    "ARAP parameter values for a port."
                INDEX { charPortIndex }
                ::= { arapPortTable 1 }

            ArapPortEntry ::=
                SEQUENCE {
                    arapPortEnabled
                        INTEGER,
                    arapPortZoneAccess
                        INTEGER,
                    arapPortZoneName
                        DisplayString,
                    arapPortMaxConnectTime
                        INTEGER,
                    arapPortGuestLoginsOk
                        INTEGER,
                    arapPortTimeConnected
                        INTEGER,
                    arapPortTimeRemaining
                        INTEGER
                }

            arapPortEnabled OBJECT-TYPE
                SYNTAX INTEGER { disabled(1), enabled(2) }
                ACCESS read-write
                STATUS mandatory
                DESCRIPTION
                    "Indicates if ARAP connections are allowed on this port."
                ::= { arapPortEntry 1 }

            arapPortZoneAccess OBJECT-TYPE
                SYNTAX INTEGER { all(1), local(2), none(3), namedzone(4) }
                ACCESS read-write
                STATUS mandatory
                DESCRIPTION
                    "Indicates the AppleTalk zones that ARAP connections on
                    this port may access: none, local, all, or named zone."
                ::= { arapPortEntry 2 }

            arapPortZoneName OBJECT-TYPE
                SYNTAX DisplayString (SIZE (0..32))
                ACCESS read-write
                STATUS mandatory
                DESCRIPTION
                    "If this port's arapPortZoneAccess field indicates a
                    named zone, this field contains the zone name."
                ::= { arapPortEntry 3 }

            arapPortMaxConnectTime OBJECT-TYPE
                SYNTAX INTEGER
                ACCESS read-write
                STATUS mandatory
                DESCRIPTION
                    "Maximum number of minutes a single ARAP connection may
                    exist on the port before a server initiated disconnect.
                    To set no limit on the amount of time that an ARAP user
                    may be connected, set this object to -1."
                ::= { arapPortEntry 4 }

            arapPortGuestLoginsOk OBJECT-TYPE
                SYNTAX INTEGER { disabled(1), enabled(2) }
                ACCESS read-write
                STATUS mandatory
                DESCRIPTION
                    "Indicates if 'Guest' logins (with no password) are
                    allowed on the port."
                ::= { arapPortEntry 5 }

            arapPortTimeConnected OBJECT-TYPE
                SYNTAX INTEGER
                ACCESS read-only
                STATUS mandatory
                DESCRIPTION
                    "Indicates the number of minutes the current ARAP
                    connection has been established on the port, rounded
                    up to the nearest minute.  Gets return -1 if no ARAP
                    user is currently connected on the port or if ARAP is
                    not enabled on the port."
                ::= { arapPortEntry 6 }

            arapPortTimeRemaining OBJECT-TYPE
                SYNTAX INTEGER
                ACCESS read-write
                STATUS mandatory
                DESCRIPTION
                    "Indicates the number of minutes the current ARAP
                    connection may remain on the port before a server
                    initiated disconnect will occur, rounded up to the
                    nearest minute.  To set no limit on the amount of
                    time that the current ARAP user may continue to be
                    connected, set this object to the maximum value
                    in the range.  Gets return -1 if no ARAP user is
                    currently connected on the port or if ARAP is not
                    enabled on the port.  Gets also return -1 if there
                    is a user connected and there is no limit on the
                    amount of time that the current user may be connected."
                ::= { arapPortEntry 7 }

     END
