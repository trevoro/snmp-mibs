FUJITSU-EXTENDED-NONOS-AWN-MIB-V06

DEFINITIONS ::= BEGIN

-- Fujitsu extended MIB for EW6000(AWN) series
-- All Rights Reserved, Copyright Fujitsu Limited 1998-2000

-- V6.04 2000/02/16

IMPORTS
    IpAddress, Counter, enterprises, Gauge	FROM RFC1155-SMI
    DisplayString			FROM RFC1213-MIB
    OBJECT-TYPE				FROM RFC-1212;

fujitsu		OBJECT IDENTIFIER ::= { enterprises 211 }
product		OBJECT IDENTIFIER ::= { fujitsu 1 }
nonos		OBJECT IDENTIFIER ::= { product 127 }
awn		OBJECT IDENTIFIER ::= { nonos 29 }

--
--
-- groups in awnSystem
--
--
awnSystem	OBJECT IDENTIFIER ::= { awn 1 }

-- the awnSysNode group

awnSysNode	OBJECT IDENTIFIER ::= { awnSystem 1 }

awnSysNodeInformation	OBJECT-TYPE
    SYNTAX  OCTET STRING (SIZE(512))
    ACCESS  read-only
    STATUS  mandatory
    DESCRIPTION
           "System information"
    ::= { awnSysNode 1 }

awnSysNodeCommonStatus OBJECT-TYPE 
    SYNTAX  OCTET STRING (SIZE(256))
    ACCESS  read-only
    STATUS  mandatory
    DESCRIPTION
           "System status"
    ::= { awnSysNode 2 }

awnSysNodeClk OBJECT-TYPE 
    SYNTAX  OCTET STRING (SIZE(4))
    ACCESS  read-only
    STATUS  mandatory
    DESCRIPTION
           "Not supported"
    ::= { awnSysNode 3 }

-- groups in awnSysCom

awnSysCom		OBJECT IDENTIFIER ::= { awnSystem 2 }

awnSysComDevice		OBJECT-TYPE
    SYNTAX  OCTET STRING (SIZE(80))
    ACCESS  read-only
    STATUS  mandatory
    DESCRIPTION
           "COM unit package status"
   ::= { awnSysCom 1 }

awnSysComPort      OBJECT-TYPE
    SYNTAX  OCTET STRING(SIZE(192))
    ACCESS  read-only
    STATUS  mandatory
    DESCRIPTION
           "COM unit port status"
    ::= { awnSysCom 2 }

awnSysComDevice2      OBJECT-TYPE
    SYNTAX  OCTET STRING(SIZE(68))
    ACCESS  read-only
    STATUS  mandatory
    DESCRIPTION
           "COM unit package status"
    ::= { awnSysCom 3 }

awnSysComPort2      OBJECT-TYPE
    SYNTAX  OCTET STRING(SIZE(120))
    ACCESS  read-only
    STATUS  mandatory
    DESCRIPTION
           "COM unit port status"
    ::= { awnSysCom 4 }

-- groups in awnSysLs

awnSysLs             OBJECT IDENTIFIER ::= { awnSystem 3 }

awnSysLsTable         OBJECT-TYPE
    SYNTAX  SEQUENCE OF AwnSysLsEntry
    ACCESS  not-accessible
    STATUS  mandatory
    DESCRIPTION
           "Table"
    ::= { awnSysLs 1 }
        
awnSysLsEntry         OBJECT-TYPE
    SYNTAX  AwnSysLsEntry
    ACCESS  not-accessible
    STATUS  mandatory
    DESCRIPTION
           "Entry"
    INDEX  { awnSysLsUnit }
    ::= { awnSysLsTable 1 }

AwnSysLsEntry ::= SEQUENCE {
	awnSysLsUnit	INTEGER,
	awnSysLsDevice	OCTET STRING,
	awnSysLsPort	OCTET STRING
}

awnSysLsUnit         OBJECT-TYPE
    SYNTAX  INTEGER (1..8)
    ACCESS  read-only
    STATUS  mandatory
    DESCRIPTION
           "LS unit number"
    ::= { awnSysLsEntry 1 }

awnSysLsDevice          OBJECT-TYPE
    SYNTAX  OCTET STRING (SIZE(64))
    ACCESS  read-only
    STATUS  mandatory
    DESCRIPTION
           "Package status"
    ::= { awnSysLsEntry 2 }

awnSysLsPort         OBJECT-TYPE
    SYNTAX  OCTET STRING (SIZE(560))
    ACCESS  read-only
    STATUS  mandatory
    DESCRIPTION
           "Port status"
    ::= { awnSysLsEntry 3 }

awnSysLsDevice2          OBJECT-TYPE
    SYNTAX  OCTET STRING (SIZE(80))
    ACCESS  read-only
    STATUS  mandatory
    DESCRIPTION
           "Package status"
    ::= { awnSysLsEntry 4 }

awnSysLsPort2         OBJECT-TYPE
    SYNTAX  OCTET STRING (SIZE(720))
    ACCESS  read-only
    STATUS  mandatory
    DESCRIPTION
           "Port status"
    ::= { awnSysLsEntry 5 }

-- groups in awnSysLine

awnSysLine            OBJECT IDENTIFIER ::= { awnSystem 4 }

awnSysLineTable            OBJECT-TYPE
    SYNTAX  SEQUENCE OF AwnSysLineEntry
    ACCESS  not-accessible
    STATUS  mandatory
    DESCRIPTION
            "Table"
    ::= { awnSysLine 1 }

awnSysLineEntry            OBJECT-TYPE
    SYNTAX  AwnSysLineEntry
    ACCESS  not-accessible
    STATUS  mandatory
    DESCRIPTION
           "Entry"
    INDEX   { awnSysLineUnit, awnSysLineCard, awnSysLinePort }
    ::= { awnSysLineTable 1 }

AwnSysLineEntry           ::= SEQUENCE {
             awnSysLineUnit                       INTEGER,
             awnSysLineCard                       INTEGER,
             awnSysLinePort                       INTEGER,
             awnSysLineChannel                    OCTET STRING,
             awnSysLineMegalink                   OCTET STRING
}

awnSysLineUnit               OBJECT-TYPE
    SYNTAX  INTEGER (1..8)
    ACCESS  read-only
    STATUS  mandatory
    DESCRIPTION
           "LS unit number"
    ::= { awnSysLineEntry 1 }

awnSysLineCard               OBJECT-TYPE
    SYNTAX  INTEGER (1..18)
    ACCESS  read-only
    STATUS  mandatory
    DESCRIPTION
           "LS card number"
    ::= { awnSysLineEntry 2 }

awnSysLinePort            OBJECT-TYPE
    SYNTAX  INTEGER (1..8)
    ACCESS  read-only
    STATUS  mandatory
    DESCRIPTION
           "LS port number"
    ::= { awnSysLineEntry 3 }

awnSysLineChannel        OBJECT-TYPE
    SYNTAX  OCTET STRING (SIZE(384))
    ACCESS  read-only
    STATUS  mandatory
    DESCRIPTION
           "Channel status"
    ::= { awnSysLineEntry 4 }

awnSysLineMegalink        OBJECT-TYPE
    SYNTAX  OCTET STRING (SIZE(256))
    ACCESS  read-only
    STATUS  mandatory
    DESCRIPTION
           "Megalink status"
    ::= { awnSysLineEntry 5 }

-- groups in awnSysError      

awnSysError           OBJECT IDENTIFIER ::= { awnSystem 5 }

awnSysErrorLog            OBJECT-TYPE
    SYNTAX  DisplayString
    ACCESS  read-only     
    STATUS  mandatory
    DESCRIPTION
           "Error logging"
    ::= { awnSysError 1 }

-- groups in awnSysChannel

awnSysChannel            OBJECT IDENTIFIER ::= { awnSystem 6 }

awnSysChannelTable            OBJECT-TYPE
    SYNTAX  SEQUENCE OF AwnSysChannelEntry
    ACCESS  not-accessible
    STATUS  mandatory
    DESCRIPTION
            "Table"
    ::= { awnSysChannel 1 }

awnSysChannelEntry            OBJECT-TYPE
    SYNTAX  AwnSysChannelEntry
    ACCESS  not-accessible
    STATUS  mandatory
    DESCRIPTION
           "Entry"
    INDEX   { awnSysChannelUnit, awnSysChannelCard, awnSysChannelPort, awnSysChannelTimeslot }
    ::= { awnSysChannelTable 1 }

AwnSysChannelEntry           ::= SEQUENCE {
	awnSysChannelUnit                       INTEGER,
	awnSysChannelCard                       INTEGER,
	awnSysChannelPort                       INTEGER,
	awnSysChannelTimeslot                   INTEGER,
	awnSysChannelBackup                     OCTET STRING,
	awnSysChannelBackup2                    OCTET STRING
}

awnSysChannelUnit               OBJECT-TYPE
    SYNTAX  INTEGER (1..8)
    ACCESS  read-only
    STATUS  mandatory
    DESCRIPTION
           "LS unit number"
    ::= { awnSysChannelEntry 1 }

awnSysChannelCard               OBJECT-TYPE
    SYNTAX  INTEGER (1..18)
    ACCESS  read-only
    STATUS  mandatory
    DESCRIPTION
           "LS card number"
    ::= { awnSysChannelEntry 2 }

awnSysChannelPort            OBJECT-TYPE
    SYNTAX  INTEGER (1..8)
    ACCESS  read-only
    STATUS  mandatory
    DESCRIPTION
           "LS port number"
    ::= { awnSysChannelEntry 3 }

awnSysChannelTimeslot            OBJECT-TYPE
    SYNTAX  INTEGER (1..96)
    ACCESS  read-only
    STATUS  mandatory
    DESCRIPTION
           "TS number"
    ::= { awnSysChannelEntry 4 }

awnSysChannelBackup        OBJECT-TYPE
    SYNTAX  OCTET STRING (SIZE(576))
    ACCESS  read-only
    STATUS  mandatory
    DESCRIPTION
           "Backup status(part 1)"
    ::= { awnSysChannelEntry 5 }

awnSysChannelBackup2        OBJECT-TYPE
    SYNTAX  OCTET STRING (SIZE(512))
    ACCESS  read-only
    STATUS  mandatory
    DESCRIPTION
           "Backup status(part 2)"
    ::= { awnSysChannelEntry 6 }

-- groups in awnSysEvent

awnSysEvent OBJECT IDENTIFIER ::= { awnSystem 7 }

awnSysEventTable            OBJECT-TYPE
    SYNTAX  SEQUENCE OF AwnSysEventEntry
    ACCESS  not-accessible
    STATUS  mandatory
    DESCRIPTION
            "Table"
    ::= { awnSysEvent 1 }

awnSysEventEntry            OBJECT-TYPE
    SYNTAX  AwnSysEventEntry
    ACCESS  not-accessible
    STATUS  mandatory
    DESCRIPTION
            "Entry"
    ::= { awnSysEventTable 1 }

AwnSysEventEntry ::= SEQUENCE {
	awnSysEventThreshold		DisplayString
}

awnSysEventThreshold               OBJECT-TYPE
    SYNTAX  DisplayString
    ACCESS  not-accessible
    STATUS  mandatory
    DESCRIPTION
           "Threshold alarm"
    ::= { awnSysEventEntry 1 }

-- groups in awnSysPort

awnSysPort OBJECT IDENTIFIER ::= { awnSystem 8 }

awnSysPortTable            OBJECT-TYPE
    SYNTAX  SEQUENCE OF AwnSysPortEntry
    ACCESS  not-accessible
    STATUS  mandatory
    DESCRIPTION
            "Table"
    ::= { awnSysPort 1 }

awnSysPortEntry            OBJECT-TYPE
    SYNTAX  AwnSysPortEntry
    ACCESS  not-accessible
    STATUS  mandatory
    DESCRIPTION
           "Entry"
    INDEX   { awnSysPortSlot, awnSysPortAdapter, awnSysPortPort }
    ::= { awnSysPortTable 1 }

AwnSysPortEntry ::= SEQUENCE {
	awnSysPortSlot		INTEGER,
	awnSysPortAdapter	INTEGER,
	awnSysPortPort		INTEGER,
	awnSysPortMegalink	OCTET STRING,
	awnSysPortMegalink2	OCTET STRING
}

awnSysPortSlot               OBJECT-TYPE
    SYNTAX  INTEGER (1..4)
    ACCESS  read-only
    STATUS  mandatory
    DESCRIPTION
           "COM port number"
    ::= { awnSysPortEntry 1 }

awnSysPortAdapter               OBJECT-TYPE
    SYNTAX  INTEGER (1..2)
    ACCESS  read-only
    STATUS  mandatory
    DESCRIPTION
           "COM adapter number"
    ::= { awnSysPortEntry 2 }

awnSysPortPort            OBJECT-TYPE
    SYNTAX  INTEGER (1..4)
    ACCESS  read-only
    STATUS  mandatory
    DESCRIPTION
           "COM port number"
    ::= { awnSysPortEntry 3 }

awnSysPortMegalink        OBJECT-TYPE
    SYNTAX  OCTET STRING (SIZE(244))
    ACCESS  read-only
    STATUS  mandatory
    DESCRIPTION
           "Megalink status(part 1)"
    ::= { awnSysPortEntry 4 }

awnSysPortMegalink2        OBJECT-TYPE
    SYNTAX  OCTET STRING (SIZE(256))
    ACCESS  read-only
    STATUS  mandatory
    DESCRIPTION
           "Megalink status(part 2)"
    ::= { awnSysPortEntry 5 }

-- groups in awnSysConnComVcc

awnSysConnComVcc OBJECT IDENTIFIER ::= { awnSystem 9 }

awnSysConnComVccTable            OBJECT-TYPE
    SYNTAX  SEQUENCE OF AwnSysConnComVccEntry
    ACCESS  not-accessible
    STATUS  mandatory
    DESCRIPTION
            "Table"
    ::= { awnSysConnComVcc 1 }

awnSysConnComVccEntry            OBJECT-TYPE
    SYNTAX  AwnSysConnComVccEntry
    ACCESS  not-accessible
    STATUS  mandatory
    DESCRIPTION
           "Entry"
    INDEX   { awnSysConnComVccSlot, awnSysConnComVccAdapter, awnSysConnComVccPort, awnSysConnComVccVpi,awnSysConnComVccVci }
    ::= { awnSysConnComVccTable 1 }

AwnSysConnComVccEntry ::= SEQUENCE {
	awnSysConnComVccSlot                          INTEGER,
	awnSysConnComVccAdapter                       INTEGER,
	awnSysConnComVccPort                          INTEGER,
	awnSysConnComVccVpi                           INTEGER,
	awnSysConnComVccVci                           INTEGER,
	awnSysConnComVccState                         OCTET STRING
}

awnSysConnComVccSlot               OBJECT-TYPE
    SYNTAX  INTEGER (1..4)
    ACCESS  read-only
    STATUS  mandatory
    DESCRIPTION
           "COM slot number"
    ::= { awnSysConnComVccEntry 1 }

awnSysConnComVccAdapter               OBJECT-TYPE
    SYNTAX  INTEGER (1..2)
    ACCESS  read-only
    STATUS  mandatory
    DESCRIPTION
           "COM adapter number"
    ::= { awnSysConnComVccEntry 2 }

awnSysConnComVccPort            OBJECT-TYPE
    SYNTAX  INTEGER (1..4)
    ACCESS  read-only
    STATUS  mandatory
    DESCRIPTION
           "COM port number"
    ::= { awnSysConnComVccEntry 3 }

awnSysConnComVccVpi            OBJECT-TYPE
    SYNTAX  INTEGER (0..255)
    ACCESS  read-only
    STATUS  mandatory
    DESCRIPTION
           "VPI"
    ::= { awnSysConnComVccEntry 4 }

awnSysConnComVccVci            OBJECT-TYPE
    SYNTAX  INTEGER (0..4095)
    ACCESS  read-only
    STATUS  mandatory
    DESCRIPTION
           "VCI"
    ::= { awnSysConnComVccEntry 5 }

awnSysConnComVccState        OBJECT-TYPE
    SYNTAX  OCTET STRING (SIZE(100))
    ACCESS  read-only
    STATUS  mandatory
    DESCRIPTION
           "State"
    ::= { awnSysConnComVccEntry 6 }

-- groups in awnSysConnLsVcc

awnSysConnLsVcc            OBJECT IDENTIFIER ::= { awnSystem 10 }

awnSysConnLsVccTable            OBJECT-TYPE
    SYNTAX  SEQUENCE OF AwnSysConnLsVccEntry
    ACCESS  not-accessible
    STATUS  mandatory
    DESCRIPTION
            "Table"
    ::= { awnSysConnLsVcc 1 }

awnSysConnLsVccEntry            OBJECT-TYPE
    SYNTAX  AwnSysConnLsVccEntry
    ACCESS  not-accessible
    STATUS  mandatory
    DESCRIPTION
           "Entry"
    INDEX   { awnSysConnLsVccSlot, awnSysConnLsVccUnit, awnSysConnLsVccCard, awnSysConnLsVccPort, awnSysConnLsVccTimeslot, awnSysConnLsVccVpi, awnSysConnLsVccVci }
    ::= { awnSysConnLsVccTable 1 }

AwnSysConnLsVccEntry		::= SEQUENCE {
	awnSysConnLsVccUnit		INTEGER,
	awnSysConnLsVccCard		INTEGER,
	awnSysConnLsVccPort		INTEGER,
	awnSysConnLsVccTimeslot		INTEGER,
	awnSysConnLsVccVpi		INTEGER,
	awnSysConnLsVccVci		INTEGER,
	awnSysConnLsVccState		OCTET STRING
}

awnSysConnLsVccUnit               OBJECT-TYPE
    SYNTAX  INTEGER (1..8)
    ACCESS  read-only
    STATUS  mandatory
    DESCRIPTION
           "LS unit number"
    ::= { awnSysConnLsVccEntry 1 }

awnSysConnLSVccCard               OBJECT-TYPE
    SYNTAX  INTEGER (1..18)
    ACCESS  read-only
    STATUS  mandatory
    DESCRIPTION
           "LS card number"
    ::= { awnSysConnLsVccEntry 2 }

awnSysConnLsVccPort            OBJECT-TYPE
    SYNTAX  INTEGER (1..8)
    ACCESS  read-only
    STATUS  mandatory
    DESCRIPTION
           "LS port number"
    ::= { awnSysConnLsVccEntry 3 }

awnSysConnLsVccTimeslot            OBJECT-TYPE
    SYNTAX  INTEGER (0..96)
    ACCESS  read-only
    STATUS  mandatory
    DESCRIPTION
           "Timeslot number"
    ::= { awnSysConnLsVccEntry 4 }

awnSysConnLsVccVpi            OBJECT-TYPE
    SYNTAX  INTEGER (0..255)
    ACCESS  read-only
    STATUS  mandatory
    DESCRIPTION
           "VPI"
    ::= { awnSysConnLsVccEntry 5 }

awnSysConnLsVccVci            OBJECT-TYPE
    SYNTAX  INTEGER (0..4095)
    ACCESS  read-only
    STATUS  mandatory
    DESCRIPTION
           "VCI"
    ::= { awnSysConnLsVccEntry 6 }


awnSysConnLsVccState        OBJECT-TYPE
    SYNTAX  OCTET STRING (SIZE(100))
    ACCESS  read-only
    STATUS  mandatory
    DESCRIPTION
           "State"
    ::= { awnSysConnLsVccEntry 7 }

-- groups in awnSysBackIpAddr

awnSysBackIpAddr            OBJECT IDENTIFIER ::= { awnSystem 11 }

--
--
-- groups in awnStatistics
--
--

awnStatistics          OBJECT IDENTIFIER ::= { awn 2 }

-- the SysStatisticsSw group

awnStatisticsSw         OBJECT IDENTIFIER ::= { awnStatistics 1 }

awnStatisticsSwport  OBJECT-TYPE
    SYNTAX  OCTET STRING (SIZE(4))
    ACCESS  not-accessible
    STATUS  obsolete
    DESCRIPTION
           "Not supported"
    ::= { awnStatisticsSw 1 }

-- the SysStatisticsLine group

awnStatisticsLine         OBJECT IDENTIFIER ::= { awnStatistics 2 }

awnStatisticsLineTable  OBJECT-TYPE
    SYNTAX  SEQUENCE OF AwnStatisticsLineEntry  
    ACCESS  not-accessible
    STATUS  obsolete
    DESCRIPTION
           "Table" 
     ::= { awnStatisticsLine 1 }

awnStatisticsLineEntry  OBJECT-TYPE
    SYNTAX  AwnStatisticsLineEntry  
    ACCESS  not-accessible
    STATUS  obsolete
    DESCRIPTION
      "Entry" 
    INDEX  { awnStatisticsLineUnit, awnStatisticsLineCard, awnStatisticsLinePort }
    ::= { awnStatisticsLineTable 1 }
	
AwnStatisticsLineEntry		::= SEQUENCE {
	awnStatisticsLineUnit		INTEGER,
	awnStatisticsLineCard		INTEGER,
	awnStatisticsLinePort		INTEGER,
	awnStatisticsLinePriWan		OCTET STRING,
	awnStatisticsLineSriWan		OCTET STRING,
	awnStatisticsLineBriWan		OCTET STRING
}

awnStatisticsLineUnit  OBJECT-TYPE
    SYNTAX  INTEGER  
    ACCESS  read-only
    STATUS  obsolete
    DESCRIPTION
           "LS unit number"
    ::= { awnStatisticsLineEntry 1 }

awnStatisticsLineCard  OBJECT-TYPE
    SYNTAX  INTEGER
    ACCESS  read-only
    STATUS  obsolete
    DESCRIPTION
           "LS card number"
    ::= { awnStatisticsLineEntry 2 }

awnStatisticsLinePort  OBJECT-TYPE
    SYNTAX  INTEGER
    ACCESS  read-only
    STATUS  obsolete
    DESCRIPTION
           "LS port number"
    ::= { awnStatisticsLineEntry 3 }

awnStatisticsLinePriWan  OBJECT-TYPE
    SYNTAX  OCTET STRING (SIZE(24))
    ACCESS  read-only
    STATUS  obsolete
    DESCRIPTION
           "PRI-WAN statistics"
    ::= { awnStatisticsLineEntry 4 }

awnStatisticsLineSriWan  OBJECT-TYPE
    SYNTAX  OCTET STRING (SIZE(24))
    ACCESS  not-accessible
    STATUS  obsolete
    DESCRIPTION
           "Not supported"
    ::= { awnStatisticsLineEntry 5 }

awnStatisticsLineBriWan  OBJECT-TYPE
    SYNTAX  OCTET STRING (SIZE(24))
    ACCESS  read-only
    STATUS  obsolete
    DESCRIPTION
           "Statistics of BRI-WAN"
    ::= { awnStatisticsLineEntry 6 }

-- the awnStatisticsComLine group

awnStatisticsComLine	OBJECT IDENTIFIER ::= { awnStatistics 3 }

awnStatisticsComLineTable	OBJECT-TYPE
    SYNTAX	SEQUENCE OF AwnStatisticsComLineEntry  
    ACCESS	not-accessible
    STATUS	mandatory
    DESCRIPTION
	"Table" 
    ::= { awnStatisticsComLine 1 }

awnStatisticsComLineEntry	OBJECT-TYPE
    SYNTAX	AwnStatisticsComLineEntry
    ACCESS	not-accessible
    STATUS	mandatory
    DESCRIPTION
	"Entry" 
    INDEX	{ awnStatisticsComLineSlot, awnStatisticsComLineAdapter, awnStatisticsComLinePort }
    ::= { awnStatisticsComLineTable 1 }

AwnStatisticsComLineEntry ::= SEQUENCE {
	awnStatisticsComLineSlot	INTEGER,
	awnStatisticsComLineAdapter	INTEGER,
	awnStatisticsComLinePort	INTEGER,
	awnStatisticsComLineAtm		OCTET STRING,
	awnStatisticsComLan		OCTET STRING
}

awnStatisticsComLineSlot	OBJECT-TYPE
    SYNTAX	INTEGER (1..4)
    ACCESS	read-only
    STATUS	mandatory
    DESCRIPTION
	"COM slot number"
    ::= { awnStatisticsComLineEntry 1 }

awnStatisticsComLineAdapter	OBJECT-TYPE
    SYNTAX	INTEGER (1..2)
    ACCESS	read-only
    STATUS	mandatory
    DESCRIPTION
	"COM adapter number"
    ::= { awnStatisticsComLineEntry 2 }

awnStatisticsComLinePort	OBJECT-TYPE
    SYNTAX	INTEGER (1..4)
    ACCESS	read-only
    STATUS	mandatory
    DESCRIPTION
	"COM port number"
    ::= { awnStatisticsComLineEntry 3 }

awnStatisticsComLineAtm		OBJECT-TYPE
    SYNTAX	OCTET STRING (SIZE(132))
    ACCESS	read-only
    STATUS	mandatory
    DESCRIPTION
	"Statictics of ATM"
    ::= { awnStatisticsComLineEntry 4 }

awnStatisticsComLan		OBJECT-TYPE
    SYNTAX	OCTET STRING (SIZE(264))
    ACCESS	read-only
    STATUS	mandatory
    DESCRIPTION
	"Statictics of LAN"
    ::= { awnStatisticsComLineEntry 5 }

-- the awnStatisticsLsLine group

awnStatisticsLsLine	OBJECT IDENTIFIER ::= { awnStatistics 4 }

awnStatisticsLsLineTable	OBJECT-TYPE
    SYNTAX	SEQUENCE OF AwnStatisticsLsLineEntry
    ACCESS	not-accessible
    STATUS	mandatory
    DESCRIPTION
	"Table" 
    ::= { awnStatisticsLsLine 1 }

awnStatisticsLsLineEntry	OBJECT-TYPE
    SYNTAX	AwnStatisticsLsLineEntry
    ACCESS	not-accessible
    STATUS	mandatory
    DESCRIPTION
	"Entry" 
    INDEX	{ awnStatisticsLsLineUnit, awnStatisticsLsLineCard, awnStatisticsLsLinePort }
    ::= { awnStatisticsLsLineTable 1 }

AwnStatisticsLsLineEntry ::= SEQUENCE {
	awnStatisticsLsLineSlot		INTEGER,
	awnStatisticsLsLineAdapter	INTEGER,
	awnStatisticsLsLinePort		INTEGER,
	awnStatisticsLsLinePriWan	OCTET STRING,
	awnStatisticsLsLineBriWan	OCTET STRING,
	awnStatisticsLsLinePriBup	OCTET STRING,
	awnStatisticsLsLineFrclad	OCTET STRING,
	awnStatisticsLsLineFrclad2	OCTET STRING,
	awnStatisticsLsLineFrclad3	OCTET STRING,
	awnStatisticsLsLineDif		OCTET STRING,
	awnStatisticsLsLineDifFrclad	OCTET STRING,
	awnStatisticsLsLinePriCes	OCTET STRING,
	awnStatisticsLsLineDtkCodec	OCTET STRING,
	awnStatisticsLsLineDtkDclad	OCTET STRING,
	awnStatisticsLsLineDtkDclad2	OCTET STRING,
	awnStatisticsLsLineOdtCodec	OCTET STRING,
	awnStatisticsLsLineOdtDclad	OCTET STRING,
	awnStatisticsLsLineSriCes	OCTET STRING,
	awnStatisticsLsLineBriBup	OCTET STRING,
	awnStatisticsLsLineLrclad	OCTET STRING,
	awnStatisticsLsLine45Mwan	OCTET STRING,
	awnStatisticsLsLineOdtCodecS	OCTET STRING,
	awnStatisticsLsLinePriWan24	OCTET STRING,
	awnStatisticsLsLineFfclad24a	OCTET STRING,
	awnStatisticsLsLineFfclad24b	OCTET STRING,
	awnStatisticsLsLineFfclad24c	OCTET STRING,
	awnStatisticsLsLineVxaWan	OCTET STRING,
	awnStatisticsLsLineBriClad	OCTET STRING
}

awnStatisticsLsLineUnit		OBJECT-TYPE
    SYNTAX	INTEGER (1..8)
    ACCESS	read-only
    STATUS	mandatory
    DESCRIPTION
	"LS unit number"
    ::= { awnStatisticsLsLineEntry 1 }

awnStatisticsLsLineCard		OBJECT-TYPE
    SYNTAX	INTEGER (1..18)
    ACCESS	read-only
    STATUS	mandatory
    DESCRIPTION
	"LS card number"
    ::= { awnStatisticsLsLineEntry 2 }

awnStatisticsLsLinePort		OBJECT-TYPE
    SYNTAX	INTEGER (1..8)
    ACCESS	read-only
    STATUS	mandatory
    DESCRIPTION
	"LS port number"
    ::= { awnStatisticsLsLineEntry 3 }

awnStatisticsLsLinePriWan	OBJECT-TYPE
    SYNTAX	OCTET STRING (SIZE(504))
    ACCESS	read-only
    STATUS	mandatory
    DESCRIPTION
	"Statictics of PRI-WAN"
    ::= { awnStatisticsLsLineEntry 4 }

awnStatisticsLsLineBriWan	OBJECT-TYPE
    SYNTAX	OCTET STRING (SIZE(120))
    ACCESS	read-only
    STATUS	mandatory
    DESCRIPTION
	"Statictics of BRI-WAN"
    ::= { awnStatisticsLsLineEntry 5 }

awnStatisticsLsLinePriBup	OBJECT-TYPE
    SYNTAX	OCTET STRING (SIZE(120))
    ACCESS	read-only
    STATUS	mandatory
    DESCRIPTION
	"Statictics of PRI-BUP"
    ::= { awnStatisticsLsLineEntry 6 }

awnStatisticsLsLineFrclad	OBJECT-TYPE
    SYNTAX	OCTET STRING (SIZE(504))
    ACCESS	read-only
    STATUS	mandatory
    DESCRIPTION
	"Statictics of FR-CLAD(part 1)"
    ::= { awnStatisticsLsLineEntry 7 }

awnStatisticsLsLineFrclad2	OBJECT-TYPE
    SYNTAX	OCTET STRING (SIZE(584))
    ACCESS	read-only
    STATUS	mandatory
    DESCRIPTION
	"Statictics of FR-CLAD(part 2)"
    ::= { awnStatisticsLsLineEntry 8 }

awnStatisticsLsLineFrclad3	OBJECT-TYPE
    SYNTAX	OCTET STRING (SIZE(584))
    ACCESS	read-only
    STATUS	mandatory
    DESCRIPTION
	"Statictics of FR-CLAD(part 3)"
    ::= { awnStatisticsLsLineEntry 9 }

awnStatisticsLsLineLineDif	OBJECT-TYPE
    SYNTAX	OCTET STRING (SIZE(128))
    ACCESS	read-only
    STATUS	mandatory
    DESCRIPTION
	"Statictics of DIF1(D-CLAD)"
    ::= { awnStatisticsLsLineEntry 10 }

awnStatisticsLsLineDifFrclad	OBJECT-TYPE
    SYNTAX	OCTET STRING (SIZE(160))
    ACCESS	read-only
    STATUS	mandatory
    DESCRIPTION
	"Statictics of DIF1/DIF2(FR-CLAD)"
    ::= { awnStatisticsLsLineEntry 11 }

awnStatisticsLsLinePriCes	OBJECT-TYPE
    SYNTAX	OCTET STRING (SIZE(328))
    ACCESS	read-only
    STATUS	mandatory
    DESCRIPTION
	"Statictics of PRI-CES"
    ::= { awnStatisticsLsLineEntry 12 }

awnStatisticsLsLineDtkCodec	OBJECT-TYPE
    SYNTAX	OCTET STRING (SIZE(724))
    ACCESS	read-only
    STATUS	mandatory
    DESCRIPTION
	"Statictics of DTK(CODEC)"
    ::= { awnStatisticsLsLineEntry 13 }

awnStatisticsLsLineDtkDclad	OBJECT-TYPE
    SYNTAX	OCTET STRING (SIZE(600))
    ACCESS	read-only
    STATUS	mandatory
    DESCRIPTION
	"Statictics of DTK(D-CLAD)(part 1)"
    ::= { awnStatisticsLsLineEntry 14 }

awnStatisticsLsLineDtkDclad2	OBJECT-TYPE
    SYNTAX	OCTET STRING (SIZE(352))
    ACCESS	read-only
    STATUS	mandatory
    DESCRIPTION
	"Statictics of DTK(D-CLAD)(part 2)"
    ::= { awnStatisticsLsLineEntry 15 }

awnStatisticsLsLineOdtCodec	OBJECT-TYPE
    SYNTAX	OCTET STRING (SIZE(124))
    ACCESS	read-only
    STATUS	mandatory
    DESCRIPTION
	"Statictics of ODT(CODEC)"
    ::= { awnStatisticsLsLineEntry 16 }

awnStatisticsLsLineOdtDclad	OBJECT-TYPE
    SYNTAX	OCTET STRING (SIZE(128))
    ACCESS	read-only
    STATUS	mandatory
    DESCRIPTION
	"Statictics of ODT(D-CLAD)"
    ::= { awnStatisticsLsLineEntry 17 }

awnStatisticsLsLineSriCes	OBJECT-TYPE
    SYNTAX	OCTET STRING (SIZE(112))
    ACCESS	read-only
    STATUS	mandatory
    DESCRIPTION
	"Statictics of ODT(D-CLAD)"
    ::= { awnStatisticsLsLineEntry 18 }

awnStatisticsLsLineBriBup	OBJECT-TYPE
    SYNTAX	OCTET STRING (SIZE(120))
    ACCESS	read-only
    STATUS	mandatory
    DESCRIPTION
	"Statictics of BRI-BUP"
    ::= { awnStatisticsLsLineEntry 19 }

awnStatisticsLsLineLrcrad	OBJECT-TYPE
    SYNTAX	OCTET STRING (SIZE(124))
    ACCESS	read-only
    STATUS	mandatory
    DESCRIPTION
	"Statictics of LR-CLAD"
    ::= { awnStatisticsLsLineEntry 20 }

awnStatisticsLsLine45Mwan	OBJECT-TYPE
    SYNTAX	OCTET STRING (SIZE(152))
    ACCESS	read-only
    STATUS	mandatory
    DESCRIPTION
	"Statictics of 45M-WAN"
    ::= { awnStatisticsLsLineEntry 21 }

awnStatisticsLsLineOdtCodecS	OBJECT-TYPE
    SYNTAX	OCTET STRING (SIZE(144))
    ACCESS	read-only
    STATUS	mandatory
    DESCRIPTION
	"Statictics of ODT(CODEC)+signal"
    ::= { awnStatisticsLsLineEntry 22 }

awnStatisticsLsLinePriWan24	OBJECT-TYPE
    SYNTAX	OCTET STRING (SIZE(500))
    ACCESS	read-only
    STATUS	mandatory
    DESCRIPTION
	"Statictics of PRI-WAN24"
    ::= { awnStatisticsLsLineEntry 23 }

awnStatisticsLsLineFfclad24a	OBJECT-TYPE
    SYNTAX	OCTET STRING (SIZE(496))
    ACCESS	read-only
    STATUS	mandatory
    DESCRIPTION
	"Statictics of FF-CLAD24(part 1)"
    ::= { awnStatisticsLsLineEntry 24 }

awnStatisticsLsLineFfclad24b	OBJECT-TYPE
    SYNTAX	OCTET STRING (SIZE(584))
    ACCESS	read-only
    STATUS	mandatory
    DESCRIPTION
	"Statictics of FF-CLAD24(part 2)"
    ::= { awnStatisticsLsLineEntry 25 }

awnStatisticsLsLineFfclad24c	OBJECT-TYPE
    SYNTAX	OCTET STRING (SIZE(588))
    ACCESS	read-only
    STATUS	mandatory
    DESCRIPTION
	"Statictics of FF-CLAD24(part 3)"
    ::= { awnStatisticsLsLineEntry 26 }

awnStatisticsLsLineVxaWan	OBJECT-TYPE
    SYNTAX	OCTET STRING (SIZE(116))
    ACCESS	read-only
    STATUS	mandatory
    DESCRIPTION
	"Statictics of VXA-WAN"
    ::= { awnStatisticsLsLineEntry 27 }

awnStatisticsLsLineBriClad	OBJECT-TYPE
    SYNTAX	OCTET STRING (SIZE(160))
    ACCESS	read-only
    STATUS	mandatory
    DESCRIPTION
	"Statictics of BRI-CLAD"
    ::= { awnStatisticsLsLineEntry 28 }

-- the awnStatisticsComNniPort group

awnStatisticsComNniPort	OBJECT IDENTIFIER ::= { awnStatistics 5 }

awnStatisticsComNniPortTable	OBJECT-TYPE
    SYNTAX	SEQUENCE OF AwnStatisticsComNniPortEntry
    ACCESS	not-accessible
    STATUS	mandatory
    DESCRIPTION
	"Table" 
    ::= { awnStatisticsComNniPort 1 }

awnStatisticsComNniPortEntry	OBJECT-TYPE
    SYNTAX	AwnStatisticsComNniPortEntry
    ACCESS	not-accessible
    STATUS	mandatory
    DESCRIPTION
	"Entry" 
    INDEX	{ awnStatisticsComNniPortSlot, awnStatisticsComNniPortAdapter, awnStatisticsComNniPortPort }
    ::= { awnStatisticsComNniPortTable 1 }

AwnStatisticsComNniPortEntry ::= SEQUENCE {
	awnStatisticsComNniPortSlot	INTEGER,
	awnStatisticsComNniPortAdapter	INTEGER,
	awnStatisticsComNniPortPort	INTEGER,
	awnStatisticsComNniPortData	OCTET STRING
}

awnStatisticsComNniPortSlot	OBJECT-TYPE
    SYNTAX	INTEGER (1..4)
    ACCESS	read-only
    STATUS	mandatory
    DESCRIPTION
	"COM slot number"
    ::= { awnStatisticsComNniPortEntry 1 }

awnStatisticsComNniPortAdapter	OBJECT-TYPE
    SYNTAX	INTEGER (1..2)
    ACCESS	read-only
    STATUS	mandatory
    DESCRIPTION
	"COM adapter number"
    ::= { awnStatisticsComNniPortEntry 2 }

awnStatisticsComNniPortPort	OBJECT-TYPE
    SYNTAX	INTEGER (1..4)
    ACCESS	read-only
    STATUS	mandatory
    DESCRIPTION
	"COM port number"
    ::= { awnStatisticsComNniPortEntry 3 }

awnStatisticsComNniPortData	OBJECT-TYPE
    SYNTAX	OCTET STRING (SIZE(456))
    ACCESS	read-only
    STATUS	mandatory
    DESCRIPTION
	"Data"
    ::= { awnStatisticsComNniPortEntry 4 }

-- the awnStatisticsComNniVp group

awnStatisticsComNniVp	OBJECT IDENTIFIER ::= { awnStatistics 6 }

awnStatisticsComNniVpTable	OBJECT-TYPE
    SYNTAX	SEQUENCE OF AwnStatisticsComNniVpEntry
    ACCESS	not-accessible
    STATUS	mandatory
    DESCRIPTION
	"Table" 
    ::= { awnStatisticsComNniVp 1 }

awnStatisticsComNniVpEntry	OBJECT-TYPE
    SYNTAX	AwnStatisticsComNniVpEntry
    ACCESS	not-accessible
    STATUS	mandatory
    DESCRIPTION
	"Entry" 
    INDEX	{ awnStatisticsComNniVpSlot, awnStatisticsComNniVpAdapter, awnStatisticsComNniVpPort, awnStatisticsComNniVpVpi }
    ::= { awnStatisticsComNniVpTable 1 }

AwnStatisticsComNniVpEntry ::= SEQUENCE {
	awnStatisticsComNniVpSlot	INTEGER,
	awnStatisticsComNniVpAdapter	INTEGER,
	awnStatisticsComNniVpPort	INTEGER,
	awnStatisticsComNniVpVpi	INTEGER,
	awnStatisticsComNniVpData	OCTET STRING
}

awnStatisticsComNniVpSlot	OBJECT-TYPE
    SYNTAX	INTEGER (1..4)
    ACCESS	read-only
    STATUS	mandatory
    DESCRIPTION
	"COM slot number"
    ::= { awnStatisticsComNniVpEntry 1 }

awnStatisticsComNniVpAdapter	OBJECT-TYPE
    SYNTAX	INTEGER (1..2)
    ACCESS	read-only
    STATUS	mandatory
    DESCRIPTION
	"COM adapter number"
    ::= { awnStatisticsComNniVpEntry 2 }

awnStatisticsComNniVpPort	OBJECT-TYPE
    SYNTAX	INTEGER (1..4)
    ACCESS	read-only
    STATUS	mandatory
    DESCRIPTION
	"COM port number"
    ::= { awnStatisticsComNniVpEntry 3 }

awnStatisticsComNniVpVpi	OBJECT-TYPE
    SYNTAX	INTEGER (1..255)
    ACCESS	read-only
    STATUS	mandatory
    DESCRIPTION
	"VPI"
    ::= { awnStatisticsComNniVpEntry 4 }

awnStatisticsComNniVptData	OBJECT-TYPE
    SYNTAX	OCTET STRING (SIZE(456))
    ACCESS	read-only
    STATUS	mandatory
    DESCRIPTION
	"Data"
    ::= { awnStatisticsComNniVpEntry 5 }

-- the awnStatisticsLsWanTs group

awnStatisticsLsWanTs	OBJECT IDENTIFIER ::= { awnStatistics 7 }

awnStatisticsLsWanTsTable	OBJECT-TYPE
    SYNTAX	SEQUENCE OF AwnStatisticsLsWanTsEntry
    ACCESS	not-accessible
    STATUS	mandatory
    DESCRIPTION
	"Table" 
    ::= { awnStatisticsLsWanTs 1 }

awnStatisticsLsWanTsEntry	OBJECT-TYPE
    SYNTAX	AwnStatisticsLsWanTsEntry
    ACCESS	not-accessible
    STATUS	mandatory
    DESCRIPTION
	"Entry" 
    INDEX	{ awnStatisticsLsWanTsUnit, awnStatisticsLsWanTsCard, awnStatisticsLsWanTsPort, awnStatisticsLsWanTsTs }
    ::= { awnStatisticsLsWanTsTable 1 }

AwnStatisticsLsWanTsEntry ::= SEQUENCE {
	awnStatisticsLsWanTsUnit	INTEGER,
	awnStatisticsLsWanTsCard	INTEGER,
	awnStatisticsLsWanTsPort	INTEGER,
	awnStatisticsLsWanTsTs		INTEGER,
	awnStatisticsLsWanTsData	OCTET STRING
}

awnStatisticsLsWanTsUnit	OBJECT-TYPE
    SYNTAX	INTEGER (1..8)
    ACCESS	read-only
    STATUS	mandatory
    DESCRIPTION
	"LS unit number"
    ::= { awnStatisticsLsWanTsEntry 1 }

awnStatisticsLsWanTsCard	OBJECT-TYPE
    SYNTAX	INTEGER (1..18)
    ACCESS	read-only
    STATUS	mandatory
    DESCRIPTION
	"LS card number"
    ::= { awnStatisticsLsWanTsEntry 2 }

awnStatisticsLsWanTsPort	OBJECT-TYPE
    SYNTAX	INTEGER (1..8)
    ACCESS	read-only
    STATUS	mandatory
    DESCRIPTION
	"LS port number"
    ::= { awnStatisticsLsWanTsEntry 3 }

awnStatisticsLsWanTsTs		OBJECT-TYPE
    SYNTAX	INTEGER (1..96)
    ACCESS	read-only
    STATUS	mandatory
    DESCRIPTION
	"TS number"
    ::= { awnStatisticsLsWanTsEntry 4 }

awnStatisticsLsWanTsData	OBJECT-TYPE
    SYNTAX	OCTET STRING (SIZE(456))
    ACCESS	read-only
    STATUS	mandatory
    DESCRIPTION
	"Data"
    ::= { awnStatisticsLsWanTsEntry 5 }

-- the awnStatisticsComNniPortRt group

awnStatisticsComNniPortRt	OBJECT IDENTIFIER ::= { awnStatistics 8 }

awnStatisticsComNniPortRtTable	OBJECT-TYPE
    SYNTAX	SEQUENCE OF AwnStatisticsComNniPortRtEntry
    ACCESS	not-accessible
    STATUS	mandatory
    DESCRIPTION
	"Table" 
    ::= { awnStatisticsComNniPortRt 1 }

awnStatisticsComNniPortRtEntry	OBJECT-TYPE
    SYNTAX	AwnStatisticsComNniPortRtEntry
    ACCESS	not-accessible
    STATUS	mandatory
    DESCRIPTION
	"Entry" 
    INDEX	{ awnStatisticsComNniPortRtSlot, awnStatisticsComNniPortRtAdapter, awnStatisticsComNniPortRtPort, awnStatisticsComNniPortRtCategory, awnStatisticsComNniPortRtType }
    ::= { awnStatisticsComNniPortRtTable 1 }

AwnStatisticsComNniPortRtEntry ::= SEQUENCE {
	awnStatisticsComNniPortRtSlot		INTEGER,
	awnStatisticsComNniPortRtAdapter	INTEGER,
	awnStatisticsComNniPortRtPort		INTEGER,
	awnStatisticsComNniPortRtCategory	INTEGER,
	awnStatisticsComNniPortRtType		INTEGER,
	awnStatisticsComNniPortRtData		Gauge
}

awnStatisticsComNniPortRtSlot	OBJECT-TYPE
    SYNTAX	INTEGER (1..4)
    ACCESS	read-only
    STATUS	mandatory
    DESCRIPTION
	"Com slot number"
    ::= { awnStatisticsComNniPortRtEntry 1 }

awnStatisticsComNniPortRtAdapter	OBJECT-TYPE
    SYNTAX	INTEGER (1..2)
    ACCESS	read-only
    STATUS	mandatory
    DESCRIPTION
	"COM adapter number"
    ::= { awnStatisticsComNniPortRtEntry 2 }

awnStatisticsComNniPortRtPort	OBJECT-TYPE
    SYNTAX	INTEGER (1..4)
    ACCESS	read-only
    STATUS	mandatory
    DESCRIPTION
	"COM port number"
    ::= { awnStatisticsComNniPortRtEntry 3 }

awnStatisticsComNniPortRtCategory	OBJECT-TYPE
    SYNTAX	INTEGER (1..9)
    ACCESS	read-only
    STATUS	mandatory
    DESCRIPTION
	"Category"
    ::= { awnStatisticsComNniPortRtEntry 4 }

awnStatisticsComNniPortRtType	OBJECT-TYPE
    SYNTAX	INTEGER (1..3)
    ACCESS	read-only
    STATUS	mandatory
    DESCRIPTION
	"Type"
    ::= { awnStatisticsComNniPortRtEntry 5 }

awnStatisticsComNniPortRtData	OBJECT-TYPE
    SYNTAX	Gauge (1..4294967295)
    ACCESS	read-only
    STATUS	mandatory
    DESCRIPTION
	"Data"
    ::= { awnStatisticsComNniPortRtEntry 6 }

-- the awnStatisticsComNniVpRt group

awnStatisticsComNniVpRt	OBJECT IDENTIFIER ::= { awnStatistics 9 }

awnStatisticsComNniVpRtTable	OBJECT-TYPE
    SYNTAX	SEQUENCE OF AwnStatisticsComNniPortRtEntry2
    ACCESS	not-accessible
    STATUS	mandatory
    DESCRIPTION
	"Table" 
    ::= { awnStatisticsComNniVpRt 1 }

awnStatisticsComNniVpRtEntry	OBJECT-TYPE
    SYNTAX	AwnStatisticsComNniPortRtEntry2
    ACCESS	not-accessible
    STATUS	mandatory
    DESCRIPTION
	"Entry" 
    INDEX	{ awnStatisticsComNniVpRtSlot, awnStatisticsComNniVpRtAdapter, awnStatisticsComNniVpRtPort, awnStatisticsComNniVpRtVpi, awnStatisticsComNniVpRtCategory, awnStatisticsComNniVpRtType }
    ::= { awnStatisticsComNniVpRtTable 1 }

AwnStatisticsComNniPortRtEntry2 ::= SEQUENCE {
	awnStatisticsComNniVptRtSlot	INTEGER,
	awnStatisticsComNniVpRtAdapter	INTEGER,
	awnStatisticsComNniVpRtPort	INTEGER,
	awnStatisticsComNniVpRtVpi	INTEGER,
	awnStatisticsComNniVpRtCategory	INTEGER,
	awnStatisticsComNniVpRtType	INTEGER,
	awnStatisticsComNniVpRtData	Gauge
}

awnStatisticsComNniVpRtSlot	OBJECT-TYPE
    SYNTAX	INTEGER (1..4)
    ACCESS	read-only
    STATUS	mandatory
    DESCRIPTION
	"Com slot number"
    ::= { awnStatisticsComNniVpRtEntry 1 }

awnStatisticsComNniVpRtAdapter	OBJECT-TYPE
    SYNTAX	INTEGER (1..2)
    ACCESS	read-only
    STATUS	mandatory
    DESCRIPTION
	"COM adapter number"
    ::= { awnStatisticsComNniVpRtEntry 2 }

awnStatisticsComNniVpRtPort	OBJECT-TYPE
    SYNTAX	INTEGER (1..4)
    ACCESS	read-only
    STATUS	mandatory
    DESCRIPTION
	"COM port number"
    ::= { awnStatisticsComNniVpRtEntry 3 }

awnStatisticsComNniVpRtVpi	OBJECT-TYPE
    SYNTAX	INTEGER (0..255)
    ACCESS	read-only
    STATUS	mandatory
    DESCRIPTION
	"VPI"
    ::= { awnStatisticsComNniVpRtEntry 4 }

awnStatisticsComNniVpRtCategory	OBJECT-TYPE
    SYNTAX	INTEGER (1..9)
    ACCESS	read-only
    STATUS	mandatory
    DESCRIPTION
	"Category"
    ::= { awnStatisticsComNniVpRtEntry 5 }

awnStatisticsComNniVpRtType	OBJECT-TYPE
    SYNTAX	INTEGER (1..3)
    ACCESS	read-only
    STATUS	mandatory
    DESCRIPTION
	"Type"
    ::= { awnStatisticsComNniVpRtEntry 6 }

awnStatisticsComNniVpRtData	OBJECT-TYPE
    SYNTAX	Gauge (1..4294967295)
    ACCESS	read-only
    STATUS	mandatory
    DESCRIPTION
	"Data"
    ::= { awnStatisticsComNniVpRtEntry 7 }

-- the awnStatisticsLsWanTsRt group

awnStatisticsLsWanTsRt	OBJECT IDENTIFIER ::= { awnStatistics 10 }

awnStatisticsLsWanTsRtTable	OBJECT-TYPE
    SYNTAX	SEQUENCE OF AwnStatisticsComNniPortRtEntry3
    ACCESS	not-accessible
    STATUS	mandatory
    DESCRIPTION
	"Table" 
    ::= { awnStatisticsLsWanTsRt 1 }

awnStatisticsLsWanTsRtEntry	OBJECT-TYPE
    SYNTAX	AwnStatisticsComNniPortRtEntry3
    ACCESS	not-accessible
    STATUS	mandatory
    DESCRIPTION
	"Entry" 
    INDEX	{ awnStatisticsLsWanTsRtUnit, awnStatisticsLsWanTsRtCard, awnStatisticsLsWanTsRtPort, awnStatisticsLsWanTsRtTs, awnStatisticsLsWanTsRtCategory, awnStatisticsLsWanTsRtType }
    ::= { awnStatisticsLsWanTsRtTable 1 }

AwnStatisticsComNniPortRtEntry3 ::= SEQUENCE {
	awnStatisticsLsWanTsRtUnit	INTEGER,
	awnStatisticsLsWanTsRtCard	INTEGER,
	awnStatisticsLsWanTsRtPort	INTEGER,
	awnStatisticsLsWanTsRtTs	INTEGER,
	awnStatisticsLsWanTsRtCategory	INTEGER,
	awnStatisticsLsWanTsRtType	INTEGER,
	awnStatisticsLsWanTsRtData	Gauge
}

awnStatisticsLsWanTsRtUnit	OBJECT-TYPE
    SYNTAX	INTEGER (1..8)
    ACCESS	read-only
    STATUS	mandatory
    DESCRIPTION
	"LS unit number"
    ::= { awnStatisticsLsWanTsRtEntry 1 }

awnStatisticsLsWanTsRtCard	OBJECT-TYPE
    SYNTAX	INTEGER (1..18)
    ACCESS	read-only
    STATUS	mandatory
    DESCRIPTION
	"LS card number"
    ::= { awnStatisticsLsWanTsRtEntry 2 }

awnStatisticsLsWanTsRtPort	OBJECT-TYPE
    SYNTAX	INTEGER (1..8)
    ACCESS	read-only
    STATUS	mandatory
    DESCRIPTION
	"LS port number"
    ::= { awnStatisticsLsWanTsRtEntry 3 }

awnStatisticsLsWanTsRtTs	OBJECT-TYPE
    SYNTAX	INTEGER (1..96)
    ACCESS	read-only
    STATUS	mandatory
    DESCRIPTION
	"TS number"
    ::= { awnStatisticsLsWanTsRtEntry 4 }

awnStatisticsLsWanTsRtCategory	OBJECT-TYPE
    SYNTAX	INTEGER (1..9)
    ACCESS	read-only
    STATUS	mandatory
    DESCRIPTION
	"Category"
    ::= { awnStatisticsLsWanTsRtEntry 5 }

awnStatisticsLsWanTsRtType	OBJECT-TYPE
    SYNTAX	INTEGER (1..3)
    ACCESS	read-only
    STATUS	mandatory
    DESCRIPTION
	"Type"
    ::= { awnStatisticsLsWanTsRtEntry 6 }

awnStatisticsLsWanTsRtData	OBJECT-TYPE
    SYNTAX	Gauge (1..4294967295)
    ACCESS	read-only
    STATUS	mandatory
    DESCRIPTION
	"Data"
    ::= { awnStatisticsLsWanTsRtEntry 7 }

-- the awnStatisticsVccAtmLine group

awnStatisticsVccAtmLine	OBJECT IDENTIFIER ::= { awnStatistics 11 }

awnStatisticsVccAtmLineTable	OBJECT-TYPE
    SYNTAX	SEQUENCE OF AwnStatisticsVccAtmLineEntry
    ACCESS	not-accessible
    STATUS	mandatory
    DESCRIPTION
	"Table" 
    ::= { awnStatisticsVccAtmLine 1 }

awnStatisticsVccAtmLineEntry	OBJECT-TYPE
    SYNTAX	AwnStatisticsVccAtmLineEntry
    ACCESS	not-accessible
    STATUS	mandatory
    DESCRIPTION
	"Entry" 
    INDEX	{ awnStatisticsVccAtmLineSlot, awnStatisticsVccAtmLineAdapter, awnStatisticsVccAtmLinePort, awnStatisticsVccAtmLineVpi, awnStatisticsVccAtmLineVci, awnStatisticsVccAtmLineType }
    ::= { awnStatisticsVccAtmLineTable 1 }

AwnStatisticsVccAtmLineEntry ::= SEQUENCE {
	awnStatisticsVccAtmLineSlot	INTEGER,
	awnStatisticsVccAtmLineAdapter	INTEGER,
	awnStatisticsVccAtmLinePort	INTEGER,
	awnStatisticsVccAtmLineVpi	INTEGER,
	awnStatisticsVccAtmLineVci	INTEGER,
	awnStatisticsVccAtmLineType	INTEGER,
	awnStatisticsVccAtmLineData	Gauge
}

awnStatisticsVccAtmLineSlot	OBJECT-TYPE
    SYNTAX	INTEGER (1..4)
    ACCESS	read-only
    STATUS	mandatory
    DESCRIPTION
	"Com slot number"
    ::= { awnStatisticsVccAtmLineEntry 1 }

awnStatisticsVccAtmLineAdapter	OBJECT-TYPE
    SYNTAX	INTEGER (1..2)
    ACCESS	read-only
    STATUS	mandatory
    DESCRIPTION
	"COM adapter number"
    ::= { awnStatisticsVccAtmLineEntry 2 }

awnStatisticsVccAtmLinePort	OBJECT-TYPE
    SYNTAX	INTEGER (1..4)
    ACCESS	read-only
    STATUS	mandatory
    DESCRIPTION
	"COM port number"
    ::= { awnStatisticsVccAtmLineEntry 3 }

awnStatisticsVccAtmLineVpi	OBJECT-TYPE
    SYNTAX	INTEGER (0..255)
    ACCESS	read-only
    STATUS	mandatory
    DESCRIPTION
	"VPI"
    ::= { awnStatisticsVccAtmLineEntry 4 }

awnStatisticsVccAtmLineVci	OBJECT-TYPE
    SYNTAX	INTEGER (32..4095)
    ACCESS	read-only
    STATUS	mandatory
    DESCRIPTION
	"VCI"
    ::= { awnStatisticsVccAtmLineEntry 5 }

awnStatisticsVccAtmLineType	OBJECT-TYPE
    SYNTAX	INTEGER (1..3)
    ACCESS	read-only
    STATUS	mandatory
    DESCRIPTION
	"Type"
    ::= { awnStatisticsVccAtmLineEntry 6 }

awnStatisticsVccAtmLineData	OBJECT-TYPE
    SYNTAX	Gauge (1..4294967295)
    ACCESS	read-only
    STATUS	mandatory
    DESCRIPTION
	"Data"
    ::= { awnStatisticsVccAtmLineEntry 7 }

-- the awnStatisticsVpcAtmLine group

awnStatisticsVpcAtmLine	OBJECT IDENTIFIER ::= { awnStatistics 12 }

awnStatisticsVpcAtmLineTable	OBJECT-TYPE
    SYNTAX	SEQUENCE OF AwnStatisticsVpcAtmLineEntry
    ACCESS	not-accessible
    STATUS	mandatory
    DESCRIPTION
	"Table" 
    ::= { awnStatisticsVpcAtmLine 1 }

awnStatisticsVpcAtmLineEntry	OBJECT-TYPE
    SYNTAX	AwnStatisticsVpcAtmLineEntry
    ACCESS	not-accessible
    STATUS	mandatory
    DESCRIPTION
	"Entry" 
    INDEX	{ awnStatisticsVpcAtmLineSlot, awnStatisticsVpcAtmLineAdapter, awnStatisticsVpcAtmLinePort, awnStatisticsVpcAtmLineVpi, awnStatisticsVpcAtmLineType }
    ::= { awnStatisticsVpcAtmLineTable 1 }

AwnStatisticsVpcAtmLineEntry ::= SEQUENCE {
	awnStatisticsVpcAtmLineSlot	INTEGER,
	awnStatisticsVpcAtmLineAdapter	INTEGER,
	awnStatisticsVpcAtmLinePort	INTEGER,
	awnStatisticsVpcAtmLineVpi	INTEGER,
	awnStatisticsVpcAtmLineType	INTEGER,
	awnStatisticsVpcAtmLineData	Gauge
}

awnStatisticsVpcAtmLineSlot	OBJECT-TYPE
    SYNTAX	INTEGER (1..4)
    ACCESS	read-only
    STATUS	mandatory
    DESCRIPTION
	"Com slot number"
    ::= { awnStatisticsVpcAtmLineEntry 1 }

awnStatisticsVpcAtmLineAdapter	OBJECT-TYPE
    SYNTAX	INTEGER (1..2)
    ACCESS	read-only
    STATUS	mandatory
    DESCRIPTION
	"COM adapter number"
    ::= { awnStatisticsVpcAtmLineEntry 2 }

awnStatisticsVpcAtmLinePort	OBJECT-TYPE
    SYNTAX	INTEGER (1..4)
    ACCESS	read-only
    STATUS	mandatory
    DESCRIPTION
	"COM port number"
    ::= { awnStatisticsVpcAtmLineEntry 3 }

awnStatisticsVpcAtmLineVpi	OBJECT-TYPE
    SYNTAX	INTEGER (0..255)
    ACCESS	read-only
    STATUS	mandatory
    DESCRIPTION
	"VPI"
    ::= { awnStatisticsVpcAtmLineEntry 4 }

awnStatisticsVpcAtmLineType	OBJECT-TYPE
    SYNTAX	INTEGER (1..3)
    ACCESS	read-only
    STATUS	mandatory
    DESCRIPTION
	"Type"
    ::= { awnStatisticsVpcAtmLineEntry 5 }

awnStatisticsVpcAtmLineData	OBJECT-TYPE
    SYNTAX	Gauge (1..4294967295)
    ACCESS	read-only
    STATUS	mandatory
    DESCRIPTION
	"Data"
    ::= { awnStatisticsVpcAtmLineEntry 6 }

-- the awnStatisticsVccWanTs group

awnStatisticsVccWanTs	OBJECT IDENTIFIER ::= { awnStatistics 13 }

awnStatisticsVccWanTsTable	OBJECT-TYPE
    SYNTAX	SEQUENCE OF AwnStatisticsVccWanTsEntry
    ACCESS	not-accessible
    STATUS	mandatory
    DESCRIPTION
	"Table" 
    ::= { awnStatisticsVccWanTs 1 }

awnStatisticsVccWanTsEntry	OBJECT-TYPE
    SYNTAX	AwnStatisticsVccWanTsEntry
    ACCESS	not-accessible
    STATUS	mandatory
    DESCRIPTION
	"Entry" 
    INDEX	{ awnStatisticsVccWanTsUnit, awnStatisticsVccWanTsCard, awnStatisticsVccWanTsPort, awnStatisticsVccWanTsTs, awnStatisticsVccWanTsVpi, awnStatisticsVccWanTsVci, awnStatisticsVccWanTsType }
    ::= { awnStatisticsVccWanTsTable 1 }

AwnStatisticsVccWanTsEntry ::= SEQUENCE {
	awnStatisticsVccWanTsUnit	INTEGER,
	awnStatisticsVccWanTsCard	INTEGER,
	awnStatisticsVccWanTsPort	INTEGER,
	awnStatisticsVccWanTsTs		INTEGER,
	awnStatisticsVccWanTsVpi	INTEGER,
	awnStatisticsVccWanTsVci	INTEGER,
	awnStatisticsVccWanTsType	INTEGER,
	awnStatisticsVccWanTsData	Gauge
}

awnStatisticsVccWanTsUnit	OBJECT-TYPE
    SYNTAX	INTEGER (1..8)
    ACCESS	read-only
    STATUS	mandatory
    DESCRIPTION
	"LS unit number"
    ::= { awnStatisticsVccWanTsEntry 1 }

awnStatisticsVccWanTsCard	OBJECT-TYPE
    SYNTAX	INTEGER (1..18)
    ACCESS	read-only
    STATUS	mandatory
    DESCRIPTION
	"LS card number"
    ::= { awnStatisticsVccWanTsEntry 2 }

awnStatisticsVccWanTsPort	OBJECT-TYPE
    SYNTAX	INTEGER (1..8)
    ACCESS	read-only
    STATUS	mandatory
    DESCRIPTION
	"LS port number"
    ::= { awnStatisticsVccWanTsEntry 3 }

awnStatisticsVccWanTsTs		OBJECT-TYPE
    SYNTAX	INTEGER (1..96)
    ACCESS	read-only
    STATUS	mandatory
    DESCRIPTION
	"LS TS number"
    ::= { awnStatisticsVccWanTsEntry 4 }

awnStatisticsVccWanTsVpi	OBJECT-TYPE
    SYNTAX	INTEGER (0..255)
    ACCESS	read-only
    STATUS	mandatory
    DESCRIPTION
	"VPI"
    ::= { awnStatisticsVccWanTsEntry 5 }

awnStatisticsVccWanTsVci	OBJECT-TYPE
    SYNTAX	INTEGER (0..4095)
    ACCESS	read-only
    STATUS	mandatory
    DESCRIPTION
	"VCI"
    ::= { awnStatisticsVccWanTsEntry 6 }

awnStatisticsVccWanTsType	OBJECT-TYPE
    SYNTAX	INTEGER (1..3)
    ACCESS	read-only
    STATUS	mandatory
    DESCRIPTION
	"Type"
    ::= { awnStatisticsVccWanTsEntry 7 }

awnStatisticsVccWanTsData	OBJECT-TYPE
    SYNTAX	Gauge (0..4294967295)
    ACCESS	read-only
    STATUS	mandatory
    DESCRIPTION
	"Data"
    ::= { awnStatisticsVccWanTsEntry 8 }

-- the awnStatisticsVccFrLine group

awnStatisticsVccFrLine	OBJECT IDENTIFIER ::= { awnStatistics 14 }

awnStatisticsVccFrLineTable	OBJECT-TYPE
    SYNTAX	SEQUENCE OF AwnStatisticsVccFrLineEntry
    ACCESS	not-accessible
    STATUS	mandatory
    DESCRIPTION
	"Table" 
    ::= { awnStatisticsVccFrLine 1 }

awnStatisticsVccFrLineEntry	OBJECT-TYPE
    SYNTAX	AwnStatisticsVccFrLineEntry
    ACCESS	not-accessible
    STATUS	mandatory
    DESCRIPTION
	"Entry" 
    INDEX	{ awnStatisticsVccFrLineUnit, awnStatisticsVccFrLineCard, awnStatisticsVccFrLinePort, awnStatisticsVccFrLineTimeslot, awnStatisticsVccFrLineDlci, awnStatisticsVccFrLineType }
    ::= { awnStatisticsVccFrLineTable 1 }

AwnStatisticsVccFrLineEntry ::= SEQUENCE {
	awnStatisticsVccFrLineUnit	INTEGER,
	awnStatisticsVccFrLineCard	INTEGER,
	awnStatisticsVccFrLinePort	INTEGER,
	awnStatisticsVccFrLineTimeslot	INTEGER,
	awnStatisticsVccFrLineDlci	INTEGER,
	awnStatisticsVccFrLineType	INTEGER,
	awnStatisticsVccFrLineData	Gauge
}

awnStatisticsVccFrLineUnit	OBJECT-TYPE
    SYNTAX	INTEGER (1..8)
    ACCESS	read-only
    STATUS	mandatory
    DESCRIPTION
	"LS unit number"
    ::= { awnStatisticsVccFrLineEntry 1 }

awnStatisticsVccFrLineCard	OBJECT-TYPE
    SYNTAX	INTEGER (1..18)
    ACCESS	read-only
    STATUS	mandatory
    DESCRIPTION
	"LS card number"
    ::= { awnStatisticsVccFrLineEntry 2 }

awnStatisticsVccFrLinePort	OBJECT-TYPE
    SYNTAX	INTEGER (1..8)
    ACCESS	read-only
    STATUS	mandatory
    DESCRIPTION
	"LS port number"
    ::= { awnStatisticsVccFrLineEntry 3 }

awnStatisticsVccFrLineTimeslot	OBJECT-TYPE
    SYNTAX	INTEGER (1..96)
    ACCESS	read-only
    STATUS	mandatory
    DESCRIPTION
	"Timeslot number"
    ::= { awnStatisticsVccFrLineEntry 4 }

awnStatisticsVccFrLineDlci	OBJECT-TYPE
    SYNTAX	INTEGER (1..1022)
    ACCESS	read-only
    STATUS	mandatory
    DESCRIPTION
	"DLCI"
    ::= { awnStatisticsVccFrLineEntry 5 }

awnStatisticsVccFrLineType	OBJECT-TYPE
    SYNTAX	INTEGER (1..3)
    ACCESS	read-only
    STATUS	mandatory
    DESCRIPTION
	"Type"
    ::= { awnStatisticsVccFrLineEntry 6 }

awnStatisticsVccFrLineData	OBJECT-TYPE
    SYNTAX	Gauge (0..4294967295)
    ACCESS	read-only
    STATUS	mandatory
    DESCRIPTION
	"Data"
    ::= { awnStatisticsVccFrLineEntry 7 }

-- the awnStatisticsVccFfLine group

awnStatisticsVccFfLine	OBJECT IDENTIFIER ::= { awnStatistics 15 }

awnStatisticsVccFfLineTable	OBJECT-TYPE
    SYNTAX	SEQUENCE OF AwnStatisticsVccFfLineEntry
    ACCESS	not-accessible
    STATUS	mandatory
    DESCRIPTION
	"Table" 
    ::= { awnStatisticsVccFfLine 1 }

awnStatisticsVccFfLineEntry	OBJECT-TYPE
    SYNTAX	AwnStatisticsVccFfLineEntry
    ACCESS	not-accessible
    STATUS	mandatory
    DESCRIPTION
	"Entry" 
    INDEX	{ awnStatisticsVccFfLineUnit, awnStatisticsVccFfLineCard, awnStatisticsVccFfLinePort, awnStatisticsVccFfLineTimeslot, awnStatisticsVccFfLineType }
    ::= { awnStatisticsVccFfLineTable 1 }

AwnStatisticsVccFfLineEntry ::= SEQUENCE {
	awnStatisticsVccFfLineUnit	INTEGER,
	awnStatisticsVccFfLineCard	INTEGER,
	awnStatisticsVccFfLinePort	INTEGER,
	awnStatisticsVccFfLineTimeslot	INTEGER,
	awnStatisticsVccFfLineType	INTEGER,
	awnStatisticsVccFfLineData	Gauge
}

awnStatisticsVccFfLineUnit	OBJECT-TYPE
    SYNTAX	INTEGER (1..8)
    ACCESS	read-only
    STATUS	mandatory
    DESCRIPTION
	"LS unit number"
    ::= { awnStatisticsVccFfLineEntry 1 }

awnStatisticsVccFfLineCard	OBJECT-TYPE
    SYNTAX	INTEGER (1..18)
    ACCESS	read-only
    STATUS	mandatory
    DESCRIPTION
	"LS card number"
    ::= { awnStatisticsVccFfLineEntry 2 }

awnStatisticsVccFfLinePort	OBJECT-TYPE
    SYNTAX	INTEGER (1..8)
    ACCESS	read-only
    STATUS	mandatory
    DESCRIPTION
	"LS port number"
    ::= { awnStatisticsVccFfLineEntry 3 }

awnStatisticsVccFfLineTimeslot	OBJECT-TYPE
    SYNTAX	INTEGER (1..96)
    ACCESS	read-only
    STATUS	mandatory
    DESCRIPTION
	"Timeslot number"
    ::= { awnStatisticsVccFfLineEntry 4 }

awnStatisticsVccFfLineType	OBJECT-TYPE
    SYNTAX	INTEGER (1..3)
    ACCESS	read-only
    STATUS	mandatory
    DESCRIPTION
	"Type"
    ::= { awnStatisticsVccFfLineEntry 5 }

awnStatisticsVccFfLineData	OBJECT-TYPE
    SYNTAX	Gauge (0..4294967295)
    ACCESS	read-only
    STATUS	mandatory
    DESCRIPTION
	"Data"
    ::= { awnStatisticsVccFfLineEntry 6 }

-- the awnStatisticsLsWanVp group

awnStatisticsLsWanVp	OBJECT IDENTIFIER ::= { awnStatistics 16 }

awnStatisticsLsWanVpTable	OBJECT-TYPE
    SYNTAX	SEQUENCE OF AwnStatisticsLsWanVpEntry
    ACCESS	not-accessible
    STATUS	mandatory
    DESCRIPTION
	"Table" 
    ::= { awnStatisticsLsWanVp 1 }

awnStatisticsLsWanVpEntry	OBJECT-TYPE
    SYNTAX	AwnStatisticsLsWanVpEntry
    ACCESS	not-accessible
    STATUS	mandatory
    DESCRIPTION
	"Entry" 
    INDEX	{ awnStatisticsLsWanVpUnit, awnStatisticsLsWanVpCard, awnStatisticsLsWanVpPort, awnStatisticsLsWanVpVpi }
    ::= { awnStatisticsLsWanVpTable 1 }

AwnStatisticsLsWanVpEntry ::= SEQUENCE {
	awnStatisticsLsWanVpUnit	INTEGER,
	awnStatisticsLsWanVpCard	INTEGER,
	awnStatisticsLsWanVpPort	INTEGER,
	awnStatisticsLsWanVpVpi		INTEGER,
	awnStatisticsLsWanVpData	Gauge
}

awnStatisticsLsWanVpUnit	OBJECT-TYPE
    SYNTAX	INTEGER (1..8)
    ACCESS	read-only
    STATUS	mandatory
    DESCRIPTION
	"LS unit number"
    ::= { awnStatisticsLsWanVpEntry 1 }

awnStatisticsLsWanVpCard	OBJECT-TYPE
    SYNTAX	INTEGER (1..18)
    ACCESS	read-only
    STATUS	mandatory
    DESCRIPTION
	"LS card number"
    ::= { awnStatisticsLsWanVpEntry 2 }

awnStatisticsLsWanVpPort	OBJECT-TYPE
    SYNTAX	INTEGER (1..8)
    ACCESS	read-only
    STATUS	mandatory
    DESCRIPTION
	"LS port number"
    ::= { awnStatisticsLsWanVpEntry 3 }

awnStatisticsLsWanVpVpi		OBJECT-TYPE
    SYNTAX	INTEGER (0..254)
    ACCESS	read-only
    STATUS	mandatory
    DESCRIPTION
	"VPI"
    ::= { awnStatisticsLsWanVpEntry 4 }

awnStatisticsLsWanVpData	OBJECT-TYPE
    SYNTAX	OCTET STRING (SIZE(456))
    ACCESS	read-only
    STATUS	mandatory
    DESCRIPTION
	"Data"
    ::= { awnStatisticsLsWanVpEntry 5 }

-- the awnStatisticsLsWanVpRt group

awnStatisticsLsWanVpRt	OBJECT IDENTIFIER ::= { awnStatistics 17 }

awnStatisticsLsWanVpRtTable	OBJECT-TYPE
    SYNTAX	SEQUENCE OF AwnStatisticsLsWanVpRtEntry
    ACCESS	not-accessible
    STATUS	mandatory
    DESCRIPTION
	"Table" 
    ::= { awnStatisticsLsWanVpRt 1 }

awnStatisticsLsWanVpRtEntry	OBJECT-TYPE
    SYNTAX	AwnStatisticsLsWanVpRtEntry
    ACCESS	not-accessible
    STATUS	mandatory
    DESCRIPTION
	"Entry" 
    INDEX	{ awnStatisticsLsWanVpRtUnit, awnStatisticsLsWanVpRtCard, awnStatisticsLsWanVpRtPort, awnStatisticsLsWanVpRtVpi, awnStatisticsLsWanVpRtCategory, awnStatisticsLsWanVpRtType }
    ::= { awnStatisticsLsWanVpRtTable 1 }

AwnStatisticsLsWanVpRtEntry ::= SEQUENCE {
	awnStatisticsLsWanVpRtUnit	INTEGER,
	awnStatisticsLsWanVpRtCard	INTEGER,
	awnStatisticsLsWanVpRtPort	INTEGER,
	awnStatisticsLsWanVpRtVpi	INTEGER,
	awnStatisticsLsWanVpRtCategory	INTEGER,
	awnStatisticsLsWanVpRtType	INTEGER,
	awnStatisticsLsWanVpRtData	Gauge
}

awnStatisticsLsWanVpRtUnit	OBJECT-TYPE
    SYNTAX	INTEGER (1..8)
    ACCESS	read-only
    STATUS	mandatory
    DESCRIPTION
	"LS unit number"
    ::= { awnStatisticsLsWanVpRtEntry 1 }

awnStatisticsLsWanVpRtCard	OBJECT-TYPE
    SYNTAX	INTEGER (1..18)
    ACCESS	read-only
    STATUS	mandatory
    DESCRIPTION
	"LS card number"
    ::= { awnStatisticsLsWanVpRtEntry 2 }

awnStatisticsLsWanVpRtPort	OBJECT-TYPE
    SYNTAX	INTEGER (1..1)
    ACCESS	read-only
    STATUS	mandatory
    DESCRIPTION
	"LS port number"
    ::= { awnStatisticsLsWanVpRtEntry 3 }

awnStatisticsLsWanVpRtVpi	OBJECT-TYPE
    SYNTAX	INTEGER (0..254)
    ACCESS	read-only
    STATUS	mandatory
    DESCRIPTION
	"VPI"
    ::= { awnStatisticsLsWanVpRtEntry 4 }

awnStatisticsLsWanVpRtCategory	OBJECT-TYPE
    SYNTAX	INTEGER (1..9)
    ACCESS	read-only
    STATUS	mandatory
    DESCRIPTION
	"Category"
    ::= { awnStatisticsLsWanVpRtEntry 5 }

awnStatisticsLsWanVpRtType	OBJECT-TYPE
    SYNTAX	INTEGER (1..3)
    ACCESS	read-only
    STATUS	mandatory
    DESCRIPTION
	"Type"
    ::= { awnStatisticsLsWanVpRtEntry 6 }

awnStatisticsLsWanVpRtData	OBJECT-TYPE
    SYNTAX	Gauge (0..4294967295)
    ACCESS	read-only
    STATUS	mandatory
    DESCRIPTION
	"Data"
    ::= { awnStatisticsLsWanVpRtEntry 7 }

-- the awnStatisticsComAtmLine group

awnStatisticsComAtmLine	OBJECT IDENTIFIER ::= { awnStatistics 18 }

awnStatisticsComAtmLineTable	OBJECT-TYPE
    SYNTAX	SEQUENCE OF AwnStatisticsComAtmLineEntry
    ACCESS	not-accessible
    STATUS	mandatory
    DESCRIPTION
	"Table" 
    ::= { awnStatisticsComAtmLine 1 }

awnStatisticsComAtmLineEntry	OBJECT-TYPE
    SYNTAX	AwnStatisticsComAtmLineEntry
    ACCESS	not-accessible
    STATUS	mandatory
    DESCRIPTION
	"Entry" 
    INDEX	{ awnStatisticsComAtmLineSlot, awnStatisticsComAtmLineAdapter, awnStatisticsComAtmLinePort, awnStatisticsComAtmLineVpi  }
    ::= { awnStatisticsComAtmLineTable 1 }

AwnStatisticsComAtmLineEntry ::= SEQUENCE {
	awnStatisticsComAtmLineSlot	INTEGER,
	awnStatisticsComAtmLineAdapter	INTEGER,
	awnStatisticsComAtmLinePort	INTEGER,
	awnStatisticsComAtmLineVpi	INTEGER,
	awnStatisticsVpcAtmLineData	Gauge
}

awnStatisticsComAtmLineSlot	OBJECT-TYPE
    SYNTAX	INTEGER (1..4)
    ACCESS	read-only
    STATUS	mandatory
    DESCRIPTION
	"Com slot number"
    ::= { awnStatisticsComAtmLineEntry 1 }

awnStatisticsComAtmLineAdapter	OBJECT-TYPE
    SYNTAX	INTEGER (1..2)
    ACCESS	read-only
    STATUS	mandatory
    DESCRIPTION
	"COM adapter number"
    ::= { awnStatisticsComAtmLineEntry 2 }

awnStatisticsComAtmLinePort	OBJECT-TYPE
    SYNTAX	INTEGER (1..4)
    ACCESS	read-only
    STATUS	mandatory
    DESCRIPTION
	"COM port number"
    ::= { awnStatisticsComAtmLineEntry 3 }

awnStatisticsComAtmLineVpi	OBJECT-TYPE
    SYNTAX	INTEGER (0..255)
    ACCESS	read-only
    STATUS	mandatory
    DESCRIPTION
	"VPI"
    ::= { awnStatisticsComAtmLineEntry 4 }

awnStatisticsComAtmLineData	OBJECT-TYPE
    SYNTAX	OCTET STRING (SIZE(104))
    ACCESS	read-only
    STATUS	mandatory
    DESCRIPTION
	"Data"
    ::= { awnStatisticsComAtmLineEntry 5 }

-- the awnStatisticsLsTs group

awnStatisticsLsTs	OBJECT IDENTIFIER ::= { awnStatistics 19 }

awnStatisticsLsTsTable	OBJECT-TYPE
    SYNTAX	SEQUENCE OF AwnStatisticsLsTsEntry
    ACCESS	not-accessible
    STATUS	mandatory
    DESCRIPTION
	"Table" 
    ::= { awnStatisticsLsTs 1 }

awnStatisticsLsTsEntry	OBJECT-TYPE
    SYNTAX	AwnStatisticsLsTsEntry
    ACCESS	not-accessible
    STATUS	mandatory
    DESCRIPTION
	"Entry" 
    INDEX	{ awnStatisticsLsTsUnit, awnStatisticsLsTsCard, awnStatisticsLsTsPort, awnStatisticsLsTsTs }
    ::= { awnStatisticsLsTsTable 1 }

AwnStatisticsLsTsEntry ::= SEQUENCE {
	awnStatisticsLsTsUnit	INTEGER,
	awnStatisticsLsTsCard	INTEGER,
	awnStatisticsLsTsPort	INTEGER,
	awnStatisticsLsTsTs	INTEGER,
	awnStatisticsLsTsData	OCTET STRING
}

awnStatisticsLsTsUnit	OBJECT-TYPE
    SYNTAX	INTEGER (1..8)
    ACCESS	read-only
    STATUS	mandatory
    DESCRIPTION
	"LS unit number"
    ::= { awnStatisticsLsTsEntry 1 }

awnStatisticsLsTsCard	OBJECT-TYPE
    SYNTAX	INTEGER (1..18)
    ACCESS	read-only
    STATUS	mandatory
    DESCRIPTION
	"LS card number"
    ::= { awnStatisticsLsTsEntry 2 }

awnStatisticsLsTsPort	OBJECT-TYPE
    SYNTAX	INTEGER (1..8)
    ACCESS	read-only
    STATUS	mandatory
    DESCRIPTION
	"LS port number"
    ::= { awnStatisticsLsTsEntry 3 }

awnStatisticsLsTsTs	OBJECT-TYPE
    SYNTAX	INTEGER (1..24)
    ACCESS	read-only
    STATUS	mandatory
    DESCRIPTION
	"LS port number"
    ::= { awnStatisticsLsTsEntry 4 }

awnStatisticsLsTsData	OBJECT-TYPE
    SYNTAX	OCTET STRING (SIZE(104))
    ACCESS	read-only
    STATUS	mandatory
    DESCRIPTION
	"Data"
    ::= { awnStatisticsLsTsEntry 5 }

-- the awnStatisticsSys group

awnStatisticsSys	OBJECT IDENTIFIER ::= { awnStatistics 20 }

awnStatisticsSysDroppedCells	OBJECT-TYPE
    SYNTAX	OCTET STRING (SIZE(100))
    ACCESS	read-only
    STATUS	mandatory
    DESCRIPTION
	"Data"
    ::= { awnStatisticsSys 1 }

-- the awnStatisticsIpFrame group

awnStatisticsIpFrame	OBJECT IDENTIFIER ::= { awnStatistics 21 }

awnStatisticsIpFrameTable	OBJECT-TYPE
    SYNTAX	SEQUENCE OF AwnStatisticsIpFrameEntry
    ACCESS	not-accessible
    STATUS	mandatory
    DESCRIPTION
	"Table" 
    ::= { awnStatisticsIpFrame 1 }

awnStatisticsIpFrameEntry	OBJECT-TYPE
    SYNTAX	AwnStatisticsIpFrameEntry
    ACCESS	not-accessible
    STATUS	mandatory
    DESCRIPTION
	"Entry" 
    INDEX	{ awnStatisticsIpFrameAddr }
    ::= { awnStatisticsIpFrameTable 1 }

AwnStatisticsIpFrameEntry ::= SEQUENCE {
	awnStatisticsIpFrameAddr	IpAddress,
	awnStatisticsIpFrameData	OCTET STRING
}

awnStatisticsIpFrameAddr	OBJECT-TYPE
    SYNTAX	IpAddress
    ACCESS	read-only
    STATUS	mandatory
    DESCRIPTION
	"IP Address"
    ::= { awnStatisticsIpFrameEntry 1 }

awnStatisticsIpFrameData	OBJECT-TYPE
    SYNTAX	OCTET STRING (SIZE(108))
    ACCESS	read-only
    STATUS	mandatory
    DESCRIPTION
	"Data"
    ::= { awnStatisticsIpFrameEntry 2 }

-- the awnStatisticsDlci group

awnStatisticsDlci	OBJECT IDENTIFIER ::= { awnStatistics 22 }

awnStatisticsDlciTable	OBJECT-TYPE
    SYNTAX	SEQUENCE OF AwnStatisticsDlciEntry
    ACCESS	not-accessible
    STATUS	mandatory
    DESCRIPTION
	"Table" 
    ::= { awnStatisticsDlci 1 }

awnStatisticsDlciEntry	OBJECT-TYPE
    SYNTAX	AwnStatisticsDlciEntry
    ACCESS	not-accessible
    STATUS	mandatory
    DESCRIPTION
	"Entry" 
    INDEX	{ awnStatisticsDlciUnit, awnStatisticsDlciCard, awnStatisticsDlciPort, awnStatisticsDlciTimeslot, awnStatisticsDlciDlci }
    ::= { awnStatisticsDlciTable 1 }

AwnStatisticsDlciEntry ::= SEQUENCE {
	awnStatisticsDlciUnit		INTEGER,
	awnStatisticsDlciCard		INTEGER,
	awnStatisticsDlciPort		INTEGER,
	awnStatisticsDlciTimeslot	INTEGER,
	awnStatisticsDlciDlci		INTEGER,
	awnStatisticsDlciBriClad	OCTET STRING
}

awnStatisticsDlciUnit	OBJECT-TYPE
    SYNTAX	INTEGER (1..8)
    ACCESS	read-only
    STATUS	mandatory
    DESCRIPTION
	"LS unit number"
    ::= { awnStatisticsDlciEntry 1 }

awnStatisticsDlciCard	OBJECT-TYPE
    SYNTAX	INTEGER (1..18)
    ACCESS	read-only
    STATUS	mandatory
    DESCRIPTION
	"LS card number"
    ::= { awnStatisticsDlciEntry 2 }

awnStatisticsDlciPort	OBJECT-TYPE
    SYNTAX	INTEGER (1..8)
    ACCESS	read-only
    STATUS	mandatory
    DESCRIPTION
	"LS port number"
    ::= { awnStatisticsDlciEntry 3 }

awnStatisticsDlciTimeslot	OBJECT-TYPE
    SYNTAX	INTEGER (1..96)
    ACCESS	read-only
    STATUS	mandatory
    DESCRIPTION
	"Timeslot number"
    ::= { awnStatisticsDlciEntry 4 }

awnStatisticsDlciDlci	OBJECT-TYPE
    SYNTAX	INTEGER (1..1022)
    ACCESS	read-only
    STATUS	mandatory
    DESCRIPTION
	"DLCI"
    ::= { awnStatisticsDlciEntry 5 }

awnStatisticsDlciBriClad	OBJECT-TYPE
    SYNTAX	OCTET STRING (SIZE(168))
    ACCESS	read-only
    STATUS	mandatory
    DESCRIPTION
	"BRI-CLAD Data"
    ::= { awnStatisticsDlciEntry 6 }

--
--
-- groups in awnIlmi
--
--

awnIlmi		OBJECT IDENTIFIER ::= { awn 3 }

-- the awnIlmiIns group

awnIlmiIns	OBJECT IDENTIFIER ::= { awnIlmi 1 }

awnIlmiInsRouteadd	OBJECT-TYPE
    SYNTAX	INTEGER --(0, 1)
    ACCESS	read-only
    STATUS	mandatory
    DESCRIPTION
	"Routeadd"
    ::= { awnIlmiIns 1 }

awnIlmiInsRoutedel	OBJECT-TYPE
    SYNTAX	INTEGER --(0, 1)
    ACCESS	read-only
    STATUS	mandatory
    DESCRIPTION
	"Routedel"
    ::= { awnIlmiIns 2 }

-- V06

END
