--			Ascend mibike MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIKE-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfIke  OBJECT IDENTIFIER ::= { configuration 165}

	-- The mibmibProfIke table
	--
	-- This table contains parameters for the mibmibProfIke profile
	--

    mibmibProfIkeTable	OBJECT-TYPE
	SYNTAX		SEQUENCE OF MibmibProfIkeEntry
	ACCESS		not-accessible
	STATUS		mandatory
	DESCRIPTION	"A list of mibmibProfIke profile entries."
	::= { mibmibProfIke 1 }

    mibmibProfIkeEntry	OBJECT-TYPE
	SYNTAX		MibmibProfIkeEntry
	ACCESS		not-accessible
	STATUS		mandatory
	DESCRIPTION	"A mibmibProfIke entry containing objects that
			 maps to the parameters of mibmibProfIke profile."
	INDEX		{ mibProfIke-IkeProtectionSuiteName }
	::= { mibmibProfIkeTable 1 }

    MibmibProfIkeEntry ::=
	SEQUENCE {
	    mibProfIke-IkeProtectionSuiteName
		DisplayString,
	    mibProfIke-Phase1Mode
		INTEGER,
	    mibProfIke-EncryptionAlgorithm
		INTEGER,
	    mibProfIke-HashAlgorithm
		INTEGER,
	    mibProfIke-AuthenticationMethod
		INTEGER,
	    mibProfIke-DiffieHellmanGroup
		INTEGER,
	    mibProfIke-SaLife-TimeLimit
		INTEGER,
	    mibProfIke-SaLife-SizeLimit
		INTEGER,
	    mibProfIke-SaLife-AnticipateRekey
		INTEGER,
	    mibProfIke-SaLife-LifeNegotiationFallback
		INTEGER,
	    mibProfIke-SaLife-IdleTimeout
		INTEGER,
	    mibProfIke-SaLimit
		INTEGER,
	    mibProfIke-Next
		DisplayString,
	    mibProfIke-Action-o
		INTEGER
	}

    mibProfIke-IkeProtectionSuiteName	OBJECT-TYPE
	SYNTAX	DisplayString
	ACCESS	read-only
	STATUS	mandatory
	DESCRIPTION	"The name of this IKE protection suite."
	::= { mibmibProfIkeEntry 1 }

    mibProfIke-Phase1Mode	OBJECT-TYPE
	SYNTAX	INTEGER {
		    main (1),
		    aggressive (2)
		}
	ACCESS	read-write
	STATUS	mandatory
	DESCRIPTION	"IKE Phase 1 mode, for ISAKMP Security Association establishment."
	::= { mibmibProfIkeEntry 2 }

    mibProfIke-EncryptionAlgorithm	OBJECT-TYPE
	SYNTAX	INTEGER {
		    desCbc (1),
		    n-3desCbc (2)
		}
	ACCESS	read-write
	STATUS	mandatory
	DESCRIPTION	"Encryption algorithm to be used by IKE."
	::= { mibmibProfIkeEntry 3 }

    mibProfIke-HashAlgorithm	OBJECT-TYPE
	SYNTAX	INTEGER {
		    md5 (1),
		    sha (2),
		    tiger (3)
		}
	ACCESS	read-write
	STATUS	mandatory
	DESCRIPTION	"Hash algorithm to be used by IKE."
	::= { mibmibProfIkeEntry 4 }

    mibProfIke-AuthenticationMethod	OBJECT-TYPE
	SYNTAX	INTEGER {
		    presharedKey (1)
		}
	ACCESS	read-write
	STATUS	mandatory
	DESCRIPTION	"Authentication method for ISAKMP messages."
	::= { mibmibProfIkeEntry 5 }

    mibProfIke-DiffieHellmanGroup	OBJECT-TYPE
	SYNTAX	INTEGER {
		    n-1 (1),
		    n-2 (2)
		}
	ACCESS	read-write
	STATUS	mandatory
	DESCRIPTION	"Diffie-Hellman group."
	::= { mibmibProfIkeEntry 6 }

    mibProfIke-SaLife-TimeLimit	OBJECT-TYPE
	SYNTAX	INTEGER
	ACCESS	read-write
	STATUS	mandatory
	DESCRIPTION	"Lifetime of the SA in seconds. The SA will expire at the end of the lifetime. The value of 0 disables the timer."
	::= { mibmibProfIkeEntry 7 }

    mibProfIke-SaLife-SizeLimit	OBJECT-TYPE
	SYNTAX	INTEGER
	ACCESS	read-write
	STATUS	mandatory
	DESCRIPTION	"Maximum number of kilobytes (KB) covered by the SA before it expires. The value of 0 disables the counter."
	::= { mibmibProfIkeEntry 8 }

    mibProfIke-SaLife-AnticipateRekey	OBJECT-TYPE
	SYNTAX	INTEGER
	ACCESS	read-write
	STATUS	mandatory
	DESCRIPTION	"A percentage of lifetime or lifesize to trigger negotiation of a new SA before the old one expires (a.k.a. soft lifetime)."
	::= { mibmibProfIkeEntry 9 }

    mibProfIke-SaLife-LifeNegotiationFallback	OBJECT-TYPE
	SYNTAX	INTEGER {
		    fail (1),
		    complete (2),
		    notification (3)
		}
	ACCESS	read-write
	STATUS	mandatory
	DESCRIPTION	"What to do when local policy requires a shorter life than what is proposed by SA initiator. Applies to IPSec SAs only."
	::= { mibmibProfIkeEntry 10 }

    mibProfIke-SaLife-IdleTimeout	OBJECT-TYPE
	SYNTAX	INTEGER
	ACCESS	read-write
	STATUS	mandatory
	DESCRIPTION	"SA lifetime without traffic."
	::= { mibmibProfIkeEntry 11 }

    mibProfIke-SaLimit	OBJECT-TYPE
	SYNTAX	INTEGER
	ACCESS	read-write
	STATUS	mandatory
	DESCRIPTION	"Maximum number of IPSec SAs that can be negotiated under cover of the IKE SA before it expires. The value of 0 disables the limit."
	::= { mibmibProfIkeEntry 12 }

    mibProfIke-Next	OBJECT-TYPE
	SYNTAX	DisplayString
	ACCESS	read-write
	STATUS	mandatory
	DESCRIPTION	"The name of the next IKE protection suite."
	::= { mibmibProfIkeEntry 13 }

    mibProfIke-Action-o	OBJECT-TYPE
	SYNTAX	INTEGER {
		    noAction (1),
		    createProfile (2),
		    deleteProfile (3)
		}
	ACCESS	read-write
	STATUS	mandatory
	DESCRIPTION	""
	::= { mibmibProfIkeEntry 14 }

END
