-- ****************************************************************************
--
--                      HP Hotswap 2 Subsystem
--      Management Information Base for SNMP Network Management
--
--      Version Q.01.00 (12/16/97)
-- 
--      Copyright 1997 Hewlett-Packard Company.
--      All Rights Reserved.
--
--      The information in this document is subject to change without notice.
--
--      The HP Enterprise number is 11.
--      The ASN.1 prefix to, and including the HP Enterprise is:
--      1.3.6.1.4.1.11
--
-- ****************************************************************************
-- Summary of HP NSA Hotswap 2 Subsystem Information MIB
-- ****************************************************************************
--
-- hp  (1.3.6.1.4.1.11)
--    nm  (1.3.6.1.4.1.11.2)
--       hpnsa  (1.3.6.1.4.1.11.2.23)
--          hpnsaHotswap2 Group    (hpnsa.27)
--             hpnsaHS2MibRev Group                               (hpnsa.27.1)             
--                hpnsaHS2MibRevMajor                             (hpnsa.27.1.1)  
--                hpnsaHS2MibRevMinor                             (hpnsa.27.1.2)
--
--             hpnsaHS2Cage Group                                 (hpnsa.27.2)
--                hpnsaHS2CageTable                               (hpnsa.27.2.1)
--                   hpnsaHS2CageEntry                            (hpnsa.27.2.1.1)
--                      hpnsaHS2CageIndex                         (hpnsa.27.2.1.1.1)
--                      hpnsaHS2Cage12VPower                      (hpnsa.27.2.1.1.2)
--                      hpnsaHS2CageTerminator1                   (hpnsa.27.2.1.1.3)
--                      hpnsaHS2CageTerminator2                   (hpnsa.27.2.1.1.4)
--                      hpnsaHS2CageSCSICable1                    (hpnsa.27.2.1.1.5)
--                      hpnsaHS2CageSCSICable2                    (hpnsa.27.2.1.1.6)
--                      hpnsaHS2CageBaseSCSIAddress               (hpnsa.27.2.1.1.7)
--                      hpnsaHS2CageTemperature                   (hpnsa.27.2.1.1.8)
--                      hpnsaHS2CageTemperatureWarningThreshold   (hpnsa.27.2.1.1.9)
--                      hpnsaHS2CageTemperatureAlertThreshold     (hpnsa.27.2.1.1.10)
--                      hpnsaHS2CageManagementBoardFRU            (hpnsa.27.2.1.1.11)
--                      hpnsaHS2CageInterconnectFRU               (hpnsa.27.2.1.1.12)
--                      hpnsaHS2CageFirmwareMajorRev              (hpnsa.27.2.1.1.13)
--                      hpnsaHS2CageFirmwareMinorRev              (hpnsa.27.2.1.1.14)
--
--             hpnsaHS2Slot Group                                 (hpnsa.27.3)
--                hpnsaHS2SlotTable                               (hpnsa.27.3.1)
--                   hpnsaHS2SlotEntry                            (hpnsa.27.3.1.1)
--                      hpnsaHS2SlotCageIndex                     (hpnsa.27.3.1.1.1)
--                      hpnsaHS2SlotIndex                         (hpnsa.27.3.1.1.2)
--                      hpnsaHS2DrivePresent                      (hpnsa.27.3.1.1.3)
--                      hpnsaHS2DriveSCSIBusType                  (hpnsa.27.3.1.1.4)
--                      hpnsaHS2DriveIdentify                     (hpnsa.27.3.1.1.5)
--
-- ******************************************************************************
HPHOTSWAP2SUBSYSTEM-MIB DEFINITIONS ::= BEGIN
   IMPORTS
      enterprises    FROM RFC1155-SMI
      DisplayString  FROM RFC1213-MIB
      OBJECT-TYPE    FROM RFC-1212;
		
   hp                   OBJECT IDENTIFIER ::= { enterprises 11 }
   nm                   OBJECT IDENTIFIER ::= { hp 2 }
   hpnsa                OBJECT IDENTIFIER ::= { nm 23 }  
   hpnsaHotswap2        OBJECT IDENTIFIER ::= { hpnsa 27 }
   hpnsaHS2MibRev       OBJECT IDENTIFIER ::= { hpnsaHotswap2 1 }
   hpnsaHS2Cage         OBJECT IDENTIFIER ::= { hpnsaHotswap2 2 }
   hpnsaHS2Slot         OBJECT IDENTIFIER ::= { hpnsaHotswap2 3 }

-- ****************************************************************************
--   HP Hotswap 2 Subsystem Information MIB 
--   =====================================
--
-- hp  (1.3.6.1.4.1.11)
--    nm  (1.3.6.1.4.1.11.2)
--       hpnsa  (1.3.6.1.4.1.11.2.23)
--          hpnsaHotswap2 Group  (hpnsa.27)
--             hpnsaHS2MibRev Group   (hpnsa.27.1)             
--                hpnsaHS2MibRevMajor  (hpnsa.27.1.1)
--                hpnsaHS2MibRevMinor  (hpnsa.27.1.2)
--
--    Implementation of the MibRev group is mandatory for all HPNSA Agents
--    supporting the HP Hotswap 2 Subsystem MIB.
--
--    An HPNSA Agent conforming to this document will return a
--    hpnsaHSMibRevMajor of 1 and a hpnsaHSMibRevMinor of 0. 
--
-- ****************************************************************************

    hpnsaHS2MibRevMajor OBJECT-TYPE
        SYNTAX  INTEGER
        ACCESS  read-only
        STATUS  mandatory
        DESCRIPTION
            "The major revision level of the MIB."
        ::= { hpnsaHS2MibRev 1 }

    hpnsaHS2MibRevMinor OBJECT-TYPE
        SYNTAX  INTEGER
        ACCESS  read-only
        STATUS  mandatory
        DESCRIPTION
            "The minor revision level of the MIB."
        ::= { hpnsaHS2MibRev 2 }

-- *************************************************************************************
-- hp  (1.3.6.1.4.1.11)
--    nm  (1.3.6.1.4.1.11.2)
--       hpnsa  (1.3.6.1.4.1.11.2.23)
--          hpnsaHotswap2 Group  (hpnsa.27)
--             hpnsaHS2Cage Group                                 (hpnsa.27.2)
--                hpnsaHS2CageTable                               (hpnsa.27.2.1)
--                   hpnsaHS2CageEntry                            (hpnsa.27.2.1.1)
--                      hpnsaHS2CageIndex                         (hpnsa.27.2.1.1.1)
--                      hpnsaHS2Cage12VPower                      (hpnsa.27.2.1.1.2)
--                      hpnsaHS2CageTerminator1                   (hpnsa.27.2.1.1.3)
--                      hpnsaHS2CageTerminator2                   (hpnsa.27.2.1.1.4)
--                      hpnsaHS2CageSCSICable1                    (hpnsa.27.2.1.1.5)
--                      hpnsaHS2CageSCSICable2                    (hpnsa.27.2.1.1.6)
--                      hpnsaHS2CageBaseSCSIAddress               (hpnsa.27.2.1.1.7)
--                      hpnsaHS2CageTemperature                   (hpnsa.27.2.1.1.8)
--                      hpnsaHS2CageTemperatureWarningThreshold   (hpnsa.27.2.1.1.9)
--                      hpnsaHS2CageTemperatureAlertThreshold     (hpnsa.27.2.1.1.10)
--                      hpnsaHS2CageManagementBoardFRU            (hpnsa.27.2.1.1.11)
--                      hpnsaHS2CageInterconnectFRU               (hpnsa.27.2.1.1.12)
--                      hpnsaHS2CageFirmwareMajorRev              (hpnsa.27.2.1.1.13)
--                      hpnsaHS2CageFirmwareMinorRev              (hpnsa.27.2.1.1.14)
--
-- ****************************************************************************************
--   HP Hotswap 2 Subsystem Cage Information Table
-- ****************************************************************************

   hpnsaHS2CageTable OBJECT-TYPE
      SYNTAX  SEQUENCE OF HpnsaHotswap2CageEntry
      ACCESS  not-accessible
      STATUS  mandatory
      DESCRIPTION
          " A table of Hotswap 2 Subsystem cage information entries."
      ::= { hpnsaHS2Cage  1 }

   hpnsaHS2CageEntry OBJECT-TYPE
      SYNTAX  HpnsaHotswap2CageEntry
      ACCESS  not-accessible
      STATUS  mandatory
      DESCRIPTION
          " Hotswap 2 Subsystem cage information."
      INDEX   { hpnsaHS2CageIndex }
      ::= { hpnsaHS2CageTable 1 }

      HpnsaHotswap2CageEntry ::= SEQUENCE {
         hpnsaHS2CageIndex                         INTEGER,
         hpnsaHS2Cage12VPower                      INTEGER,
         hpnsaHS2CageTerminator1                   INTEGER,
         hpnsaHS2CageTerminator2                   INTEGER,
         hpnsaHS2CageSCSICable1                    INTEGER,
         hpnsaHS2CageSCSICable2                    INTEGER,
         hpnsaHS2CageBaseSCSIAddress               INTEGER,
         hpnsaHS2CageTemperature                   INTEGER,
         hpnsaHS2CageTemperatureWarningThreshold   INTEGER,
         hpnsaHS2CageTemperatureAlertThreshold     INTEGER,
         hpnsaHS2CageManagementBoardFRU            OCTET STRING,
         hpnsaHS2CageInterconnectFRU               OCTET STRING,
         hpnsaHS2CageFirmwareMajorRev              INTEGER,
         hpnsaHS2CageFirmwareMinorRev              INTEGER
         }

   hpnsaHS2CageIndex OBJECT-TYPE
      SYNTAX  INTEGER 
      ACCESS  read-only
      STATUS  mandatory
      DESCRIPTION
         "A unique index for the Hotswap 2 Cage."
      ::= { hpnsaHS2CageEntry 1 }

   hpnsaHS2Cage12VPower OBJECT-TYPE
      SYNTAX  INTEGER {
                        absent(1),
                        present(2)
                      }
      ACCESS  read-only
      STATUS  mandatory
      DESCRIPTION
         "The current state of the 12V DC power."
      ::= { hpnsaHS2CageEntry 2 }

   hpnsaHS2CageTerminator1 OBJECT-TYPE
      SYNTAX  INTEGER {
                        not-attached(1),
                        attached(2)
                      }
      ACCESS  read-only
      STATUS  mandatory
      DESCRIPTION
         "The current state of Terminator 1."
      ::= { hpnsaHS2CageEntry 3 }

   hpnsaHS2CageTerminator2 OBJECT-TYPE
      SYNTAX  INTEGER {
                        not-attached(1),
                        attached(2)
                      }
      ACCESS  read-only
      STATUS  mandatory
      DESCRIPTION
         "The current state of Terminator 2."
      ::= { hpnsaHS2CageEntry 4 }

   hpnsaHS2CageSCSICable1 OBJECT-TYPE
      SYNTAX  INTEGER {
                        not-attached(1),
                        attached(2)
                      }
      ACCESS  read-only
      STATUS  mandatory
      DESCRIPTION
         "The current state of SCSI Cable 1."
      ::= { hpnsaHS2CageEntry 5 }

   hpnsaHS2CageSCSICable2 OBJECT-TYPE
      SYNTAX  INTEGER {
                        not-attached(1),
                        attached(2)
                      }
      ACCESS  read-only
      STATUS  mandatory
      DESCRIPTION
         "The current state of SCSI Cable 2."
      ::= { hpnsaHS2CageEntry 6 }

   hpnsaHS2CageBaseSCSIAddress OBJECT-TYPE
      SYNTAX  INTEGER
      ACCESS  read-write
      STATUS  mandatory
      DESCRIPTION
         "The base SCSI address of this cage."
      ::= { hpnsaHS2CageEntry 7 }

   hpnsaHS2CageTemperature OBJECT-TYPE                
      SYNTAX  INTEGER 
      ACCESS  read-only
      STATUS  mandatory
      DESCRIPTION
         "The current temperature reading for the temperature sensor (in celcius)."
      ::= { hpnsaHS2CageEntry 8 }

   hpnsaHS2CageTemperatureWarningThreshold OBJECT-TYPE
      SYNTAX  INTEGER
      ACCESS  read-write
      STATUS  mandatory
      DESCRIPTION
         "The warning threshold for the temperature sensor (in celsius)."
      ::= { hpnsaHS2CageEntry 9 }

   hpnsaHS2CageTemperatureAlertThreshold OBJECT-TYPE
      SYNTAX  INTEGER
      ACCESS  read-write
      STATUS  mandatory
      DESCRIPTION
         "The alert threshold for the temperature sensor (in celsius)."
      ::= { hpnsaHS2CageEntry 10 }

   hpnsaHS2CageManagementBoardFRU OBJECT-TYPE
      SYNTAX  OCTET STRING (SIZE (0..255))
      ACCESS  read-only
      STATUS  mandatory
      DESCRIPTION
         "The Field Replaceable Unit (FRU) Management Board information."
      ::= { hpnsaHS2CageEntry 11 }

   hpnsaHS2CageInterconnectFRU OBJECT-TYPE
      SYNTAX  OCTET STRING (SIZE (0..255))
      ACCESS  read-only
      STATUS  mandatory
      DESCRIPTION
         "The Field Replaceable Unit (FRU) Interconnect Board information."
      ::= { hpnsaHS2CageEntry 12 }

   hpnsaHS2CageFirmwareMajorRev OBJECT-TYPE                
      SYNTAX  INTEGER 
      ACCESS  read-only
      STATUS  mandatory
      DESCRIPTION
         "The major firmware revision of the Management Board."
      ::= { hpnsaHS2CageEntry 13 }

   hpnsaHS2CageFirmwareMinorRev OBJECT-TYPE                
      SYNTAX  INTEGER 
      ACCESS  read-only
      STATUS  mandatory
      DESCRIPTION
         "The minor firmware revision of the Management Board."
      ::= { hpnsaHS2CageEntry 14 }

-- *************************************************************************************
-- hp  (1.3.6.1.4.1.11)
--    nm  (1.3.6.1.4.1.11.2)
--       hpnsa  (1.3.6.1.4.1.11.2.23)
--          hpnsaHotswap2 Group    (hpnsa.27)
--             hpnsaHS2Slot Group                                 (hpnsa.27.3)
--                hpnsaHS2SlotTable                               (hpnsa.27.3.1)
--                   hpnsaHS2SlotEntry                            (hpnsa.27.3.1.1)
--                      hpnsaHS2SlotCageIndex                     (hpnsa.27.3.1.1.1)
--                      hpnsaHS2SlotIndex                         (hpnsa.27.3.1.1.2)
--                      hpnsaHS2DrivePresent                      (hpnsa.27.3.1.1.3)
--                      hpnsaHS2DriveSCSIBusType                  (hpnsa.27.3.1.1.4)
--                      hpnsaHS2DriveIdentify                     (hpnsa.27.3.1.1.5)
--
-- *************************************************************************************
--   HP Hotswap 2 Subsystem Slot Table
-- ****************************************************************************

   hpnsaHS2SlotTable OBJECT-TYPE
      SYNTAX  SEQUENCE OF HpnsaHotswap2SlotEntry
      ACCESS  not-accessible
      STATUS  mandatory
      DESCRIPTION
          "A table of Hotswap 2 Subsystem Slot information entries."
      ::= { hpnsaHS2Slot 1 }

   hpnsaHS2SlotEntry OBJECT-TYPE
      SYNTAX  HpnsaHotswap2SlotEntry
      ACCESS  not-accessible
      STATUS  mandatory
      DESCRIPTION
          " Hotswap 2 Subsystem Slot information."
      INDEX   { hpnsaHS2SlotCageIndex , hpnsaHS2SlotIndex }
      ::= { hpnsaHS2SlotTable 1 }

   HpnsaHotswap2SlotEntry ::= SEQUENCE {
      hpnsaHS2SlotCageIndex         INTEGER,
      hpnsaHS2SlotIndex             INTEGER,
      hpnsaHS2DrivePresent          INTEGER,
      hpnsaHS2DriveSCSIBusType      INTEGER,
      hpnsaHS2DriveIdentify         INTEGER
      }                           

   hpnsaHS2SlotCageIndex OBJECT-TYPE
      SYNTAX  INTEGER
      ACCESS  read-only
      STATUS  mandatory
      DESCRIPTION
          "A unique index for the Hotswap 2 cage."
      ::= { hpnsaHS2SlotEntry 1 }

   hpnsaHS2SlotIndex OBJECT-TYPE
      SYNTAX  INTEGER
      ACCESS  read-only
      STATUS  mandatory
      DESCRIPTION
         "Physical slot number in the Hotswap 2 cage."
      ::= { hpnsaHS2SlotEntry 2 }

   hpnsaHS2DrivePresent OBJECT-TYPE
      SYNTAX  INTEGER {
                        not-present(1),
                        present(2)
                      }
      ACCESS  read-only
      STATUS  mandatory
      DESCRIPTION
         "Defines whether there is a drive present in this slot."
      ::= { hpnsaHS2SlotEntry 3 }

   hpnsaHS2DriveSCSIBusType OBJECT-TYPE
      SYNTAX  INTEGER {
                        se(1),
                        lvd(2),
                        hvd(3),
                        none(4)
                      }
      ACCESS  read-only
      STATUS  mandatory
      DESCRIPTION
         "The SCSI Bus type with which this drive is attached."
      ::= { hpnsaHS2SlotEntry 4 }

   hpnsaHS2DriveIdentify OBJECT-TYPE
      SYNTAX  INTEGER
      ACCESS  read-write
      STATUS  mandatory
      DESCRIPTION
         "Select or unselect a drive to provide a visual indicator signal for user to locate drive."
      ::= { hpnsaHS2SlotEntry 5 }

END
