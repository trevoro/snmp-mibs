Nortel-Magellan-Passport-FrameRelayAtmMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      PassportCounter64,
      InterfaceIndex,
      Gauge32,
      Integer32,
      Unsigned32
   FROM Nortel-Magellan-Passport-StandardTextualConventionsMIB

      AsciiString,
      NonReplicated,
      HexString,
      EnterpriseDateAndTime,
      Link,
      IntegerSequence,
      Unsigned64
   FROM Nortel-Magellan-Passport-TextualConventionsMIB;




-- LAST-UPDATED   "9905250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrameRelayAtm Enterprise MIB."

frameRelayAtmMIB OBJECT IDENTIFIER ::= { passportMIBs 51 }










-- FrameRelayAtmInterface/n
-- This component defines an instance of the Frame Relay to ATM 
-- interworking interface. It manages the set of Frame Relay DLCI 
-- connections that are interworked with ATM connections. The 
-- component instance value is a unique positive integer within a 
-- module. Framer is created whenever the FrAtm is added. Users who 
-- need VirtualFramer should delete the Framer first, then add the 
-- VirtualFramer.

frAtm OBJECT IDENTIFIER ::= { components 72 }



frAtmRowStatusTable OBJECT-TYPE
   SYNTAX     SEQUENCE OF FrAtmRowStatusEntry
   ACCESS     not-accessible
   STATUS     mandatory
   DESCRIPTION
     "This entry controls the addition and deletion of 
      frAtm components."
::= { frAtm 1 }

frAtmRowStatusEntry OBJECT-TYPE
   SYNTAX     FrAtmRowStatusEntry
   ACCESS     not-accessible
   STATUS     mandatory
   DESCRIPTION
     "A single entry in the table represents a single 
      frAtm component."
   INDEX {
      frAtmIndex }
::= { frAtmRowStatusTable 1 }

FrAtmRowStatusEntry ::= SEQUENCE {
   frAtmRowStatus
      RowStatus,
   frAtmComponentName
      DisplayString,
   frAtmStorageType
      StorageType,
   frAtmIndex
      Integer32 }

frAtmRowStatus OBJECT-TYPE
   SYNTAX     RowStatus 
   ACCESS     read-write
   STATUS     mandatory
   DESCRIPTION
     "This variable is used as the basis for SNMP naming of
      frAtm components.
      These components can be added and deleted."
::= { frAtmRowStatusEntry 1 }

frAtmComponentName OBJECT-TYPE
   SYNTAX     DisplayString 
   ACCESS     read-only
   STATUS     mandatory
   DESCRIPTION
     "This variable provides the component's string name for
      use with the ASCII Console Interface"
::= { frAtmRowStatusEntry 2 }

frAtmStorageType OBJECT-TYPE
   SYNTAX     StorageType 
   ACCESS     read-only
   STATUS     mandatory
   DESCRIPTION
     "This variable represents the storage type value for the
      frAtm tables."
::= { frAtmRowStatusEntry 4 }

frAtmIndex OBJECT-TYPE
   SYNTAX     Integer32 (1..65535)
   ACCESS     not-accessible
   STATUS     mandatory
   DESCRIPTION
     "This variable represents the index for the frAtm tables."
::= { frAtmRowStatusEntry 10 }

frAtmCidDataTable OBJECT-TYPE
   SYNTAX     SEQUENCE OF FrAtmCidDataEntry
   ACCESS     not-accessible
   STATUS     mandatory
   DESCRIPTION
     "This group contains the attribute for a component's Customer 
      Identifier (CID). Refer to the attribute description for a detailed 
      explanation of CIDs."
::= { frAtm 10 }

frAtmCidDataEntry OBJECT-TYPE
   SYNTAX     FrAtmCidDataEntry
   ACCESS     not-accessible
   STATUS     mandatory
   DESCRIPTION
     "An entry in the frAtmCidDataTable."
   INDEX {
      frAtmIndex }
::= { frAtmCidDataTable 1 }

FrAtmCidDataEntry ::= SEQUENCE {
   frAtmCustomerIdentifier
      Unsigned32 }

frAtmCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { frAtmCidDataEntry 1 }

frAtmStateTable OBJECT-TYPE
   SYNTAX     SEQUENCE OF FrAtmStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { frAtm 11 }

frAtmStateEntry OBJECT-TYPE
   SYNTAX     FrAtmStateEntry
   ACCESS     not-accessible
   STATUS     mandatory
   DESCRIPTION
     "An entry in the frAtmStateTable."
   INDEX {
      frAtmIndex }
::= { frAtmStateTable 1 }

FrAtmStateEntry ::= SEQUENCE {
   frAtmAdminState
      INTEGER,
   frAtmOperationalState
      INTEGER,
   frAtmUsageState
      INTEGER,
   frAtmAvailabilityStatus
      OCTET STRING,
   frAtmProceduralStatus
      OCTET STRING,
   frAtmControlStatus
      OCTET STRING,
   frAtmAlarmStatus
      OCTET STRING,
   frAtmStandbyStatus
      INTEGER,
   frAtmUnknownStatus
      INTEGER }

frAtmAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { frAtmStateEntry 1 }

frAtmOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { frAtmStateEntry 2 }

frAtmUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { frAtmStateEntry 3 }

frAtmAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { frAtmStateEntry 4 }

frAtmProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { frAtmStateEntry 5 }

frAtmControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { frAtmStateEntry 6 }

frAtmAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { frAtmStateEntry 7 }

frAtmStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { frAtmStateEntry 8 }

frAtmUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { frAtmStateEntry 9 }

frAtmStatsTable OBJECT-TYPE
   SYNTAX     SEQUENCE OF FrAtmStatsEntry
   ACCESS     not-accessible
   STATUS     mandatory
   DESCRIPTION
     "FrUni/n Statistics
      This group contains the statistics about the operational behavior of 
      the service at the interface level."
::= { frAtm 12 }

frAtmStatsEntry OBJECT-TYPE
   SYNTAX     FrAtmStatsEntry
   ACCESS     not-accessible
   STATUS     mandatory
   DESCRIPTION
     "An entry in the frAtmStatsTable."
   INDEX {
      frAtmIndex }
::= { frAtmStatsTable 1 }

FrAtmStatsEntry ::= SEQUENCE {
   frAtmLastUnknownDlci
      Unsigned32,
   frAtmUnknownDlciFramesFromIf
      Counter32,
   frAtmInvalidHeaderFramesFromIf
      Counter32 }

frAtmLastUnknownDlci OBJECT-TYPE
   SYNTAX     Unsigned32 (0..1023)
   ACCESS     read-only
   STATUS     mandatory
   DESCRIPTION
     "This attribute identifies the most recent DLCI which user frames 
      were received on for which a DLCI has not been provisioned on the 
      port."
   DEFVAL     { 0 }
::= { frAtmStatsEntry 1 }

frAtmUnknownDlciFramesFromIf OBJECT-TYPE
   SYNTAX     Counter32 
   ACCESS     read-only
   STATUS     mandatory
   DESCRIPTION
     "This attribute contains a count of the number of frames received 
      from the interface with an unknown DLCI (DLCI which is not 
      provisioned). When the maximum is reached the count wraps to 
      zero."
::= { frAtmStatsEntry 2 }

frAtmInvalidHeaderFramesFromIf OBJECT-TYPE
   SYNTAX     Counter32 
   ACCESS     read-only
   STATUS     mandatory
   DESCRIPTION
     "This attribute counts the number of frames received from the 
      interface with an invalid header format. When the maximum is 
      reached the count wraps to zero."
::= { frAtmStatsEntry 3 }

frAtmIfEntryTable OBJECT-TYPE
   SYNTAX     SEQUENCE OF FrAtmIfEntryEntry
   ACCESS     not-accessible
   STATUS     mandatory
   DESCRIPTION
     "This group contains the provisionable attributes for the ifEntry."
::= { frAtm 13 }

frAtmIfEntryEntry OBJECT-TYPE
   SYNTAX     FrAtmIfEntryEntry
   ACCESS     not-accessible
   STATUS     mandatory
   DESCRIPTION
     "An entry in the frAtmIfEntryTable."
   INDEX {
      frAtmIndex }
::= { frAtmIfEntryTable 1 }

FrAtmIfEntryEntry ::= SEQUENCE {
   frAtmIfAdminStatus
      INTEGER,
   frAtmIfIndex
      InterfaceIndex }

frAtmIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { frAtmIfEntryEntry 1 }

frAtmIfIndex OBJECT-TYPE
   SYNTAX     InterfaceIndex (1..65535)
   ACCESS     read-only
   STATUS     mandatory
   DESCRIPTION
     "This is the index for the IfEntry. Its value is automatically initialized 
      during the provisioning process."
::= { frAtmIfEntryEntry 2 }

frAtmOperStatusTable OBJECT-TYPE
   SYNTAX     SEQUENCE OF FrAtmOperStatusEntry
   ACCESS     not-accessible
   STATUS     mandatory
   DESCRIPTION
     "This group includes the Operational Status attribute. This attribute 
      defines the current operational state of this component."
::= { frAtm 14 }

frAtmOperStatusEntry OBJECT-TYPE
   SYNTAX     FrAtmOperStatusEntry
   ACCESS     not-accessible
   STATUS     mandatory
   DESCRIPTION
     "An entry in the frAtmOperStatusTable."
   INDEX {
      frAtmIndex }
::= { frAtmOperStatusTable 1 }

FrAtmOperStatusEntry ::= SEQUENCE {
   frAtmSnmpOperStatus
      INTEGER }

frAtmSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { frAtmOperStatusEntry 1 }

frAtmEmissionPriorityQsTable OBJECT-TYPE
   SYNTAX     SEQUENCE OF FrAtmEmissionPriorityQsEntry
   ACCESS     not-accessible
   STATUS     mandatory
   DESCRIPTION
     "This group contains the provisionable attribute to specifie the 
      number of Frame Relay egress emission priority queues to be used 
      on that Frame Relay Interface"
::= { frAtm 15 }

frAtmEmissionPriorityQsEntry OBJECT-TYPE
   SYNTAX     FrAtmEmissionPriorityQsEntry
   ACCESS     not-accessible
   STATUS     mandatory
   DESCRIPTION
     "An entry in the frAtmEmissionPriorityQsTable."
   INDEX {
      frAtmIndex }
::= { frAtmEmissionPriorityQsTable 1 }

FrAtmEmissionPriorityQsEntry ::= SEQUENCE {
   frAtmNumberOfEmissionQs
      Unsigned32 }

frAtmNumberOfEmissionQs OBJECT-TYPE
   SYNTAX     Unsigned32 (2 | 4)
   ACCESS     read-write
   STATUS     mandatory
   DESCRIPTION
     "This attribute specifies the number of egress emission priority 
      queues that will be used for that Frame Relay interface. The 
      possible values of this attribute are 2 or 4:
      For V.35, V.11, HSSI, E1, DS1, E3, DS3 or 8pDS1 the possible 
      values are: 2 (in which case they are hardware queues), or 4 (in 
      which case they are software queues).
      For DS1C, E1C or DS3C the possible values are 2, 4 (in all cases 
      they are software queues)."
   DEFVAL     { 2 }
::= { frAtmEmissionPriorityQsEntry 1 }

frAtmFrmToIfByQueueTable OBJECT-TYPE
   SYNTAX     SEQUENCE OF FrAtmFrmToIfByQueueEntry
   ACCESS     not-accessible
   STATUS     mandatory
   DESCRIPTION
     "This attribute counts the total number of frames transmitted to the 
      interface per egress emission priority queue since the component 
      has been activated. There is potientially a maximum of 4 emission 
      priority queues. The number of available egress queues varies 
      according to the value of the provisionable attribute 
      numberOfEmissionQs. Egress queue 0 has the lowest priority, while 
      egress queue 3 has the highest priority. The queue values
      are only indicated when the numberOfEmissionQs is set to 4 
      queues."
::= { frAtm 341 }

frAtmFrmToIfByQueueEntry OBJECT-TYPE
   SYNTAX     FrAtmFrmToIfByQueueEntry
   ACCESS     not-accessible
   STATUS     mandatory
   DESCRIPTION
     "An entry in the frAtmFrmToIfByQueueTable."
   INDEX {
      frAtmIndex,
      frAtmFrmToIfByQueueIndex }
::= { frAtmFrmToIfByQueueTable 1 }

FrAtmFrmToIfByQueueEntry ::= SEQUENCE {
   frAtmFrmToIfByQueueIndex
      Integer32,
   frAtmFrmToIfByQueueValue
      Unsigned32 }

frAtmFrmToIfByQueueIndex OBJECT-TYPE
   SYNTAX     Integer32 (0..3)
   ACCESS     not-accessible
   STATUS     mandatory
   DESCRIPTION
     "This variable represents the index for the frAtmFrmToIfByQueueTable."
::= { frAtmFrmToIfByQueueEntry 1 }

frAtmFrmToIfByQueueValue OBJECT-TYPE
   SYNTAX     Unsigned32 (0..4294967295)
   ACCESS     read-only
   STATUS     mandatory
   DESCRIPTION
     "This variable represents an individual value for the
      frAtmFrmToIfByQueueTable."
::= { frAtmFrmToIfByQueueEntry 2 }

frAtmOctetToIfByQueueTable OBJECT-TYPE
   SYNTAX     SEQUENCE OF FrAtmOctetToIfByQueueEntry
   ACCESS     not-accessible
   STATUS     mandatory
   DESCRIPTION
     "This attribute counts the total number of octets transmitted from the 
      service to the interface per emission priority queue since the 
      component has been activated. There is potientially a maximum of 
      4 emission priority queues. The number of available egress queues 
      varies according to the value of the provisionable attribute 
      numberOfEmissionQs. Egress queue 0 has the lowest priority, while 
      egress queue 3 has the highest priority."
::= { frAtm 342 }

frAtmOctetToIfByQueueEntry OBJECT-TYPE
   SYNTAX     FrAtmOctetToIfByQueueEntry
   ACCESS     not-accessible
   STATUS     mandatory
   DESCRIPTION
     "An entry in the frAtmOctetToIfByQueueTable."
   INDEX {
      frAtmIndex,
      frAtmOctetToIfByQueueIndex }
::= { frAtmOctetToIfByQueueTable 1 }

FrAtmOctetToIfByQueueEntry ::= SEQUENCE {
   frAtmOctetToIfByQueueIndex
      Integer32,
   frAtmOctetToIfByQueueValue
      Unsigned32 }

frAtmOctetToIfByQueueIndex OBJECT-TYPE
   SYNTAX     Integer32 (0..3)
   ACCESS     not-accessible
   STATUS     mandatory
   DESCRIPTION
     "This variable represents the index for the frAtmOctetToIfByQueueTable."
::= { frAtmOctetToIfByQueueEntry 1 }

frAtmOctetToIfByQueueValue OBJECT-TYPE
   SYNTAX     Unsigned32 (0..4294967295)
   ACCESS     read-only
   STATUS     mandatory
   DESCRIPTION
     "This variable represents an individual value for the
      frAtmOctetToIfByQueueTable."
::= { frAtmOctetToIfByQueueEntry 2 }


-- FrUni/n Framer
-- FrNni/n Framer
-- FrAtm/n Framer
-- This component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

frAtmFramer OBJECT IDENTIFIER ::= { frAtm 2 }



frAtmFramerRowStatusTable OBJECT-TYPE
   SYNTAX     SEQUENCE OF FrAtmFramerRowStatusEntry
   ACCESS     not-accessible
   STATUS     mandatory
   DESCRIPTION
     "This entry controls the addition and deletion of 
      frAtmFramer components."
::= { frAtmFramer 1 }

frAtmFramerRowStatusEntry OBJECT-TYPE
   SYNTAX     FrAtmFramerRowStatusEntry
   ACCESS     not-accessible
   STATUS     mandatory
   DESCRIPTION
     "A single entry in the table represents a single 
      frAtmFramer component."
   INDEX {
      frAtmIndex,
      frAtmFramerIndex }
::= { frAtmFramerRowStatusTable 1 }

FrAtmFramerRowStatusEntry ::= SEQUENCE {
   frAtmFramerRowStatus
      RowStatus,
   frAtmFramerComponentName
      DisplayString,
   frAtmFramerStorageType
      StorageType,
   frAtmFramerIndex
      NonReplicated }

frAtmFramerRowStatus OBJECT-TYPE
   SYNTAX     RowStatus 
   ACCESS     read-write
   STATUS     mandatory
   DESCRIPTION
     "This variable is used as the basis for SNMP naming of
      frAtmFramer components.
      These components can be added and deleted."
::= { frAtmFramerRowStatusEntry 1 }

frAtmFramerComponentName OBJECT-TYPE
   SYNTAX     DisplayString 
   ACCESS     read-only
   STATUS     mandatory
   DESCRIPTION
     "This variable provides the component's string name for
      use with the ASCII Console Interface"
::= { frAtmFramerRowStatusEntry 2 }

frAtmFramerStorageType OBJECT-TYPE
   SYNTAX     StorageType 
   ACCESS     read-only
   STATUS     mandatory
   DESCRIPTION
     "This variable represents the storage type value for the
      frAtmFramer tables."
::= { frAtmFramerRowStatusEntry 4 }

frAtmFramerIndex OBJECT-TYPE
   SYNTAX     NonReplicated 
   ACCESS     not-accessible
   STATUS     mandatory
   DESCRIPTION
     "This variable represents the index for the frAtmFramer tables."
::= { frAtmFramerRowStatusEntry 10 }

frAtmFramerProvTable OBJECT-TYPE
   SYNTAX     SEQUENCE OF FrAtmFramerProvEntry
   ACCESS     not-accessible
   STATUS     mandatory
   DESCRIPTION
     "This group contains the base provisioning data for the Framer 
      component. Application or hardware interface specific provisioning 
      data is contained in other provisionable Framer groups."
::= { frAtmFramer 10 }

frAtmFramerProvEntry OBJECT-TYPE
   SYNTAX     FrAtmFramerProvEntry
   ACCESS     not-accessible
   STATUS     mandatory
   DESCRIPTION
     "An entry in the frAtmFramerProvTable."
   INDEX {
      frAtmIndex,
      frAtmFramerIndex }
::= { frAtmFramerProvTable 1 }

FrAtmFramerProvEntry ::= SEQUENCE {
   frAtmFramerInterfaceName
      Link }

frAtmFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { frAtmFramerProvEntry 1 }

frAtmFramerLinkTable OBJECT-TYPE
   SYNTAX     SEQUENCE OF FrAtmFramerLinkEntry
   ACCESS     not-accessible
   STATUS     mandatory
   DESCRIPTION
     "This group contains attributes defining the framing of data on the 
      link interface."
::= { frAtmFramer 11 }

frAtmFramerLinkEntry OBJECT-TYPE
   SYNTAX     FrAtmFramerLinkEntry
   ACCESS     not-accessible
   STATUS     mandatory
   DESCRIPTION
     "An entry in the frAtmFramerLinkTable."
   INDEX {
      frAtmIndex,
      frAtmFramerIndex }
::= { frAtmFramerLinkTable 1 }

FrAtmFramerLinkEntry ::= SEQUENCE {
   frAtmFramerFlagsBetweenFrames
      Unsigned32 }

frAtmFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { frAtmFramerLinkEntry 4 }

frAtmFramerStateTable OBJECT-TYPE
   SYNTAX     SEQUENCE OF FrAtmFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frAtmFramer 12 }

frAtmFramerStateEntry OBJECT-TYPE
   SYNTAX     FrAtmFramerStateEntry
   ACCESS     not-accessible
   STATUS     mandatory
   DESCRIPTION
     "An entry in the frAtmFramerStateTable."
   INDEX {
      frAtmIndex,
      frAtmFramerIndex }
::= { frAtmFramerStateTable 1 }

FrAtmFramerStateEntry ::= SEQUENCE {
   frAtmFramerAdminState
      INTEGER,
   frAtmFramerOperationalState
      INTEGER,
   frAtmFramerUsageState
      INTEGER }

frAtmFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frAtmFramerStateEntry 1 }

frAtmFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frAtmFramerStateEntry 2 }

frAtmFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frAtmFramerStateEntry 3 }

frAtmFramerStatsTable OBJECT-TYPE
   SYNTAX     SEQUENCE OF FrAtmFramerStatsEntry
   ACCESS     not-accessible
   STATUS     mandatory
   DESCRIPTION
     "This group contains the operational statistics data for a Framer 
      component."
::= { frAtmFramer 13 }

frAtmFramerStatsEntry OBJECT-TYPE
   SYNTAX     FrAtmFramerStatsEntry
   ACCESS     not-accessible
   STATUS     mandatory
   DESCRIPTION
     "An entry in the frAtmFramerStatsTable."
   INDEX {
      frAtmIndex,
      frAtmFramerIndex }
::= { frAtmFramerStatsTable 1 }

FrAtmFramerStatsEntry ::= SEQUENCE {
   frAtmFramerFrmToIf
      Counter32,
   frAtmFramerFrmFromIf
      Counter32,
   frAtmFramerOctetFromIf
      Counter32,
   frAtmFramerAborts
      Counter32,
   frAtmFramerCrcErrors
      Counter32,
   frAtmFramerLrcErrors
      Counter32,
   frAtmFramerNonOctetErrors
      Counter32,
   frAtmFramerOverruns
      Counter32,
   frAtmFramerUnderruns
      Counter32,
   frAtmFramerLargeFrmErrors
      Counter32,
   frAtmFramerFrmModeErrors
      Counter32 }

frAtmFramerFrmToIf OBJECT-TYPE
   SYNTAX     Counter32 
   ACCESS     read-only
   STATUS     mandatory
   DESCRIPTION
     "The number of frames transmitted to the link interface by Framer.
      
      Note: This does not include the number of frames transmitted 
      directly to the hardware queue, thus bypassing the Framer 
      component."
::= { frAtmFramerStatsEntry 1 }

frAtmFramerFrmFromIf OBJECT-TYPE
   SYNTAX     Counter32 
   ACCESS     read-only
   STATUS     mandatory
   DESCRIPTION
     "The number of frames received from the link interface by Framer."
::= { frAtmFramerStatsEntry 2 }

frAtmFramerOctetFromIf OBJECT-TYPE
   SYNTAX     Counter32 
   ACCESS     read-only
   STATUS     mandatory
   DESCRIPTION
     "The number of bytes received from the link interface by Framer."
::= { frAtmFramerStatsEntry 3 }

frAtmFramerAborts OBJECT-TYPE
   SYNTAX     Counter32 
   ACCESS     read-only
   STATUS     mandatory
   DESCRIPTION
     "This attribute is the total number of aborts received."
::= { frAtmFramerStatsEntry 4 }

frAtmFramerCrcErrors OBJECT-TYPE
   SYNTAX     Counter32 
   ACCESS     read-only
   STATUS     mandatory
   DESCRIPTION
     "This attribute is the total number of frames with CRC errors, 
      occurring in the receive direction from the link."
::= { frAtmFramerStatsEntry 5 }

frAtmFramerLrcErrors OBJECT-TYPE
   SYNTAX     Counter32 
   ACCESS     read-only
   STATUS     mandatory
   DESCRIPTION
     "This attribute is the total number of frames with LRC errors, 
      occurring in the Tx link prior to transmission onto the link."
::= { frAtmFramerStatsEntry 6 }

frAtmFramerNonOctetErrors OBJECT-TYPE
   SYNTAX     Counter32 
   ACCESS     read-only
   STATUS     mandatory
   DESCRIPTION
     "This attribute is the total number of frames that were non octet 
      aligned."
::= { frAtmFramerStatsEntry 7 }

frAtmFramerOverruns OBJECT-TYPE
   SYNTAX     Counter32 
   ACCESS     read-only
   STATUS     mandatory
   DESCRIPTION
     "This attribute is the total number of frames received from the link 
      for which overruns occurred."
::= { frAtmFramerStatsEntry 8 }

frAtmFramerUnderruns OBJECT-TYPE
   SYNTAX     Counter32 
   ACCESS     read-only
   STATUS     mandatory
   DESCRIPTION
     "This attribute is the total number of frames transmitted to the link 
      for which underruns occurred."
::= { frAtmFramerStatsEntry 9 }

frAtmFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { frAtmFramerStatsEntry 10 }

frAtmFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { frAtmFramerStatsEntry 11 }

frAtmFramerUtilTable OBJECT-TYPE
   SYNTAX     SEQUENCE OF FrAtmFramerUtilEntry
   ACCESS     not-accessible
   STATUS     mandatory
   DESCRIPTION
     "This group contains the link utilizaiton operational data for a 
      Framer component."
::= { frAtmFramer 14 }

frAtmFramerUtilEntry OBJECT-TYPE
   SYNTAX     FrAtmFramerUtilEntry
   ACCESS     not-accessible
   STATUS     mandatory
   DESCRIPTION
     "An entry in the frAtmFramerUtilTable."
   INDEX {
      frAtmIndex,
      frAtmFramerIndex }
::= { frAtmFramerUtilTable 1 }

FrAtmFramerUtilEntry ::= SEQUENCE {
   frAtmFramerNormPrioLinkUtilToIf
      Gauge32,
   frAtmFramerNormPrioLinkUtilFromIf
      Gauge32 }

frAtmFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities (TP) of 0, 6 and 9 and/or Emission Priority of 2 
      and 3. The utilization is the average for the last minute."
   DEFVAL     { 0 }
::= { frAtmFramerUtilEntry 1 }

frAtmFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { frAtmFramerUtilEntry 3 }


-- FrUni/n LocalManagementInterface
-- FrNni/n LocalManagementInterface
-- FrAtm/n LocalManagementInterface
-- This component defines the parameters for implementing the Local 
-- Management Interface protocol.

frAtmLmi OBJECT IDENTIFIER ::= { frAtm 3 }



frAtmLmiRowStatusTable OBJECT-TYPE
   SYNTAX     SEQUENCE OF FrAtmLmiRowStatusEntry
   ACCESS     not-accessible
   STATUS     mandatory
   DESCRIPTION
     "This entry controls the addition and deletion of 
      frAtmLmi components."
::= { frAtmLmi 1 }

frAtmLmiRowStatusEntry OBJECT-TYPE
   SYNTAX     FrAtmLmiRowStatusEntry
   ACCESS     not-accessible
   STATUS     mandatory
   DESCRIPTION
     "A single entry in the table represents a single 
      frAtmLmi component."
   INDEX {
      frAtmIndex,
      frAtmLmiIndex }
::= { frAtmLmiRowStatusTable 1 }

FrAtmLmiRowStatusEntry ::= SEQUENCE {
   frAtmLmiRowStatus
      RowStatus,
   frAtmLmiComponentName
      DisplayString,
   frAtmLmiStorageType
      StorageType,
   frAtmLmiIndex
      NonReplicated }

frAtmLmiRowStatus OBJECT-TYPE
   SYNTAX     RowStatus 
   ACCESS     read-only
   STATUS     mandatory
   DESCRIPTION
     "This variable is used as the basis for SNMP naming of
      frAtmLmi components.
      These components cannot be added nor deleted."
::= { frAtmLmiRowStatusEntry 1 }

frAtmLmiComponentName OBJECT-TYPE
   SYNTAX     DisplayString 
   ACCESS     read-only
   STATUS     mandatory
   DESCRIPTION
     "This variable provides the component's string name for
      use with the ASCII Console Interface"
::= { frAtmLmiRowStatusEntry 2 }

frAtmLmiStorageType OBJECT-TYPE
   SYNTAX     StorageType 
   ACCESS     read-only
   STATUS     mandatory
   DESCRIPTION
     "This variable represents the storage type value for the
      frAtmLmi tables."
::= { frAtmLmiRowStatusEntry 4 }

frAtmLmiIndex OBJECT-TYPE
   SYNTAX     NonReplicated 
   ACCESS     not-accessible
   STATUS     mandatory
   DESCRIPTION
     "This variable represents the index for the frAtmLmi tables."
::= { frAtmLmiRowStatusEntry 10 }

frAtmLmiParmsTable OBJECT-TYPE
   SYNTAX     SEQUENCE OF FrAtmLmiParmsEntry
   ACCESS     not-accessible
   STATUS     mandatory
   DESCRIPTION
     "This group contains the provisionable attributes of the LMI 
      component."
::= { frAtmLmi 10 }

frAtmLmiParmsEntry OBJECT-TYPE
   SYNTAX     FrAtmLmiParmsEntry
   ACCESS     not-accessible
   STATUS     mandatory
   DESCRIPTION
     "An entry in the frAtmLmiParmsTable."
   INDEX {
      frAtmIndex,
      frAtmLmiIndex }
::= { frAtmLmiParmsTable 1 }

FrAtmLmiParmsEntry ::= SEQUENCE {
   frAtmLmiProcedures
      INTEGER,
   frAtmLmiAsyncStatusReport
      INTEGER,
   frAtmLmiErrorEventThreshold
      Unsigned32,
   frAtmLmiEventCount
      Unsigned32,
   frAtmLmiCheckPointTimer
      Unsigned32,
   frAtmLmiMessageCountTimer
      Unsigned32,
   frAtmLmiIgnoreActiveBit
      INTEGER,
   frAtmLmiSide
      INTEGER,
   frAtmLmiPvcConfigParmsInFsr
      INTEGER }

frAtmLmiProcedures OBJECT-TYPE
   SYNTAX     INTEGER  {
                 none(0),
                 vendorForum(1),
                 ansi(2),
                 itu(3),
                 autoConfigure(4) }
   ACCESS     read-write
   STATUS     mandatory
   DESCRIPTION
     "This attribute selects the procedures to be used for the Local 
      Management Interface. The following procedures are supported:
      
      none: no Local Management Interface procedures are running on 
      this interface. This accommodates Frame Relay user equipment that 
      has not implemented any LMI procedures. The remaining attributes 
      of this group are ignored.
      
      vendorForum: Local Management Interface procedures from the 
      Vendor Forum specification are supported on this interface. DLCI 
      1023 is used for the LMI protocol. This value cannot be used if the 
      side attribute is both.
      
      ansi: Local Management Interface procedures from the ANSI 
      specification are supported. DLCI 0 is used for the LMI protocol.
      
      itu: Local Management Interface procedures from the ITU-T 
      specification are supported. DLCI 0 is used for the LMI protocol. 
      Was previously ccitt.
      
      autoConfigure: The interface determines automatically which 
      Local Management Interface procedures to use. This value cannot 
      be used if the side attribute is user.
      
      The procedures currently in use can be seen in the operational 
      attribute opProcedures."
   DEFVAL     { autoConfigure }
::= { frAtmLmiParmsEntry 1 }

frAtmLmiAsyncStatusReport OBJECT-TYPE
   SYNTAX     INTEGER  {
                 off(0),
                 on(1) }
   ACCESS     read-write
   STATUS     mandatory
   DESCRIPTION
     "This attribute selects the use of asynchronous PVC status report 
      procedures as specified in ANSI, CCITT, and Vendor Forum. 
      
      This attribute can be set to on or off. If procedures is set to none, 
      this attribute is ignored."
   DEFVAL     { off }
::= { frAtmLmiParmsEntry 2 }

frAtmLmiErrorEventThreshold OBJECT-TYPE
   SYNTAX     Unsigned32 (1..10)
   ACCESS     read-write
   STATUS     mandatory
   DESCRIPTION
     "An event is defined as follows: (1) receipt of a STATUS ENQUIRY 
      message; or (2) expiration of timer T392. An error event is (1) 
      nonreceipt of STATUS ENQUIRY in T392 seconds; (2) invalid 
      contents of a LMI message; (3) invalid receive sequence number. 
      This attribute specifies the number of error events which, if they 
      occur within eventCount events, cause a protocol error condition. 
      The condition is cleared after eventCount sequential correct events 
      occur. This attribute corresponds to the nN2 parameter described in 
      the Vendor Forum Specification. 
      
      It must be less than or equal to eventCount."
   DEFVAL     { 3 }
::= { frAtmLmiParmsEntry 3 }

frAtmLmiEventCount OBJECT-TYPE
   SYNTAX     Unsigned32 (1..10)
   ACCESS     read-write
   STATUS     mandatory
   DESCRIPTION
     "This attribute specifies the number of contiguous events within 
      which no more than eventErrorThreshold error events are allowed. 
      This attribute corresponds to the nN3 parameter described in the 
      Vendor Forum Specification. 
      
      It must be greater than or equal to errorEventThreshold."
   DEFVAL     { 4 }
::= { frAtmLmiParmsEntry 4 }

frAtmLmiCheckPointTimer OBJECT-TYPE
   SYNTAX     Unsigned32 (5 | 10 | 15 | 20 | 25 | 30)
   ACCESS     read-write
   STATUS     mandatory
   DESCRIPTION
     "This attribute selects the time (in seconds) within which a STATUS 
      ENQUIRY message is expected. This attribute corresponds to the 
      nT2 parameter described in the Vendor Forum Specification.
      
      It must be less than messageCountTimer."
   DEFVAL     { 15 }
::= { frAtmLmiParmsEntry 5 }

frAtmLmiMessageCountTimer OBJECT-TYPE
   SYNTAX     Unsigned32 (5 | 10 | 15 | 20 | 25 | 30)
   ACCESS     read-write
   STATUS     mandatory
   DESCRIPTION
     "This attribute selects the time (in seconds) within which at most five 
      (this is a fixed value and corresponds to maximum message count in 
      VendorForum) STATUS ENQUIRY messages are expected. This 
      attribute applies only when the lmiProcedures is set to 
      vendorForum.
      
      messageCountTimer must always be greater than checkPointTimer."
   DEFVAL     { 20 }
::= { frAtmLmiParmsEntry 6 }

frAtmLmiIgnoreActiveBit OBJECT-TYPE
   SYNTAX     INTEGER  {
                 no(0),
                 yes(1) }
   ACCESS     read-write
   STATUS     mandatory
   DESCRIPTION
     "This attribute specifies whether the Frame Relay LMI Active Bit 
      (A-bit) has a bearing on the transfer of user data across this Frame 
      Relay interface for both directions of traffic flow.
      
      When this attribute is set to yes, the A-bit status of a user DLCI 
      connection does not affect data transfer.
      
      When this attribute is set to no, data received from the local 
      interface will be discarded if an A-bit =0 condition exists towards 
      the local user. Data being sent to the local interface is discarded if 
      an A-bit = 0 condition exists towards the subnet."
   DEFVAL     { no }
::= { frAtmLmiParmsEntry 7 }

frAtmLmiSide OBJECT-TYPE
   SYNTAX     INTEGER  {
                 network(0),
                 user(1),
                 both(2) }
   ACCESS     read-write
   STATUS     mandatory
   DESCRIPTION
     "This attribute can be set to user, network, or both. 
      
      When this attribute is set to user, USP LMI procedures are running. 
      When this attribute is set to network, NSP LMI procedures are 
      running. When this attribute is set to both, USPNSP LMI 
      procedures are running.
      When the value is both, the procedures attribute must not be set to 
      vendorForum. 
      Setting the value to user when the procedures attribute is set to 
      autoConfigure is disallowed semantically."
   DEFVAL     { network }
::= { frAtmLmiParmsEntry 8 }

frAtmLmiPvcConfigParmsInFsr OBJECT-TYPE
   SYNTAX     INTEGER  {
                 no(0),
                 yes(1) }
   ACCESS     read-write
   STATUS     mandatory
   DESCRIPTION
     "When this attribute is set to yes, additional Q.933 information 
      elements are included in the LMI Full Status message to facilitate 
      CPE PVC parameter configuring.
      
      When set to yes, the Check Prov command fails if the Lmi side is 
      not set to network.
      
      When set to yes, Check Prov fails if the number of DLCIs on the 
      FrUni is greater than 300.
      
      If the service is not a FrUni this attribute is ignored."
   DEFVAL     { no }
::= { frAtmLmiParmsEntry 9 }

frAtmLmiStateTable OBJECT-TYPE
   SYNTAX     SEQUENCE OF FrAtmLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frAtmLmi 11 }

frAtmLmiStateEntry OBJECT-TYPE
   SYNTAX     FrAtmLmiStateEntry
   ACCESS     not-accessible
   STATUS     mandatory
   DESCRIPTION
     "An entry in the frAtmLmiStateTable."
   INDEX {
      frAtmIndex,
      frAtmLmiIndex }
::= { frAtmLmiStateTable 1 }

FrAtmLmiStateEntry ::= SEQUENCE {
   frAtmLmiAdminState
      INTEGER,
   frAtmLmiOperationalState
      INTEGER,
   frAtmLmiUsageState
      INTEGER }

frAtmLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frAtmLmiStateEntry 1 }

frAtmLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frAtmLmiStateEntry 2 }

frAtmLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frAtmLmiStateEntry 3 }

frAtmLmiPsiTable OBJECT-TYPE
   SYNTAX     SEQUENCE OF FrAtmLmiPsiEntry
   ACCESS     not-accessible
   STATUS     mandatory
   DESCRIPTION
     "This group provides the protocol status of the Local Management 
      Interface."
::= { frAtmLmi 12 }

frAtmLmiPsiEntry OBJECT-TYPE
   SYNTAX     FrAtmLmiPsiEntry
   ACCESS     not-accessible
   STATUS     mandatory
   DESCRIPTION
     "An entry in the frAtmLmiPsiTable."
   INDEX {
      frAtmIndex,
      frAtmLmiIndex }
::= { frAtmLmiPsiTable 1 }

FrAtmLmiPsiEntry ::= SEQUENCE {
   frAtmLmiProtocolStatus
      INTEGER,
   frAtmLmiOpProcedures
      INTEGER }

frAtmLmiProtocolStatus OBJECT-TYPE
   SYNTAX     INTEGER  {
                 errorCondition(0),
                 normalCondition(1),
                 configuring(2) }
   ACCESS     read-only
   STATUS     mandatory
   DESCRIPTION
     "This attribute indicates whether the LMI is in an error condition or 
      whether the LMI procedures are behaving normally. When 
      operating with no LMI protocol, this attribute is always set to 
      normalCondition. When operating with LMI procedures, this 
      attribute is set to errorCondition after n392 of the last n393 events 
      are in error. The consequence of an errorCondition is that all 
      DLCIs on this interface will become inactive in both directions. The 
      errorCondition is cleared and a normalCondition is indicated when 
      a sufficient number of events have occurred without error. In ANSI, 
      this occurs when n393 consecutive good events take place.
      
      If the procedures attribute is set to autoConfigure, this attribute is 
      set to configuring while adaptive LMI determines which LMI 
      procedures are running on the link. A single LMI error event during 
      auto configuration causes the attribute value to change to 
      errorCondition. If during configuring no LMI message is received, 
      an LMI errorCondition is raised after n392 x t392 seconds."
::= { frAtmLmiPsiEntry 1 }

frAtmLmiOpProcedures OBJECT-TYPE
   SYNTAX     INTEGER  {
                 none(0),
                 vendorForum(1),
                 ansi(2),
                 itu(3),
                 unknown(4) }
   ACCESS     read-only
   STATUS     mandatory
   DESCRIPTION
     "The opProcedures attribute indicates the procedures being used for 
      the Local Management Interface. This attribute should be ignored if 
      protocolStatus is not normalCondition. The following procedures 
      are supported:
      
      none: Local Management Interface procedures are not running on 
      this interface. This accommodates Frame Relay user equipment that 
      has not implemented any LMI procedures.
      
      vendorForum: Local Management Interface procedures from the 
      Vendor Forum specification are running on this interface. DLCI 
      1023 is used for the LMI protocol.
      
      ansi: Local Management Interface procedures from the ANSI 
      specification are running. DLCI 0 is used for the LMI protocol.
      
      itu: Local Management Interface procedures from the ITU-T 
      specification are running. DLCI 0 is used for the LMI protocol. Was 
      previously ccitt.
      
      unknown: Local Management Interface procedures have yet to be 
      determined by Adaptive LMI."
::= { frAtmLmiPsiEntry 2 }

frAtmLmiStatsTable OBJECT-TYPE
   SYNTAX     SEQUENCE OF FrAtmLmiStatsEntry
   ACCESS     not-accessible
   STATUS     mandatory
   DESCRIPTION
     "This group contains the operational statistics for the Frame Relay 
      Local Management Interface."
::= { frAtmLmi 13 }

frAtmLmiStatsEntry OBJECT-TYPE
   SYNTAX     FrAtmLmiStatsEntry
   ACCESS     not-accessible
   STATUS     mandatory
   DESCRIPTION
     "An entry in the frAtmLmiStatsTable."
   INDEX {
      frAtmIndex,
      frAtmLmiIndex }
::= { frAtmLmiStatsTable 1 }

FrAtmLmiStatsEntry ::= SEQUENCE {
   frAtmLmiKeepAliveStatusToIf
      Counter32,
   frAtmLmiFullStatusToIf
      Counter32,
   frAtmLmiKeepAliveStatusEnqFromIf
      Counter32,
   frAtmLmiFullStatusEnqFromIf
      Counter32,
   frAtmLmiNetworkSideEventHistory
      AsciiString,
   frAtmLmiProtocolErrors
      Counter32,
   frAtmLmiUnexpectedIes
      Counter32,
   frAtmLmiSequenceErrors
      Counter32,
   frAtmLmiUnexpectedReports
      Counter32,
   frAtmLmiPollingVerifTimeouts
      Counter32,
   frAtmLmiKeepAliveEnqToIf
      Counter32,
   frAtmLmiFullStatusEnqToIf
      Counter32,
   frAtmLmiUserSideEventHistory
      AsciiString,
   frAtmLmiStatusSequenceErrors
      Counter32,
   frAtmLmiNoStatusReportCount
      Counter32 }

frAtmLmiKeepAliveStatusToIf OBJECT-TYPE
   SYNTAX     Counter32 
   ACCESS     read-only
   STATUS     mandatory
   DESCRIPTION
     "This attribute counts the number of Local Management Interface 
      keep alive status messages sent to the external user device in 
      response to a status enquiry for keep alive status. When the 
      maximum count is exceeded it wraps to zero."
::= { frAtmLmiStatsEntry 1 }

frAtmLmiFullStatusToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { frAtmLmiStatsEntry 2 }

frAtmLmiKeepAliveStatusEnqFromIf OBJECT-TYPE
   SYNTAX     Counter32 
   ACCESS     read-only
   STATUS     mandatory
   DESCRIPTION
     "This attribute counts the number of Local Management Interface 
      valid keep alive status enquiry messages received from the external 
      user device. When the maximum count is reached it wraps to zero."
::= { frAtmLmiStatsEntry 3 }

frAtmLmiFullStatusEnqFromIf OBJECT-TYPE
   SYNTAX     Counter32 
   ACCESS     read-only
   STATUS     mandatory
   DESCRIPTION
     "This attribute counts the number of Local Management Interface 
      valid full status enquiry messages received from the external user 
      device. When the maximum count is reached it wraps to zero."
::= { frAtmLmiStatsEntry 4 }

frAtmLmiNetworkSideEventHistory OBJECT-TYPE
   SYNTAX     AsciiString (SIZE (1..10))
   ACCESS     read-only
   STATUS     mandatory
   DESCRIPTION
     "This attribute displays the Local Management Interface network 
      side procedure event history in order of occurrence. An event is 
      represented by a single symbol. A '+' symbol indicates a good 
      event. An 'X' symbol indicates a protocol error event. The leftmost 
      event is the most recent to occur. The provisioned eventCount (nN3/
      N393) dictates the maximum number of events displayed. A good 
      event is triggered by receipt of a valid status enquiry message. An 
      error event is one of three possibilities, either a nT2/T392 timer 
      expiry, receipt of a status enquiry message with bad sequence 
      numbers, or when lmiProcedures is provisioned to vendorForum 
      and we receive more than nN4 status enquiry messages within the 
      provisioned messageCountTimer (nT3)."
::= { frAtmLmiStatsEntry 5 }

frAtmLmiProtocolErrors OBJECT-TYPE
   SYNTAX     Counter32 
   ACCESS     read-only
   STATUS     mandatory
   DESCRIPTION
     "This attribute counts the number of Local Management Interface 
      protocol errors. It is the sum of the sequence (sequenceErrors), 
      timeout (pollingVerifTimeouts) and too many status enquiry 
      messages received within the messageCountTimer (nT3) errors. The 
      too many status enquiries error only applies when lmiProcedures is 
      set to vendorForum. When the maximum count is exceeded it 
      wraps to zero."
::= { frAtmLmiStatsEntry 6 }

frAtmLmiUnexpectedIes OBJECT-TYPE
   SYNTAX     Counter32 
   ACCESS     read-only
   STATUS     mandatory
   DESCRIPTION
     "This attribute counts the number of Local Management Interface 
      frames received with an Information Element identifier that is 
      unknown or unexpected. An unexpected Information Element is not 
      a protocol error. When the maximum count is reached, this counter 
      wraps to zero."
::= { frAtmLmiStatsEntry 7 }

frAtmLmiSequenceErrors OBJECT-TYPE
   SYNTAX     Counter32 
   ACCESS     read-only
   STATUS     mandatory
   DESCRIPTION
     "This attribute counts the number of Local Management Interface 
      Status Enquiry message sequence errors. A sequence error is receipt 
      of a Status Enquiry message with a receive sequence number not 
      equal to the last send sequence number. When the maximum count 
      is reached the counter wraps to zero."
::= { frAtmLmiStatsEntry 8 }

frAtmLmiUnexpectedReports OBJECT-TYPE
   SYNTAX     Counter32 
   ACCESS     read-only
   STATUS     mandatory
   DESCRIPTION
     "This attribute counts the number of Local Management Interface 
      frames received with an unknown or unexpected report type. An 
      unexpected report type is not a protocol error. When the maximum 
      count is reached the counter wraps to zero."
::= { frAtmLmiStatsEntry 9 }

frAtmLmiPollingVerifTimeouts OBJECT-TYPE
   SYNTAX     Counter32 
   ACCESS     read-only
   STATUS     mandatory
   DESCRIPTION
     "This attribute counts the number of checkPointTImer (t392) timer 
      expiries occurring on the Local Management Interface. When the 
      maximum count is reached the counter wraps to zero."
::= { frAtmLmiStatsEntry 10 }

frAtmLmiKeepAliveEnqToIf OBJECT-TYPE
   SYNTAX     Counter32 
   ACCESS     read-only
   STATUS     mandatory
   DESCRIPTION
     "This attribute counts the number of Local Management Interface 
      keep alive enquiry status messages sent to the external user device 
      for keep alive status. When the maximum count is reached it wraps 
      to zero."
::= { frAtmLmiStatsEntry 11 }

frAtmLmiFullStatusEnqToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { frAtmLmiStatsEntry 12 }

frAtmLmiUserSideEventHistory OBJECT-TYPE
   SYNTAX     AsciiString (SIZE (1..10))
   ACCESS     read-only
   STATUS     mandatory
   DESCRIPTION
     "This attribute displays the Local Management Interface user side 
      procedure event history in order of occurrence. An event is 
      represented by a single symbol. A '+' symbol indicates a good 
      event. An 'X' symbol indicates a protocol error event. The left most 
      event is the most recent to occur. The provisioned eventCount (nN3/
      N393) dictates the maximum number of events displayed. A good 
      event is triggered by receipt of a valid status message. An error 
      event is either a nT1/T391 timer expiry or receipt of a status 
      message with bad sequence numbers."
::= { frAtmLmiStatsEntry 13 }

frAtmLmiStatusSequenceErrors OBJECT-TYPE
   SYNTAX     Counter32 
   ACCESS     read-only
   STATUS     mandatory
   DESCRIPTION
     "This attribute counts the number of Local Management Interface 
      Status message sequence errors. A sequence error is receipt of a 
      Status message with a receive sequence number not equal to the last 
      send sequence number. When the maximum count is reached the 
      counter wraps to zero."
::= { frAtmLmiStatsEntry 14 }

frAtmLmiNoStatusReportCount OBJECT-TYPE
   SYNTAX     Counter32 
   ACCESS     read-only
   STATUS     mandatory
   DESCRIPTION
     "This attribute counts the number of times when no status report or 
      an invalid status report comes from the external network. This 
      attribute is incremented in two cases: 
      i) after a status enquiry is sent out and T391 timer expires without 
      having a status report received.
      ii) an invalid status report is received.
      
      When the maximum count is reached it wraps to zero."
::= { frAtmLmiStatsEntry 15 }

frAtmLmiUspParmsTable OBJECT-TYPE
   SYNTAX     SEQUENCE OF FrAtmLmiUspParmsEntry
   ACCESS     not-accessible
   STATUS     mandatory
   DESCRIPTION
     "This group contains the provisionable attributes of the Local 
      Management Interface user side procedure."
::= { frAtmLmi 14 }

frAtmLmiUspParmsEntry OBJECT-TYPE
   SYNTAX     FrAtmLmiUspParmsEntry
   ACCESS     not-accessible
   STATUS     mandatory
   DESCRIPTION
     "An entry in the frAtmLmiUspParmsTable."
   INDEX {
      frAtmIndex,
      frAtmLmiIndex }
::= { frAtmLmiUspParmsTable 1 }

FrAtmLmiUspParmsEntry ::= SEQUENCE {
   frAtmLmiFullStatusPollingCycles
      Unsigned32,
   frAtmLmiLinkVerificationTimer
      Unsigned32 }

frAtmLmiFullStatusPollingCycles OBJECT-TYPE
   SYNTAX     Unsigned32 (1..255)
   ACCESS     read-write
   STATUS     mandatory
   DESCRIPTION
     "This attribute specifies how frequently the Frame Relay UNI service 
      should initiate a Status Enquiry for a full PVC status report. A 
      polling cycle is a Status Enquiry and Status Report exchange. 
      
      This attribute is used only if the side attribute is either user or both."
   DEFVAL     { 6 }
::= { frAtmLmiUspParmsEntry 1 }

frAtmLmiLinkVerificationTimer OBJECT-TYPE
   SYNTAX     Unsigned32 (5 | 10 | 15 | 20 | 25 | 30)
   ACCESS     read-write
   STATUS     mandatory
   DESCRIPTION
     "This attribute specifies how frequently the Frame Relay UNI service 
      should initiate a Status Enquiry for link integrity verification. It 
      must be less than checkPointTimer (t392).
      
      When the Lmi side is network, this attribute is ignored."
   DEFVAL     { 10 }
::= { frAtmLmiUspParmsEntry 2 }


-- FrAtm/n DataLinkConnectionIdentifier/n
-- This component represents a data link connection. The instance 
-- value defines the DLCI value for this connection. For example, 
-- Dlci/30 defines a logical connection with a DLCI of 30. 
-- 
-- The Dlci component is a subcomponent of FrAtm, and is 
-- responsible for the Frame Relay U-plane (User-plane) protocol for 
-- the specified data link connection.

frAtmDlci OBJECT IDENTIFIER ::= { frAtm 4 }



frAtmDlciRowStatusTable OBJECT-TYPE
   SYNTAX     SEQUENCE OF FrAtmDlciRowStatusEntry
   ACCESS     not-accessible
   STATUS     mandatory
   DESCRIPTION
     "This entry controls the addition and deletion of 
      frAtmDlci components."
::= { frAtmDlci 1 }

frAtmDlciRowStatusEntry OBJECT-TYPE
   SYNTAX     FrAtmDlciRowStatusEntry
   ACCESS     not-accessible
   STATUS     mandatory
   DESCRIPTION
     "A single entry in the table represents a single 
      frAtmDlci component."
   INDEX {
      frAtmIndex,
      frAtmDlciIndex }
::= { frAtmDlciRowStatusTable 1 }

FrAtmDlciRowStatusEntry ::= SEQUENCE {
   frAtmDlciRowStatus
      RowStatus,
   frAtmDlciComponentName
      DisplayString,
   frAtmDlciStorageType
      StorageType,
   frAtmDlciIndex
      Integer32 }

frAtmDlciRowStatus OBJECT-TYPE
   SYNTAX     RowStatus 
   ACCESS     read-write
   STATUS     mandatory
   DESCRIPTION
     "This variable is used as the basis for SNMP naming of
      frAtmDlci components.
      These components can be added and deleted."
::= { frAtmDlciRowStatusEntry 1 }

frAtmDlciComponentName OBJECT-TYPE
   SYNTAX     DisplayString 
   ACCESS     read-only
   STATUS     mandatory
   DESCRIPTION
     "This variable provides the component's string name for
      use with the ASCII Console Interface"
::= { frAtmDlciRowStatusEntry 2 }

frAtmDlciStorageType OBJECT-TYPE
   SYNTAX     StorageType 
   ACCESS     read-only
   STATUS     mandatory
   DESCRIPTION
     "This variable represents the storage type value for the
      frAtmDlci tables."
::= { frAtmDlciRowStatusEntry 4 }

frAtmDlciIndex OBJECT-TYPE
   SYNTAX     Integer32 (16..1007)
   ACCESS     not-accessible
   STATUS     mandatory
   DESCRIPTION
     "This variable represents the index for the frAtmDlci tables."
::= { frAtmDlciRowStatusEntry 10 }

frAtmDlciStateTable OBJECT-TYPE
   SYNTAX     SEQUENCE OF FrAtmDlciStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frAtmDlci 10 }

frAtmDlciStateEntry OBJECT-TYPE
   SYNTAX     FrAtmDlciStateEntry
   ACCESS     not-accessible
   STATUS     mandatory
   DESCRIPTION
     "An entry in the frAtmDlciStateTable."
   INDEX {
      frAtmIndex,
      frAtmDlciIndex }
::= { frAtmDlciStateTable 1 }

FrAtmDlciStateEntry ::= SEQUENCE {
   frAtmDlciAdminState
      INTEGER,
   frAtmDlciOperationalState
      INTEGER,
   frAtmDlciUsageState
      INTEGER }

frAtmDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frAtmDlciStateEntry 1 }

frAtmDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frAtmDlciStateEntry 2 }

frAtmDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frAtmDlciStateEntry 3 }

frAtmDlciABitTable OBJECT-TYPE
   SYNTAX     SEQUENCE OF FrAtmDlciABitEntry
   ACCESS     not-accessible
   STATUS     mandatory
   DESCRIPTION
     "This group contains the A-Bit status information for this Data Link 
      Connection Identifier."
::= { frAtmDlci 11 }

frAtmDlciABitEntry OBJECT-TYPE
   SYNTAX     FrAtmDlciABitEntry
   ACCESS     not-accessible
   STATUS     mandatory
   DESCRIPTION
     "An entry in the frAtmDlciABitTable."
   INDEX {
      frAtmIndex,
      frAtmDlciIndex }
::= { frAtmDlciABitTable 1 }

FrAtmDlciABitEntry ::= SEQUENCE {
   frAtmDlciABitStatusToIf
      INTEGER,
   frAtmDlciABitReasonToIf
      INTEGER,
   frAtmDlciABitStatusFromIf
      INTEGER,
   frAtmDlciABitReasonFromIf
      INTEGER }

frAtmDlciABitStatusToIf OBJECT-TYPE
   SYNTAX     INTEGER  {
                 inactive(0),
                 active(1),
                 notApplicable(2) }
   ACCESS     read-only
   STATUS     mandatory
   DESCRIPTION
     "This attribute contains the most recent A-bit status sent to the 
      interface. The A-bit status is part of the LMI protocol, and indicates 
      the remote end's willingness to accept data from the local interface. 
      When an inactive setting is sent out, the Frame Relay service will 
      discard any data offered from the local interface. When an active 
      setting is sent out, the Frame Relay service tries to process all data 
      offered from the local interface."
::= { frAtmDlciABitEntry 1 }

frAtmDlciABitReasonToIf OBJECT-TYPE
   SYNTAX     INTEGER  {
                 notApplicable(0),
                 remoteUserSignaled(1),
                 localLmiError(2),
                 remoteLmiError(3),
                 localLinkDown(4),
                 remoteLinkDown(5),
                 pvcDown(6) }
   ACCESS     read-only
   STATUS     mandatory
   DESCRIPTION
     "This attribute provides the reason (if any) for an inactive status to be 
      sent to the interface. This reason is notApplicable for an active 
      status."
::= { frAtmDlciABitEntry 2 }

frAtmDlciABitStatusFromIf OBJECT-TYPE
   SYNTAX     INTEGER  {
                 inactive(0),
                 active(1),
                 notApplicable(2) }
   ACCESS     read-only
   STATUS     mandatory
   DESCRIPTION
     "This attribute indicates the most recent A-Bit status received from 
      the interface."
::= { frAtmDlciABitEntry 3 }

frAtmDlciABitReasonFromIf OBJECT-TYPE
   SYNTAX     INTEGER  {
                 notApplicable(0),
                 remoteUserSignaled(1),
                 localLmiError(2),
                 localLinkDown(4),
                 pvcDown(6),
                 missingFromLmiReport(7) }
   ACCESS     read-only
   STATUS     mandatory
   DESCRIPTION
     "This attribute provides the reason (if any) for an inactive status to be 
      sent to the subnet.
      The value is notApplicable when the aBitStatusFromIf attribute is 
      active.
      The value is remoteUserSignaled if the remote interface originating 
      the A-Bit status detects that the virtual circuit is down at the remote 
      network through the LMI protocol. The remote interface must be 
      running network site LMI protocol for this A-Bit status reason to be 
      sent.
      The value is localLmiError if the LMI protocol is down at this 
      interface.
      The value is localLinkDown if the physical link is disabled at this 
      interface.
      The value is pvcDown if no A-Bit status has been sent to this 
      interface from the local network.
      The value is missingFromLmiReport if the remote interface did not 
      provide a reason along with the inactive A-Bit status.
      DESCRIPTION"
::= { frAtmDlciABitEntry 4 }

frAtmDlciSpOpTable OBJECT-TYPE
   SYNTAX     SEQUENCE OF FrAtmDlciSpOpEntry
   ACCESS     not-accessible
   STATUS     mandatory
   DESCRIPTION
     "This group contains service parameters for the Dlci component."
::= { frAtmDlci 12 }

frAtmDlciSpOpEntry OBJECT-TYPE
   SYNTAX     FrAtmDlciSpOpEntry
   ACCESS     not-accessible
   STATUS     mandatory
   DESCRIPTION
     "An entry in the frAtmDlciSpOpTable."
   INDEX {
      frAtmIndex,
      frAtmDlciIndex }
::= { frAtmDlciSpOpTable 1 }

FrAtmDlciSpOpEntry ::= SEQUENCE {
   frAtmDlciMaximumFrameSize
      Unsigned32,
   frAtmDlciRateEnforcement
      INTEGER,
   frAtmDlciCommittedInformationRate
      Unsigned32,
   frAtmDlciCommittedBurstSize
      Unsigned32,
   frAtmDlciExcessBurstSize
      Unsigned32,
   frAtmDlciMeasurementInterval
      Unsigned32,
   frAtmDlciEmissionPriorityToIf
      INTEGER,
   frAtmDlciDlciType
      INTEGER,
   frAtmDlciTroubled
      INTEGER,
   frAtmDlciTroubledReason
      INTEGER }

frAtmDlciMaximumFrameSize OBJECT-TYPE
   SYNTAX     Unsigned32 (1..8187)
   ACCESS     read-only
   STATUS     mandatory
   DESCRIPTION
     "This attribute indicates the maximum number of octets which can 
      be included in the information field. This definition does not include 
      the FrameRelay header and CRC octets. This attribute corresponds 
      to the dN1 parameter described in the Vendor Forum Specification."
::= { frAtmDlciSpOpEntry 1 }

frAtmDlciRateEnforcement OBJECT-TYPE
   SYNTAX     INTEGER  {
                 off(0),
                 on(1) }
   ACCESS     read-only
   STATUS     mandatory
   DESCRIPTION
     "This attribute indicates whether rate enforcement is in effect for this 
      user Data Link Connection on this FrAtm interface. 
      
      When rate enforcement is on, Committed Information Rate (CIR) 
      and DE=1 traffic will be measured and enforced.
      
      When rate enforcement is off, all frames from the user will be 
      accepted and no modifications to the frame with respect to the DE 
      bit will be made."
::= { frAtmDlciSpOpEntry 2 }

frAtmDlciCommittedInformationRate OBJECT-TYPE
   SYNTAX     Unsigned32 (0..50000000)
   ACCESS     read-only
   STATUS     mandatory
   DESCRIPTION
     "This attribute indicates the committed information rate (CIR) in bits 
      per second (bit/s) and represents the rate at which the network 
      agrees to transfer information under normal conditions when 
      rateEnforcement is on. This rate is measured over a measurement 
      interval (t).
      
      This attribute is not applicable when rateEnforcement is off."
::= { frAtmDlciSpOpEntry 3 }

frAtmDlciCommittedBurstSize OBJECT-TYPE
   SYNTAX     Unsigned32 (0..50000000)
   ACCESS     read-only
   STATUS     mandatory
   DESCRIPTION
     "This attribute indicates the committed burst size (Bc) in bits and 
      represents the amount of data that a network agrees to transfer 
      under normal conditions over a measurement interval (t) when 
      rateEnforcement is on. Data marked with DE=1 is not accounted for 
      in committed burst size.
      
      This attribute is not applicable when rateEnforcement is off."
::= { frAtmDlciSpOpEntry 4 }

frAtmDlciExcessBurstSize OBJECT-TYPE
   SYNTAX     Unsigned32 (0..50000000)
   ACCESS     read-only
   STATUS     mandatory
   DESCRIPTION
     "This attribute indicates the excess burst size (Be) in bits and 
      represents the amount of uncommitted data that the network 
      attempts to deliver over measurement interval (t) when 
      rateEnforcement is on. Data marked DE=1 by the user or by the 
      network is accounted for here.
      
      This attribute is not applicable ignored when rateEnforcement is 
      off."
::= { frAtmDlciSpOpEntry 5 }

frAtmDlciMeasurementInterval OBJECT-TYPE
   SYNTAX     Unsigned32 (0..4294967295)
   ACCESS     read-only
   STATUS     mandatory
   DESCRIPTION
     "This attribute indicates the time interval over which rates and burst 
      sizes are measured.
      
      This attribute is not applicable when rateEnforcement is off."
::= { frAtmDlciSpOpEntry 6 }

frAtmDlciEmissionPriorityToIf OBJECT-TYPE
   SYNTAX     INTEGER (0 | 1 | 2 | 3)
   ACCESS     read-only
   STATUS     mandatory
   DESCRIPTION
     "This attribute indicates the emission priority of frames sent to the 
      interface.
      
      If the value of FrAtm/n numberOfEmissionQs is 2, set the value of 
      this attribute to either 0 or 1; if the value of FrAtm/n 
      numberOfEmissionQs is 4, set the value of this attribute to one of 0, 
      1, 2, 3."
::= { frAtmDlciSpOpEntry 7 }

frAtmDlciDlciType OBJECT-TYPE
   SYNTAX     INTEGER  {
                 serviceInterworking(0),
                 networkInterworking(1) }
   ACCESS     read-only
   STATUS     mandatory
   DESCRIPTION
     "This attribute indicates the type of DLCI.
      A value of serviceInterworking indicates that a FrAtm/n Dlci/n Siwf 
      component is present.
      A value of networkInterworking indicates that a FrAtm/n Dlci/n 
      Niwf component is present."
::= { frAtmDlciSpOpEntry 8 }

frAtmDlciTroubled OBJECT-TYPE
   SYNTAX     INTEGER  {
                 no(0),
                 yes(1) }
   ACCESS     read-only
   STATUS     mandatory
   DESCRIPTION
     "This attribute indicates whether or not the connection is in a 
      troubled state. Connections may become troubled for the following 
      reasons; if CAC failed to admit the call, or if one of the attributes 
      aBitStatusToIf, aBitStatusFromIf goes inactive; otherwise it is set to 
      no."
   DEFVAL     { no }
::= { frAtmDlciSpOpEntry 9 }

frAtmDlciTroubledReason OBJECT-TYPE
   SYNTAX     INTEGER  {
                 notApplicable(0),
                 notAdmitted(1) }
   ACCESS     read-only
   STATUS     mandatory
   DESCRIPTION
     "This attribute provides the reason (if any) for a troubled connection. 
      
      A value of notApplicable indicates no current failures; either 
      Connection Admission Control (CAC) is off, or call was admitted.
      
      A value of notAdmitted indicates the CAC algorithm fails to admit 
      this connection. Check if there is a sufficient bandwidth allocation."
   DEFVAL     { notApplicable }
::= { frAtmDlciSpOpEntry 10 }

frAtmDlciStatsTable OBJECT-TYPE
   SYNTAX     SEQUENCE OF FrAtmDlciStatsEntry
   ACCESS     not-accessible
   STATUS     mandatory
   DESCRIPTION
     "This group contains the operational statistics for the Frame Relay 
      Data Link Connection Identifier."
::= { frAtmDlci 13 }

frAtmDlciStatsEntry OBJECT-TYPE
   SYNTAX     FrAtmDlciStatsEntry
   ACCESS     not-accessible
   STATUS     mandatory
   DESCRIPTION
     "An entry in the frAtmDlciStatsTable."
   INDEX {
      frAtmIndex,
      frAtmDlciIndex }
::= { frAtmDlciStatsTable 1 }

FrAtmDlciStatsEntry ::= SEQUENCE {
   frAtmDlciFrmToIf
      Counter32,
   frAtmDlciFecnFrmToIf
      Counter32,
   frAtmDlciBecnFrmToIf
      Counter32,
   frAtmDlciDeFrmToIf
      Counter32,
   frAtmDlciDiscCongestedToIf
      Counter32,
   frAtmDlciDiscDeCongestedToIf
      Counter32,
   frAtmDlciFrmFromIf
      Counter32,
   frAtmDlciFecnFrmFromIf
      Counter32,
   frAtmDlciBecnFrmFromIf
      Counter32,
   frAtmDlciEfciFrmFromNetwork
      Counter32,
   frAtmDlciDeFrmFromIf
      Counter32,
   frAtmDlciExcessFrmFromIf
      Counter32,
   frAtmDlciDiscExcessFromIf
      Counter32,
   frAtmDlciDiscFrameAbit
      Counter32,
   frAtmDlciDiscCongestedFromIf
      Counter32,
   frAtmDlciDiscDeCongestedFromIf
      Counter32,
   frAtmDlciErrorShortFrmFromIf
      Counter32,
   frAtmDlciErrorLongFrmFromIf
      Counter32,
   frAtmDlciBecnFrmSetByService
      Counter32,
   frAtmDlciBytesToIf
      Counter32,
   frAtmDlciDeBytesToIf
      Counter32,
   frAtmDlciDiscCongestedToIfBytes
      Counter32,
   frAtmDlciDiscDeCongestedToIfBytes
      Counter32,
   frAtmDlciBytesFromIf
      Counter32,
   frAtmDlciDeBytesFromIf
      Counter32,
   frAtmDlciExcessBytesFromIf
      Counter32,
   frAtmDlciDiscExcessFromIfBytes
      Counter32,
   frAtmDlciDiscByteAbit
      Counter32,
   frAtmDlciDiscCongestedFromIfBytes
      Counter32,
   frAtmDlciDiscDeCongestedFromIfBytes
      Counter32,
   frAtmDlciErrorShortBytesFromIf
      Counter32,
   frAtmDlciErrorLongBytesFromIf
      Counter32 }

frAtmDlciFrmToIf OBJECT-TYPE
   SYNTAX     Counter32 
   ACCESS     read-only
   STATUS     mandatory
   DESCRIPTION
     "This attribute counts the number of frames sent to the interface. 
      When the maximum count is reached, the count wraps to zero."
::= { frAtmDlciStatsEntry 1 }

frAtmDlciFecnFrmToIf OBJECT-TYPE
   SYNTAX     Counter32 
   ACCESS     read-only
   STATUS     mandatory
   DESCRIPTION
     "This attribute counts the number of frames sent to the interface with 
      the Forward Explicit Congestion Notification (FECN) bit set. When 
      the maximum count is reached, the count wraps to zero."
::= { frAtmDlciStatsEntry 2 }

frAtmDlciBecnFrmToIf OBJECT-TYPE
   SYNTAX     Counter32 
   ACCESS     read-only
   STATUS     mandatory
   DESCRIPTION
     "This attribute counts the number of frames sent to the interface with 
      the Backward Explicit Congestion Notification (BECN) bit set. 
      When the maximum count is reached, the count wraps to zero."
::= { frAtmDlciStatsEntry 3 }

frAtmDlciDeFrmToIf OBJECT-TYPE
   SYNTAX     Counter32 
   ACCESS     read-only
   STATUS     mandatory
   DESCRIPTION
     "This attribute counts the number of frames sent to the interface with 
      the Discard Eligibility (DE) bit set. When the maximum count is 
      reached, the count wraps to zero."
::= { frAtmDlciStatsEntry 4 }

frAtmDlciDiscCongestedToIf OBJECT-TYPE
   SYNTAX     Counter32 
   ACCESS     read-only
   STATUS     mandatory
   DESCRIPTION
     "This attribute counts the number of frame discards at the Frame 
      Relay service due to local congestion in the direction toward the 
      interface. When the maximum count is reached, the count wraps to 
      zero."
::= { frAtmDlciStatsEntry 5 }

frAtmDlciDiscDeCongestedToIf OBJECT-TYPE
   SYNTAX     Counter32 
   ACCESS     read-only
   STATUS     mandatory
   DESCRIPTION
     "This attribute counts the number of discarded frames, with the 
      Discard Eligibility (DE) bit set, at the Frame Relay service, due to 
      local congestion in the direction toward the interface. When the 
      maximum count is reached, the count wraps to zero."
::= { frAtmDlciStatsEntry 6 }

frAtmDlciFrmFromIf OBJECT-TYPE
   SYNTAX     Counter32 
   ACCESS     read-only
   STATUS     mandatory
   DESCRIPTION
     "This attribute counts the number of frames received from the 
      interface. Frames that are discarded due to error or excess are not 
      counted. When the maximum count is reached, the count wraps to 
      zero."
::= { frAtmDlciStatsEntry 7 }

frAtmDlciFecnFrmFromIf OBJECT-TYPE
   SYNTAX     Counter32 
   ACCESS     read-only
   STATUS     mandatory
   DESCRIPTION
     "This attribute counts the number of frames received from the 
      interface with the Forward Explicit Congestion Notification (FECN) 
      bit set. When the maximum count is reached, the count wraps to 
      zero."
::= { frAtmDlciStatsEntry 8 }

frAtmDlciBecnFrmFromIf OBJECT-TYPE
   SYNTAX     Counter32 
   ACCESS     read-only
   STATUS     mandatory
   DESCRIPTION
     "This attribute counts the number of frames received from the 
      interface with the Backward Explicit Congestion Notification 
      (BECN) bit set. When the maximum count is reached, the count 
      wraps to zero."
::= { frAtmDlciStatsEntry 9 }

frAtmDlciEfciFrmFromNetwork OBJECT-TYPE
   SYNTAX     Counter32 
   ACCESS     read-only
   STATUS     mandatory
   DESCRIPTION
     "This attribute counts the number of frames received from the 
      interworking function with the Explicit Forward Congestion 
      Indication (EFCI) bit set. When the maximum count is reached, the 
      count wraps to zero."
::= { frAtmDlciStatsEntry 10 }

frAtmDlciDeFrmFromIf OBJECT-TYPE
   SYNTAX     Counter32 
   ACCESS     read-only
   STATUS     mandatory
   DESCRIPTION
     "This attribute counts the number of frames received from the 
      interface with the Discard Eligibility (DE) bit set. When the 
      maximum count is reached, the count wraps to zero."
::= { frAtmDlciStatsEntry 11 }

frAtmDlciExcessFrmFromIf OBJECT-TYPE
   SYNTAX     Counter32 
   ACCESS     read-only
   STATUS     mandatory
   DESCRIPTION
     "This attribute counts the number of frames received from the 
      interface with the Discard Eligibility (DE) bit clear, but 
      subsequently set by the network due to rate enforcement. When the 
      maximum count is reached, the count wraps to zero."
::= { frAtmDlciStatsEntry 12 }

frAtmDlciDiscExcessFromIf OBJECT-TYPE
   SYNTAX     Counter32 
   ACCESS     read-only
   STATUS     mandatory
   DESCRIPTION
     "This attribute counts the number of frames which were discarded 
      due to rate enforcement. When the maximum count is reached, the 
      count wraps to zero."
::= { frAtmDlciStatsEntry 13 }

frAtmDlciDiscFrameAbit OBJECT-TYPE
   SYNTAX     Counter32 
   ACCESS     read-only
   STATUS     mandatory
   DESCRIPTION
     "This attribute counts the number of frame discards at the Frame 
      Relay Service, due to an inactive PVC status, in the direction 
      toward the interworking function. When the maximum count is 
      reached, the count wraps to zero."
::= { frAtmDlciStatsEntry 14 }

frAtmDlciDiscCongestedFromIf OBJECT-TYPE
   SYNTAX     Counter32 
   ACCESS     read-only
   STATUS     mandatory
   DESCRIPTION
     "This attribute counts the number of frame discards at the Frame 
      Relay service due to local congestion in the direction toward the 
      interworking function. When the maximum count is reached, the 
      count wraps to zero."
::= { frAtmDlciStatsEntry 15 }

frAtmDlciDiscDeCongestedFromIf OBJECT-TYPE
   SYNTAX     Counter32 
   ACCESS     read-only
   STATUS     mandatory
   DESCRIPTION
     "This attribute counts the number of discarded frames, with the 
      Discard Eligibility (DE) bit set due to local congestion in the 
      direction toward the interworking function. When the maximum 
      count is reached, the count wraps to zero."
::= { frAtmDlciStatsEntry 16 }

frAtmDlciErrorShortFrmFromIf OBJECT-TYPE
   SYNTAX     Counter32 
   ACCESS     read-only
   STATUS     mandatory
   DESCRIPTION
     "This attribute counts the number of frames received with 0 octets in 
      the information field. When the maximum count is reached, the 
      count wraps to zero."
::= { frAtmDlciStatsEntry 17 }

frAtmDlciErrorLongFrmFromIf OBJECT-TYPE
   SYNTAX     Counter32 
   ACCESS     read-only
   STATUS     mandatory
   DESCRIPTION
     "This attribute counts the number of frames received with number of 
      octets in the information field greater than the subscribed 
      maximum. When the maximum count is reached, the count wraps to 
      zero. The hardware ignores frame lengths greater than the hardware 
      receive buffer, and therfore does not includes them in this count."
::= { frAtmDlciStatsEntry 18 }

frAtmDlciBecnFrmSetByService OBJECT-TYPE
   SYNTAX     Counter32 
   ACCESS     read-only
   STATUS     mandatory
   DESCRIPTION
     "This attribute counts the number of frames with BECN set by the 
      Frame Relay service. It is incremented when the Frame Relay 
      service sets BECN on a frame upon detecting local congestion. This 
      count is incremented regardless of whether the frame already bears 
      a set BECN bit since its use is to determine the place of congestion. 
      When the maximum count is reached, the count wraps to zero."
::= { frAtmDlciStatsEntry 19 }

frAtmDlciBytesToIf OBJECT-TYPE
   SYNTAX     Counter32 
   ACCESS     read-only
   STATUS     mandatory
   DESCRIPTION
     "This attribute counts the number of bytes sent out the interface. 
      When the maximum count is reached, the count wraps to zero."
::= { frAtmDlciStatsEntry 20 }

frAtmDlciDeBytesToIf OBJECT-TYPE
   SYNTAX     Counter32 
   ACCESS     read-only
   STATUS     mandatory
   DESCRIPTION
     "This attribute counts the number of bytes sent to the interface with 
      the Discard Eligibility (DE) bit set. When the maximum count is 
      reached, the count wraps to zero."
::= { frAtmDlciStatsEntry 21 }

frAtmDlciDiscCongestedToIfBytes OBJECT-TYPE
   SYNTAX     Counter32 
   ACCESS     read-only
   STATUS     mandatory
   DESCRIPTION
     "This attribute counts the number of byte discards at the Frame 
      Relay service due to local congestion in the direction toward the 
      link. When the maximum count is reached, the count wraps to zero."
::= { frAtmDlciStatsEntry 22 }

frAtmDlciDiscDeCongestedToIfBytes OBJECT-TYPE
   SYNTAX     Counter32 
   ACCESS     read-only
   STATUS     mandatory
   DESCRIPTION
     "This attribute counts the number of discard eligible (DE=1) byte 
      discards at the Frame Relay service due to local congestion in the 
      direction toward the link. When the maximum count is reached, the 
      count wraps to zero."
::= { frAtmDlciStatsEntry 23 }

frAtmDlciBytesFromIf OBJECT-TYPE
   SYNTAX     Counter32 
   ACCESS     read-only
   STATUS     mandatory
   DESCRIPTION
     "This attribute counts the number of bytes received from the 
      interface. Bytes that are discarded due to error or excess are not 
      counted. When the maximum count is reached, the count wraps to 
      zero."
::= { frAtmDlciStatsEntry 24 }

frAtmDlciDeBytesFromIf OBJECT-TYPE
   SYNTAX     Counter32 
   ACCESS     read-only
   STATUS     mandatory
   DESCRIPTION
     "This attribute counts the number of bytes received from the 
      interface with the Discard Eligibility (DE) bit set. When the 
      maximum count is reached, the count wraps to zero."
::= { frAtmDlciStatsEntry 25 }

frAtmDlciExcessBytesFromIf OBJECT-TYPE
   SYNTAX     Counter32 
   ACCESS     read-only
   STATUS     mandatory
   DESCRIPTION
     "This attribute counts the number of bytes received from the 
      interface with the Discard Eligibility (DE) bit clear, but 
      subsequently set by the network due to rate enforcement. When the 
      maximum count is reached, the count wraps to zero."
::= { frAtmDlciStatsEntry 26 }

frAtmDlciDiscExcessFromIfBytes OBJECT-TYPE
   SYNTAX     Counter32 
   ACCESS     read-only
   STATUS     mandatory
   DESCRIPTION
     "This attribute counts the number of bytes which were discarded due 
      to rate enforcement. When the maximum count is reached, the 
      count wraps to zero."
::= { frAtmDlciStatsEntry 27 }

frAtmDlciDiscByteAbit OBJECT-TYPE
   SYNTAX     Counter32 
   ACCESS     read-only
   STATUS     mandatory
   DESCRIPTION
     "This attribute counts the bytes number of which were discarded due 
      to the A-bit being turned off. When the maximum count is reached, 
      the count wraps to zero."
::= { frAtmDlciStatsEntry 28 }

frAtmDlciDiscCongestedFromIfBytes OBJECT-TYPE
   SYNTAX     Counter32 
   ACCESS     read-only
   STATUS     mandatory
   DESCRIPTION
     "This attribute counts the number of byte discards at the Frame 
      Relay service due to local congestion in the direction toward the 
      interworking function. When the maximum count is reached, the 
      count wraps to zero."
::= { frAtmDlciStatsEntry 29 }

frAtmDlciDiscDeCongestedFromIfBytes OBJECT-TYPE
   SYNTAX     Counter32 
   ACCESS     read-only
   STATUS     mandatory
   DESCRIPTION
     "This attribute counts the number of discard eligible (DE=1) byte 
      discards at the Frame Relay service due to local congestion in the 
      direction toward the interworking function. When the maximum 
      count is reached, the count wraps to zero."
::= { frAtmDlciStatsEntry 30 }

frAtmDlciErrorShortBytesFromIf OBJECT-TYPE
   SYNTAX     Counter32 
   ACCESS     read-only
   STATUS     mandatory
   DESCRIPTION
     "This attribute counts the number of bytes received with 0 octets in 
      the information field. When the maximum count is reached, the 
      count wraps to zero."
::= { frAtmDlciStatsEntry 31 }

frAtmDlciErrorLongBytesFromIf OBJECT-TYPE
   SYNTAX     Counter32 
   ACCESS     read-only
   STATUS     mandatory
   DESCRIPTION
     "This attribute counts the number of bytes received when the number 
      of octets in the information field is greater than the subscribed 
      maximum. The hardware ignores bytes lengths greater than the 
      hardware receive buffer and therefore does not include them in this 
      count.
      
      When the maximum count is reached, the count wraps to zero."
::= { frAtmDlciStatsEntry 32 }

frAtmDlciCalldTable OBJECT-TYPE
   SYNTAX     SEQUENCE OF FrAtmDlciCalldEntry
   ACCESS     not-accessible
   STATUS     mandatory
   DESCRIPTION
     "This group contains the operational values for the FrAtm Dlci call 
      data. If the accountingEnabled attribute is no, then this group 
      except for accountingEnabled is not displayed."
::= { frAtmDlci 14 }

frAtmDlciCalldEntry OBJECT-TYPE
   SYNTAX     FrAtmDlciCalldEntry
   ACCESS     not-accessible
   STATUS     mandatory
   DESCRIPTION
     "An entry in the frAtmDlciCalldTable."
   INDEX {
      frAtmIndex,
      frAtmDlciIndex }
::= { frAtmDlciCalldTable 1 }

FrAtmDlciCalldEntry ::= SEQUENCE {
   frAtmDlciAccountingEnabled
      INTEGER,
   frAtmDlciAccountingEnd
      INTEGER,
   frAtmDlciCorrelationTag
      HexString }

frAtmDlciAccountingEnabled OBJECT-TYPE
   SYNTAX     INTEGER  {
                 no(0),
                 yes(1) }
   ACCESS     read-only
   STATUS     mandatory
   DESCRIPTION
     "This attribute indicates whether accounting is enabled. To enable 
      accounting, the FrAtm Ca accountCollection attribute must be non-
      empty and FrAtm Dlci Sp accounting attribute must be on."
::= { frAtmDlciCalldEntry 1 }

frAtmDlciAccountingEnd OBJECT-TYPE
   SYNTAX     INTEGER  {
                 callingEnd(0),
                 calledEnd(1) }
   ACCESS     read-only
   STATUS     mandatory
   DESCRIPTION
     "This attribute indicates whether this DLCI represents the called or 
      calling end of the connection. If the accountingEnabled attribute is 
      no, then this attribute is not displayed."
::= { frAtmDlciCalldEntry 2 }

frAtmDlciCorrelationTag OBJECT-TYPE
   SYNTAX     HexString (SIZE (0..28))
   ACCESS     read-only
   STATUS     mandatory
   DESCRIPTION
     "This attribute indicates the unique string which identifies this 
      connection. The value of this operational attribute can be 
      provisioned in the correlationTag attribute of either the Siwf Npvc, 
      Siwf Spvc, or Niwf Spvc subcomponents. For the Siwf Spvc and Niwf 
      Spvc cases, when the provisionable correlationTag is an empty 
      string, then this attribute receives the value of a system- generated 
      correlationTag. Downstream processing uses this attribute to 
      correlate accounting records issued at different nodes in the 
      network. If the accountingEnabled attribute is no, then this attribute 
      is not displayed."
   DEFVAL     { ''H }  -- ""
::= { frAtmDlciCalldEntry 3 }

frAtmDlciIntTable OBJECT-TYPE
   SYNTAX     SEQUENCE OF FrAtmDlciIntEntry
   ACCESS     not-accessible
   STATUS     mandatory
   DESCRIPTION
     "This group contains the operational statistics for the FrAtm Dlci 
      interval data."
::= { frAtmDlci 15 }

frAtmDlciIntEntry OBJECT-TYPE
   SYNTAX     FrAtmDlciIntEntry
   ACCESS     not-accessible
   STATUS     mandatory
   DESCRIPTION
     "An entry in the frAtmDlciIntTable."
   INDEX {
      frAtmIndex,
      frAtmDlciIndex }
::= { frAtmDlciIntTable 1 }

FrAtmDlciIntEntry ::= SEQUENCE {
   frAtmDlciStartTime
      EnterpriseDateAndTime,
   frAtmDlciTotalIngressBytes
      Unsigned64,
   frAtmDlciTotalEgressBytes
      Unsigned64,
   frAtmDlciEirIngressBytes
      Unsigned64,
   frAtmDlciEirEgressBytes
      Unsigned64,
   frAtmDlciDiscardedBytes
      Unsigned64,
   frAtmDlciTotalIngressFrames
      Unsigned32,
   frAtmDlciTotalEgressFrames
      Unsigned32,
   frAtmDlciEirIngressFrames
      Unsigned32,
   frAtmDlciEirEgressFrames
      Unsigned32,
   frAtmDlciDiscardedFrames
      Unsigned32,
   frAtmDlciElapsedDifference
      Unsigned32 }

frAtmDlciStartTime OBJECT-TYPE
   SYNTAX     EnterpriseDateAndTime (SIZE (0 | 19))
   ACCESS     read-only
   STATUS     mandatory
   DESCRIPTION
     "This attribute indicates the start time of this interval. A new interval 
      is started each time an accounting record is generated and call at a 
      setup. If the accountingEnabled attribute is no, then this attribute is 
      not displayed."
::= { frAtmDlciIntEntry 1 }

frAtmDlciTotalIngressBytes OBJECT-TYPE
   SYNTAX     Unsigned64 (SIZE (8))
   ACCESS     read-only
   STATUS     mandatory
   DESCRIPTION
     "This attribute counts the total payload bytes in received from the 
      link since the start of the interval. To calculate total valid payload 
      bytes received from link, subtract discardedBytes from this 
      attribute. The start of the interval is captured in the startTime 
      attribute. The count is reset to zero when an accounting record is 
      generated or at call setup. If the accountingEnabled attribute is no, 
      then this attribute is not displayed."
::= { frAtmDlciIntEntry 2 }

frAtmDlciTotalEgressBytes OBJECT-TYPE
   SYNTAX     Unsigned64 (SIZE (8))
   ACCESS     read-only
   STATUS     mandatory
   DESCRIPTION
     "This attribute counts the total payload bytes sent to the link since 
      the start of the interval. The start of the interval is captured in the 
      startTime attribute. The count is reset to zero when an accounting 
      record is generated or at call setup. If the accountingEnabled 
      attribute is no, then this attribute is not displayed."
::= { frAtmDlciIntEntry 3 }

frAtmDlciEirIngressBytes OBJECT-TYPE
   SYNTAX     Unsigned64 (SIZE (8))
   ACCESS     read-only
   STATUS     mandatory
   DESCRIPTION
     "This attribute counts the total valid payload bytes in frames with the 
      Discard Eligibility (DE) bit set to 1 received from the link since the 
      start of the interval. Subtract this attribute and discardedBytes from 
      totalIngressBytes to calculate total valid payload bytes in frames 
      received from the link, with the DE bit set to 0. The start of the 
      interval is captured in the startTime attribute. The count is reset to 
      zero when an accounting record is generated or at call setup. If the 
      accountingEnabled attribute is no, then this attribute is not 
      displayed."
::= { frAtmDlciIntEntry 4 }

frAtmDlciEirEgressBytes OBJECT-TYPE
   SYNTAX     Unsigned64 (SIZE (8))
   ACCESS     read-only
   STATUS     mandatory
   DESCRIPTION
     "This attribute counts the total valid payload bytes in frames with the 
      Discard Eligibility (DE) bit set sent to the link since the start of the 
      interval. Subtract the value of this attribute from totalEgressBytes to 
      calculate total valid payload bytes in frames, with DE set to 0, sent 
      to the link. The start of the interval is captured in the startTime 
      attribute. The count is reset to zero when an accounting record is 
      generated or at call setup. If the accountingEnabled attribute is no, 
      then this attribute is not displayed."
::= { frAtmDlciIntEntry 5 }

frAtmDlciDiscardedBytes OBJECT-TYPE
   SYNTAX     Unsigned64 (SIZE (8))
   ACCESS     read-only
   STATUS     mandatory
   DESCRIPTION
     "This attribute counts the total payload bytes in invalid frames 
      received from the link and discarded at the DLCI since the start of 
      the interval. This count is a sum of octets in frames discarded due 
      to: frames too long or too short; A-Bit off; or to rate enforcement. 
      The start of the interval is captured in the startTime attribute. The 
      count is reset to zero when an accounting record is generated or at 
      call setup. If the accountingEnabled attribute is no, then this 
      attribute is not displayed."
::= { frAtmDlciIntEntry 6 }

frAtmDlciTotalIngressFrames OBJECT-TYPE
   SYNTAX     Unsigned32 (0..4294967295)
   ACCESS     read-only
   STATUS     mandatory
   DESCRIPTION
     "This attribute counts the total number of frames received from the 
      link since the start of the interval. To calculate the total valid 
      number of frames received from the link, subtract discardedFrames 
      from this attribute. The start of the interval is captured in the 
      startTime attribute. The count is reset to zero when an accounting 
      record is generated or at call setup. If the accountingEnabled 
      attribute is no, then this attribute is not displayed."
   DEFVAL     { 0 }
::= { frAtmDlciIntEntry 7 }

frAtmDlciTotalEgressFrames OBJECT-TYPE
   SYNTAX     Unsigned32 (0..4294967295)
   ACCESS     read-only
   STATUS     mandatory
   DESCRIPTION
     "This attribute counts the total number of frames sent to the link 
      since the start of the interval. The start of the interval is captured in 
      the startTime attribute. The count is reset to zero when an 
      accounting record is generated or at call setup. If the 
      accountingEnabled attribute is no, then this attribute is not 
      displayed."
   DEFVAL     { 0 }
::= { frAtmDlciIntEntry 8 }

frAtmDlciEirIngressFrames OBJECT-TYPE
   SYNTAX     Unsigned32 (0..4294967295)
   ACCESS     read-only
   STATUS     mandatory
   DESCRIPTION
     "This attribute counts the number of valid frames with the Discard 
      Eligibility (DE) bit set to 1 received from the link since the start of 
      the interval. Subtract this attribute and discardedFrames from 
      totalIngressFrames to calculate total valid frames received from the 
      link, with the DE bit set to 0. The start of the interval is captured in 
      the startTime attribute. The count is reset to zero when an 
      accounting record is generated or at call setup. If the 
      accountingEnabled attribute is no, then this attribute is not 
      displayed."
   DEFVAL     { 0 }
::= { frAtmDlciIntEntry 9 }

frAtmDlciEirEgressFrames OBJECT-TYPE
   SYNTAX     Unsigned32 (0..4294967295)
   ACCESS     read-only
   STATUS     mandatory
   DESCRIPTION
     "This attribute counts the number of frames with the Discard 
      Eligibility (DE) bit set sent to the link since the start of the interval. 
      Subtract the value of this attribute from totalEgressFrames to 
      calculate total frames, with DE set to 0, sent to the link.The start of 
      the interval is captured in the startTime attribute. The count is reset 
      to zero when an accounting record is generated call setup. If the 
      accountingEnabled attribute is no, then this attribute is not 
      displayed."
   DEFVAL     { 0 }
::= { frAtmDlciIntEntry 10 }

frAtmDlciDiscardedFrames OBJECT-TYPE
   SYNTAX     Unsigned32 (0..4294967295)
   ACCESS     read-only
   STATUS     mandatory
   DESCRIPTION
     "This attribute counts the number of invalid frames received from the 
      link and discarded at the DLCI. The count is reset to zero when an 
      accounting record is generated or at call setup. The count is a sum 
      of frames discarded due to: frames too long or too short; A-Bit is 
      off; or rate enforcement. If the accountingEnabled attribute is no, 
      then this attribute is not displayed."
   DEFVAL     { 0 }
::= { frAtmDlciIntEntry 11 }

frAtmDlciElapsedDifference OBJECT-TYPE
   SYNTAX     Unsigned32 (0..4294967295)
   ACCESS     read-only
   STATUS     mandatory
   DESCRIPTION
     "This attribute indicates the elapsed time representing the of this 
      interval data. It is the elapsed time in 0.1 second increments since 
      the start of the interval. If the accountingEnabled attribute is no, 
      then this attribute is not displayed."
   DEFVAL     { 0 }
::= { frAtmDlciIntEntry 12 }


-- FrAtm/n Dlci/n ServiceParameters
-- This component is a subcomponent of Dlci. It contains the 
-- provisionable attributes for the parent Dlci component.

frAtmDlciSp OBJECT IDENTIFIER ::= { frAtmDlci 2 }



frAtmDlciSpRowStatusTable OBJECT-TYPE
   SYNTAX     SEQUENCE OF FrAtmDlciSpRowStatusEntry
   ACCESS     not-accessible
   STATUS     mandatory
   DESCRIPTION
     "This entry controls the addition and deletion of 
      frAtmDlciSp components."
::= { frAtmDlciSp 1 }

frAtmDlciSpRowStatusEntry OBJECT-TYPE
   SYNTAX     FrAtmDlciSpRowStatusEntry
   ACCESS     not-accessible
   STATUS     mandatory
   DESCRIPTION
     "A single entry in the table represents a single 
      frAtmDlciSp component."
   INDEX {
      frAtmIndex,
      frAtmDlciIndex,
      frAtmDlciSpIndex }
::= { frAtmDlciSpRowStatusTable 1 }

FrAtmDlciSpRowStatusEntry ::= SEQUENCE {
   frAtmDlciSpRowStatus
      RowStatus,
   frAtmDlciSpComponentName
      DisplayString,
   frAtmDlciSpStorageType
      StorageType,
   frAtmDlciSpIndex
      NonReplicated }

frAtmDlciSpRowStatus OBJECT-TYPE
   SYNTAX     RowStatus 
   ACCESS     read-only
   STATUS     mandatory
   DESCRIPTION
     "This variable is used as the basis for SNMP naming of
      frAtmDlciSp components.
      These components cannot be added nor deleted."
::= { frAtmDlciSpRowStatusEntry 1 }

frAtmDlciSpComponentName OBJECT-TYPE
   SYNTAX     DisplayString 
   ACCESS     read-only
   STATUS     mandatory
   DESCRIPTION
     "This variable provides the component's string name for
      use with the ASCII Console Interface"
::= { frAtmDlciSpRowStatusEntry 2 }

frAtmDlciSpStorageType OBJECT-TYPE
   SYNTAX     StorageType 
   ACCESS     read-only
   STATUS     mandatory
   DESCRIPTION
     "This variable represents the storage type value for the
      frAtmDlciSp tables."
::= { frAtmDlciSpRowStatusEntry 4 }

frAtmDlciSpIndex OBJECT-TYPE
   SYNTAX     NonReplicated 
   ACCESS     not-accessible
   STATUS     mandatory
   DESCRIPTION
     "This variable represents the index for the frAtmDlciSp tables."
::= { frAtmDlciSpRowStatusEntry 10 }

frAtmDlciSpProvTable OBJECT-TYPE
   SYNTAX     SEQUENCE OF FrAtmDlciSpProvEntry
   ACCESS     not-accessible
   STATUS     mandatory
   DESCRIPTION
     "This group contains the provisionable attributes for the Data Link 
      Connection Identifier. These attributes reflect the service parameters 
      specific to this instance of DLCI. The congestion control attributes 
      in this group are defined in T1.606 Addendum 1."
::= { frAtmDlciSp 10 }

frAtmDlciSpProvEntry OBJECT-TYPE
   SYNTAX     FrAtmDlciSpProvEntry
   ACCESS     not-accessible
   STATUS     mandatory
   DESCRIPTION
     "An entry in the frAtmDlciSpProvTable."
   INDEX {
      frAtmIndex,
      frAtmDlciIndex,
      frAtmDlciSpIndex }
::= { frAtmDlciSpProvTable 1 }

FrAtmDlciSpProvEntry ::= SEQUENCE {
   frAtmDlciSpMaximumFrameSize
      Unsigned32,
   frAtmDlciSpRateEnforcement
      INTEGER,
   frAtmDlciSpCommittedInformationRate
      Unsigned32,
   frAtmDlciSpCommittedBurstSize
      Unsigned32,
   frAtmDlciSpExcessBurstSize
      Unsigned32,
   frAtmDlciSpMeasurementInterval
      Unsigned32,
   frAtmDlciSpEmissionPriorityToIf
      INTEGER,
   frAtmDlciSpEmissionPrioToIf
      INTEGER,
   frAtmDlciSpAccounting
      INTEGER }

frAtmDlciSpMaximumFrameSize OBJECT-TYPE
   SYNTAX     Unsigned32 (1..8187)
   ACCESS     read-write
   STATUS     mandatory
   DESCRIPTION
     "This attribute specifies the maximum number of octets which may 
      be included in the information field. The Frame Relay header and 
      CRC octets are not included in this definition. This attribute 
      corresponds to the dN1 parameter described in the Vendor Forum 
      Specification."
   DEFVAL     { 2100 }
::= { frAtmDlciSpProvEntry 1 }

frAtmDlciSpRateEnforcement OBJECT-TYPE
   SYNTAX     INTEGER  {
                 off(0),
                 on(1) }
   ACCESS     read-write
   STATUS     mandatory
   DESCRIPTION
     "This attribute specifies whether rate enforcement is in effect for this 
      user data link connection. 
      
      When rateEnforcement is on, the CIR and De=1 traffic will be 
      measured and enforced. 
      
      When rateEnforcement is off, all frames from the user are accepted 
      and no modifications to the frame with respect to the De bit will be 
      made."
   DEFVAL     { on }
::= { frAtmDlciSpProvEntry 2 }

frAtmDlciSpCommittedInformationRate OBJECT-TYPE
   SYNTAX     Unsigned32 (0..50000000)
   ACCESS     read-write
   STATUS     mandatory
   DESCRIPTION
     "This attribute specifies the committed information rate (CIR). It 
      represents the rate at which the network agrees to transfer 
      information under normal conditions when rate enforcement is in 
      effect.
      
      When rate enforcement is not in effect, this attribute is ignored.
      
      Determination of the actual CIR is based on 
      committedInformationRate, committedBurstSize and a measurement 
      interval. The measurement interval is determined internally when 
      committedInformationRate has a non-zero value. Otherwise, it is 
      based on measurementInterval which must be explicitly 
      provisioned.
      
      Note: The committedBurstSize must have a value of 0 when rate 
      enforcement is in effect and committedInformationRate has a value 
      of 0."
   DEFVAL     { 64000 }
::= { frAtmDlciSpProvEntry 3 }

frAtmDlciSpCommittedBurstSize OBJECT-TYPE
   SYNTAX     Unsigned32 (0..50000000)
   ACCESS     read-write
   STATUS     mandatory
   DESCRIPTION
     "This attribute specifies the committed burst size (Bc). It represents 
      the amount of data that a network agrees to transfer under normal 
      conditions over a measurement interval when rate enforcement is in 
      effect. Data marked DE=1 is not accounted for in the committed 
      burst size.
      
      When rate enforcement is not in effect, this attribute is ignored. 
      
      Note: The committedInformationRate must have a value of 0 when 
      rate enforcement is in effect and committedBurstSize has a value of 
      0."
   DEFVAL     { 64000 }
::= { frAtmDlciSpProvEntry 4 }

frAtmDlciSpExcessBurstSize OBJECT-TYPE
   SYNTAX     Unsigned32 (0..50000000)
   ACCESS     read-write
   STATUS     mandatory
   DESCRIPTION
     "This attribute specifies the excess burst size (Be). It represents the 
      amount of uncommitted data that the network will attempt to deliver 
      over a measurement interval when rate enforcement is in effect. 
      Data marked DE=1 by the user or by the network is accounted for 
      here.
      
      committedInformationRate, committedBurstSize, and 
      excessBurstSize cannot all be zero when rate enforcement is in 
      effect."
   DEFVAL     { 0 }
::= { frAtmDlciSpProvEntry 5 }

frAtmDlciSpMeasurementInterval OBJECT-TYPE
   SYNTAX     Unsigned32 (0..25500)
   ACCESS     read-write
   STATUS     mandatory
   DESCRIPTION
     "This attribute specifies the time interval over which rates and burst 
      sizes are measured when rate enforcement is in effect.
      
      When rate enforcement is in effect and both 
      committedInformationRate and committedBurstSize have values of 
      zero, this attribute must have a non-zero value.
      
      When rate enforcement is not in effect or when 
      committedInformationRate and committedBurstSize have non-zero 
      values, this attribute is ignored.
      
      When committedInformationRate and committedBurstSize have 
      non-zero values, the time interval is internally calculated. In this 
      situation, measurementInterval is ignored, and it does not represent 
      the time interval."
   DEFVAL     { 0 }
::= { frAtmDlciSpProvEntry 6 }

frAtmDlciSpEmissionPriorityToIf OBJECT-TYPE
   SYNTAX     INTEGER  {
                 low(0),
                 high(3) }
   ACCESS     read-write
   STATUS     obsolete
   DESCRIPTION
     "This attribute specifies the emission priority of frames sent to the 
      interface.
      
      The high priority frames in the high priority frame queue will be 
      served before the low priority frames in the low priority queue.
      
      This attribute is obsoleted. During migration, its value will be 
      transferred to emissionPriToIf."
   DEFVAL     { low }
::= { frAtmDlciSpProvEntry 7 }

frAtmDlciSpEmissionPrioToIf OBJECT-TYPE
   SYNTAX     INTEGER (0 | 1 | 2 | 3)
   ACCESS     read-write
   STATUS     obsolete
   DESCRIPTION
     "This attribute specifies the emission priority of frames sent to the 
      interface.
      
      Frames in a higher priority queue will be sent before frames in a 
      lower priority queue.
      
      The value of this attribute must be greater than or equal to 0, and 
      less than the value of the provisionable attribute 
      numberOfEmissionQs."
   DEFVAL     { 0 }
::= { frAtmDlciSpProvEntry 8 }

frAtmDlciSpAccounting OBJECT-TYPE
   SYNTAX     INTEGER  {
                 off(0),
                 on(1) }
   ACCESS     read-write
   STATUS     mandatory
   DESCRIPTION
     "This attribute allows the operator to control accounting for this 
      DLCI. To enable accounting data collection and record generation, 
      the value of this attribute must be on and at least one of the 
      accountCollection reasons in the FrAtm Ca component must be set."
   DEFVAL     { off }
::= { frAtmDlciSpProvEntry 9 }


-- FrAtm/n Dlci/n ServiceInterworkingFunction
-- The Siwf component provides the service interworking function 
-- capability between a Frame Relay data link connection and an ATM 
-- connection.

frAtmDlciSiwf OBJECT IDENTIFIER ::= { frAtmDlci 3 }



frAtmDlciSiwfRowStatusTable OBJECT-TYPE
   SYNTAX     SEQUENCE OF FrAtmDlciSiwfRowStatusEntry
   ACCESS     not-accessible
   STATUS     mandatory
   DESCRIPTION
     "This entry controls the addition and deletion of 
      frAtmDlciSiwf components."
::= { frAtmDlciSiwf 1 }

frAtmDlciSiwfRowStatusEntry OBJECT-TYPE
   SYNTAX     FrAtmDlciSiwfRowStatusEntry
   ACCESS     not-accessible
   STATUS     mandatory
   DESCRIPTION
     "A single entry in the table represents a single 
      frAtmDlciSiwf component."
   INDEX {
      frAtmIndex,
      frAtmDlciIndex,
      frAtmDlciSiwfIndex }
::= { frAtmDlciSiwfRowStatusTable 1 }

FrAtmDlciSiwfRowStatusEntry ::= SEQUENCE {
   frAtmDlciSiwfRowStatus
      RowStatus,
   frAtmDlciSiwfComponentName
      DisplayString,
   frAtmDlciSiwfStorageType
      StorageType,
   frAtmDlciSiwfIndex
      NonReplicated }

frAtmDlciSiwfRowStatus OBJECT-TYPE
   SYNTAX     RowStatus 
   ACCESS     read-write
   STATUS     mandatory
   DESCRIPTION
     "This variable is used as the basis for SNMP naming of
      frAtmDlciSiwf components.
      These components can be added and deleted."
::= { frAtmDlciSiwfRowStatusEntry 1 }

frAtmDlciSiwfComponentName OBJECT-TYPE
   SYNTAX     DisplayString 
   ACCESS     read-only
   STATUS     mandatory
   DESCRIPTION
     "This variable provides the component's string name for
      use with the ASCII Console Interface"
::= { frAtmDlciSiwfRowStatusEntry 2 }

frAtmDlciSiwfStorageType OBJECT-TYPE
   SYNTAX     StorageType 
   ACCESS     read-only
   STATUS     mandatory
   DESCRIPTION
     "This variable represents the storage type value for the
      frAtmDlciSiwf tables."
::= { frAtmDlciSiwfRowStatusEntry 4 }

frAtmDlciSiwfIndex OBJECT-TYPE
   SYNTAX     NonReplicated 
   ACCESS     not-accessible
   STATUS     mandatory
   DESCRIPTION
     "This variable represents the index for the frAtmDlciSiwf tables."
::= { frAtmDlciSiwfRowStatusEntry 10 }

frAtmDlciSiwfConnOpTable OBJECT-TYPE
   SYNTAX     SEQUENCE OF FrAtmDlciSiwfConnOpEntry
   ACCESS     not-accessible
   STATUS     mandatory
   DESCRIPTION
     "This group contains operational attributes for the ATM connection."
::= { frAtmDlciSiwf 11 }

frAtmDlciSiwfConnOpEntry OBJECT-TYPE
   SYNTAX     FrAtmDlciSiwfConnOpEntry
   ACCESS     not-accessible
   STATUS     mandatory
   DESCRIPTION
     "An entry in the frAtmDlciSiwfConnOpTable."
   INDEX {
      frAtmIndex,
      frAtmDlciIndex,
      frAtmDlciSiwfIndex }
::= { frAtmDlciSiwfConnOpTable 1 }

FrAtmDlciSiwfConnOpEntry ::= SEQUENCE {
   frAtmDlciSiwfDiscardPriority
      INTEGER,
   frAtmDlciSiwfAtmServiceCategory
      INTEGER,
   frAtmDlciSiwfTrafficParmConvPolicy
      INTEGER,
   frAtmDlciSiwfAvgFrameSize
      INTEGER,
   frAtmDlciSiwfRemoteAddress
      AsciiString,
   frAtmDlciSiwfRemoteConnectionIdentifier
      IntegerSequence }

frAtmDlciSiwfDiscardPriority OBJECT-TYPE
   SYNTAX     INTEGER  {
                 dp1(1),
                 dp2(2),
                 dp3(3) }
   ACCESS     read-only
   STATUS     mandatory
   DESCRIPTION
     "This attribute indicates the discard priority of frames sent to and 
      received from the ATM connection.
      
      When discardPriority is dp3 the frames belonging to this 
      connection will be discarded first when the FrAtm/n Dlci/n Siwf and 
      the ATM End-Point experience congestion.
      
      When discardPriority is dp2 the frames belonging to this 
      connection will be discarded after all the dp3 priority frames are 
      discarded when the FrAtm/n Dlci/n Siwf and the ATM End-Point 
      experience congestion.
      
      When discardPriority is dp1 the frames belonging to this 
      connection will be discarded after all the dp2 and dp3 priority 
      frames are discarded when the FrAtm/n Dlci/n Siwf and the ATM 
      End-Point experience congestion."
::= { frAtmDlciSiwfConnOpEntry 2 }

frAtmDlciSiwfAtmServiceCategory OBJECT-TYPE
   SYNTAX     INTEGER  {
                 ubr(0),
                 cbr(1),
                 rtVbr(2),
                 nrtVbr(3),
                 notApplicable(5) }
   ACCESS     read-only
   STATUS     mandatory
   DESCRIPTION
     "This attribute indicates the ATM service category that is used for 
      this connection. This attribute is only displayed for SPVCs."
::= { frAtmDlciSiwfConnOpEntry 4 }

frAtmDlciSiwfTrafficParmConvPolicy OBJECT-TYPE
   SYNTAX     INTEGER  {
                 n3(3),
                 n4(4),
                 n5(5),
                 n6(6),
                 notApplicable(7) }
   ACCESS     read-only
   STATUS     mandatory
   DESCRIPTION
     "This attribute indicates the traffic parameter conversion policy that 
      is being used for this connection. 
      
      For Npvcs, this attribute is not displayed.
      
      Policy 3 characterizes the traffic in the following way:
      - ATM traffic descriptor type 6 is selected
      - ATM service category rtVbr and nrtVbr supported only
      - PCR0+1 is based on AR
      - SCR0+1 is based on CIR and EIR
      - MBS0+1 is based on Bc, Be, CIR, EIR and AR
      - Takes into account that the instantaneous rate of the frame relay 
      stream can be above CIR and up to the AR.
      
      Policy 4 characterizes the traffic in the following way:
      - ATM traffic descriptor type 7 or 8 is selected. Type 7 is chosen 
      when non-conforming cells are to be discarded and type 8 when 
      non-conforming cells are tagged by UPC traffic policer.
      - PCR0+1 is based on AR
      - SCR0 is based on CIR
      - MBS0 is based on Bc, CIR, and AR
      - There is no direct characterization of EIR. The allowed EIR can be 
      derived using the difference between the AR and CIR.
      
      Policy 5 characterizes the traffic in the following way:
      - ATM traffic descriptor type 7 or 8 is selected. Type 7 is chosen 
      when non-conforming cells are to be discarded and type 8 when 
      non-conforming cells are tagged by UPC traffic policer
      - ATM service category rtVbr and nrtVbr supported only
      - PCR0+1 is based on CIR and EIR
      - SCR0 is based on the CIR
      - MBS0 is based on the CIR
      - The maximum PCR is no longer based on the AR but rather on the 
      CIR and EIR or CIR.
      
      Policy 6 characterizes the traffic in the following way:
      - ATM traffic descriptor type 3 is selected
      - ATM service category ubr, cbr, rtVbr and nrtVbr supported only
      - PCR0+1 is based only on CIR.
      DESCRIPTION"
::= { frAtmDlciSiwfConnOpEntry 5 }

frAtmDlciSiwfAvgFrameSize OBJECT-TYPE
   SYNTAX     INTEGER (0..8187)
   ACCESS     read-only
   STATUS     mandatory
   DESCRIPTION
     "This attribute indicates the average frame size that is used for this 
      connection as part of the traffic parameter conversion policy.
      Average frame size is not applicable for Npvcs, and therefore it is 
      not displayed."
::= { frAtmDlciSiwfConnOpEntry 6 }

frAtmDlciSiwfRemoteAddress OBJECT-TYPE
   SYNTAX     AsciiString (SIZE (1..44))
   ACCESS     read-only
   STATUS     mandatory
   DESCRIPTION
     "This attribute indicates the remote address (native E.164, native 
      X.121 or NSAP) for this connection. This attribute is only diplayed 
      for SPVCs."
::= { frAtmDlciSiwfConnOpEntry 8 }

frAtmDlciSiwfRemoteConnectionIdentifier OBJECT-TYPE
   SYNTAX     IntegerSequence (SIZE (3..9))
   ACCESS     read-only
   STATUS     mandatory
   DESCRIPTION
     "This attribute indicates the remote connection identifier. This 
      identifier is either a remote Atm Vpi.Vci logical channel number or a 
      remote Frame Relay Dlci logical channel number. The remote Atm 
      Vpi.Vci logical channel number is displayed as 'Vpi.Vci'. and the 
      remote Frame Relay Dlci logical channel number is displayed as 
      '0.remoteDlci'.
      For NPVCs, this attribute is not diplayed."
::= { frAtmDlciSiwfConnOpEntry 9 }

frAtmDlciSiwfSdOpTable OBJECT-TYPE
   SYNTAX     SEQUENCE OF FrAtmDlciSiwfSdOpEntry
   ACCESS     not-accessible
   STATUS     mandatory
   DESCRIPTION
     "This group contains operational information for a Siwf component."
::= { frAtmDlciSiwf 12 }

frAtmDlciSiwfSdOpEntry OBJECT-TYPE
   SYNTAX     FrAtmDlciSiwfSdOpEntry
   ACCESS     not-accessible
   STATUS     mandatory
   DESCRIPTION
     "An entry in the frAtmDlciSiwfSdOpTable."
   INDEX {
      frAtmIndex,
      frAtmDlciIndex,
      frAtmDlciSiwfIndex }
::= { frAtmDlciSiwfSdOpTable 1 }

FrAtmDlciSiwfSdOpEntry ::= SEQUENCE {
   frAtmDlciSiwfMode
      INTEGER,
   frAtmDlciSiwfDeToClpMapping
      INTEGER,
   frAtmDlciSiwfClpToDeMapping
      INTEGER,
   frAtmDlciSiwfFecnToEfciMapping
      INTEGER,
   frAtmDlciSiwfCrToUuMapping
      INTEGER,
   frAtmDlciSiwfTransferPriority
      INTEGER,
   frAtmDlciSiwfAssignedBandwidthPool
      INTEGER }

frAtmDlciSiwfMode OBJECT-TYPE
   SYNTAX     INTEGER  {
                 translationMode(0),
                 transparentMode(1),
                 speTranslationMode(2) }
   ACCESS     read-only
   STATUS     mandatory
   DESCRIPTION
     "This attribute indicates the mode of interoperability between the 
      Frame Relay and ATM connections regarding upper layer protocol 
      encapsulations.
      
      A value of translationMode indicates that the interworking function 
      performs translation between RFC 1490 and RFC 1483 
      encapsulated headers, including routed protocol translation, bridged 
      protocol translation, and connection oriented protocol translation 
      (except for RFC 1490 connection oriented protocol without RFC 
      1490 header, which is done in speTranslationMode).
      
      A value of transparentMode indicates that the interworking 
      function forwards data without altering the upper layer user 
      protocol encapsulation. Transparent mode is selected when the 
      upper layer user protocol encapsulation methods are compatible 
      between terminal equipments.
      
      A value of speTranslationMode indicates that the interworking 
      function performs single protocol translation between RFC 1490 
      with no header and RFC 1483 encapsulated packets."
::= { frAtmDlciSiwfSdOpEntry 1 }

frAtmDlciSiwfDeToClpMapping OBJECT-TYPE
   SYNTAX     INTEGER  {
                 always0(0),
                 always1(1),
                 preserve(2) }
   ACCESS     read-only
   STATUS     mandatory
   DESCRIPTION
     "This attribute indicates the type of DE to CLP mapping that is 
      performed in the Frame Relay to ATM direction.
      
      A value of preserve indicates that the DE field in a Q.922 core 
      frame is copied to the ATM CLP field of every cell containing the 
      information of that frame.
      
      A value of always0 indicates that the CLP field of every generated 
      ATM cell is always 0.
      
      A value of always1 indicates that the CLP field of every generated 
      ATM cell is always1."
::= { frAtmDlciSiwfSdOpEntry 2 }

frAtmDlciSiwfClpToDeMapping OBJECT-TYPE
   SYNTAX     INTEGER  {
                 always0(0),
                 always1(1),
                 preserve(2) }
   ACCESS     read-only
   STATUS     mandatory
   DESCRIPTION
     "This attribute indicates the type of CLP to DE mapping that is 
      performed in the ATM to Frame Relay direction.
      
      A value of preserve indicates that the DE field of the Q.922 Core 
      frame is set when one or more ATM cells belonging to an AAL5 
      frame have their CLP field set.
      
      A value of always0 indicates that the DE field of the Q.922 Core 
      frame is always set to 0.
      
      A value of always1 indicates that the DE field of the Q.922 Core 
      frame is always set to 1."
::= { frAtmDlciSiwfSdOpEntry 3 }

frAtmDlciSiwfFecnToEfciMapping OBJECT-TYPE
   SYNTAX     INTEGER  {
                 always0(0),
                 preserve(2) }
   ACCESS     read-only
   STATUS     mandatory
   DESCRIPTION
     "This attribute indicates the type of FECN to EFCI mapping that is 
      performed in the Frame Relay to ATM direction.
      
      A value of preserve indicates that the FECN field in a Q.922 Core 
      frame is copied directly to the ATM EFCI field of every cell.
      
      A value of always0 indicates that the EFCI field in every ATM cell 
      generated is set to 0."
::= { frAtmDlciSiwfSdOpEntry 4 }

frAtmDlciSiwfCrToUuMapping OBJECT-TYPE
   SYNTAX     INTEGER  {
                 always0(0),
                 preserve(2) }
   ACCESS     read-only
   STATUS     obsolete
   DESCRIPTION
     "This attribute indicates the type of CR to UU mapping that is 
      performed in the Frame Relay to ATM direction.
      
      A value of preserve indicates that the CR field in the Q.922 Core 
      frame is mapped directly to the ATM UU field of every cell 
      generated by the AAL5 segmentation process.
      
      A value of always0 indicates that the UU field in every ATM cell 
      generated is set to 0."
   DEFVAL     { preserve }
::= { frAtmDlciSiwfSdOpEntry 5 }

frAtmDlciSiwfTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 notApplicable(253) }
   ACCESS     read-only
   STATUS     mandatory
   DESCRIPTION
     "This attribute indicates the transfer priority used to establish the 
      connection. 
      For Npvcs, the value will be notApplicable."
::= { frAtmDlciSiwfSdOpEntry 6 }

frAtmDlciSiwfAssignedBandwidthPool OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     mandatory
   DESCRIPTION
     "This attribute specifies the bandwidth pool which is used by this 
      Dlci."
::= { frAtmDlciSiwfSdOpEntry 7 }

frAtmDlciSiwfSiwfSpvcOpTable OBJECT-TYPE
   SYNTAX     SEQUENCE OF FrAtmDlciSiwfSiwfSpvcOpEntry
   ACCESS     not-accessible
   STATUS     mandatory
   DESCRIPTION
     "This group contains operational attributes for the FrAtm Dlci Siwf 
      Spvc connection."
::= { frAtmDlciSiwf 13 }

frAtmDlciSiwfSiwfSpvcOpEntry OBJECT-TYPE
   SYNTAX     FrAtmDlciSiwfSiwfSpvcOpEntry
   ACCESS     not-accessible
   STATUS     mandatory
   DESCRIPTION
     "An entry in the frAtmDlciSiwfSiwfSpvcOpTable."
   INDEX {
      frAtmIndex,
      frAtmDlciIndex,
      frAtmDlciSiwfIndex }
::= { frAtmDlciSiwfSiwfSpvcOpTable 1 }

FrAtmDlciSiwfSiwfSpvcOpEntry ::= SEQUENCE {
   frAtmDlciSiwfPeakCellRate0
      Unsigned32,
   frAtmDlciSiwfPeakCellRate01
      Unsigned32,
   frAtmDlciSiwfSustainedCellRate0
      Unsigned32,
   frAtmDlciSiwfSustainedCellRate01
      Unsigned32,
   frAtmDlciSiwfMaximumBurstSize0
      Unsigned32,
   frAtmDlciSiwfMaximumBurstSize01
      Unsigned32,
   frAtmDlciSiwfEquivalentBitRate
      Unsigned32,
   frAtmDlciSiwfType
      INTEGER,
   frAtmDlciSiwfVccClearCause
      Unsigned32,
   frAtmDlciSiwfVccCauseDiag
      HexString }

frAtmDlciSiwfPeakCellRate0 OBJECT-TYPE
   SYNTAX     Unsigned32 (0..4294967295)
   ACCESS     read-only
   STATUS     mandatory
   DESCRIPTION
     "This attribute indicates the Peak Cell Rate (PCR) of the ATM VCC 
      to which this interworking function is linked for all cells (with 
      CLP=0 and CLP=1).
      
      The pcr0 is derived from the remote end traffic parameters using the 
      conversion policy of the transferPriorityMapping.
      
      For NPVCs, this attribute is not displayed."
::= { frAtmDlciSiwfSiwfSpvcOpEntry 1 }

frAtmDlciSiwfPeakCellRate01 OBJECT-TYPE
   SYNTAX     Unsigned32 (0..4294967295)
   ACCESS     read-only
   STATUS     mandatory
   DESCRIPTION
     "This attribute indicates the Peak Cell Rate (PCR) of the ATM VCC 
      to which this interworking function is linked for all cells (with 
      CLP=0 and CLP=1).
      
      The pcr01 is derived from the remote end traffic parameters using 
      the conversion policy of the transferPriorityMapping.
      
      For NPVCs, this attribute is not displayed."
::= { frAtmDlciSiwfSiwfSpvcOpEntry 2 }

frAtmDlciSiwfSustainedCellRate0 OBJECT-TYPE
   SYNTAX     Unsigned32 (0..4294967295)
   ACCESS     read-only
   STATUS     mandatory
   DESCRIPTION
     "This attribute indicates the Sustained Cell Rate (SCR) of the ATM 
      VCC to which this interworking function is linked for high priority 
      cells (with CLP=0).
      
      The scr0 is derived from the remote end traffic parameters using the 
      conversion policy of the transferPriorityMapping.
      
      For NPVCs, this attribute is not dispalyed."
::= { frAtmDlciSiwfSiwfSpvcOpEntry 3 }

frAtmDlciSiwfSustainedCellRate01 OBJECT-TYPE
   SYNTAX     Unsigned32 (0..4294967295)
   ACCESS     read-only
   STATUS     mandatory
   DESCRIPTION
     "This attribute indicates the Sustained Cell Rate (SCR) of the ATM 
      VCC that to which this interworking function is linked for all cells 
      (with CLP=0 and CLP=1).
      
      The scr01 is derived from the remote end traffic parameters using 
      the conversion policy of the transferPriorityMapping.
      
      For NPVCs, this attribute is not dispalyed."
::= { frAtmDlciSiwfSiwfSpvcOpEntry 4 }

frAtmDlciSiwfMaximumBurstSize0 OBJECT-TYPE
   SYNTAX     Unsigned32 (0..4294967295)
   ACCESS     read-only
   STATUS     mandatory
   DESCRIPTION
     "This attribute indicates the Maximum Burst Size (MBS) of the 
      ATM VCC to which this interworking function is linked for high 
      priority cells (with CLP=0).
      
      The mbs0 is derived from the remote end traffic parameters using 
      the conversion policy of the transferPriorityMapping.
      
      For NPVCs, this attribute is not dispalyed."
::= { frAtmDlciSiwfSiwfSpvcOpEntry 5 }

frAtmDlciSiwfMaximumBurstSize01 OBJECT-TYPE
   SYNTAX     Unsigned32 (0..4294967295)
   ACCESS     read-only
   STATUS     mandatory
   DESCRIPTION
     "This attribute indicates the Maximum Burst Size (MBS) of the 
      ATM VCC to which this interworking function is linked for all cells 
      (with CLP=0 and CLP=1).
      
      The mbs01 is derived from the remote end traffic parameters using 
      the conversion policy of the transferPriorityMapping.
      
      For NPVCs, this attribute is not displayed."
::= { frAtmDlciSiwfSiwfSpvcOpEntry 6 }

frAtmDlciSiwfEquivalentBitRate OBJECT-TYPE
   SYNTAX     Unsigned32 (0..4294967295)
   ACCESS     read-only
   STATUS     mandatory
   DESCRIPTION
     "This attribute indicates the access reserved bandwidth for this FR-
      ATM connection when CAC is on. If a connection is subcribed to 
      CIR only or CIR plus EIR service, the EBR reserved is CIR. If a 
      connection is subcribed to EIR only service, the EBR reserved is 0."
::= { frAtmDlciSiwfSiwfSpvcOpEntry 7 }

frAtmDlciSiwfType OBJECT-TYPE
   SYNTAX     INTEGER  {
                 master(0),
                 slave(1),
                 notApplicable(2) }
   ACCESS     read-only
   STATUS     mandatory
   DESCRIPTION
     "This attribute indicates if the component provisioned is a calling or 
      called end. If the value is master, the Dlci Siwf Spvc component is 
      provisioned as a calling end and is responsible for originating the 
      call to set up the ATM VCC. If the value is slave, this Dlci Siwf 
      component is provisioned as a called end and is responsible for 
      terminating call setup requests from the remote end. This attribute is 
      not displayed for NPVCs."
::= { frAtmDlciSiwfSiwfSpvcOpEntry 9 }

frAtmDlciSiwfVccClearCause OBJECT-TYPE
   SYNTAX     Unsigned32 (0..255)
   ACCESS     read-only
   STATUS     mandatory
   DESCRIPTION
     "This attribute indicates the cause value of the last release message 
      received from the network. This attribute is not displayed for 
      NPVCs.
      
      Please refer to ATM User-Network Interface Specification for 
      possible clear causes."
::= { frAtmDlciSiwfSiwfSpvcOpEntry 10 }

frAtmDlciSiwfVccCauseDiag OBJECT-TYPE
   SYNTAX     HexString (SIZE (1..8))
   ACCESS     read-only
   STATUS     mandatory
   DESCRIPTION
     "This attribute indicates the diagnostic value of the last release 
      message received from the network. This attribute is not displayed 
      for NPVCs.
      
      Please refer to ATM User-Network Interface Specification for 
      possible diagnostic values."
::= { frAtmDlciSiwfSiwfSpvcOpEntry 15 }

frAtmDlciSiwfStatsTable OBJECT-TYPE
   SYNTAX     SEQUENCE OF FrAtmDlciSiwfStatsEntry
   ACCESS     not-accessible
   STATUS     mandatory
   DESCRIPTION
     "This group contains statistics for the Siwf component."
::= { frAtmDlciSiwf 14 }

frAtmDlciSiwfStatsEntry OBJECT-TYPE
   SYNTAX     FrAtmDlciSiwfStatsEntry
   ACCESS     not-accessible
   STATUS     mandatory
   DESCRIPTION
     "An entry in the frAtmDlciSiwfStatsTable."
   INDEX {
      frAtmIndex,
      frAtmDlciIndex,
      frAtmDlciSiwfIndex }
::= { frAtmDlciSiwfStatsTable 1 }

FrAtmDlciSiwfStatsEntry ::= SEQUENCE {
   frAtmDlciSiwfUnknown1490Frames
      Counter32,
   frAtmDlciSiwfInvalid1490Frames
      Counter32,
   frAtmDlciSiwfLastUnknown1490ProtocolHeader
      HexString,
   frAtmDlciSiwfUnknown1483Frames
      Counter32,
   frAtmDlciSiwfInvalid1483Frames
      Counter32,
   frAtmDlciSiwfLastUnknown1483ProtocolHeader
      HexString }

frAtmDlciSiwfUnknown1490Frames OBJECT-TYPE
   SYNTAX     Counter32 
   ACCESS     read-only
   STATUS     mandatory
   DESCRIPTION
     "This attribute counts the number of frames received from the 
      interface that have a frame header that is not recognized by the RFC 
      1490. 
      
      When the maximum count is reached, it wraps to zero."
::= { frAtmDlciSiwfStatsEntry 1 }

frAtmDlciSiwfInvalid1490Frames OBJECT-TYPE
   SYNTAX     Counter32 
   ACCESS     read-only
   STATUS     mandatory
   DESCRIPTION
     "This attribute counts the number of frames received from the 
      interface that have an invalid frame header. An invalid frame header 
      occurs when the frame has less than the expected number of bytes. 
      
      When the maximum count is reached, the count wraps to zero."
::= { frAtmDlciSiwfStatsEntry 2 }

frAtmDlciSiwfLastUnknown1490ProtocolHeader OBJECT-TYPE
   SYNTAX     HexString (SIZE (1..8))
   ACCESS     read-only
   STATUS     mandatory
   DESCRIPTION
     "This attribute contains the most recent unrecognized protocol 
      header that was received from the interface. 
      
      All the RFC 1490 protocols described in sections 5.3.1.1 through 
      5.3.1.3 of FRF.8 are supported, except ARP is not supported."
::= { frAtmDlciSiwfStatsEntry 3 }

frAtmDlciSiwfUnknown1483Frames OBJECT-TYPE
   SYNTAX     Counter32 
   ACCESS     read-only
   STATUS     mandatory
   DESCRIPTION
     "This attribute counts the number of frames received from the ATM 
      connection that have a frame header that is not recognized by the 
      RFC 1483. 
      
      When the maximum count is reached, it wraps to zero."
::= { frAtmDlciSiwfStatsEntry 4 }

frAtmDlciSiwfInvalid1483Frames OBJECT-TYPE
   SYNTAX     Counter32 
   ACCESS     read-only
   STATUS     mandatory
   DESCRIPTION
     "This attribute counts the number of frames received from the ATM 
      connection that have an invalid frame header. An invalid frame 
      header occurs when the frame has less than the expected number of 
      bytes. 
      
      When the maximum count is reached, it wraps to zero."
::= { frAtmDlciSiwfStatsEntry 5 }

frAtmDlciSiwfLastUnknown1483ProtocolHeader OBJECT-TYPE
   SYNTAX     HexString (SIZE (1..8))
   ACCESS     read-only
   STATUS     mandatory
   DESCRIPTION
     "This attribute identifies the most recent unrecognized protocol 
      header that was received from the ATM connection.
      
      All the RFC 1483 protocols described in sections 5.3.1.1 through 
      5.3.1.3 of FRF.8 are supported except ARP."
::= { frAtmDlciSiwfStatsEntry 6 }


-- FrAtm/n Dlci/n Siwf ServiceDescriptor
-- The Sd component contains provisioning information for its parent 
-- Siwf component. It is a required component when Npvc is 
-- provisioned. In the case of Spvc, if this component is not 
-- provisioned, the connection will use the provisioning information 
-- from the FrAtm Ca component.

frAtmDlciSiwfSd OBJECT IDENTIFIER ::= { frAtmDlciSiwf 2 }



frAtmDlciSiwfSdRowStatusTable OBJECT-TYPE
   SYNTAX     SEQUENCE OF FrAtmDlciSiwfSdRowStatusEntry
   ACCESS     not-accessible
   STATUS     mandatory
   DESCRIPTION
     "This entry controls the addition and deletion of 
      frAtmDlciSiwfSd components."
::= { frAtmDlciSiwfSd 1 }

frAtmDlciSiwfSdRowStatusEntry OBJECT-TYPE
   SYNTAX     FrAtmDlciSiwfSdRowStatusEntry
   ACCESS     not-accessible
   STATUS     mandatory
   DESCRIPTION
     "A single entry in the table represents a single 
      frAtmDlciSiwfSd component."
   INDEX {
      frAtmIndex,
      frAtmDlciIndex,
      frAtmDlciSiwfIndex,
      frAtmDlciSiwfSdIndex }
::= { frAtmDlciSiwfSdRowStatusTable 1 }

FrAtmDlciSiwfSdRowStatusEntry ::= SEQUENCE {
   frAtmDlciSiwfSdRowStatus
      RowStatus,
   frAtmDlciSiwfSdComponentName
      DisplayString,
   frAtmDlciSiwfSdStorageType
      StorageType,
   frAtmDlciSiwfSdIndex
      NonReplicated }

frAtmDlciSiwfSdRowStatus OBJECT-TYPE
   SYNTAX     RowStatus 
   ACCESS     read-write
   STATUS     mandatory
   DESCRIPTION
     "This variable is used as the basis for SNMP naming of
      frAtmDlciSiwfSd components.
      These components can be added and deleted."
::= { frAtmDlciSiwfSdRowStatusEntry 1 }

frAtmDlciSiwfSdComponentName OBJECT-TYPE
   SYNTAX     DisplayString 
   ACCESS     read-only
   STATUS     mandatory
   DESCRIPTION
     "This variable provides the component's string name for
      use with the ASCII Console Interface"
::= { frAtmDlciSiwfSdRowStatusEntry 2 }

frAtmDlciSiwfSdStorageType OBJECT-TYPE
   SYNTAX     StorageType 
   ACCESS     read-only
   STATUS     mandatory
   DESCRIPTION
     "This variable represents the storage type value for the
      frAtmDlciSiwfSd tables."
::= { frAtmDlciSiwfSdRowStatusEntry 4 }

frAtmDlciSiwfSdIndex OBJECT-TYPE
   SYNTAX     NonReplicated 
   ACCESS     not-accessible
   STATUS     mandatory
   DESCRIPTION
     "This variable represents the index for the frAtmDlciSiwfSd tables."
::= { frAtmDlciSiwfSdRowStatusEntry 10 }

frAtmDlciSiwfSdProvTable OBJECT-TYPE
   SYNTAX     SEQUENCE OF FrAtmDlciSiwfSdProvEntry
   ACCESS     not-accessible
   STATUS     mandatory
   DESCRIPTION
     "This group contains provisionable attributes for the parent Siwf 
      component."
::= { frAtmDlciSiwfSd 10 }

frAtmDlciSiwfSdProvEntry OBJECT-TYPE
   SYNTAX     FrAtmDlciSiwfSdProvEntry
   ACCESS     not-accessible
   STATUS     mandatory
   DESCRIPTION
     "An entry in the frAtmDlciSiwfSdProvTable."
   INDEX {
      frAtmIndex,
      frAtmDlciIndex,
      frAtmDlciSiwfIndex,
      frAtmDlciSiwfSdIndex }
::= { frAtmDlciSiwfSdProvTable 1 }

FrAtmDlciSiwfSdProvEntry ::= SEQUENCE {
   frAtmDlciSiwfSdMode
      INTEGER,
   frAtmDlciSiwfSdDeToClpMapping
      INTEGER,
   frAtmDlciSiwfSdClpToDeMapping
      INTEGER,
   frAtmDlciSiwfSdFecnToEfciMapping
      INTEGER,
   frAtmDlciSiwfSdCrToUuMapping
      INTEGER }

frAtmDlciSiwfSdMode OBJECT-TYPE
   SYNTAX     INTEGER  {
                 translationMode(0),
                 transparentMode(1),
                 speTranslationMode(2),
                 sameAsInterface(255) }
   ACCESS     read-write
   STATUS     mandatory
   DESCRIPTION
     "This attribute specifies the mode of interoperability between the 
      Frame Relay and ATM connections regarding upper layer protocol 
      encapsulations.
      
      When translationMode is selected, the interworking function 
      performs translations between RFC 1490 and RFC 1483 
      encapsulated headers, including routed protocol translation, bridged 
      protocol translation, and connection oriented protocol translation 
      (except for RFC 1490 connection oriented protocol without RFC 
      1490 header, which is done in speTranslationMode). 
      
      A value of transparentMode indicates that the interworking 
      function forwards data without altering the upper layer user 
      protocol encapsulation. Transparent mode is selected when the 
      upper layer user protocol encapsulation methods are compatible 
      between terminal equipments.
      
      A value of speTranslationMode indicates that the interworking 
      function performs single protocol translation between RFC 1490 
      with no header and RFC 1483 encapsulated packets.
      
      The default value is sameAsInterface, which means as defined in 
      FrAtm/n Ca sdMode."
   DEFVAL     { sameAsInterface }
::= { frAtmDlciSiwfSdProvEntry 1 }

frAtmDlciSiwfSdDeToClpMapping OBJECT-TYPE
   SYNTAX     INTEGER  {
                 always0(0),
                 always1(1),
                 preserve(2),
                 sameAsInterface(255) }
   ACCESS     read-write
   STATUS     mandatory
   DESCRIPTION
     "This attribute specifies the DE to CLP mapping that is performed in 
      the Frame Relay to ATM direction.
      
      When preserve is selected, the DE field in the Q.922 core frame is 
      mapped to the ATM CLP field of every cell generated by the 
      segmentation process of the AAL5 PDU containing the information 
      of that frame.
      
      When always0 is selected, the CLP field of every ATM cell 
      generated by the segmentation process of the AAL5 PDU 
      containing the information of that frame is always set to 0.
      
      When always1 is selected, the CLP field of every ATM cell 
      generated by the segmentation process of the AAL5 PDU 
      containing the information of that frame is always set to 1."
   DEFVAL     { sameAsInterface }
::= { frAtmDlciSiwfSdProvEntry 2 }

frAtmDlciSiwfSdClpToDeMapping OBJECT-TYPE
   SYNTAX     INTEGER  {
                 always0(0),
                 always1(1),
                 preserve(2),
                 sameAsInterface(255) }
   ACCESS     read-write
   STATUS     mandatory
   DESCRIPTION
     "This attribute specifies the type of CLP to DE mapping that is 
      performed in the ATM to Frame Relay to direction.
      
      When preserve is selected, the DE field of the Q.922 Core frame is 
      set when one or more ATM cells belonging to an AAL5 frame have 
      their CLP field set.
      
      When always0 is selected, the DE field of the Q.922 Core frame is 
      always set to 0.
      
      When always1 is selected, the DE field of the Q.922 Core frame is 
      always set to 1."
   DEFVAL     { sameAsInterface }
::= { frAtmDlciSiwfSdProvEntry 3 }

frAtmDlciSiwfSdFecnToEfciMapping OBJECT-TYPE
   SYNTAX     INTEGER  {
                 always0(0),
                 preserve(2),
                 sameAsInterface(255) }
   ACCESS     read-write
   STATUS     mandatory
   DESCRIPTION
     "This attribute specifies the type of FECN to EFCI mapping that is 
      performed in the Frame Relay to ATM direction.
      
      When preserve is selected, the FECN field in the Q.922 Core frame 
      is mapped directly to the ATM EFCI field of every cell generated by 
      the AAL5 segmentation process.
      
      When always0 is selected, the EFCI field in every ATM cell 
      generated is set to 0."
   DEFVAL     { sameAsInterface }
::= { frAtmDlciSiwfSdProvEntry 4 }

frAtmDlciSiwfSdCrToUuMapping OBJECT-TYPE
   SYNTAX     INTEGER  {
                 always0(0),
                 preserve(2),
                 sameAsInterface(255) }
   ACCESS     read-write
   STATUS     obsolete
   DESCRIPTION
     "This attribute indicates the type of CR to UU mapping that is 
      performed in the Frame Relay to ATM direction.
      
      A value of preserve indicates that the CR field in the Q.922 Core 
      frame is mapped directly to the ATM UU field of every cell 
      generated by the AAL5 segmentation process.
      
      A value of always0 indicates that the UU field in every ATM cell 
      generated is set to 0."
   DEFVAL     { sameAsInterface }
::= { frAtmDlciSiwfSdProvEntry 5 }


-- FrAtm/n Dlci/n Siwf NailedUpPvc
-- This component associates an interworking function with an ATM 
-- connection.

frAtmDlciSiwfNPvc OBJECT IDENTIFIER ::= { frAtmDlciSiwf 3 }



frAtmDlciSiwfNPvcRowStatusTable OBJECT-TYPE
   SYNTAX     SEQUENCE OF FrAtmDlciSiwfNPvcRowStatusEntry
   ACCESS     not-accessible
   STATUS     mandatory
   DESCRIPTION
     "This entry controls the addition and deletion of 
      frAtmDlciSiwfNPvc components."
::= { frAtmDlciSiwfNPvc 1 }

frAtmDlciSiwfNPvcRowStatusEntry OBJECT-TYPE
   SYNTAX     FrAtmDlciSiwfNPvcRowStatusEntry
   ACCESS     not-accessible
   STATUS     mandatory
   DESCRIPTION
     "A single entry in the table represents a single 
      frAtmDlciSiwfNPvc component."
   INDEX {
      frAtmIndex,
      frAtmDlciIndex,
      frAtmDlciSiwfIndex,
      frAtmDlciSiwfNPvcIndex }
::= { frAtmDlciSiwfNPvcRowStatusTable 1 }

FrAtmDlciSiwfNPvcRowStatusEntry ::= SEQUENCE {
   frAtmDlciSiwfNPvcRowStatus
      RowStatus,
   frAtmDlciSiwfNPvcComponentName
      DisplayString,
   frAtmDlciSiwfNPvcStorageType
      StorageType,
   frAtmDlciSiwfNPvcIndex
      NonReplicated }

frAtmDlciSiwfNPvcRowStatus OBJECT-TYPE
   SYNTAX     RowStatus 
   ACCESS     read-write
   STATUS     mandatory
   DESCRIPTION
     "This variable is used as the basis for SNMP naming of
      frAtmDlciSiwfNPvc components.
      These components can be added and deleted."
::= { frAtmDlciSiwfNPvcRowStatusEntry 1 }

frAtmDlciSiwfNPvcComponentName OBJECT-TYPE
   SYNTAX     DisplayString 
   ACCESS     read-only
   STATUS     mandatory
   DESCRIPTION
     "This variable provides the component's string name for
      use with the ASCII Console Interface"
::= { frAtmDlciSiwfNPvcRowStatusEntry 2 }

frAtmDlciSiwfNPvcStorageType OBJECT-TYPE
   SYNTAX     StorageType 
   ACCESS     read-only
   STATUS     mandatory
   DESCRIPTION
     "This variable represents the storage type value for the
      frAtmDlciSiwfNPvc tables."
::= { frAtmDlciSiwfNPvcRowStatusEntry 4 }

frAtmDlciSiwfNPvcIndex OBJECT-TYPE
   SYNTAX     NonReplicated 
   ACCESS     not-accessible
   STATUS     mandatory
   DESCRIPTION
     "This variable represents the index for the frAtmDlciSiwfNPvc tables."
::= { frAtmDlciSiwfNPvcRowStatusEntry 10 }

frAtmDlciSiwfNPvcProvTable OBJECT-TYPE
   SYNTAX     SEQUENCE OF FrAtmDlciSiwfNPvcProvEntry
   ACCESS     not-accessible
   STATUS     mandatory
   DESCRIPTION
     "This group contains provisionable attributes for the NPvc 
      component."
::= { frAtmDlciSiwfNPvc 10 }

frAtmDlciSiwfNPvcProvEntry OBJECT-TYPE
   SYNTAX     FrAtmDlciSiwfNPvcProvEntry
   ACCESS     not-accessible
   STATUS     mandatory
   DESCRIPTION
     "An entry in the frAtmDlciSiwfNPvcProvTable."
   INDEX {
      frAtmIndex,
      frAtmDlciIndex,
      frAtmDlciSiwfIndex,
      frAtmDlciSiwfNPvcIndex }
::= { frAtmDlciSiwfNPvcProvTable 1 }

FrAtmDlciSiwfNPvcProvEntry ::= SEQUENCE {
   frAtmDlciSiwfNPvcAtmConnection
      Link,
   frAtmDlciSiwfNPvcCorrelationTag
      HexString }

frAtmDlciSiwfNPvcAtmConnection OBJECT-TYPE
   SYNTAX     Link 
   ACCESS     read-write
   STATUS     mandatory
   DESCRIPTION
     "This attribute specifies the ATM connection to which the 
      interworking function is linked.
      
      The ATM connection must be linked to an ATM end-point. For 
      example AtmIf/m Vcc/m Nep."
::= { frAtmDlciSiwfNPvcProvEntry 1 }

frAtmDlciSiwfNPvcCorrelationTag OBJECT-TYPE
   SYNTAX     HexString (SIZE (0..28))
   ACCESS     read-write
   STATUS     mandatory
   DESCRIPTION
     "This attribute specifies a unique string, set by the operator, which 
      identifies the call for accounting purposes. Downstream processing 
      uses this attribute to correlate accounting records issued at different 
      nodes in the network. Normally, this value is provisioned with the 
      same value at each end of the connection. If the value of 
      accountingEnabled is no, this attribute has no effect. This attribute 
      is also visible in the FrAtm Dlci component when accounting is 
      enabled."
   DEFVAL     { ''H }  -- ""
::= { frAtmDlciSiwfNPvcProvEntry 3 }

frAtmDlciSiwfNPvcSiwfNpvcOpTable OBJECT-TYPE
   SYNTAX     SEQUENCE OF FrAtmDlciSiwfNPvcSiwfNpvcOpEntry
   ACCESS     not-accessible
   STATUS     mandatory
   DESCRIPTION
     "This group contains the operational attributes for the FrAtm Dlci 
      Siwf Npvc connection."
::= { frAtmDlciSiwfNPvc 11 }

frAtmDlciSiwfNPvcSiwfNpvcOpEntry OBJECT-TYPE
   SYNTAX     FrAtmDlciSiwfNPvcSiwfNpvcOpEntry
   ACCESS     not-accessible
   STATUS     mandatory
   DESCRIPTION
     "An entry in the frAtmDlciSiwfNPvcSiwfNpvcOpTable."
   INDEX {
      frAtmIndex,
      frAtmDlciIndex,
      frAtmDlciSiwfIndex,
      frAtmDlciSiwfNPvcIndex }
::= { frAtmDlciSiwfNPvcSiwfNpvcOpTable 1 }

FrAtmDlciSiwfNPvcSiwfNpvcOpEntry ::= SEQUENCE {
   frAtmDlciSiwfNPvcConnectionToAtm
      RowPointer }

frAtmDlciSiwfNPvcConnectionToAtm OBJECT-TYPE
   SYNTAX     RowPointer 
   ACCESS     read-only
   STATUS     mandatory
   DESCRIPTION
     "This attribute indicates the ATM connection to which the 
      interworking function is linked."
::= { frAtmDlciSiwfNPvcSiwfNpvcOpEntry 1 }


-- FrAtm/n Dlci/n Siwf SoftPvc 
-- The Spvc component specifies the remote end for a soft PVC.

frAtmDlciSiwfSPvc OBJECT IDENTIFIER ::= { frAtmDlciSiwf 4 }



frAtmDlciSiwfSPvcRowStatusTable OBJECT-TYPE
   SYNTAX     SEQUENCE OF FrAtmDlciSiwfSPvcRowStatusEntry
   ACCESS     not-accessible
   STATUS     mandatory
   DESCRIPTION
     "This entry controls the addition and deletion of 
      frAtmDlciSiwfSPvc components."
::= { frAtmDlciSiwfSPvc 1 }

frAtmDlciSiwfSPvcRowStatusEntry OBJECT-TYPE
   SYNTAX     FrAtmDlciSiwfSPvcRowStatusEntry
   ACCESS     not-accessible
   STATUS     mandatory
   DESCRIPTION
     "A single entry in the table represents a single 
      frAtmDlciSiwfSPvc component."
   INDEX {
      frAtmIndex,
      frAtmDlciIndex,
      frAtmDlciSiwfIndex,
      frAtmDlciSiwfSPvcIndex }
::= { frAtmDlciSiwfSPvcRowStatusTable 1 }

FrAtmDlciSiwfSPvcRowStatusEntry ::= SEQUENCE {
   frAtmDlciSiwfSPvcRowStatus
      RowStatus,
   frAtmDlciSiwfSPvcComponentName
      DisplayString,
   frAtmDlciSiwfSPvcStorageType
      StorageType,
   frAtmDlciSiwfSPvcIndex
      NonReplicated }

frAtmDlciSiwfSPvcRowStatus OBJECT-TYPE
   SYNTAX     RowStatus 
   ACCESS     read-write
   STATUS     mandatory
   DESCRIPTION
     "This variable is used as the basis for SNMP naming of
      frAtmDlciSiwfSPvc components.
      These components can be added and deleted."
::= { frAtmDlciSiwfSPvcRowStatusEntry 1 }

frAtmDlciSiwfSPvcComponentName OBJECT-TYPE
   SYNTAX     DisplayString 
   ACCESS     read-only
   STATUS     mandatory
   DESCRIPTION
     "This variable provides the component's string name for
      use with the ASCII Console Interface"
::= { frAtmDlciSiwfSPvcRowStatusEntry 2 }

frAtmDlciSiwfSPvcStorageType OBJECT-TYPE
   SYNTAX     StorageType 
   ACCESS     read-only
   STATUS     mandatory
   DESCRIPTION
     "This variable represents the storage type value for the
      frAtmDlciSiwfSPvc tables."
::= { frAtmDlciSiwfSPvcRowStatusEntry 4 }

frAtmDlciSiwfSPvcIndex OBJECT-TYPE
   SYNTAX     NonReplicated 
   ACCESS     not-accessible
   STATUS     mandatory
   DESCRIPTION
     "This variable represents the index for the frAtmDlciSiwfSPvc tables."
::= { frAtmDlciSiwfSPvcRowStatusEntry 10 }

frAtmDlciSiwfSPvcProvTable OBJECT-TYPE
   SYNTAX     SEQUENCE OF FrAtmDlciSiwfSPvcProvEntry
   ACCESS     not-accessible
   STATUS     mandatory
   DESCRIPTION
     "This group contains provisionable attributes for the soft PVC 
      component."
::= { frAtmDlciSiwfSPvc 10 }

frAtmDlciSiwfSPvcProvEntry OBJECT-TYPE
   SYNTAX     FrAtmDlciSiwfSPvcProvEntry
   ACCESS     not-accessible
   STATUS     mandatory
   DESCRIPTION
     "An entry in the frAtmDlciSiwfSPvcProvTable."
   INDEX {
      frAtmIndex,
      frAtmDlciIndex,
      frAtmDlciSiwfIndex,
      frAtmDlciSiwfSPvcIndex }
::= { frAtmDlciSiwfSPvcProvTable 1 }

FrAtmDlciSiwfSPvcProvEntry ::= SEQUENCE {
   frAtmDlciSiwfSPvcRemoteAddress
      AsciiString,
   frAtmDlciSiwfSPvcRemoteConnectionIdentifier
      IntegerSequence,
   frAtmDlciSiwfSPvcCorrelationTag
      HexString }

frAtmDlciSiwfSPvcRemoteAddress OBJECT-TYPE
   SYNTAX     AsciiString (SIZE (3..44))
   ACCESS     read-write
   STATUS     mandatory
   DESCRIPTION
     "This attribute specifies the remote address of the SPVC. 
      
      It is represented as a prefix NPI string and a sequence of up to 15 
      digits to specify either a native (E.164 or X.121) address format or 
      Atm End System Address(AESA) in ISO NSAP format.
      
      For example:	
      native E.164 = 'e.upto15digits'
      native X.121 = 'x.upto14digits'
      NSAP E.164 ATM address = 'n.upto15digits.ESI.SEL'
      NSAP address = '40 hexadecimal digits'"
::= { frAtmDlciSiwfSPvcProvEntry 2 }

frAtmDlciSiwfSPvcRemoteConnectionIdentifier OBJECT-TYPE
   SYNTAX     IntegerSequence (SIZE (3..9))
   ACCESS     read-write
   STATUS     mandatory
   DESCRIPTION
     "This attribute specifies the remote connection identifier. The 
      identifier is either a remote Atm Vpi.Vci logical channel number 
      assignment or a remote Frame Relay Dlci logical channel number 
      assignment. The remote Atm Vpi.Vci logical channel number is 
      input as 'Vpi.Vci'. and the remote Frame Relay Dlci logical 
      channel number is input as '0.remoteDlci'."
::= { frAtmDlciSiwfSPvcProvEntry 3 }

frAtmDlciSiwfSPvcCorrelationTag OBJECT-TYPE
   SYNTAX     HexString (SIZE (0..28))
   ACCESS     read-write
   STATUS     mandatory
   DESCRIPTION
     "This attribute specifies the unique string, set by the operator, which 
      identifies the call for accounting purposes. Downstream processing 
      uses this attribute to correlate accounting records issued at different 
      nodes in the network. If the value of accountingEnabled is no, this 
      attribute has no effect. This attribute is also visible in the FrAtm 
      Dlci component when accounting is enabled. When this attribute is 
      an empty string, the operational correlationTag attribute in the 
      FrAtm Dlci component receives the value of a system-generated 
      correlationTag."
   DEFVAL     { ''H }  -- ""
::= { frAtmDlciSiwfSPvcProvEntry 4 }


-- FrAtm/n Dlci/n Siwf QualityOfService
-- The QoS component provides quality of service overrides for its 
-- parent Siwf component.

frAtmDlciSiwfQoS OBJECT IDENTIFIER ::= { frAtmDlciSiwf 5 }



frAtmDlciSiwfQoSRowStatusTable OBJECT-TYPE
   SYNTAX     SEQUENCE OF FrAtmDlciSiwfQoSRowStatusEntry
   ACCESS     not-accessible
   STATUS     mandatory
   DESCRIPTION
     "This entry controls the addition and deletion of 
      frAtmDlciSiwfQoS components."
::= { frAtmDlciSiwfQoS 1 }

frAtmDlciSiwfQoSRowStatusEntry OBJECT-TYPE
   SYNTAX     FrAtmDlciSiwfQoSRowStatusEntry
   ACCESS     not-accessible
   STATUS     mandatory
   DESCRIPTION
     "A single entry in the table represents a single 
      frAtmDlciSiwfQoS component."
   INDEX {
      frAtmIndex,
      frAtmDlciIndex,
      frAtmDlciSiwfIndex,
      frAtmDlciSiwfQoSIndex }
::= { frAtmDlciSiwfQoSRowStatusTable 1 }

FrAtmDlciSiwfQoSRowStatusEntry ::= SEQUENCE {
   frAtmDlciSiwfQoSRowStatus
      RowStatus,
   frAtmDlciSiwfQoSComponentName
      DisplayString,
   frAtmDlciSiwfQoSStorageType
      StorageType,
   frAtmDlciSiwfQoSIndex
      NonReplicated }

frAtmDlciSiwfQoSRowStatus OBJECT-TYPE
   SYNTAX     RowStatus 
   ACCESS     read-write
   STATUS     mandatory
   DESCRIPTION
     "This variable is used as the basis for SNMP naming of
      frAtmDlciSiwfQoS components.
      These components can be added and deleted."
::= { frAtmDlciSiwfQoSRowStatusEntry 1 }

frAtmDlciSiwfQoSComponentName OBJECT-TYPE
   SYNTAX     DisplayString 
   ACCESS     read-only
   STATUS     mandatory
   DESCRIPTION
     "This variable provides the component's string name for
      use with the ASCII Console Interface"
::= { frAtmDlciSiwfQoSRowStatusEntry 2 }

frAtmDlciSiwfQoSStorageType OBJECT-TYPE
   SYNTAX     StorageType 
   ACCESS     read-only
   STATUS     mandatory
   DESCRIPTION
     "This variable represents the storage type value for the
      frAtmDlciSiwfQoS tables."
::= { frAtmDlciSiwfQoSRowStatusEntry 4 }

frAtmDlciSiwfQoSIndex OBJECT-TYPE
   SYNTAX     NonReplicated 
   ACCESS     not-accessible
   STATUS     mandatory
   DESCRIPTION
     "This variable represents the index for the frAtmDlciSiwfQoS tables."
::= { frAtmDlciSiwfQoSRowStatusEntry 10 }

frAtmDlciSiwfQoSProvTable OBJECT-TYPE
   SYNTAX     SEQUENCE OF FrAtmDlciSiwfQoSProvEntry
   ACCESS     not-accessible
   STATUS     mandatory
   DESCRIPTION
     "This group contains the provisionable quality of service attributes 
      for the Qos component."
::= { frAtmDlciSiwfQoS 10 }

frAtmDlciSiwfQoSProvEntry OBJECT-TYPE
   SYNTAX     FrAtmDlciSiwfQoSProvEntry
   ACCESS     not-accessible
   STATUS     mandatory
   DESCRIPTION
     "An entry in the frAtmDlciSiwfQoSProvTable."
   INDEX {
      frAtmIndex,
      frAtmDlciIndex,
      frAtmDlciSiwfIndex,
      frAtmDlciSiwfQoSIndex }
::= { frAtmDlciSiwfQoSProvTable 1 }

FrAtmDlciSiwfQoSProvEntry ::= SEQUENCE {
   frAtmDlciSiwfQoSEmissionPriorityToIf
      INTEGER,
   frAtmDlciSiwfQoSTransferPriority
      INTEGER }

frAtmDlciSiwfQoSEmissionPriorityToIf OBJECT-TYPE
   SYNTAX     INTEGER  {
                 n0(0),
                 n1(1),
                 n2(2),
                 n3(3),
                 deriveFromTp(254),
                 sameAsInterface(255) }
   ACCESS     read-write
   STATUS     mandatory
   DESCRIPTION
     "This attribute specifies the emission priority of frames sent to the 
      FrAtm interface. Frames in a higher priority queue, represented by a 
      numerically higher number, will be sent before frames in a lower 
      priority queue.
      The value of this attribute is interpreted according to the value of 
      the provisionable attribute numberOfEmissionQs under the parent 
      FrAtm component. If the numberOfEmissionQs attribute is set to 2, 
      emissionPriorityToIf value of 0 is mapped to emission priority 
      queue 0 representing a lower priority queue, and 
      emissionPriorityToIf values of 1, 2, and 3 are mapped to emission 
      priority queue 1 representing the highest priority queue. If the 
      numberOfEmissionQs is set to 4, the emissionPriorityToIf values 
      are directly assigned to the emission priority queues.
      A value of deriveFromTp specifies that the emission priority is to 
      be extracted from the Mod Frs AtmNet Tpm/n component using the 
      transferPriority attribute.
      A value of sameAsInterface specifies that the emission priority is to 
      be extracted from the FrAtm Ca component using the 
      niwfEmissionPriorityToIf attribute."
   DEFVAL     { sameAsInterface }
::= { frAtmDlciSiwfQoSProvEntry 1 }

frAtmDlciSiwfQoSTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 sameAsInterface(255) }
   ACCESS     read-write
   STATUS     mandatory
   DESCRIPTION
     "This attribute specifies the transfer priority of frames sent to the 
      ATM connection using this particular Dlci.
      In the Frame Relay to ATM direction, the tp is used to select the 
      ATM service category of the connection.
      In the ATM to Frame Relay direction, the tp is used to select the 
      FrAtm emission priority queue.
      A value of sameAsInterface specifies that the emission priority is to 
      be extracted from the FrAtm Ca component using the 
      siwfTransferPriority attribute.
      DESCRIPTION"
   DEFVAL     { sameAsInterface }
::= { frAtmDlciSiwfQoSProvEntry 2 }


-- An AtmConnection component is created for each ATM connection 
-- established by an application. It shows where the data traffic for this 
-- connection is directed.

frAtmDlciSiwfAtmCon OBJECT IDENTIFIER ::= { frAtmDlciSiwf 6 }



frAtmDlciSiwfAtmConRowStatusTable OBJECT-TYPE
   SYNTAX     SEQUENCE OF FrAtmDlciSiwfAtmConRowStatusEntry
   ACCESS     not-accessible
   STATUS     mandatory
   DESCRIPTION
     "This entry controls the addition and deletion of 
      frAtmDlciSiwfAtmCon components."
::= { frAtmDlciSiwfAtmCon 1 }

frAtmDlciSiwfAtmConRowStatusEntry OBJECT-TYPE
   SYNTAX     FrAtmDlciSiwfAtmConRowStatusEntry
   ACCESS     not-accessible
   STATUS     mandatory
   DESCRIPTION
     "A single entry in the table represents a single 
      frAtmDlciSiwfAtmCon component."
   INDEX {
      frAtmIndex,
      frAtmDlciIndex,
      frAtmDlciSiwfIndex,
      frAtmDlciSiwfAtmConIndex }
::= { frAtmDlciSiwfAtmConRowStatusTable 1 }

FrAtmDlciSiwfAtmConRowStatusEntry ::= SEQUENCE {
   frAtmDlciSiwfAtmConRowStatus
      RowStatus,
   frAtmDlciSiwfAtmConComponentName
      DisplayString,
   frAtmDlciSiwfAtmConStorageType
      StorageType,
   frAtmDlciSiwfAtmConIndex
      NonReplicated }

frAtmDlciSiwfAtmConRowStatus OBJECT-TYPE
   SYNTAX     RowStatus 
   ACCESS     read-only
   STATUS     mandatory
   DESCRIPTION
     "This variable is used as the basis for SNMP naming of
      frAtmDlciSiwfAtmCon components.
      These components cannot be added nor deleted."
::= { frAtmDlciSiwfAtmConRowStatusEntry 1 }

frAtmDlciSiwfAtmConComponentName OBJECT-TYPE
   SYNTAX     DisplayString 
   ACCESS     read-only
   STATUS     mandatory
   DESCRIPTION
     "This variable provides the component's string name for
      use with the ASCII Console Interface"
::= { frAtmDlciSiwfAtmConRowStatusEntry 2 }

frAtmDlciSiwfAtmConStorageType OBJECT-TYPE
   SYNTAX     StorageType 
   ACCESS     read-only
   STATUS     mandatory
   DESCRIPTION
     "This variable represents the storage type value for the
      frAtmDlciSiwfAtmCon tables."
::= { frAtmDlciSiwfAtmConRowStatusEntry 4 }

frAtmDlciSiwfAtmConIndex OBJECT-TYPE
   SYNTAX     NonReplicated 
   ACCESS     not-accessible
   STATUS     mandatory
   DESCRIPTION
     "This variable represents the index for the frAtmDlciSiwfAtmCon tables."
::= { frAtmDlciSiwfAtmConRowStatusEntry 10 }

frAtmDlciSiwfAtmConOperTable OBJECT-TYPE
   SYNTAX     SEQUENCE OF FrAtmDlciSiwfAtmConOperEntry
   ACCESS     not-accessible
   STATUS     mandatory
   DESCRIPTION
     "This attribute group contains the operational attributes for the 
      NapAtmConnection component."
::= { frAtmDlciSiwfAtmCon 10 }

frAtmDlciSiwfAtmConOperEntry OBJECT-TYPE
   SYNTAX     FrAtmDlciSiwfAtmConOperEntry
   ACCESS     not-accessible
   STATUS     mandatory
   DESCRIPTION
     "An entry in the frAtmDlciSiwfAtmConOperTable."
   INDEX {
      frAtmIndex,
      frAtmDlciIndex,
      frAtmDlciSiwfIndex,
      frAtmDlciSiwfAtmConIndex }
::= { frAtmDlciSiwfAtmConOperTable 1 }

FrAtmDlciSiwfAtmConOperEntry ::= SEQUENCE {
   frAtmDlciSiwfAtmConNextHop
      RowPointer }

frAtmDlciSiwfAtmConNextHop OBJECT-TYPE
   SYNTAX     RowPointer 
   ACCESS     read-only
   STATUS     mandatory
   DESCRIPTION
     "This attribute shows the component name of the AtmIf Vcc Ep or 
      AtmCon component to which this switched connection is 
      established."
::= { frAtmDlciSiwfAtmConOperEntry 1 }


-- FrAtm/n Dlci/n NetworkInterworkingFunction
-- The Niwf component provides the network interworking function 
-- capability between a Frame Relay data link connection and a FRF.5 
-- ATM end point.

frAtmDlciNiwf OBJECT IDENTIFIER ::= { frAtmDlci 4 }



frAtmDlciNiwfRowStatusTable OBJECT-TYPE
   SYNTAX     SEQUENCE OF FrAtmDlciNiwfRowStatusEntry
   ACCESS     not-accessible
   STATUS     mandatory
   DESCRIPTION
     "This entry controls the addition and deletion of 
      frAtmDlciNiwf components."
::= { frAtmDlciNiwf 1 }

frAtmDlciNiwfRowStatusEntry OBJECT-TYPE
   SYNTAX     FrAtmDlciNiwfRowStatusEntry
   ACCESS     not-accessible
   STATUS     mandatory
   DESCRIPTION
     "A single entry in the table represents a single 
      frAtmDlciNiwf component."
   INDEX {
      frAtmIndex,
      frAtmDlciIndex,
      frAtmDlciNiwfIndex }
::= { frAtmDlciNiwfRowStatusTable 1 }

FrAtmDlciNiwfRowStatusEntry ::= SEQUENCE {
   frAtmDlciNiwfRowStatus
      RowStatus,
   frAtmDlciNiwfComponentName
      DisplayString,
   frAtmDlciNiwfStorageType
      StorageType,
   frAtmDlciNiwfIndex
      NonReplicated }

frAtmDlciNiwfRowStatus OBJECT-TYPE
   SYNTAX     RowStatus 
   ACCESS     read-write
   STATUS     mandatory
   DESCRIPTION
     "This variable is used as the basis for SNMP naming of
      frAtmDlciNiwf components.
      These components can be added and deleted."
::= { frAtmDlciNiwfRowStatusEntry 1 }

frAtmDlciNiwfComponentName OBJECT-TYPE
   SYNTAX     DisplayString 
   ACCESS     read-only
   STATUS     mandatory
   DESCRIPTION
     "This variable provides the component's string name for
      use with the ASCII Console Interface"
::= { frAtmDlciNiwfRowStatusEntry 2 }

frAtmDlciNiwfStorageType OBJECT-TYPE
   SYNTAX     StorageType 
   ACCESS     read-only
   STATUS     mandatory
   DESCRIPTION
     "This variable represents the storage type value for the
      frAtmDlciNiwf tables."
::= { frAtmDlciNiwfRowStatusEntry 4 }

frAtmDlciNiwfIndex OBJECT-TYPE
   SYNTAX     NonReplicated 
   ACCESS     not-accessible
   STATUS     mandatory
   DESCRIPTION
     "This variable represents the index for the frAtmDlciNiwf tables."
::= { frAtmDlciNiwfRowStatusEntry 10 }

frAtmDlciNiwfOperTable OBJECT-TYPE
   SYNTAX     SEQUENCE OF FrAtmDlciNiwfOperEntry
   ACCESS     not-accessible
   STATUS     mandatory
   DESCRIPTION
     "This group contains operational networking description information 
      for a Niwf component."
::= { frAtmDlciNiwf 10 }

frAtmDlciNiwfOperEntry OBJECT-TYPE
   SYNTAX     FrAtmDlciNiwfOperEntry
   ACCESS     not-accessible
   STATUS     mandatory
   DESCRIPTION
     "An entry in the frAtmDlciNiwfOperTable."
   INDEX {
      frAtmIndex,
      frAtmDlciIndex,
      frAtmDlciNiwfIndex }
::= { frAtmDlciNiwfOperTable 1 }

FrAtmDlciNiwfOperEntry ::= SEQUENCE {
   frAtmDlciNiwfDeToClpMapping
      INTEGER,
   frAtmDlciNiwfClpToDeMapping
      INTEGER,
   frAtmDlciNiwfTransferPriority
      Unsigned32,
   frAtmDlciNiwfAtmServiceCategory
      INTEGER,
   frAtmDlciNiwfTrafficParmConvPolicy
      INTEGER,
   frAtmDlciNiwfAvgFrameSize
      INTEGER,
   frAtmDlciNiwfEquivalentBitRate
      Unsigned32,
   frAtmDlciNiwfAtmDlci
      AsciiString,
   frAtmDlciNiwfAssignedBandwidthPool
      INTEGER }

frAtmDlciNiwfDeToClpMapping OBJECT-TYPE
   SYNTAX     INTEGER  {
                 always0(0),
                 always1(1),
                 preserve(2) }
   ACCESS     read-only
   STATUS     mandatory
   DESCRIPTION
     "This attribute indicates the type of DE to CLP mapping that is 
      performed in the Frame Relay to ATM direction.
      A value of preserve indicates that the DE field in the Q.922 core 
      frame copies to the CLP field of every ATM cell containing the 
      frame.
      A value of always0 indicates that the CLP field of every ATM cell is 
      always set to 0.
      A value of always1 indicates that the CLP field of every ATM cell is 
      always set to 1."
::= { frAtmDlciNiwfOperEntry 1 }

frAtmDlciNiwfClpToDeMapping OBJECT-TYPE
   SYNTAX     INTEGER  {
                 preserve(2),
                 transparent(3) }
   ACCESS     read-only
   STATUS     mandatory
   DESCRIPTION
     "This attribute indicates the type of CLP to DE mapping that is 
      performed in the ATM to Frame Relay direction.
      A value of preserve indicates that the DE field of the Q.922 core 
      frame is set when one or more ATM cells belonging to the frame 
      has its CLP field set, or when the DE field of the FR-SSCS PDU is 
      set.
      A value of transparent indicates that the DE field of the Q.922 core 
      frame copies directly from the DE field of the FR-SSCS PDU."
::= { frAtmDlciNiwfOperEntry 2 }

frAtmDlciNiwfTransferPriority OBJECT-TYPE
   SYNTAX     Unsigned32 (0..15)
   ACCESS     read-only
   STATUS     mandatory
   DESCRIPTION
     "This attribute indicates the transfer priority in use for a specific 
      connection. This is the transfer priority that the local Frame Relay 
      network uses for this connection to an ATM network.
      In the Frame Relay to ATM direction, the tp selects the FRF.5 End 
      Point which multiplexes the frames.
      In the ATM to Frame Relay direction, the tp selects the default 
      FrAtm emission priority queue to be used by this Dlci."
::= { frAtmDlciNiwfOperEntry 3 }

frAtmDlciNiwfAtmServiceCategory OBJECT-TYPE
   SYNTAX     INTEGER  {
                 ubr(0),
                 cbr(1),
                 rtVbr(2),
                 nrtVbr(3),
                 scNotAvailable(255) }
   ACCESS     read-only
   STATUS     mandatory
   DESCRIPTION
     "This attribute indicates the ATM service category that was mapped 
      for this connection.
      A value of scNotAvailable indicates that atmServiceCategory is not 
      yet available for this connection."
::= { frAtmDlciNiwfOperEntry 4 }

frAtmDlciNiwfTrafficParmConvPolicy OBJECT-TYPE
   SYNTAX     INTEGER  {
                 policyNotAvailable(0),
                 n3(3),
                 n4(4),
                 n5(5),
                 n6(6) }
   ACCESS     read-only
   STATUS     mandatory
   DESCRIPTION
     "This attribute indicates the traffic parameter conversion policy that 
      is used for this connection.
      
      Policy 3 characterizes the traffic in the following way:
      - ATM traffic descriptor type 6 is selected.
      - PCR(0+1) is based on the ATM link rate.
      - SCR(0+1) is based on the CIR and EIR.
      - MB(0+1) is based on Bc, Be, CIR, EIR and AR.
      - Takes into account that the instantaneous rate of the frame relay 
      stream can be above CIR and up to the AR.
      
      Policy 4 characterizes the traffic in the following way:
      - ATM traffic descriptor type 7 or 8 is selected. Type 7 is chosen 
      when non-conforming cells are to be discarded and type 8 when 
      non-conforming cells are tagged by UPC traffic policer.
      - PCR(0+1) is based on AR.
      - SCR(0) is based on the CIR.
      - MBS(0) is based on Bc, CIR, and AR.
      - There is no direct characterization of EIR. The allowed EIR can be 
      derived using the difference between the AR and CIR.
      
      Policy 5 characterizes the traffic in the following way:
      - ATM traffic descriptor type 7 or 8 is selected. Type 7 is chosen 
      when non-conforming cells are to be discarded and type 8 when 
      non-conforming cells are tagged by UPC traffic policer.
      - PCR(0+1) is based on the CIR and EIR.
      - SCR(0) is based on the CIR.
      - MBS(0) is based on the CIR.
      - The maximum PCR is no longer based on the AR but rather on the 
      CIR and EIR.
      
      Policy 6 characterizes the traffic in the following way:
      - ATM traffic descriptor type 3 is selected.
      - PCR(0+1) is based only on the CIR
      policyNotAvailable indicates that the trafficParmConvPolicy is not 
      yet available for this connection."
::= { frAtmDlciNiwfOperEntry 5 }

frAtmDlciNiwfAvgFrameSize OBJECT-TYPE
   SYNTAX     INTEGER (0..8187)
   ACCESS     read-only
   STATUS     mandatory
   DESCRIPTION
     "This attribute indicates the average frame size that was used for this 
      connection as part of the traffic parameter conversion policy.
      A value of zero indicates that the avgFrameSize is not yet available 
      for this connection."
::= { frAtmDlciNiwfOperEntry 6 }

frAtmDlciNiwfEquivalentBitRate OBJECT-TYPE
   SYNTAX     Unsigned32 (0..4294967295)
   ACCESS     read-only
   STATUS     mandatory
   DESCRIPTION
     "This attribute indicates the access reserved bandwidth for this FR-
      ATM connection when CAC is on. If a connection is subcribed to 
      CIR only or CIR plus EIR service, the EBR reserved is CIR. If a 
      connection is subcribed to EIR only service, the EBR reserved is 0."
::= { frAtmDlciNiwfOperEntry 7 }

frAtmDlciNiwfAtmDlci OBJECT-TYPE
   SYNTAX     AsciiString (SIZE (0..40))
   ACCESS     read-only
   STATUS     mandatory
   DESCRIPTION
     "This attribute displays the DLCI logical channel used inside the 
      ATM VCC.
      A null value indicates that the atmDlci is not yet available for this 
      connection."
::= { frAtmDlciNiwfOperEntry 8 }

frAtmDlciNiwfAssignedBandwidthPool OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     mandatory
   DESCRIPTION
     "This attribute specifies the bandwidth pool which is used by this 
      Dlci."
::= { frAtmDlciNiwfOperEntry 9 }


-- FrAtm/n Dlci/n Niwf SoftPermanentVirtualCircuit
-- The Spvc component represents the remote end of a soft PVC.

frAtmDlciNiwfSpvc OBJECT IDENTIFIER ::= { frAtmDlciNiwf 2 }



frAtmDlciNiwfSpvcRowStatusTable OBJECT-TYPE
   SYNTAX     SEQUENCE OF FrAtmDlciNiwfSpvcRowStatusEntry
   ACCESS     not-accessible
   STATUS     mandatory
   DESCRIPTION
     "This entry controls the addition and deletion of 
      frAtmDlciNiwfSpvc components."
::= { frAtmDlciNiwfSpvc 1 }

frAtmDlciNiwfSpvcRowStatusEntry OBJECT-TYPE
   SYNTAX     FrAtmDlciNiwfSpvcRowStatusEntry
   ACCESS     not-accessible
   STATUS     mandatory
   DESCRIPTION
     "A single entry in the table represents a single 
      frAtmDlciNiwfSpvc component."
   INDEX {
      frAtmIndex,
      frAtmDlciIndex,
      frAtmDlciNiwfIndex,
      frAtmDlciNiwfSpvcIndex }
::= { frAtmDlciNiwfSpvcRowStatusTable 1 }

FrAtmDlciNiwfSpvcRowStatusEntry ::= SEQUENCE {
   frAtmDlciNiwfSpvcRowStatus
      RowStatus,
   frAtmDlciNiwfSpvcComponentName
      DisplayString,
   frAtmDlciNiwfSpvcStorageType
      StorageType,
   frAtmDlciNiwfSpvcIndex
      NonReplicated }

frAtmDlciNiwfSpvcRowStatus OBJECT-TYPE
   SYNTAX     RowStatus 
   ACCESS     read-only
   STATUS     mandatory
   DESCRIPTION
     "This variable is used as the basis for SNMP naming of
      frAtmDlciNiwfSpvc components.
      These components cannot be added nor deleted."
::= { frAtmDlciNiwfSpvcRowStatusEntry 1 }

frAtmDlciNiwfSpvcComponentName OBJECT-TYPE
   SYNTAX     DisplayString 
   ACCESS     read-only
   STATUS     mandatory
   DESCRIPTION
     "This variable provides the component's string name for
      use with the ASCII Console Interface"
::= { frAtmDlciNiwfSpvcRowStatusEntry 2 }

frAtmDlciNiwfSpvcStorageType OBJECT-TYPE
   SYNTAX     StorageType 
   ACCESS     read-only
   STATUS     mandatory
   DESCRIPTION
     "This variable represents the storage type value for the
      frAtmDlciNiwfSpvc tables."
::= { frAtmDlciNiwfSpvcRowStatusEntry 4 }

frAtmDlciNiwfSpvcIndex OBJECT-TYPE
   SYNTAX     NonReplicated 
   ACCESS     not-accessible
   STATUS     mandatory
   DESCRIPTION
     "This variable represents the index for the frAtmDlciNiwfSpvc tables."
::= { frAtmDlciNiwfSpvcRowStatusEntry 10 }

frAtmDlciNiwfSpvcProvTable OBJECT-TYPE
   SYNTAX     SEQUENCE OF FrAtmDlciNiwfSpvcProvEntry
   ACCESS     not-accessible
   STATUS     mandatory
   DESCRIPTION
     "This group contains the provisionable attributes for the soft PVC 
      component."
::= { frAtmDlciNiwfSpvc 10 }

frAtmDlciNiwfSpvcProvEntry OBJECT-TYPE
   SYNTAX     FrAtmDlciNiwfSpvcProvEntry
   ACCESS     not-accessible
   STATUS     mandatory
   DESCRIPTION
     "An entry in the frAtmDlciNiwfSpvcProvTable."
   INDEX {
      frAtmIndex,
      frAtmDlciIndex,
      frAtmDlciNiwfIndex,
      frAtmDlciNiwfSpvcIndex }
::= { frAtmDlciNiwfSpvcProvTable 1 }

FrAtmDlciNiwfSpvcProvEntry ::= SEQUENCE {
   frAtmDlciNiwfSpvcRemoteAddress
      AsciiString,
   frAtmDlciNiwfSpvcRemoteDlci
      INTEGER,
   frAtmDlciNiwfSpvcCorrelationTag
      HexString }

frAtmDlciNiwfSpvcRemoteAddress OBJECT-TYPE
   SYNTAX     AsciiString (SIZE (3..17))
   ACCESS     read-write
   STATUS     mandatory
   DESCRIPTION
     "This attribute specifies the remote address of the SPVC.
      It is represented as a prefix NPI string and a sequence of up to 15 
      digits to specify either a native E.164 or native X.121 address 
      format. For example, native E.164 = 'e.upto15digits'."
::= { frAtmDlciNiwfSpvcProvEntry 1 }

frAtmDlciNiwfSpvcRemoteDlci OBJECT-TYPE
   SYNTAX     INTEGER (16..1007 | 1022)
   ACCESS     read-write
   STATUS     mandatory
   DESCRIPTION
     "This attribute specifies the remote connection identifier. This 
      identifier is the DLCI logical channel number assignment used 
      inside the ATM pipe."
   DEFVAL     { 1022 }
::= { frAtmDlciNiwfSpvcProvEntry 2 }

frAtmDlciNiwfSpvcCorrelationTag OBJECT-TYPE
   SYNTAX     HexString (SIZE (0..28))
   ACCESS     read-write
   STATUS     mandatory
   DESCRIPTION
     "This attribute specifies aunique string, set by the operator, which 
      identifies the call for accounting purposes. Downstream processing 
      uses this attribute to correlate accounting records issued at different 
      nodes in the network. Normally, the attribute is provisioned with the 
      same value at both ends of the connection. If the value of 
      accountingEnabled is no, this attribute has no effect. This attribute 
      is also visible in the FrAtm Dlci component when accounting is 
      enabled. When this attribute is an empty string, the operational 
      correlationTag attribute in the FrAtm Dlci component receives the 
      value of a system-generated correlationTag."
   DEFVAL     { ''H }  -- ""
::= { frAtmDlciNiwfSpvcProvEntry 3 }


-- FrAtm/n Dlci/n Niwf NetworkingDescriptor
-- The Nd component provides networking descriptor overrides for its 
-- parent Niwf component.

frAtmDlciNiwfNd OBJECT IDENTIFIER ::= { frAtmDlciNiwf 3 }



frAtmDlciNiwfNdRowStatusTable OBJECT-TYPE
   SYNTAX     SEQUENCE OF FrAtmDlciNiwfNdRowStatusEntry
   ACCESS     not-accessible
   STATUS     mandatory
   DESCRIPTION
     "This entry controls the addition and deletion of 
      frAtmDlciNiwfNd components."
::= { frAtmDlciNiwfNd 1 }

frAtmDlciNiwfNdRowStatusEntry OBJECT-TYPE
   SYNTAX     FrAtmDlciNiwfNdRowStatusEntry
   ACCESS     not-accessible
   STATUS     mandatory
   DESCRIPTION
     "A single entry in the table represents a single 
      frAtmDlciNiwfNd component."
   INDEX {
      frAtmIndex,
      frAtmDlciIndex,
      frAtmDlciNiwfIndex,
      frAtmDlciNiwfNdIndex }
::= { frAtmDlciNiwfNdRowStatusTable 1 }

FrAtmDlciNiwfNdRowStatusEntry ::= SEQUENCE {
   frAtmDlciNiwfNdRowStatus
      RowStatus,
   frAtmDlciNiwfNdComponentName
      DisplayString,
   frAtmDlciNiwfNdStorageType
      StorageType,
   frAtmDlciNiwfNdIndex
      NonReplicated }

frAtmDlciNiwfNdRowStatus OBJECT-TYPE
   SYNTAX     RowStatus 
   ACCESS     read-write
   STATUS     mandatory
   DESCRIPTION
     "This variable is used as the basis for SNMP naming of
      frAtmDlciNiwfNd components.
      These components can be added and deleted."
::= { frAtmDlciNiwfNdRowStatusEntry 1 }

frAtmDlciNiwfNdComponentName OBJECT-TYPE
   SYNTAX     DisplayString 
   ACCESS     read-only
   STATUS     mandatory
   DESCRIPTION
     "This variable provides the component's string name for
      use with the ASCII Console Interface"
::= { frAtmDlciNiwfNdRowStatusEntry 2 }

frAtmDlciNiwfNdStorageType OBJECT-TYPE
   SYNTAX     StorageType 
   ACCESS     read-only
   STATUS     mandatory
   DESCRIPTION
     "This variable represents the storage type value for the
      frAtmDlciNiwfNd tables."
::= { frAtmDlciNiwfNdRowStatusEntry 4 }

frAtmDlciNiwfNdIndex OBJECT-TYPE
   SYNTAX     NonReplicated 
   ACCESS     not-accessible
   STATUS     mandatory
   DESCRIPTION
     "This variable represents the index for the frAtmDlciNiwfNd tables."
::= { frAtmDlciNiwfNdRowStatusEntry 10 }

frAtmDlciNiwfNdProvTable OBJECT-TYPE
   SYNTAX     SEQUENCE OF FrAtmDlciNiwfNdProvEntry
   ACCESS     not-accessible
   STATUS     mandatory
   DESCRIPTION
     "This group contains provisionable attributes for the parent Niwf 
      component."
::= { frAtmDlciNiwfNd 10 }

frAtmDlciNiwfNdProvEntry OBJECT-TYPE
   SYNTAX     FrAtmDlciNiwfNdProvEntry
   ACCESS     not-accessible
   STATUS     mandatory
   DESCRIPTION
     "An entry in the frAtmDlciNiwfNdProvTable."
   INDEX {
      frAtmIndex,
      frAtmDlciIndex,
      frAtmDlciNiwfIndex,
      frAtmDlciNiwfNdIndex }
::= { frAtmDlciNiwfNdProvTable 1 }

FrAtmDlciNiwfNdProvEntry ::= SEQUENCE {
   frAtmDlciNiwfNdDeToClpMapping
      INTEGER,
   frAtmDlciNiwfNdClpToDeMapping
      INTEGER,
   frAtmDlciNiwfNdTransferPriority
      INTEGER }

frAtmDlciNiwfNdDeToClpMapping OBJECT-TYPE
   SYNTAX     INTEGER  {
                 always0(0),
                 always1(1),
                 preserve(2),
                 sameAsInterface(255) }
   ACCESS     read-write
   STATUS     mandatory
   DESCRIPTION
     "This attribute specifies the type of DE to CLP mapping performs in 
      the Frame Relay to ATM direction.
      When preserve is selected, the DE field in the Q.922 core frame 
      copies to the CLP field of every ATM cell containing the frame.
      When always0 is selected, the CLP field of every ATM cell is 
      always set to 0.
      When always1 is selected, the CLP field of every ATM cell is 
      always set to 1."
   DEFVAL     { sameAsInterface }
::= { frAtmDlciNiwfNdProvEntry 1 }

frAtmDlciNiwfNdClpToDeMapping OBJECT-TYPE
   SYNTAX     INTEGER  {
                 preserve(2),
                 transparent(3),
                 sameAsInterface(255) }
   ACCESS     read-write
   STATUS     mandatory
   DESCRIPTION
     "This attribute specifies the type of CLP to DE mapping performs in 
      the ATM to Frame Relay direction.
      When preserve is selected, the DE field of the Q.922 core frame is 
      set when one or more ATM cells belonging the frame has its CLP 
      field set, or when the DE field of the FR-SSCS PDU is set.
      When transparent is selected, the DE field of the Q.922 core frame 
      copies directly from the DE field of the FR-SSCS PDU."
   DEFVAL     { sameAsInterface }
::= { frAtmDlciNiwfNdProvEntry 2 }

frAtmDlciNiwfNdTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 sameAsInterface(255) }
   ACCESS     read-write
   STATUS     obsolete
   DESCRIPTION
     "This attribute specifies the transfer priority of frames sent to and 
      received from the ATM connection.
      In the Frame Relay to ATM direction, the tp selects the FRF.5 End 
      Point which multiplexes the frames.
      In the ATM to Frame Relay direction, the tp is applied to frames on 
      a per-DLCI basis.
      This attribute is obsoleted. During migration, its value will be 
      transfered to the QualityOfService transferPriority."
   DEFVAL     { sameAsInterface }
::= { frAtmDlciNiwfNdProvEntry 3 }


-- FrAtm/n Dlci/n Niwf QualityOfService
-- The QoS component provides quality of service overrides for its 
-- parent Niwf component.

frAtmDlciNiwfQoS OBJECT IDENTIFIER ::= { frAtmDlciNiwf 4 }



frAtmDlciNiwfQoSRowStatusTable OBJECT-TYPE
   SYNTAX     SEQUENCE OF FrAtmDlciNiwfQoSRowStatusEntry
   ACCESS     not-accessible
   STATUS     mandatory
   DESCRIPTION
     "This entry controls the addition and deletion of 
      frAtmDlciNiwfQoS components."
::= { frAtmDlciNiwfQoS 1 }

frAtmDlciNiwfQoSRowStatusEntry OBJECT-TYPE
   SYNTAX     FrAtmDlciNiwfQoSRowStatusEntry
   ACCESS     not-accessible
   STATUS     mandatory
   DESCRIPTION
     "A single entry in the table represents a single 
      frAtmDlciNiwfQoS component."
   INDEX {
      frAtmIndex,
      frAtmDlciIndex,
      frAtmDlciNiwfIndex,
      frAtmDlciNiwfQoSIndex }
::= { frAtmDlciNiwfQoSRowStatusTable 1 }

FrAtmDlciNiwfQoSRowStatusEntry ::= SEQUENCE {
   frAtmDlciNiwfQoSRowStatus
      RowStatus,
   frAtmDlciNiwfQoSComponentName
      DisplayString,
   frAtmDlciNiwfQoSStorageType
      StorageType,
   frAtmDlciNiwfQoSIndex
      NonReplicated }

frAtmDlciNiwfQoSRowStatus OBJECT-TYPE
   SYNTAX     RowStatus 
   ACCESS     read-write
   STATUS     mandatory
   DESCRIPTION
     "This variable is used as the basis for SNMP naming of
      frAtmDlciNiwfQoS components.
      These components can be added and deleted."
::= { frAtmDlciNiwfQoSRowStatusEntry 1 }

frAtmDlciNiwfQoSComponentName OBJECT-TYPE
   SYNTAX     DisplayString 
   ACCESS     read-only
   STATUS     mandatory
   DESCRIPTION
     "This variable provides the component's string name for
      use with the ASCII Console Interface"
::= { frAtmDlciNiwfQoSRowStatusEntry 2 }

frAtmDlciNiwfQoSStorageType OBJECT-TYPE
   SYNTAX     StorageType 
   ACCESS     read-only
   STATUS     mandatory
   DESCRIPTION
     "This variable represents the storage type value for the
      frAtmDlciNiwfQoS tables."
::= { frAtmDlciNiwfQoSRowStatusEntry 4 }

frAtmDlciNiwfQoSIndex OBJECT-TYPE
   SYNTAX     NonReplicated 
   ACCESS     not-accessible
   STATUS     mandatory
   DESCRIPTION
     "This variable represents the index for the frAtmDlciNiwfQoS tables."
::= { frAtmDlciNiwfQoSRowStatusEntry 10 }

frAtmDlciNiwfQoSProvTable OBJECT-TYPE
   SYNTAX     SEQUENCE OF FrAtmDlciNiwfQoSProvEntry
   ACCESS     not-accessible
   STATUS     mandatory
   DESCRIPTION
     "This group contains the provisionable quality of service attributes 
      for the Qos component."
::= { frAtmDlciNiwfQoS 10 }

frAtmDlciNiwfQoSProvEntry OBJECT-TYPE
   SYNTAX     FrAtmDlciNiwfQoSProvEntry
   ACCESS     not-accessible
   STATUS     mandatory
   DESCRIPTION
     "An entry in the frAtmDlciNiwfQoSProvTable."
   INDEX {
      frAtmIndex,
      frAtmDlciIndex,
      frAtmDlciNiwfIndex,
      frAtmDlciNiwfQoSIndex }
::= { frAtmDlciNiwfQoSProvTable 1 }

FrAtmDlciNiwfQoSProvEntry ::= SEQUENCE {
   frAtmDlciNiwfQoSEmissionPriorityToIf
      INTEGER,
   frAtmDlciNiwfQoSTransferPriority
      INTEGER }

frAtmDlciNiwfQoSEmissionPriorityToIf OBJECT-TYPE
   SYNTAX     INTEGER  {
                 n0(0),
                 n1(1),
                 n2(2),
                 n3(3),
                 deriveFromTp(254),
                 sameAsInterface(255) }
   ACCESS     read-write
   STATUS     mandatory
   DESCRIPTION
     "This attribute specifies the emission priority of frames sent to the 
      FrAtm interface. Frames in a higher priority queue, depicted by a 
      numerically higher number, are sent before frames in a lower 
      priority queue.
      The value of this attribute is interpreted according to the value of 
      the provisionable attribute numberOfEmissionQs under the parent 
      FrAtm component. If the numberOfEmissionQs attribute is set to 2, 
      emissionPriorityToIf value of 0 maps to emission priority queue 0 
      representing a lower priority queue, and emissionPriorityToIf values 
      of 1, 2, and 3 map to emission priority queue 1 representing the 
      highest priority queue. If the numberOfEmissionQs is set to 4, the 
      emissionPriorityToIf values are directly assigned to the emission 
      priority queues.
      A value of deriveFromTp specifies that the emission priority is to 
      be extracted from the Mod Frs AtmNet Tpm/n component using the 
      transferPriority attribute.
      A value of sameAsInterface specifies that the emission priority is 
      extracts from the FrAtm Ca component using the 
      niwfEmissionPriorityToIf attribute."
   DEFVAL     { sameAsInterface }
::= { frAtmDlciNiwfQoSProvEntry 1 }

frAtmDlciNiwfQoSTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 sameAsInterface(255) }
   ACCESS     read-write
   STATUS     mandatory
   DESCRIPTION
     "This attribute specifies the transfer priority of frames sent to the 
      ATM connection.
      In the Frame Relay to ATM direction, the tp selects the FRF.5 End 
      Point which multiplexes the frames.
      In the ATM to Frame Relay direction, the tp selects the default 
      FrAtm emission priority queue to be used by this DLCI.
      A value of sameAsInterface specifies that the emission priority is to 
      be extracted from the FrAtm Ca component using the 
      niwfTransferPriority attribute.
      DESCRIPTION"
   DEFVAL     { sameAsInterface }
::= { frAtmDlciNiwfQoSProvEntry 2 }


-- FrAtm/n Dlci/n EgressServiceParameters
-- This component contains the provisionable attributes of the egress 
-- direction for the parent Dlci component.

frAtmDlciEgSp OBJECT IDENTIFIER ::= { frAtmDlci 5 }



frAtmDlciEgSpRowStatusTable OBJECT-TYPE
   SYNTAX     SEQUENCE OF FrAtmDlciEgSpRowStatusEntry
   ACCESS     not-accessible
   STATUS     mandatory
   DESCRIPTION
     "This entry controls the addition and deletion of 
      frAtmDlciEgSp components."
::= { frAtmDlciEgSp 1 }

frAtmDlciEgSpRowStatusEntry OBJECT-TYPE
   SYNTAX     FrAtmDlciEgSpRowStatusEntry
   ACCESS     not-accessible
   STATUS     mandatory
   DESCRIPTION
     "A single entry in the table represents a single 
      frAtmDlciEgSp component."
   INDEX {
      frAtmIndex,
      frAtmDlciIndex,
      frAtmDlciEgSpIndex }
::= { frAtmDlciEgSpRowStatusTable 1 }

FrAtmDlciEgSpRowStatusEntry ::= SEQUENCE {
   frAtmDlciEgSpRowStatus
      RowStatus,
   frAtmDlciEgSpComponentName
      DisplayString,
   frAtmDlciEgSpStorageType
      StorageType,
   frAtmDlciEgSpIndex
      NonReplicated }

frAtmDlciEgSpRowStatus OBJECT-TYPE
   SYNTAX     RowStatus 
   ACCESS     read-write
   STATUS     mandatory
   DESCRIPTION
     "This variable is used as the basis for SNMP naming of
      frAtmDlciEgSp components.
      These components can be added and deleted."
::= { frAtmDlciEgSpRowStatusEntry 1 }

frAtmDlciEgSpComponentName OBJECT-TYPE
   SYNTAX     DisplayString 
   ACCESS     read-only
   STATUS     mandatory
   DESCRIPTION
     "This variable provides the component's string name for
      use with the ASCII Console Interface"
::= { frAtmDlciEgSpRowStatusEntry 2 }

frAtmDlciEgSpStorageType OBJECT-TYPE
   SYNTAX     StorageType 
   ACCESS     read-only
   STATUS     mandatory
   DESCRIPTION
     "This variable represents the storage type value for the
      frAtmDlciEgSp tables."
::= { frAtmDlciEgSpRowStatusEntry 4 }

frAtmDlciEgSpIndex OBJECT-TYPE
   SYNTAX     NonReplicated 
   ACCESS     not-accessible
   STATUS     mandatory
   DESCRIPTION
     "This variable represents the index for the frAtmDlciEgSp tables."
::= { frAtmDlciEgSpRowStatusEntry 10 }

frAtmDlciEgSpProvTable OBJECT-TYPE
   SYNTAX     SEQUENCE OF FrAtmDlciEgSpProvEntry
   ACCESS     not-accessible
   STATUS     mandatory
   DESCRIPTION
     "This group contains the provisionable attributes of the egress 
      direction for the Data Link Connection Identifier. These attributes 
      reflect the service parameters for the egress direction specific to this 
      instance of Dlci."
::= { frAtmDlciEgSp 10 }

frAtmDlciEgSpProvEntry OBJECT-TYPE
   SYNTAX     FrAtmDlciEgSpProvEntry
   ACCESS     not-accessible
   STATUS     mandatory
   DESCRIPTION
     "An entry in the frAtmDlciEgSpProvTable."
   INDEX {
      frAtmIndex,
      frAtmDlciIndex,
      frAtmDlciEgSpIndex }
::= { frAtmDlciEgSpProvTable 1 }

FrAtmDlciEgSpProvEntry ::= SEQUENCE {
   frAtmDlciEgSpCommittedInformationRate
      Unsigned32,
   frAtmDlciEgSpCommittedBurstSize
      Unsigned32,
   frAtmDlciEgSpExcessBurstSize
      Unsigned32,
   frAtmDlciEgSpMeasurementInterval
      Unsigned32 }

frAtmDlciEgSpCommittedInformationRate OBJECT-TYPE
   SYNTAX     Unsigned32 (0..50000000)
   ACCESS     read-write
   STATUS     mandatory
   DESCRIPTION
     "This attribute specifies the committed information rate (CIR) for the 
      egress direction. It is used for bandwidth reservation for the purpose 
      of performing a Call Admission Control (CAC) function towards 
      the egress link.
      
      This attribute is not used to perform rate enforcement towards the 
      egress link."
   DEFVAL     { 64000 }
::= { frAtmDlciEgSpProvEntry 1 }

frAtmDlciEgSpCommittedBurstSize OBJECT-TYPE
   SYNTAX     Unsigned32 (0..50000000)
   ACCESS     read-write
   STATUS     mandatory
   DESCRIPTION
     "This attribute specifies the committed burst size (Bc) for the egress 
      direction. It is used for bandwidth reservation for the purpose of 
      performing a Call Admission Control (CAC) function towards the 
      egress link.
      
      This attribute is not used to perform rate enforcement towards the 
      egress link."
   DEFVAL     { 64000 }
::= { frAtmDlciEgSpProvEntry 2 }

frAtmDlciEgSpExcessBurstSize OBJECT-TYPE
   SYNTAX     Unsigned32 (0..50000000)
   ACCESS     read-write
   STATUS     mandatory
   DESCRIPTION
     "This attribute specifies the excess burst size (Be) for the egress 
      direction. It is used for bandwidth reservation for the purpose of 
      performing a Call Admission Control (CAC) function towards the 
      egress link.
      
      This attribute is not used to perform rate enforcement towards the 
      egress link."
   DEFVAL     { 0 }
::= { frAtmDlciEgSpProvEntry 3 }

frAtmDlciEgSpMeasurementInterval OBJECT-TYPE
   SYNTAX     Unsigned32 (0..25500)
   ACCESS     read-write
   STATUS     mandatory
   DESCRIPTION
     "This attribute specifies the time interval for the egress direction. It is 
      used for bandwidth reservation for the purpose of performing a Call 
      Admission Control (CAC) function towards the egress link.
      
      This attribute is not used to perform rate enforcement towards the 
      egress link."
   DEFVAL     { 0 }
::= { frAtmDlciEgSpProvEntry 4 }


-- FrUni/n VirtualFramer
-- FrDte/n VirtualFramer
-- The VirtualFramer component binds two services together to 
-- provide data transfer between them. It is mutually exclusive from 
-- Framer component. 

frAtmVFramer OBJECT IDENTIFIER ::= { frAtm 5 }



frAtmVFramerRowStatusTable OBJECT-TYPE
   SYNTAX     SEQUENCE OF FrAtmVFramerRowStatusEntry
   ACCESS     not-accessible
   STATUS     mandatory
   DESCRIPTION
     "This entry controls the addition and deletion of 
      frAtmVFramer components."
::= { frAtmVFramer 1 }

frAtmVFramerRowStatusEntry OBJECT-TYPE
   SYNTAX     FrAtmVFramerRowStatusEntry
   ACCESS     not-accessible
   STATUS     mandatory
   DESCRIPTION
     "A single entry in the table represents a single 
      frAtmVFramer component."
   INDEX {
      frAtmIndex,
      frAtmVFramerIndex }
::= { frAtmVFramerRowStatusTable 1 }

FrAtmVFramerRowStatusEntry ::= SEQUENCE {
   frAtmVFramerRowStatus
      RowStatus,
   frAtmVFramerComponentName
      DisplayString,
   frAtmVFramerStorageType
      StorageType,
   frAtmVFramerIndex
      NonReplicated }

frAtmVFramerRowStatus OBJECT-TYPE
   SYNTAX     RowStatus 
   ACCESS     read-write
   STATUS     mandatory
   DESCRIPTION
     "This variable is used as the basis for SNMP naming of
      frAtmVFramer components.
      These components can be added and deleted."
::= { frAtmVFramerRowStatusEntry 1 }

frAtmVFramerComponentName OBJECT-TYPE
   SYNTAX     DisplayString 
   ACCESS     read-only
   STATUS     mandatory
   DESCRIPTION
     "This variable provides the component's string name for
      use with the ASCII Console Interface"
::= { frAtmVFramerRowStatusEntry 2 }

frAtmVFramerStorageType OBJECT-TYPE
   SYNTAX     StorageType 
   ACCESS     read-only
   STATUS     mandatory
   DESCRIPTION
     "This variable represents the storage type value for the
      frAtmVFramer tables."
::= { frAtmVFramerRowStatusEntry 4 }

frAtmVFramerIndex OBJECT-TYPE
   SYNTAX     NonReplicated 
   ACCESS     not-accessible
   STATUS     mandatory
   DESCRIPTION
     "This variable represents the index for the frAtmVFramer tables."
::= { frAtmVFramerRowStatusEntry 10 }

frAtmVFramerProvTable OBJECT-TYPE
   SYNTAX     SEQUENCE OF FrAtmVFramerProvEntry
   ACCESS     not-accessible
   STATUS     mandatory
   DESCRIPTION
     "This group contains provisionable attributes for the VirtualFramer 
      component."
::= { frAtmVFramer 10 }

frAtmVFramerProvEntry OBJECT-TYPE
   SYNTAX     FrAtmVFramerProvEntry
   ACCESS     not-accessible
   STATUS     mandatory
   DESCRIPTION
     "An entry in the frAtmVFramerProvTable."
   INDEX {
      frAtmIndex,
      frAtmVFramerIndex }
::= { frAtmVFramerProvTable 1 }

FrAtmVFramerProvEntry ::= SEQUENCE {
   frAtmVFramerOtherVirtualFramer
      Link,
   frAtmVFramerLogicalProcessor
      Link }

frAtmVFramerOtherVirtualFramer OBJECT-TYPE
   SYNTAX     Link 
   ACCESS     read-write
   STATUS     mandatory
   DESCRIPTION
     "This attribute specifies the other VirtualFramer to which the service 
      is linked, for example, FrUni/n VirtualFramer, FrDte/n 
      VirtualFramer."
::= { frAtmVFramerProvEntry 1 }

frAtmVFramerLogicalProcessor OBJECT-TYPE
   SYNTAX     Link 
   ACCESS     read-write
   STATUS     mandatory
   DESCRIPTION
     "This attribute specifies the logical processor on which the service 
      component will reside."
::= { frAtmVFramerProvEntry 2 }

frAtmVFramerStateTable OBJECT-TYPE
   SYNTAX     SEQUENCE OF FrAtmVFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frAtmVFramer 11 }

frAtmVFramerStateEntry OBJECT-TYPE
   SYNTAX     FrAtmVFramerStateEntry
   ACCESS     not-accessible
   STATUS     mandatory
   DESCRIPTION
     "An entry in the frAtmVFramerStateTable."
   INDEX {
      frAtmIndex,
      frAtmVFramerIndex }
::= { frAtmVFramerStateTable 1 }

FrAtmVFramerStateEntry ::= SEQUENCE {
   frAtmVFramerAdminState
      INTEGER,
   frAtmVFramerOperationalState
      INTEGER,
   frAtmVFramerUsageState
      INTEGER }

frAtmVFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frAtmVFramerStateEntry 1 }

frAtmVFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frAtmVFramerStateEntry 2 }

frAtmVFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frAtmVFramerStateEntry 3 }

frAtmVFramerStatsTable OBJECT-TYPE
   SYNTAX     SEQUENCE OF FrAtmVFramerStatsEntry
   ACCESS     not-accessible
   STATUS     mandatory
   DESCRIPTION
     "This group contains the operational statistics data for a 
      VirtualFramer component."
::= { frAtmVFramer 12 }

frAtmVFramerStatsEntry OBJECT-TYPE
   SYNTAX     FrAtmVFramerStatsEntry
   ACCESS     not-accessible
   STATUS     mandatory
   DESCRIPTION
     "An entry in the frAtmVFramerStatsTable."
   INDEX {
      frAtmIndex,
      frAtmVFramerIndex }
::= { frAtmVFramerStatsTable 1 }

FrAtmVFramerStatsEntry ::= SEQUENCE {
   frAtmVFramerFrmToOtherVFramer
      PassportCounter64,
   frAtmVFramerFrmFromOtherVFramer
      PassportCounter64,
   frAtmVFramerOctetFromOtherVFramer
      PassportCounter64 }

frAtmVFramerFrmToOtherVFramer OBJECT-TYPE
   SYNTAX     PassportCounter64 
   ACCESS     read-only
   STATUS     mandatory
   DESCRIPTION
     "This attribute counts the frames transmitted to the 
      otherVirtualFramer."
::= { frAtmVFramerStatsEntry 2 }

frAtmVFramerFrmFromOtherVFramer OBJECT-TYPE
   SYNTAX     PassportCounter64 
   ACCESS     read-only
   STATUS     mandatory
   DESCRIPTION
     "This attribute counts the frames received from the 
      otherVirtualFramer."
::= { frAtmVFramerStatsEntry 3 }

frAtmVFramerOctetFromOtherVFramer OBJECT-TYPE
   SYNTAX     PassportCounter64 
   ACCESS     read-only
   STATUS     mandatory
   DESCRIPTION
     "This attribute counts the octets received from the 
      otherVirtualFramer."
::= { frAtmVFramerStatsEntry 5 }


-- FrAtm/n Address
-- The Addr component contains the address for a FrAtm interface that 
-- supports native E.164 or X.121.

frAtmAddr OBJECT IDENTIFIER ::= { frAtm 6 }



frAtmAddrRowStatusTable OBJECT-TYPE
   SYNTAX     SEQUENCE OF FrAtmAddrRowStatusEntry
   ACCESS     not-accessible
   STATUS     mandatory
   DESCRIPTION
     "This entry controls the addition and deletion of 
      frAtmAddr components."
::= { frAtmAddr 1 }

frAtmAddrRowStatusEntry OBJECT-TYPE
   SYNTAX     FrAtmAddrRowStatusEntry
   ACCESS     not-accessible
   STATUS     mandatory
   DESCRIPTION
     "A single entry in the table represents a single 
      frAtmAddr component."
   INDEX {
      frAtmIndex,
      frAtmAddrIndex }
::= { frAtmAddrRowStatusTable 1 }

FrAtmAddrRowStatusEntry ::= SEQUENCE {
   frAtmAddrRowStatus
      RowStatus,
   frAtmAddrComponentName
      DisplayString,
   frAtmAddrStorageType
      StorageType,
   frAtmAddrIndex
      NonReplicated }

frAtmAddrRowStatus OBJECT-TYPE
   SYNTAX     RowStatus 
   ACCESS     read-write
   STATUS     mandatory
   DESCRIPTION
     "This variable is used as the basis for SNMP naming of
      frAtmAddr components.
      These components can be added and deleted."
::= { frAtmAddrRowStatusEntry 1 }

frAtmAddrComponentName OBJECT-TYPE
   SYNTAX     DisplayString 
   ACCESS     read-only
   STATUS     mandatory
   DESCRIPTION
     "This variable provides the component's string name for
      use with the ASCII Console Interface"
::= { frAtmAddrRowStatusEntry 2 }

frAtmAddrStorageType OBJECT-TYPE
   SYNTAX     StorageType 
   ACCESS     read-only
   STATUS     mandatory
   DESCRIPTION
     "This variable represents the storage type value for the
      frAtmAddr tables."
::= { frAtmAddrRowStatusEntry 4 }

frAtmAddrIndex OBJECT-TYPE
   SYNTAX     NonReplicated 
   ACCESS     not-accessible
   STATUS     mandatory
   DESCRIPTION
     "This variable represents the index for the frAtmAddr tables."
::= { frAtmAddrRowStatusEntry 10 }

frAtmAddrProvTable OBJECT-TYPE
   SYNTAX     SEQUENCE OF FrAtmAddrProvEntry
   ACCESS     not-accessible
   STATUS     mandatory
   DESCRIPTION
     "This group specifies the address of the FrAtm Interface."
::= { frAtmAddr 10 }

frAtmAddrProvEntry OBJECT-TYPE
   SYNTAX     FrAtmAddrProvEntry
   ACCESS     not-accessible
   STATUS     mandatory
   DESCRIPTION
     "An entry in the frAtmAddrProvTable."
   INDEX {
      frAtmIndex,
      frAtmAddrIndex }
::= { frAtmAddrProvTable 1 }

FrAtmAddrProvEntry ::= SEQUENCE {
   frAtmAddrAddress
      AsciiString }

frAtmAddrAddress OBJECT-TYPE
   SYNTAX     AsciiString (SIZE (1..17))
   ACCESS     read-write
   STATUS     mandatory
   DESCRIPTION
     "This attribute contains digits which form the unique identifier of the 
      customer. It is the equivalent of the telephone number in the 
      telephone network (either native E.164 or X.121 address formats). 
      
      For example, E.164 prefix 'e.613722', X.121 prefix 'x.302'."
::= { frAtmAddrProvEntry 2 }

frAtmAddrAddrOpTable OBJECT-TYPE
   SYNTAX     SEQUENCE OF FrAtmAddrAddrOpEntry
   ACCESS     not-accessible
   STATUS     mandatory
   DESCRIPTION
     "This group display the address of the FrAtm Interface."
::= { frAtmAddr 11 }

frAtmAddrAddrOpEntry OBJECT-TYPE
   SYNTAX     FrAtmAddrAddrOpEntry
   ACCESS     not-accessible
   STATUS     mandatory
   DESCRIPTION
     "An entry in the frAtmAddrAddrOpTable."
   INDEX {
      frAtmIndex,
      frAtmAddrIndex }
::= { frAtmAddrAddrOpTable 1 }

FrAtmAddrAddrOpEntry ::= SEQUENCE {
   frAtmAddrMyAddress
      AsciiString }

frAtmAddrMyAddress OBJECT-TYPE
   SYNTAX     AsciiString (SIZE (40))
   ACCESS     read-only
   STATUS     mandatory
   DESCRIPTION
     "This attribute displays the parent FRATM component's address in 
      the ISO NSAP format."
::= { frAtmAddrAddrOpEntry 1 }


-- FrAtm/n ConnectionAdministrator
-- The Ca component allows common subscription options applicable 
-- to interworking with ATM  networking to be specified by the 
-- network operator on a FrAtm interface. The values defined under 
-- the Ca component interface defaults are  used for the majority of 
-- the connections. For exception cases, the interface defaults specified 
-- in the Ca component can be overridden on a per connection basis by 
-- provisioning FrAtm Dlci Siwf Qos or FrAtm Dlci Niwf Qos 
-- components.

frAtmCa OBJECT IDENTIFIER ::= { frAtm 7 }



frAtmCaRowStatusTable OBJECT-TYPE
   SYNTAX     SEQUENCE OF FrAtmCaRowStatusEntry
   ACCESS     not-accessible
   STATUS     mandatory
   DESCRIPTION
     "This entry controls the addition and deletion of 
      frAtmCa components."
::= { frAtmCa 1 }

frAtmCaRowStatusEntry OBJECT-TYPE
   SYNTAX     FrAtmCaRowStatusEntry
   ACCESS     not-accessible
   STATUS     mandatory
   DESCRIPTION
     "A single entry in the table represents a single 
      frAtmCa component."
   INDEX {
      frAtmIndex,
      frAtmCaIndex }
::= { frAtmCaRowStatusTable 1 }

FrAtmCaRowStatusEntry ::= SEQUENCE {
   frAtmCaRowStatus
      RowStatus,
   frAtmCaComponentName
      DisplayString,
   frAtmCaStorageType
      StorageType,
   frAtmCaIndex
      NonReplicated }

frAtmCaRowStatus OBJECT-TYPE
   SYNTAX     RowStatus 
   ACCESS     read-only
   STATUS     mandatory
   DESCRIPTION
     "This variable is used as the basis for SNMP naming of
      frAtmCa components.
      These components cannot be added nor deleted."
::= { frAtmCaRowStatusEntry 1 }

frAtmCaComponentName OBJECT-TYPE
   SYNTAX     DisplayString 
   ACCESS     read-only
   STATUS     mandatory
   DESCRIPTION
     "This variable provides the component's string name for
      use with the ASCII Console Interface"
::= { frAtmCaRowStatusEntry 2 }

frAtmCaStorageType OBJECT-TYPE
   SYNTAX     StorageType 
   ACCESS     read-only
   STATUS     mandatory
   DESCRIPTION
     "This variable represents the storage type value for the
      frAtmCa tables."
::= { frAtmCaRowStatusEntry 4 }

frAtmCaIndex OBJECT-TYPE
   SYNTAX     NonReplicated 
   ACCESS     not-accessible
   STATUS     mandatory
   DESCRIPTION
     "This variable represents the index for the frAtmCa tables."
::= { frAtmCaRowStatusEntry 10 }

frAtmCaProvTable OBJECT-TYPE
   SYNTAX     SEQUENCE OF FrAtmCaProvEntry
   ACCESS     not-accessible
   STATUS     mandatory
   DESCRIPTION
     "This attribute group contains the common provisionable attributes 
      of the Ca component."
::= { frAtmCa 10 }

frAtmCaProvEntry OBJECT-TYPE
   SYNTAX     FrAtmCaProvEntry
   ACCESS     not-accessible
   STATUS     mandatory
   DESCRIPTION
     "An entry in the frAtmCaProvTable."
   INDEX {
      frAtmIndex,
      frAtmCaIndex }
::= { frAtmCaProvTable 1 }

FrAtmCaProvEntry ::= SEQUENCE {
   frAtmCaCallAdmissionControl
      INTEGER,
   frAtmCaOverrideLinkRate
      Unsigned32 }

frAtmCaCallAdmissionControl OBJECT-TYPE
   SYNTAX     INTEGER  {
                 off(0),
                 on(1) }
   ACCESS     read-write
   STATUS     mandatory
   DESCRIPTION
     "This attribute specifies the control to turn on Call Admission 
      Control (CAC).  The default value for CAC is off."
   DEFVAL     { off }
::= { frAtmCaProvEntry 1 }

frAtmCaOverrideLinkRate OBJECT-TYPE
   SYNTAX     Unsigned32 (0..520000000)
   ACCESS     read-write
   STATUS     mandatory
   DESCRIPTION
     "This attribute allows the link rate to be overridden for this interface.  
      This allows the user to specify a value other than the actual physical 
      link rate computed when a Framer component is provisioned.  In 
      the absence of a Framer component, or when a VirtualFramer 
      component is provisioned, this value needs to be explictly set to 
      provide an equivalent link rate.
      
      This attribute provides control on the amount of bandwidth 
      available for performing CAC. This attribute also provides the 
      requested amount of bandwidth that is negotiated across an  ATM 
      network for traffic conversion polices 3 and 4, since these policies 
      are a function of the access rate."
   DEFVAL     { 0 }
::= { frAtmCaProvEntry 2 }

frAtmCaSdTable OBJECT-TYPE
   SYNTAX     SEQUENCE OF FrAtmCaSdEntry
   ACCESS     not-accessible
   STATUS     mandatory
   DESCRIPTION
     "This group contains provisionable service interworking attributes 
      for the FrAtm component. The attributes defined in this group 
      provide the defaults for all the connections on the FrAtm interface."
::= { frAtmCa 11 }

frAtmCaSdEntry OBJECT-TYPE
   SYNTAX     FrAtmCaSdEntry
   ACCESS     not-accessible
   STATUS     mandatory
   DESCRIPTION
     "An entry in the frAtmCaSdTable."
   INDEX {
      frAtmIndex,
      frAtmCaIndex }
::= { frAtmCaSdTable 1 }

FrAtmCaSdEntry ::= SEQUENCE {
   frAtmCaSdMode
      INTEGER,
   frAtmCaSdDeToClpMapping
      INTEGER,
   frAtmCaSdClpToDeMapping
      INTEGER,
   frAtmCaSdFecnToEfciMapping
      INTEGER,
   frAtmCaSdCrToUuMapping
      INTEGER }

frAtmCaSdMode OBJECT-TYPE
   SYNTAX     INTEGER  {
                 translationMode(0),
                 transparentMode(1),
                 speTranslationMode(2) }
   ACCESS     read-write
   STATUS     mandatory
   DESCRIPTION
     "This attribute specifies the mode of interoperability between the 
      Frame Relay and ATM connections regarding upper layer protocol 
      encapsulations. This is used as the default for all the connections on 
      the interface.
      
      When translationMode is selected, the interworking function 
      performs translations between RFC1490 and RFC1483 
      encapsulated headers.  This includes routed protocol translation, 
      bridged protocol translation, and connection oriented protocol 
      translation (except for RFC 1490 connection oriented protocol 
      without RFC 1490 header, which is done in speTranslationMode). 
      
      A value of transparentMode indicates that the interworking 
      function is forwarding data without altering the upper layer user 
      protocol encapsulation. Use transparent mode when the upper layer 
      user protocol encapsulation methods are compatible between 
      terminal equipments.
      
      A value of speTranslationMode indicates that the interworking 
      function performs single protocol translation between RFC1490 
      with no header and RFC1483 encapsulated packets."
   DEFVAL     { translationMode }
::= { frAtmCaSdEntry 1 }

frAtmCaSdDeToClpMapping OBJECT-TYPE
   SYNTAX     INTEGER  {
                 always0(0),
                 always1(1),
                 preserve(2) }
   ACCESS     read-write
   STATUS     mandatory
   DESCRIPTION
     "This attribute specifies the DE to CLP mapping that is performed in 
      the Frame Relay to ATM direction. This is used as the default for all 
      the connections on the interface.
      
      When preserve is selected, the DE field in a Q.922 core frame 
      copies to the ATM CLP field of every cell containing the 
      information of that frame.
      
      When always0 is selected, the CLP field of every generated ATM 
      cell is always 0.
      
      When always1 is selected, the CLP field of every generated ATM 
      cell is always 1."
   DEFVAL     { preserve }
::= { frAtmCaSdEntry 2 }

frAtmCaSdClpToDeMapping OBJECT-TYPE
   SYNTAX     INTEGER  {
                 always0(0),
                 always1(1),
                 preserve(2) }
   ACCESS     read-write
   STATUS     mandatory
   DESCRIPTION
     "This attribute specifies the type of CLP to DE mapping that is 
      performed in the ATM to Frame Relay direction.
      
      When preserve is selected, the DE field of the Q.922 core frame is 
      set when one or more ATM cells belonging to an AAL5 frame has 
      its CLP field set.
      
      When always0 is selected, the DE field of the Q.922 core frame is 
      always set to 0.
      
      When always1 is selected, the DE field of the Q.922 core frame is 
      always set to 1."
   DEFVAL     { preserve }
::= { frAtmCaSdEntry 3 }

frAtmCaSdFecnToEfciMapping OBJECT-TYPE
   SYNTAX     INTEGER  {
                 always0(0),
                 preserve(2) }
   ACCESS     read-write
   STATUS     mandatory
   DESCRIPTION
     "This attribute specifies the type of FECN to EFCI mapping that is 
      performed in the Frame Relay to ATM direction.
      
      When preserve is selected, the FECN field in the Q.922 Core frame 
      maps directly to the ATM EFCI field of every cell generated by the 
      AAL5 segmentation process.
      
      When always0 is selected, the EFCI field in every ATM cell 
      generated is set to 0."
   DEFVAL     { preserve }
::= { frAtmCaSdEntry 4 }

frAtmCaSdCrToUuMapping OBJECT-TYPE
   SYNTAX     INTEGER  {
                 always0(0),
                 preserve(2) }
   ACCESS     read-write
   STATUS     obsolete
   DESCRIPTION
     "This attribute indicates the type of CR to UU mapping that is 
      performed in the Frame Relay to ATM direction.
      
      A value of preserve indicates that the CR field in the Q.922 Core 
      frame maps directly to the ATM UU field of every cell generated by 
      the AAL5 segmentation process.
      
      A value of always0 indicates that the UU field in every ATM cell 
      generated is set to 0."
   DEFVAL     { preserve }
::= { frAtmCaSdEntry 5 }

frAtmCaNdTable OBJECT-TYPE
   SYNTAX     SEQUENCE OF FrAtmCaNdEntry
   ACCESS     not-accessible
   STATUS     mandatory
   DESCRIPTION
     "This group contains the default provisionable networking attributes 
      for the FrAtm component."
::= { frAtmCa 12 }

frAtmCaNdEntry OBJECT-TYPE
   SYNTAX     FrAtmCaNdEntry
   ACCESS     not-accessible
   STATUS     mandatory
   DESCRIPTION
     "An entry in the frAtmCaNdTable."
   INDEX {
      frAtmIndex,
      frAtmCaIndex }
::= { frAtmCaNdTable 1 }

FrAtmCaNdEntry ::= SEQUENCE {
   frAtmCaNdDeToClpMapping
      INTEGER,
   frAtmCaNdClpToDeMapping
      INTEGER }

frAtmCaNdDeToClpMapping OBJECT-TYPE
   SYNTAX     INTEGER  {
                 always0(0),
                 always1(1),
                 preserve(2) }
   ACCESS     read-write
   STATUS     mandatory
   DESCRIPTION
     "This attribute specifies the type of DE to CLP mapping to be 
      performed in the Frame Relay to ATM direction.
      When preserve is selected, the DE field in the Q.922 core frame  
      copies to the CLP field of every ATM cell containing the frame.
      When always0 is selected, the CLP field of every ATM cell is 
      always set to 0.
      When always1 is selected, the CLP field of every ATM cell is 
      always set to 1."
   DEFVAL     { preserve }
::= { frAtmCaNdEntry 1 }

frAtmCaNdClpToDeMapping OBJECT-TYPE
   SYNTAX     INTEGER  {
                 preserve(2),
                 transparent(3) }
   ACCESS     read-write
   STATUS     mandatory
   DESCRIPTION
     "This attribute specifies the type of CLP to DE mapping to be 
      performed in the ATM to Frame Relay direction.
      When preserve is selected, the DE field of the Q.922 core frame is 
      set when one or more ATM cells belonging to the frame has its CLP 
      field set, or when the DE field of the FR-SSCS PDU is set.
      When transparent is selected, the DE field of the Q.922 core frame 
      copies directly from the DE field of the FR-SSCS PDU."
   DEFVAL     { preserve }
::= { frAtmCaNdEntry 2 }

frAtmCaIfQoSTable OBJECT-TYPE
   SYNTAX     SEQUENCE OF FrAtmCaIfQoSEntry
   ACCESS     not-accessible
   STATUS     mandatory
   DESCRIPTION
     "This attribute group contains the provisionable quality of service 
      attributes for the parent FrAtm interface."
::= { frAtmCa 13 }

frAtmCaIfQoSEntry OBJECT-TYPE
   SYNTAX     FrAtmCaIfQoSEntry
   ACCESS     not-accessible
   STATUS     mandatory
   DESCRIPTION
     "An entry in the frAtmCaIfQoSTable."
   INDEX {
      frAtmIndex,
      frAtmCaIndex }
::= { frAtmCaIfQoSTable 1 }

FrAtmCaIfQoSEntry ::= SEQUENCE {
   frAtmCaSiwfEmissionPriorityToIf
      INTEGER,
   frAtmCaSiwfTransferPriority
      INTEGER,
   frAtmCaNiwfEmissionPriorityToIf
      INTEGER,
   frAtmCaNiwfTransferPriority
      INTEGER }

frAtmCaSiwfEmissionPriorityToIf OBJECT-TYPE
   SYNTAX     INTEGER  {
                 n0(0),
                 n1(1),
                 n2(2),
                 n3(3),
                 deriveFromTp(254) }
   ACCESS     read-write
   STATUS     mandatory
   DESCRIPTION
     "This attribute specifies the emission priority of frames sent to this 
      FrAtm interface from its service interworking functions. Frames in 
      a higher priority queue, designated by a numerically higher number, 
      are sent before frames in a lower priority queue.
      The value of this attribute is interpreted according to the value of 
      the provisionable attribute numberOfEmissionQs under the parent 
      FrAtm component. If the numberOfEmissionQs attribute is set to 2, 
      siwfEmissionPriorityToIf value of 0  maps to emission priority 
      queue 0 representing a lower priority queue, and 
      siwfEmissionPriorityToIf values of 1, 2 or 3  map to emission 
      priority queue 1 representing the highest priority queue. If the 
      numberOfEmissionQs is set to 4, the siwfEmissionPriorityToIf 
      values directly map to the emission priority queues.
      A value of deriveFromTp specifies that the emission priority is 
      extracted from the Mod Frs AtmNet Tpm/n component using the 
      siwfTransferPriority attribute.
      The siwfEmissionPriorityToIf can also be overridden on a per 
      connection basis by setting the emissionPriorityToIf attribute in the 
      FrAtm Dlci Siwf Qos component."
   DEFVAL     { n0 }
::= { frAtmCaIfQoSEntry 1 }

frAtmCaSiwfTransferPriority OBJECT-TYPE
   SYNTAX     INTEGER (0..15)
   ACCESS     read-write
   STATUS     mandatory
   DESCRIPTION
     "This attribute specifies the transfer priority of frames sent to and 
      received from the ATM connection, through the service 
      interworking functions of this interface.
      In the Frame Relay to ATM direction, the stp selects the ATM 
      service category of the connection.
      In the ATM to Frame Relay direction, the stp selects the FrAtm 
      emission priority queue.
      The siwfTransferPriority can also be overridden on a per 
      connection basis by setting the transferPriority atribute in the 
      FrAtm Dlci Siwf Qos component."
   DEFVAL     { 0 }
::= { frAtmCaIfQoSEntry 2 }

frAtmCaNiwfEmissionPriorityToIf OBJECT-TYPE
   SYNTAX     INTEGER  {
                 n0(0),
                 n1(1),
                 n2(2),
                 n3(3),
                 deriveFromTp(254) }
   ACCESS     read-write
   STATUS     mandatory
   DESCRIPTION
     "This attribute specifies the emission priority of frames sent to this 
      FrAtm interface from its network interworking functions. Frames in 
      a higher priority queue are sent before frames in a lower priority 
      queue.
      The value of this attribute is interpreted according to the value of 
      the provisionable attribute numberOfEmissionQs under the parent 
      FrAtm component. If the numberOfEmissionQs attribute is set to 2, 
      niwfEmissionPriorityToIf value of 0 maps to emission priority 
      queue 0 representing a lower priority queue, and 
      niwfEmissionPriorityToIf values of 1, 2 or 3  map to emission 
      priority queue 1 representing the highest priority queue. If the 
      numberOfEmissionQs is set to 4, the emissionPrioToIf values  
      directly assign to the emission priority queues.
      A value of deriveFromTp specifies that the emission priority is 
      extracted from the Mod Frs AtmNet Tpm/n component using the 
      niwfTransferPriority attribute.
      The niwfEmissionPriorityToIf can also be overridden on a per 
      connection basis by setting the emissionPriorityToIf atribute in the 
      FrAtm Dlci Niwf Qos component."
   DEFVAL     { deriveFromTp }
::= { frAtmCaIfQoSEntry 3 }

frAtmCaNiwfTransferPriority OBJECT-TYPE
   SYNTAX     INTEGER (0..15)
   ACCESS     read-write
   STATUS     mandatory
   DESCRIPTION
     "This attribute specifies the transfer priority of frames sent to and 
      received from the ATM connection, through the network 
      interworking functions of this interface.
      In the Frame Relay to ATM direction, the ntp selects the 
      Frf5EndPoint which multiplexes the frames.
      In the ATM to Frame Relay direction, the ntp selects the default 
      FrAtm emission priority queue.
      The niwfTransferPriority can also be overridden on a per 
      connection basis by setting the transferPriority atribute in the 
      FrAtm Dlci Niwf Qos component."
   DEFVAL     { 0 }
::= { frAtmCaIfQoSEntry 4 }

frAtmCaOpTable OBJECT-TYPE
   SYNTAX     SEQUENCE OF FrAtmCaOpEntry
   ACCESS     not-accessible
   STATUS     mandatory
   DESCRIPTION
     "This attribute group contains the operational status of the Ca 
      component."
::= { frAtmCa 14 }

frAtmCaOpEntry OBJECT-TYPE
   SYNTAX     FrAtmCaOpEntry
   ACCESS     not-accessible
   STATUS     mandatory
   DESCRIPTION
     "An entry in the frAtmCaOpTable."
   INDEX {
      frAtmIndex,
      frAtmCaIndex }
::= { frAtmCaOpTable 1 }

FrAtmCaOpEntry ::= SEQUENCE {
   frAtmCaLinkRate
      Unsigned32,
   frAtmCaNailedUpPvcs
      Gauge32,
   frAtmCaTroubledDlcis
      Gauge32,
   frAtmCaSoftPvcs
      Gauge32 }

frAtmCaLinkRate OBJECT-TYPE
   SYNTAX     Unsigned32 (0..520000000)
   ACCESS     read-only
   STATUS     mandatory
   DESCRIPTION
     "This attribute indicates the link rate.
      
      If the provisionable attribute, overrideLinkRate, under the Ca 
      component is 0, then the link rate reported is the actual link rate of 
      the port or channel.  Otherwise, the link rate reported is the 
      overrideLinkRate provisioned under the Ca component."
::= { frAtmCaOpEntry 1 }

frAtmCaNailedUpPvcs OBJECT-TYPE
   SYNTAX     Gauge32 (0..5000)
   ACCESS     read-only
   STATUS     mandatory
   DESCRIPTION
     "This attribute indicates the number of nailed-Up PVCs currently 
      provisioned on this interface."
::= { frAtmCaOpEntry 3 }

frAtmCaTroubledDlcis OBJECT-TYPE
   SYNTAX     Gauge32 (0..5000)
   ACCESS     read-only
   STATUS     mandatory
   DESCRIPTION
     "This attribute indicates the total number of DLCIs that are disabled 
      and are experiencing problems.  This counter  increments as a  
      result of the following problem scenarios:
      Abit down, PVC down,  local CAC failure, or call setup failure due 
      to network problem."
::= { frAtmCaOpEntry 5 }

frAtmCaSoftPvcs OBJECT-TYPE
   SYNTAX     Gauge32 (0..5000)
   ACCESS     read-only
   STATUS     mandatory
   DESCRIPTION
     "This attribute indicates the number of soft PVCs currently 
      provisioned on this interface."
::= { frAtmCaOpEntry 6 }

frAtmCaAccountingOptionsTable OBJECT-TYPE
   SYNTAX     SEQUENCE OF FrAtmCaAccountingOptionsEntry
   ACCESS     not-accessible
   STATUS     mandatory
   DESCRIPTION
     "This group contains the common provisioned attributes for 
      accounting on a FrAtm."
::= { frAtmCa 15 }

frAtmCaAccountingOptionsEntry OBJECT-TYPE
   SYNTAX     FrAtmCaAccountingOptionsEntry
   ACCESS     not-accessible
   STATUS     mandatory
   DESCRIPTION
     "An entry in the frAtmCaAccountingOptionsTable."
   INDEX {
      frAtmIndex,
      frAtmCaIndex }
::= { frAtmCaAccountingOptionsTable 1 }

FrAtmCaAccountingOptionsEntry ::= SEQUENCE {
   frAtmCaAccountClass
      Unsigned32,
   frAtmCaAccountCollection
      OCTET STRING,
   frAtmCaServiceExchange
      Unsigned32 }

frAtmCaAccountClass OBJECT-TYPE
   SYNTAX     Unsigned32 (0..255)
   ACCESS     read-write
   STATUS     mandatory
   DESCRIPTION
     "This attribute specifies the accounting class, which is reserved for 
      network operations usage.  Its value is an arbitrary number. The 
      accounting records the value of this attribute."
   DEFVAL     { 0 }
::= { frAtmCaAccountingOptionsEntry 1 }

frAtmCaAccountCollection OBJECT-TYPE
   SYNTAX     OCTET STRING (SIZE (1))
   ACCESS     read-write
   STATUS     mandatory
   DESCRIPTION
     "This attribute controls accounting data collection at the interface 
      level.  It contains the following values:  bill, test, study, audit, force  
      which are used to specify the reason(s) for which accounting 
      records are collected. If the bill, test, study and audit options are 
      selected in the accountCollection field, accounting records are 
      collected for bill, test, study, or audit purposes.  If the force option 
      is selected in the accountCollection field, accounting records are 
      collected regardless of whether other reasons are provisioned.  If no 
      reason is provisioned for this attribute, then accounting data 
      collection does not occur.

      Description of bits:
      bill(0)
      test(1)
      study(2)
      audit(3)
      force(4)"
   DEFVAL     { '80'H }
::= { frAtmCaAccountingOptionsEntry 2 }

frAtmCaServiceExchange OBJECT-TYPE
   SYNTAX     Unsigned32 (0..255)
   ACCESS     read-write
   STATUS     mandatory
   DESCRIPTION
     "This attribute is an arbitrary number, which is reserved for network 
      operations usage.  It is recorded in the accounting record."
   DEFVAL     { 0 }
::= { frAtmCaAccountingOptionsEntry 3 }

frAtmCaBwPoolTable OBJECT-TYPE
   SYNTAX     SEQUENCE OF FrAtmCaBwPoolEntry
   ACCESS     not-accessible
   STATUS     mandatory
   DESCRIPTION
     "Port capacity is partitioned into 16 pools (pool 0 through pool 15). 
      This attribute specifies the percentage of port capacity that is 
      allowed for each pool. The percentage for each pool ranges from 
      0% to 1000%. It allows for under or over subscription of the port. 
      Under subscription occurs when the sum of the percentage assigned 
      to the 16 pools is less than 100%. Over subscription occurs when 
      the sum of the percentage for the 16 pools exceeds 100%.  The sum 
      of the percentage assigned to the 16 pools cannot exceed 1000%.
      
      The default is full sharing of port capacity without pre-set partitions 
      between transfer priorities."
::= { frAtmCa 365 }

frAtmCaBwPoolEntry OBJECT-TYPE
   SYNTAX     FrAtmCaBwPoolEntry
   ACCESS     not-accessible
   STATUS     mandatory
   DESCRIPTION
     "An entry in the frAtmCaBwPoolTable."
   INDEX {
      frAtmIndex,
      frAtmCaIndex,
      frAtmCaBwPoolIndex }
::= { frAtmCaBwPoolTable 1 }

FrAtmCaBwPoolEntry ::= SEQUENCE {
   frAtmCaBwPoolIndex
      Integer32,
   frAtmCaBwPoolValue
      Unsigned32 }

frAtmCaBwPoolIndex OBJECT-TYPE
   SYNTAX     Integer32 (0..15)
   ACCESS     not-accessible
   STATUS     mandatory
   DESCRIPTION
     "This variable represents the frAtmCaBwPoolTable
      specific index for the frAtmCaBwPoolTable."
::= { frAtmCaBwPoolEntry 1 }

frAtmCaBwPoolValue OBJECT-TYPE
   SYNTAX     Unsigned32 (0..1000)
   ACCESS     read-write
   STATUS     mandatory
   DESCRIPTION
     "This variable represents an individual value for the
      frAtmCaBwPoolTable."
::= { frAtmCaBwPoolEntry 2 }

frAtmCaPoolProvBwTable OBJECT-TYPE
   SYNTAX     SEQUENCE OF FrAtmCaPoolProvBwEntry
   ACCESS     not-accessible
   STATUS     mandatory
   DESCRIPTION
     "This attribute indicates the total bandwidth requested for 
      provisioned connections from each bandwidth pool.  Total 
      bandwidth for a given pool can be oversubcribed or undersubcribed."
::= { frAtmCa 366 }

frAtmCaPoolProvBwEntry OBJECT-TYPE
   SYNTAX     FrAtmCaPoolProvBwEntry
   ACCESS     not-accessible
   STATUS     mandatory
   DESCRIPTION
     "An entry in the frAtmCaPoolProvBwTable."
   INDEX {
      frAtmIndex,
      frAtmCaIndex,
      frAtmCaPoolProvBwIndex }
::= { frAtmCaPoolProvBwTable 1 }

FrAtmCaPoolProvBwEntry ::= SEQUENCE {
   frAtmCaPoolProvBwIndex
      Integer32,
   frAtmCaPoolProvBwValue
      Gauge32 }

frAtmCaPoolProvBwIndex OBJECT-TYPE
   SYNTAX     Integer32 (0..15)
   ACCESS     not-accessible
   STATUS     mandatory
   DESCRIPTION
     "This variable represents the frAtmCaPoolProvBwTable
      specific index for the frAtmCaPoolProvBwTable."
::= { frAtmCaPoolProvBwEntry 1 }

frAtmCaPoolProvBwValue OBJECT-TYPE
   SYNTAX     Gauge32 (0..520000000)
   ACCESS     read-only
   STATUS     mandatory
   DESCRIPTION
     "This variable represents an individual value for the
      frAtmCaPoolProvBwTable."
::= { frAtmCaPoolProvBwEntry 2 }

frAtmCaPoolAvailBwTable OBJECT-TYPE
   SYNTAX     SEQUENCE OF FrAtmCaPoolAvailBwEntry
   ACCESS     not-accessible
   STATUS     mandatory
   DESCRIPTION
     "This attribute indicates the total available bandwidth from the 
      bandwidth pool."
::= { frAtmCa 367 }

frAtmCaPoolAvailBwEntry OBJECT-TYPE
   SYNTAX     FrAtmCaPoolAvailBwEntry
   ACCESS     not-accessible
   STATUS     mandatory
   DESCRIPTION
     "An entry in the frAtmCaPoolAvailBwTable."
   INDEX {
      frAtmIndex,
      frAtmCaIndex,
      frAtmCaPoolAvailBwIndex }
::= { frAtmCaPoolAvailBwTable 1 }

FrAtmCaPoolAvailBwEntry ::= SEQUENCE {
   frAtmCaPoolAvailBwIndex
      Integer32,
   frAtmCaPoolAvailBwValue
      Gauge32 }

frAtmCaPoolAvailBwIndex OBJECT-TYPE
   SYNTAX     Integer32 (0..15)
   ACCESS     not-accessible
   STATUS     mandatory
   DESCRIPTION
     "This variable represents the frAtmCaPoolAvailBwTable
      specific index for the frAtmCaPoolAvailBwTable."
::= { frAtmCaPoolAvailBwEntry 1 }

frAtmCaPoolAvailBwValue OBJECT-TYPE
   SYNTAX     Gauge32 (0..52000000)
   ACCESS     read-only
   STATUS     mandatory
   DESCRIPTION
     "This variable represents an individual value for the
      frAtmCaPoolAvailBwTable."
::= { frAtmCaPoolAvailBwEntry 2 }

frAtmCaPoolAdmitBwTable OBJECT-TYPE
   SYNTAX     SEQUENCE OF FrAtmCaPoolAdmitBwEntry
   ACCESS     not-accessible
   STATUS     mandatory
   DESCRIPTION
     "This attribute indicates the total admitted bandwidth from each 
      bandwidth pool. Each value is the sum of the equivalent bit rates of 
      the admitted connections."
::= { frAtmCa 380 }

frAtmCaPoolAdmitBwEntry OBJECT-TYPE
   SYNTAX     FrAtmCaPoolAdmitBwEntry
   ACCESS     not-accessible
   STATUS     mandatory
   DESCRIPTION
     "An entry in the frAtmCaPoolAdmitBwTable."
   INDEX {
      frAtmIndex,
      frAtmCaIndex,
      frAtmCaPoolAdmitBwIndex }
::= { frAtmCaPoolAdmitBwTable 1 }

FrAtmCaPoolAdmitBwEntry ::= SEQUENCE {
   frAtmCaPoolAdmitBwIndex
      Integer32,
   frAtmCaPoolAdmitBwValue
      Gauge32 }

frAtmCaPoolAdmitBwIndex OBJECT-TYPE
   SYNTAX     Integer32 (0..15)
   ACCESS     not-accessible
   STATUS     mandatory
   DESCRIPTION
     "This variable represents the frAtmCaPoolAdmitBwTable
      specific index for the frAtmCaPoolAdmitBwTable."
::= { frAtmCaPoolAdmitBwEntry 1 }

frAtmCaPoolAdmitBwValue OBJECT-TYPE
   SYNTAX     Gauge32 (0..520000000)
   ACCESS     read-only
   STATUS     mandatory
   DESCRIPTION
     "This variable represents an individual value for the
      frAtmCaPoolAdmitBwTable."
::= { frAtmCaPoolAdmitBwEntry 2 }


-- FrAtm/n Ca TransferPriorityMapping/n
-- The Tpm component defines the corresponding traffic management 
-- subscription options on a FrAtm interface corresponding to a 
-- particular transfer priority.  This component is needed only if there 
-- is a requirement to override the Mod Frs AtmNet Tpm component 
-- defaults.

frAtmCaTpm OBJECT IDENTIFIER ::= { frAtmCa 2 }



frAtmCaTpmRowStatusTable OBJECT-TYPE
   SYNTAX     SEQUENCE OF FrAtmCaTpmRowStatusEntry
   ACCESS     not-accessible
   STATUS     mandatory
   DESCRIPTION
     "This entry controls the addition and deletion of 
      frAtmCaTpm components."
::= { frAtmCaTpm 1 }

frAtmCaTpmRowStatusEntry OBJECT-TYPE
   SYNTAX     FrAtmCaTpmRowStatusEntry
   ACCESS     not-accessible
   STATUS     mandatory
   DESCRIPTION
     "A single entry in the table represents a single 
      frAtmCaTpm component."
   INDEX {
      frAtmIndex,
      frAtmCaIndex,
      frAtmCaTpmIndex }
::= { frAtmCaTpmRowStatusTable 1 }

FrAtmCaTpmRowStatusEntry ::= SEQUENCE {
   frAtmCaTpmRowStatus
      RowStatus,
   frAtmCaTpmComponentName
      DisplayString,
   frAtmCaTpmStorageType
      StorageType,
   frAtmCaTpmIndex
      Integer32 }

frAtmCaTpmRowStatus OBJECT-TYPE
   SYNTAX     RowStatus 
   ACCESS     read-write
   STATUS     mandatory
   DESCRIPTION
     "This variable is used as the basis for SNMP naming of
      frAtmCaTpm components.
      These components can be added and deleted."
::= { frAtmCaTpmRowStatusEntry 1 }

frAtmCaTpmComponentName OBJECT-TYPE
   SYNTAX     DisplayString 
   ACCESS     read-only
   STATUS     mandatory
   DESCRIPTION
     "This variable provides the component's string name for
      use with the ASCII Console Interface"
::= { frAtmCaTpmRowStatusEntry 2 }

frAtmCaTpmStorageType OBJECT-TYPE
   SYNTAX     StorageType 
   ACCESS     read-only
   STATUS     mandatory
   DESCRIPTION
     "This variable represents the storage type value for the
      frAtmCaTpm tables."
::= { frAtmCaTpmRowStatusEntry 4 }

frAtmCaTpmIndex OBJECT-TYPE
   SYNTAX     Integer32 (0..15)
   ACCESS     not-accessible
   STATUS     mandatory
   DESCRIPTION
     "This variable represents the index for the frAtmCaTpm tables."
::= { frAtmCaTpmRowStatusEntry 10 }

frAtmCaTpmProvTable OBJECT-TYPE
   SYNTAX     SEQUENCE OF FrAtmCaTpmProvEntry
   ACCESS     not-accessible
   STATUS     mandatory
   DESCRIPTION
     "This attribute group contains the provisionable attributes of the Tpm 
      component at this interface."
::= { frAtmCaTpm 10 }

frAtmCaTpmProvEntry OBJECT-TYPE
   SYNTAX     FrAtmCaTpmProvEntry
   ACCESS     not-accessible
   STATUS     mandatory
   DESCRIPTION
     "An entry in the frAtmCaTpmProvTable."
   INDEX {
      frAtmIndex,
      frAtmCaIndex,
      frAtmCaTpmIndex }
::= { frAtmCaTpmProvTable 1 }

FrAtmCaTpmProvEntry ::= SEQUENCE {
   frAtmCaTpmAssignedBandwidthPool
      INTEGER,
   frAtmCaTpmTrafficParmConvPolicy
      INTEGER,
   frAtmCaTpmAverageFrameSize
      INTEGER }

frAtmCaTpmAssignedBandwidthPool OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 samePoolAsModule(255) }
   ACCESS     read-write
   STATUS     mandatory
   DESCRIPTION
     "This attribute specifies the bandwidth pool that supports this 
      transfer priority at this interface."
   DEFVAL     { samePoolAsModule }
::= { frAtmCaTpmProvEntry 1 }

frAtmCaTpmTrafficParmConvPolicy OBJECT-TYPE
   SYNTAX     INTEGER  {
                 sameAsModule(0),
                 n3(3),
                 n4(4),
                 n5(5),
                 n6(6) }
   ACCESS     read-write
   STATUS     mandatory
   DESCRIPTION
     "This attribute specifies the traffic parameter conversion policy to use 
      for a specific transfer priority for specifying equivalent bandwidth 
      rate at the FrAtm interface. 
      
      Policy 3 characterizes the traffic in the following way:
      - ATM traffic descriptor type 6 is selected
      - ATM service category rtVbr and nrtVbr supported only
      - PCR0+1 is based on AR
      - SCR0+1 is based on CIR and EIR
      - MBS0+1 is based on Bc, Be, CIR, EIR and AR
      - Takes into account that the instantaneous rate of the Frame Relay 
      stream can be above CIR and up to the AR.
      
      Policy 4 characterizes the traffic in the following way:
      - ATM traffic descriptor type 7 or 8 is selected. Type 7 is chosen 
      when non-conforming cells are to be discarded and type 8 when 
      non-conforming cells are tagged by the UPC traffic policer.
      - PCR0+1 is based on AR
      - ATM service category rtVbr and nrtVbr supported only
      - SCR0 is based on CIR
      - MBS0 is based on Bc, CIR, and AR
      - There is no direct characterization of EIR. The allowed EIR can be 
      derived using the difference between the AR and CIR.
      
      Policy 5 characterizes the traffic in the following way:
      - ATM traffic descriptor type 7 or 8 is selected. Type 7 is chosen 
      when non-conforming cells are to be discarded and type 8 when 
      non-conforming cells are tagged by the UPC traffic policer.
      - ATM service category rtVbr and nrtVbr supported only
      - PCR0+1 is based on CIR for descriptor type 7
      - PCR0+1 is based on CIR and EIR for descriptor type 8
      - SCR0 is based on CIR
      - MBS0 is based on Bc, CIR, and AR
      - The maximum PCR is no longer based on the AR but rather on the 
      CIR and EIR or CIR
      
      Policy 6 characterizes the traffic in the following way:
      - ATM traffic descriptor type 3 is selected
      - ATM service category ubr, cbr, rtVbr and nrtVbr supported only
      - PCR0+1 is based only on CIR.
      
      The default value sameAsModule implies the 
      trafficParmConversionPolicy of Mod Frs AtmNet Tpm/n is as 
      defined as Mod Frs AtmNet Tpm/n."
   DEFVAL     { sameAsModule }
::= { frAtmCaTpmProvEntry 2 }

frAtmCaTpmAverageFrameSize OBJECT-TYPE
   SYNTAX     INTEGER (0..8187)
   ACCESS     read-write
   STATUS     mandatory
   DESCRIPTION
     "This attribute specifies the average frame size at the FrAtm interface 
      for connections using this transfer priority.  If a value of 0 is 
      specified, the average frame size defined in Mod Frs AtmNet Tpm/n 
      avgFrameSize attribute is used."
   DEFVAL     { 0 }
::= { frAtmCaTpmProvEntry 3 }




-- 
-- Version and Compliance statements
-- 



-- Object-Group Statement:
-- A list of all current accessible leaf objects.

-- OBJECTS { frAtmLmiPvcConfigParmsInFsr,
--           frAtmDlciSiwfSdFecnToEfciMapping,
--           frAtmCaBwPoolValue,
--           frAtmDlciSiwfNPvcRowStatus,
--           frAtmDlciSpComponentName,
--           frAtmDlciDiscardedFrames,
--           frAtmDlciEgSpRowStatus,
--           frAtmDlciDiscDeCongestedFromIf,
--           frAtmDlciNiwfComponentName,
--           frAtmLmiFullStatusEnqFromIf,
--           frAtmDlciNiwfTrafficParmConvPolicy,
--           frAtmDlciSiwfInvalid1483Frames,
--           frAtmDlciFecnFrmToIf,
--           frAtmDlciCommittedInformationRate,
--           frAtmVFramerStorageType,
--           frAtmDlciABitStatusFromIf,
--           frAtmDlciSiwfSdRowStatus,
--           frAtmCaPoolAvailBwValue,
--           frAtmCaTpmAssignedBandwidthPool,
--           frAtmAddrMyAddress,
--           frAtmLmiIgnoreActiveBit,
--           frAtmDlciDiscardedBytes,
--           frAtmDlciComponentName,
--           frAtmProceduralStatus,
--           frAtmDlciSiwfQoSStorageType,
--           frAtmOctetToIfByQueueValue,
--           frAtmDlciDiscDeCongestedFromIfBytes,
--           frAtmAddrComponentName,
--           frAtmDlciABitReasonFromIf,
--           frAtmDlciSiwfStorageType,
--           frAtmFramerComponentName,
--           frAtmDlciSiwfUnknown1483Frames,
--           frAtmVFramerRowStatus,
--           frAtmDlciDeBytesFromIf,
--           frAtmDlciDiscCongestedFromIf,
--           frAtmFramerUnderruns,
--           frAtmDlciSiwfInvalid1490Frames,
--           frAtmDlciDeFrmFromIf,
--           frAtmCaNiwfTransferPriority,
--           frAtmRowStatus,
--           frAtmLmiLinkVerificationTimer,
--           frAtmVFramerOperationalState,
--           frAtmLmiUnexpectedIes,
--           frAtmDlciSiwfEquivalentBitRate,
--           frAtmDlciExcessBytesFromIf,
--           frAtmCaTpmAverageFrameSize,
--           frAtmDlciMaximumFrameSize,
--           frAtmDlciSiwfNPvcCorrelationTag,
--           frAtmDlciExcessFrmFromIf,
--           frAtmDlciNiwfEquivalentBitRate,
--           frAtmDlciNiwfDeToClpMapping,
--           frAtmCaTpmTrafficParmConvPolicy,
--           frAtmLmiPollingVerifTimeouts,
--           frAtmDlciSiwfAvgFrameSize,
--           frAtmDlciNiwfAtmDlci,
--           frAtmDlciBytesFromIf,
--           frAtmDlciBecnFrmToIf,
--           frAtmDlciNiwfQoSEmissionPriorityToIf,
--           frAtmDlciNiwfClpToDeMapping,
--           frAtmDlciFrmFromIf,
--           frAtmLmiKeepAliveEnqToIf,
--           frAtmDlciSiwfDiscardPriority,
--           frAtmLmiComponentName,
--           frAtmDlciSpRowStatus,
--           frAtmLastUnknownDlci,
--           frAtmFramerFrmFromIf,
--           frAtmDlciSiwfQoSTransferPriority,
--           frAtmUnknownStatus,
--           frAtmStandbyStatus,
--           frAtmLmiProcedures,
--           frAtmDlciNiwfAssignedBandwidthPool,
--           frAtmCaSdClpToDeMapping,
--           frAtmDlciSiwfSustainedCellRate01,
--           frAtmStorageType,
--           frAtmDlciSiwfTransferPriority,
--           frAtmAddrAddress,
--           frAtmDlciNiwfQoSStorageType,
--           frAtmDlciRowStatus,
--           frAtmLmiNetworkSideEventHistory,
--           frAtmDlciNiwfStorageType,
--           frAtmDlciSpAccounting,
--           frAtmDlciErrorLongBytesFromIf,
--           frAtmAdminState,
--           frAtmCaSoftPvcs,
--           frAtmDlciNiwfAtmServiceCategory,
--           frAtmFramerRowStatus,
--           frAtmDlciErrorLongFrmFromIf,
--           frAtmDlciNiwfNdClpToDeMapping,
--           frAtmCaServiceExchange,
--           frAtmDlciUsageState,
--           frAtmAddrRowStatus,
--           frAtmIfAdminStatus,
--           frAtmVFramerFrmFromOtherVFramer,
--           frAtmDlciSiwfAtmServiceCategory,
--           frAtmDlciNiwfSpvcRemoteAddress,
--           frAtmCustomerIdentifier,
--           frAtmDlciCorrelationTag,
--           frAtmVFramerLogicalProcessor,
--           frAtmFramerUsageState,
--           frAtmLmiOpProcedures,
--           frAtmFramerNormPrioLinkUtilFromIf,
--           frAtmDlciSiwfSdMode,
--           frAtmDlciEgSpMeasurementInterval,
--           frAtmDlciOperationalState,
--           frAtmCaSdFecnToEfciMapping,
--           frAtmFramerInterfaceName,
--           frAtmDlciDiscExcessFromIfBytes,
--           frAtmDlciSiwfSdDeToClpMapping,
--           frAtmDlciSiwfSPvcStorageType,
--           frAtmUnknownDlciFramesFromIf,
--           frAtmDlciNiwfNdComponentName,
--           frAtmFramerOperationalState,
--           frAtmDlciSiwfQoSEmissionPriorityToIf,
--           frAtmCaSiwfEmissionPriorityToIf,
--           frAtmFramerFrmModeErrors,
--           frAtmDlciSiwfAtmConStorageType,
--           frAtmLmiProtocolStatus,
--           frAtmLmiProtocolErrors,
--           frAtmDlciBecnFrmSetByService,
--           frAtmDlciDiscDeCongestedToIf,
--           frAtmFramerLrcErrors,
--           frAtmAddrStorageType,
--           frAtmDlciNiwfQoSTransferPriority,
--           frAtmLmiFullStatusEnqToIf,
--           frAtmDlciSiwfRemoteConnectionIdentifier,
--           frAtmDlciStartTime,
--           frAtmLmiRowStatus,
--           frAtmFramerAborts,
--           frAtmDlciSiwfAssignedBandwidthPool,
--           frAtmDlciABitStatusToIf,
--           frAtmDlciSiwfFecnToEfciMapping,
--           frAtmDlciSiwfQoSComponentName,
--           frAtmCaRowStatus,
--           frAtmInvalidHeaderFramesFromIf,
--           frAtmDlciSiwfComponentName,
--           frAtmLmiUsageState,
--           frAtmDlciEgSpStorageType,
--           frAtmAlarmStatus,
--           frAtmDlciEmissionPriorityToIf,
--           frAtmCaPoolProvBwValue,
--           frAtmDlciDiscFrameAbit,
--           frAtmDlciTotalIngressFrames,
--           frAtmDlciDeBytesToIf,
--           frAtmDlciSiwfSdStorageType,
--           frAtmDlciSiwfAtmConRowStatus,
--           frAtmDlciDiscCongestedToIf,
--           frAtmDlciAccountingEnabled,
--           frAtmDlciDeFrmToIf,
--           frAtmLmiOperationalState,
--           frAtmDlciNiwfSpvcCorrelationTag,
--           frAtmDlciNiwfTransferPriority,
--           frAtmFramerOctetFromIf,
--           frAtmFramerNormPrioLinkUtilToIf,
--           frAtmDlciDiscByteAbit,
--           frAtmDlciTotalIngressBytes,
--           frAtmDlciTotalEgressFrames,
--           frAtmLmiMessageCountTimer,
--           frAtmLmiSide,
--           frAtmDlciDlciType,
--           frAtmDlciSpMeasurementInterval,
--           frAtmCaOverrideLinkRate,
--           frAtmDlciSiwfRemoteAddress,
--           frAtmCaNdDeToClpMapping,
--           frAtmDlciSiwfNPvcStorageType,
--           frAtmLmiNoStatusReportCount,
--           frAtmDlciNiwfNdRowStatus,
--           frAtmDlciSiwfPeakCellRate01,
--           frAtmFramerOverruns,
--           frAtmCaComponentName,
--           frAtmDlciTotalEgressBytes,
--           frAtmDlciBytesToIf,
--           frAtmDlciSiwfLastUnknown1483ProtocolHeader,
--           frAtmNumberOfEmissionQs,
--           frAtmDlciSiwfMaximumBurstSize0,
--           frAtmDlciFrmToIf,
--           frAtmLmiSequenceErrors,
--           frAtmVFramerAdminState,
--           frAtmDlciMeasurementInterval,
--           frAtmDlciSiwfUnknown1490Frames,
--           frAtmDlciEfciFrmFromNetwork,
--           frAtmVFramerOctetFromOtherVFramer,
--           frAtmCaSdMode,
--           frAtmDlciDiscCongestedFromIfBytes,
--           frAtmCaAccountCollection,
--           frAtmVFramerFrmToOtherVFramer,
--           frAtmFramerFrmToIf,
--           frAtmDlciNiwfSpvcStorageType,
--           frAtmDlciEirIngressBytes,
--           frAtmDlciEirEgressFrames,
--           frAtmCaSdDeToClpMapping,
--           frAtmDlciNiwfQoSComponentName,
--           frAtmLmiStatusSequenceErrors,
--           frAtmDlciEgSpExcessBurstSize,
--           frAtmDlciNiwfNdStorageType,
--           frAtmDlciSpMaximumFrameSize,
--           frAtmDlciSiwfQoSRowStatus,
--           frAtmDlciSiwfVccClearCause,
--           frAtmCaNiwfEmissionPriorityToIf,
--           frAtmDlciEirEgressBytes,
--           frAtmDlciSiwfRowStatus,
--           frAtmDlciSpStorageType,
--           frAtmDlciFecnFrmFromIf,
--           frAtmDlciSiwfSPvcRemoteConnectionIdentifier,
--           frAtmDlciNiwfSpvcRemoteDlci,
--           frAtmCaAccountClass,
--           frAtmLmiEventCount,
--           frAtmDlciSiwfPeakCellRate0,
--           frAtmDlciSiwfVccCauseDiag,
--           frAtmLmiCheckPointTimer,
--           frAtmDlciSpCommittedBurstSize,
--           frAtmLmiUserSideEventHistory,
--           frAtmLmiKeepAliveStatusToIf,
--           frAtmDlciStorageType,
--           frAtmSnmpOperStatus,
--           frAtmDlciSiwfAtmConNextHop,
--           frAtmDlciSiwfLastUnknown1490ProtocolHeader,
--           frAtmIfIndex,
--           frAtmDlciABitReasonToIf,
--           frAtmLmiFullStatusPollingCycles,
--           frAtmDlciErrorShortBytesFromIf,
--           frAtmDlciSiwfSPvcComponentName,
--           frAtmFramerStorageType,
--           frAtmDlciNiwfNdDeToClpMapping,
--           frAtmDlciErrorShortFrmFromIf,
--           frAtmDlciCommittedBurstSize,
--           frAtmFramerCrcErrors,
--           frAtmLmiErrorEventThreshold,
--           frAtmDlciSpRateEnforcement,
--           frAtmLmiUnexpectedReports,
--           frAtmDlciSiwfAtmConComponentName,
--           frAtmDlciSiwfDeToClpMapping,
--           frAtmCaTpmComponentName,
--           frAtmCaTpmStorageType,
--           frAtmFramerAdminState,
--           frAtmLmiAsyncStatusReport,
--           frAtmControlStatus,
--           frAtmFramerLargeFrmErrors,
--           frAtmFrmToIfByQueueValue,
--           frAtmCaNdClpToDeMapping,
--           frAtmDlciRateEnforcement,
--           frAtmDlciSiwfSPvcRemoteAddress,
--           frAtmCaCallAdmissionControl,
--           frAtmDlciBecnFrmFromIf,
--           frAtmCaLinkRate,
--           frAtmDlciSpExcessBurstSize,
--           frAtmCaStorageType,
--           frAtmDlciNiwfQoSRowStatus,
--           frAtmFramerNonOctetErrors,
--           frAtmDlciNiwfSpvcComponentName,
--           frAtmDlciEirIngressFrames,
--           frAtmDlciTroubled,
--           frAtmDlciNiwfRowStatus,
--           frAtmUsageState,
--           frAtmDlciSiwfSdComponentName,
--           frAtmDlciSiwfTrafficParmConvPolicy,
--           frAtmDlciAccountingEnd,
--           frAtmCaTroubledDlcis,
--           frAtmLmiStorageType,
--           frAtmLmiKeepAliveStatusEnqFromIf,
--           frAtmDlciDiscExcessFromIf,
--           frAtmDlciExcessBurstSize,
--           frAtmDlciSiwfType,
--           frAtmDlciSiwfSustainedCellRate0,
--           frAtmDlciEgSpComponentName,
--           frAtmLmiFullStatusToIf,
--           frAtmVFramerUsageState,
--           frAtmOperationalState,
--           frAtmCaSiwfTransferPriority,
--           frAtmDlciSiwfSdClpToDeMapping,
--           frAtmDlciDiscDeCongestedToIfBytes,
--           frAtmVFramerComponentName,
--           frAtmLmiAdminState,
--           frAtmDlciNiwfSpvcRowStatus,
--           frAtmCaNailedUpPvcs,
--           frAtmDlciSiwfNPvcComponentName,
--           frAtmDlciTroubledReason,
--           frAtmDlciEgSpCommittedBurstSize,
--           frAtmDlciSiwfSPvcRowStatus,
--           frAtmDlciSiwfNPvcConnectionToAtm,
--           frAtmDlciSiwfMode,
--           frAtmDlciSiwfMaximumBurstSize01,
--           frAtmAvailabilityStatus,
--           frAtmDlciEgSpCommittedInformationRate,
--           frAtmComponentName,
--           frAtmDlciAdminState,
--           frAtmDlciSiwfClpToDeMapping,
--           frAtmCaTpmRowStatus,
--           frAtmDlciElapsedDifference,
--           frAtmDlciSiwfSPvcCorrelationTag,
--           frAtmDlciDiscCongestedToIfBytes,
--           frAtmVFramerOtherVirtualFramer,
--           frAtmDlciSiwfNPvcAtmConnection,
--           frAtmCaPoolAdmitBwValue,
--           frAtmDlciNiwfAvgFrameSize,
--           frAtmFramerFlagsBetweenFrames,
--           frAtmDlciSpCommittedInformationRate }
-- STATUS  mandatory
-- DESCRIPTION
--   "A list of all current accessible leaf objects."

frameRelayAtmGroup OBJECT IDENTIFIER ::= { frameRelayAtmMIB 1 }
frameRelayAtmGroupBE OBJECT IDENTIFIER ::= { frameRelayAtmGroup 5 }
frameRelayAtmGroupBE01 OBJECT IDENTIFIER ::= { frameRelayAtmGroupBE 2 }
frameRelayAtmGroupBE01A OBJECT IDENTIFIER ::= { frameRelayAtmGroupBE01 2 }



-- Agent-Capabilities Statement:

-- PRODUCT-RELEASE "Passport Release 7.0 FrameRelayAtm."
-- STATUS          mandatory
-- DESCRIPTION     "FrameRelayAtm MIB: MIB Version BE01A,
--                  Software Version BG00S4C."
-- SUPPORTS        Nortel-Magellan-Passport-FrameRelayAtmMIB
--    INCLUDES     { frameRelayAtmGroupBE01A }

frameRelayAtmCapabilities OBJECT IDENTIFIER ::= { frameRelayAtmMIB 3 }
frameRelayAtmCapabilitiesBE OBJECT IDENTIFIER ::= { frameRelayAtmCapabilities 5 }
frameRelayAtmCapabilitiesBE01 OBJECT IDENTIFIER ::= { frameRelayAtmCapabilitiesBE 2 }
frameRelayAtmCapabilitiesBE01A OBJECT IDENTIFIER ::= { frameRelayAtmCapabilitiesBE01 2 }





END
