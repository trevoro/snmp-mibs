SM7-10MIB DEFINITIONS ::= BEGIN

-- Initial version. 10/1/98
-- Second turn 10/2/98  added another trap
-- Third version. 10/20/98
-- Fourth version 10/23/98  Changes in this version are
--                                      1) Deleted the FRU code from the MIB
--                                      2) The deviceUserLabel WILL BE the same as the Storage Array Name.
--                            3) Fixed typos.
--                                      4) The deviceErrorCode WILL BE the same as the MEL event number.
-- The changes came from a meeting held on 10/22/98.
-- Changes to add componentType and componentLocation 08/11/00
--
-- New version of the mib.  The mibs has been renumbered. 10/28/98
-- New version of the mib.  The mib has been renumbered to 204 08/11/00


	  IMPORTS
	      OBJECT-TYPE               FROM RFC-1212
	      TRAP-TYPE                 FROM RFC-1215
	      DisplayString             FROM RFC1213-MIB
	      IpAddress, enterprises    FROM RFC1155-SMI;

symbios   OBJECT IDENTIFIER ::= { enterprises 1123 }
wichita   OBJECT IDENTIFIER ::= { symbios 1 }
ftcollins OBJECT IDENTIFIER ::= { symbios 2 }
cosprings OBJECT IDENTIFIER ::= { symbios 3 }

sm7-10 OBJECT IDENTIFIER ::= { wichita 204 }

	infoTable OBJECT-TYPE
		 SYNTAX  SEQUENCE OF InfoEntry
		 ACCESS  not-accessible 
		 STATUS  mandatory
		 DESCRIPTION
		      "Information for array traps."
		 ::= { sm7-10 1 }

	infoEntry OBJECT-TYPE
		 SYNTAX InfoEntry
		 ACCESS not-accessible
		 STATUS mandatory
		 DESCRIPTION
		     "The data for array traps."
		 INDEX  { deviceHostIP }
		 ::= { infoTable 1 }     
	
	
	
	InfoEntry ::= 
	SEQUENCE {
		deviceHostIP
			IpAddress,
		deviceHostName
			DisplayString,
		deviceUserLabel
			DisplayString,
		deviceErrorCode
			DisplayString,
		eventTime
			DisplayString,
		trapDescription
			DisplayString,
		componentType
			DisplayString,
		componentLocation
			DisplayString
	}			
	deviceHostIP OBJECT-TYPE
		SYNTAX IpAddress
		ACCESS read-only
		STATUS mandatory
		DESCRIPTION 
			"Address of the network-attached device or device host."
		::= { infoEntry 1 }

	deviceHostName OBJECT-TYPE
		SYNTAX DisplayString (SIZE (0..17))
		ACCESS read-only
		STATUS mandatory
		DESCRIPTION
			"The user label for the host of the device being reported on."
		::= { infoEntry 2 }
		
	deviceUserLabel OBJECT-TYPE
		SYNTAX DisplayString (SIZE (0..17))
		ACCESS read-only
		STATUS mandatory
		DESCRIPTION
			"The user label for the device being reported on."
		::= { infoEntry 3 }

	deviceErrorCode OBJECT-TYPE
		SYNTAX DisplayString (SIZE (0..19))
		ACCESS read-only
		STATUS mandatory
		DESCRIPTION
			"The error code as reported by the device or host."
		::= { infoEntry 4 }

	eventTime OBJECT-TYPE
		SYNTAX DisplayString (SIZE (0..39))
		ACCESS read-only
		STATUS mandatory
		DESCRIPTION 
			"The time at which the event happen on the device."
		::= { infoEntry 5 }

	trapDescription OBJECT-TYPE
		SYNTAX DisplayString (SIZE (0..69))
		ACCESS read-only
		STATUS mandatory
		DESCRIPTION 
			"A string to indicate the nature of the trap"
		::= { infoEntry 6 }

	componentType OBJECT-TYPE
		SYNTAX DisplayString (SIZE (0..59))
		ACCESS read-only
		STATUS mandatory
		DESCRIPTION 
			"A string to identify the failing component type"
		::= { infoEntry 7 }

	componentLocation OBJECT-TYPE
		SYNTAX DisplayString (SIZE (0..39))
		ACCESS read-only
		STATUS mandatory
		DESCRIPTION 
			"A string to identify the location of the failing component"
		::= { infoEntry 8 }

	

--End of items in the info table


--
--      TRAP Definitions
--

	storageArrayCritical TRAP-TYPE
		ENTERPRISE sm7-10
		VARIABLES  { deviceHostIP, deviceHostName, deviceUserLabel, deviceErrorCode, eventTime, trapDescription, componentType, componentLocation }
		DESCRIPTION
			"This trap indicates an event where user-interaction is required immediately.
			Some example events are component failures or critical errors."
		::= 1
      END
