--
--  Title:  Appian Ethernet MIB
--
--  Dated:  11/8/99
--  Author: D. Theriault
--
--  Description:
--
--  This MIB file contains the definitions and support for the Appian
--  Optical Services Access Platform(s).
--
--  The Ethernet MIB is a single table supporting counter statistics for
--  the access ports.  Statistics support both the dot3 transmission MIB
--  as well as RMON-1 etherStats group which are combined into the Appian
--  specific Ethernet MIB as a single table.
--
APPIAN-PPORT-ETHERNET-MIB DEFINITIONS ::= BEGIN

    IMPORTS

        acPport, AcOpStatus, AcAdminStatus,
        AcSlotNumber, AcPortNumber, AcNodeId            FROM APPIAN-SMI-MIB

        acChassisCurrentTime, acChassisRingId           FROM APPIAN-CHASSIS-MIB

        MODULE-IDENTITY, OBJECT-TYPE, Counter64,
        Counter32, NOTIFICATION-TYPE                    FROM SNMPv2-SMI

        TEXTUAL-CONVENTION, TruthValue,PhysAddress,
        DisplayString                                   FROM SNMPv2-TC;
        

acEnet  MODULE-IDENTITY

    LAST-UPDATED    "0002231600Z"
    ORGANIZATION    "Appian Communications, Inc."
    CONTACT-INFO    "Douglas Theriault"

    DESCRIPTION     "Appian Communications Ethernet Access MIB which contains
                    the configuration and statistics attributes for an 802.3
                    physical interface."

    REVISION        "0002231600Z"

    DESCRIPTION     "Draft revision, Engineering use only."

    ::= { acPport 3 }

    --
    --  Common Textual Conventions for Ethernet
    --
    AcEnetSpeed ::= TEXTUAL-CONVENTION
    STATUS  current
    DESCRIPTION
    "The physical speed of this 802.3 port expressed as an integer 
    enumeration."
    SYNTAX  INTEGER {
                mb10(1), 
                mb100(2), 
                gb1(3)
            }
    
    AcEnetDuplexity ::= TEXTUAL-CONVENTION
    STATUS  current
    DESCRIPTION
    "The duplexity mode for the 802.3 interface.  The interface can be 
    configured for auto(1), full(2), or half(3) duplex mode.  Auto is the
    default and when set will negotiate with the far end for proper mode."
    SYNTAX  INTEGER {
                full(1),
                half(2)
            }
            
    AcEnetLinkState  ::= TEXTUAL-CONVENTION
    STATUS  current
    DESCRIPTION
    "Attribute which identifies the current physical state of the link."
    SYNTAX  INTEGER {
                unknown(0),
                link(1),
                nolink(2)
            }
    
-- 
-- Ethernet Statistics MIB
-- 
acEnetStatsTable    OBJECT-TYPE
    SYNTAX          SEQUENCE OF AcEnetStatsEntry
    MAX-ACCESS      not-accessible
    STATUS          current
    DESCRIPTION
    "A table containing the statistics parameters for 10/100Mb and 1Gb
    Ethernet access ports.  The index keys used in this table (slot.port)
    are mapped to ifIndex under the appian(2785).interfaces(4).ifTable(1)
    group.  The statistics table will be automatically created by the 
    access driver, regardless if configuration exists on the port or not."

    ::= { acEnet 1 }
    
acEnetStatsEntry        OBJECT-TYPE
    SYNTAX          AcEnetStatsEntry
    MAX-ACCESS      not-accessible
    STATUS          current
    DESCRIPTION
    "A row in the Ethernet Statistics table containing all Ethernet level
    statistics for a specific Ethernet access port. Rows in the statistics
    table are automatically instantiated as soon as an acEnetCfgEntry
    exists."

    INDEX   { acEnetStatsNodeId, acEnetStatsSlot, acEnetStatsPort }

    ::= { acEnetStatsTable 1 }

    AcEnetStatsEntry ::=
        SEQUENCE {
            acEnetStatsNodeId                    AcNodeId,
            acEnetStatsSlot                      AcSlotNumber,
            acEnetStatsPort                      AcPortNumber,
            acEnetStatsPktsRx                    Counter64,
            acEnetStatsPktsTx                    Counter64,
            acEnetStatsOctetsRx                  Counter64,
            acEnetStatsOctetsTx                  Counter64,
            acEnetStatsBcastPktsRx               Counter64,
            acEnetStatsBcastPktsTx               Counter64,
            acEnetStatsMcastPktsRx               Counter64,
            acEnetStatsMcastPktsTx               Counter64,
            acEnetStatsCrcAlignErrors            Counter64,
            acEnetStatsUndersizedPkts            Counter64,
            acEnetStatsOversizedPkts             Counter64,
            acEnetStatsFragmentedPkts            Counter64,
            acEnetStatsJabbers                   Counter64,
            acEnetStatsCollisions                Counter64,
            acEnetStatsPkts64Octets              Counter64,
            acEnetStatsPkts65to127Octets         Counter64,
            acEnetStatsPkts128to255Octets        Counter64,
            acEnetStatsPkts256to511Octets        Counter64,
            acEnetStatsPkts512to1023Octets       Counter64,
            acEnetStatsPkts1024to1518Octets      Counter64,
            acEnetStatsCurrentRxBandwidth        INTEGER,
            acEnetStatsCurrentTxBandwidth        INTEGER,
	    acEnetStatsPausePktsRx               Counter32,
            acEnetStatsPausePktsTx               Counter32,
	    acEnetStatsPkts1519to1522Octets	 Counter64
       }


acEnetStatsNodeId  OBJECT-TYPE
    SYNTAX  AcNodeId
    MAX-ACCESS  accessible-for-notify
    STATUS  current
    DESCRIPTION
    "The node id is the id for this specific node in the OSAP ring."

    ::= { acEnetStatsEntry 1 }

acEnetStatsSlot  OBJECT-TYPE
    SYNTAX  AcSlotNumber
    MAX-ACCESS  accessible-for-notify
    STATUS      current
    DESCRIPTION
    "The slot number within the chassis where this module entry resides."
        
    ::= { acEnetStatsEntry 2 }

acEnetStatsPort  OBJECT-TYPE
    SYNTAX  AcPortNumber
    MAX-ACCESS  accessible-for-notify
    STATUS      current
    DESCRIPTION
    "The port number on the module which represents this instance of an
    Ethernet access port."

    ::= { acEnetStatsEntry 3 }

acEnetStatsPktsRx    OBJECT-TYPE
    SYNTAX  Counter64
    MAX-ACCESS  read-only
    STATUS      current
    DESCRIPTION
    "The total number of packets received on this interface expressed as a
    64bit integer."

    ::= { acEnetStatsEntry 4 }
                                
acEnetStatsPktsTx    OBJECT-TYPE
    SYNTAX  Counter64
    MAX-ACCESS  read-only
    STATUS      current
    DESCRIPTION
    "The total number of packets transmitted on this interface expressed 
    as a 64bit integer."

    ::= { acEnetStatsEntry 5 }

acEnetStatsOctetsRx  OBJECT-TYPE
    SYNTAX  Counter64
    MAX-ACCESS  read-only
    STATUS      current
    DESCRIPTION
    "The total number of octets (bytes) received on this interface 
    expressed as a 64bit integer."

    ::= { acEnetStatsEntry 6 }

acEnetStatsOctetsTx  OBJECT-TYPE
    SYNTAX  Counter64
    MAX-ACCESS  read-only
    STATUS      current
    DESCRIPTION
    "The total number of octets (bytes) transmitted on this interface 
    expressed as a 64bit integer."

    ::= { acEnetStatsEntry 7 }

acEnetStatsBcastPktsRx   OBJECT-TYPE
    SYNTAX  Counter64
    MAX-ACCESS  read-only
    STATUS      current
    DESCRIPTION
    "The total number of broadcast packets received on this interface 
    expressed as a 64bit integer."

    ::= { acEnetStatsEntry 8 }

acEnetStatsBcastPktsTx   OBJECT-TYPE
    SYNTAX  Counter64
    MAX-ACCESS  read-only
    STATUS      current
    DESCRIPTION
    "The total number of broadcast packets transmitted on this interface 
    expressed as a 64bit integer."

    ::= { acEnetStatsEntry 9 }

acEnetStatsMcastPktsRx   OBJECT-TYPE
    SYNTAX  Counter64
    MAX-ACCESS  read-only
    STATUS      current
    DESCRIPTION
    "The total number of Multicast packets received on this interface 
    expressed as a 64bit integer."

    ::= { acEnetStatsEntry 10 }

acEnetStatsMcastPktsTx   OBJECT-TYPE
    SYNTAX  Counter64
    MAX-ACCESS  read-only
    STATUS      current
    DESCRIPTION
    "The total number of Multicast packets transmitted on this interface 
    expressed as a 64bit integer."

    ::= { acEnetStatsEntry 11 }

acEnetStatsCrcAlignErrors    OBJECT-TYPE
    SYNTAX  Counter64
    MAX-ACCESS  read-only
    STATUS      current
    DESCRIPTION
    "The total number of CRC alignment errors received on this interface 
    expressed as a 64bit integer."

    ::= { acEnetStatsEntry 12 }

acEnetStatsUndersizedPkts    OBJECT-TYPE
    SYNTAX  Counter64
    MAX-ACCESS  read-only
    STATUS      current
    DESCRIPTION
    "The total number of packets received on this interface which were 
    below a minimum 64byte length, expressed as a 64bit integer."

    ::= { acEnetStatsEntry 13 }

acEnetStatsOversizedPkts OBJECT-TYPE
    SYNTAX  Counter64
    MAX-ACCESS  read-only
    STATUS      current
    DESCRIPTION
    "The total number of packets received on this interface which were 
    determined to be greater than 1522 bytes in length, expressed as a
    64bit integer."

    ::= { acEnetStatsEntry 14 }

acEnetStatsFragmentedPkts    OBJECT-TYPE
    SYNTAX  Counter64
    MAX-ACCESS  read-only
    STATUS      current
    DESCRIPTION
    "The total number of fragmented frames detected on this interface 
    expressed as a 64bit integer."
    
    ::= { acEnetStatsEntry 15 }

acEnetStatsJabbers   OBJECT-TYPE
    SYNTAX  Counter64
    MAX-ACCESS  read-only
    STATUS      current
    DESCRIPTION
    "The total number of babbling jabbers detected on this interface, 
    expressed as a 64bit integer."

    ::= { acEnetStatsEntry 16 }

acEnetStatsCollisions    OBJECT-TYPE
    SYNTAX  Counter64
    MAX-ACCESS  read-only
    STATUS      current
    DESCRIPTION
    "The total number of collisions detected on this interface during
    transmission attempts which have exceeded the maximum count of (16)
    per frame.  This counter is expressed as a 64bit integer."

    ::= { acEnetStatsEntry 17 }

acEnetStatsPkts64Octets  OBJECT-TYPE
    SYNTAX  Counter64
    MAX-ACCESS  read-only
    STATUS      current
    DESCRIPTION
    "The total number of frames transmitted and received which were 
    exactly 64 bytes in length.  This counter is expressed as a 
    64bit integer. This allows us to support the RMON mib."

    ::= { acEnetStatsEntry 18 }

acEnetStatsPkts65to127Octets OBJECT-TYPE
    SYNTAX  Counter64
    MAX-ACCESS  read-only
    STATUS      current
    DESCRIPTION
    "The total number of packets transmitted and received on this 
    interface which were between 65 and 127 bytes in length, 
    expressed as a 64bit integer. This allows us to support the 
    RMON mib."

    ::= { acEnetStatsEntry 19 }

acEnetStatsPkts128to255Octets    OBJECT-TYPE
    SYNTAX  Counter64
    MAX-ACCESS  read-only
    STATUS      current
    DESCRIPTION
    "The total number of packets transmitted and received on this 
    interface which were between 128 and 255 bytes in length, 
    expressed as a 64bit integer.  This allows us to support the 
    RMON mib."

    ::= { acEnetStatsEntry 20 }

acEnetStatsPkts256to511Octets    OBJECT-TYPE
    SYNTAX  Counter64
    MAX-ACCESS  read-only
    
    STATUS      current
    DESCRIPTION
    "The total number of packets transmitted and received on this 
    interface which were between 256 and 511 bytes in length, 
    expressed as a 64bit integer.  This allows us to support the 
    RMON mib."

    ::= { acEnetStatsEntry 21 }

acEnetStatsPkts512to1023Octets   OBJECT-TYPE
    SYNTAX  Counter64
    MAX-ACCESS  read-only
    STATUS      current
    DESCRIPTION
    "The total number of packets transmitted and received on this 
    interface which were between 512 and 1023 bytes in length, 
    expressed as a 64bit integer.  This allows us to support the 
    RMON mib."

    ::= { acEnetStatsEntry 22 }

acEnetStatsPkts1024to1518Octets  OBJECT-TYPE
    SYNTAX  Counter64
    MAX-ACCESS  read-only
    STATUS      current
    DESCRIPTION
    "The total number of packets transmitted and received on this 
    interface which were between 1024 and 1518 bytes in length, 
    expressed as a 64bit integer.  This allows us to support the 
    RMON mib."

    ::= { acEnetStatsEntry 23 }

acEnetStatsCurrentRxBandwidth    OBJECT-TYPE
    SYNTAX  INTEGER
    MAX-ACCESS  read-only
    STATUS      current
    DESCRIPTION
    "The current receive bandwidth expressed as a percentage value between
    0 and 100%.  Bandwidth is calculated by the ethernet driver upon the 
    request for this attribute.  The value is calculated by the equation:

            bw = (( octets-rx-delta / speed ) / 100 )
    The delta counter is a value kept internally by the driver and not
    exposed in the MIB.  
    
    The bandwidth value is represented as a whole number only."

    ::= { acEnetStatsEntry 24 }

acEnetStatsCurrentTxBandwidth    OBJECT-TYPE
    SYNTAX  INTEGER
    MAX-ACCESS  read-only
    STATUS      current
    DESCRIPTION
    "The current transmit bandwidth expressed as a percentage value between
    0 and 100%.  Bandwidth is calculated by the ethernet driver upon the 
    request for this attribute.  The value is calculated by the equation:

            bw = (( octets-tx-delta / speed ) / 100 )

    The delta counter is a value kept internally by the driver and not
    exposed in the MIB.  

    The bandwidth value is represented as a whole number only."

    ::= { acEnetStatsEntry 25 }

acEnetStatsPausePktsRx OBJECT-TYPE
    SYNTAX      Counter32
    MAX-ACCESS  read-only
    STATUS      current
    DESCRIPTION "A count of MAC Control frames received on this
                 interface with an opcode indicating the PAUSE
                 operation.

                 This counter does not increment when the
                 interface is operating in half-duplex mode.

                 Discontinuities in the value of this counter can
                 occur at re-initialization of the management
                 system, and at other times."
    REFERENCE   "[IEEE 802.3 Std.], 30.3.4.3,
                 aPAUSEMACCtrlFramesReceived."
    ::= { acEnetStatsEntry 26 }

acEnetStatsPausePktsTx OBJECT-TYPE
    SYNTAX      Counter32
    MAX-ACCESS  read-only
    STATUS      current
    DESCRIPTION "A count of MAC Control frames transmitted on
                 this interface with an opcode indicating the
                 PAUSE operation.

                 This counter does not increment when the
                 interface is operating in half-duplex mode.

                 Discontinuities in the value of this counter can
                 occur at re-initialization of the management
                 system, and at other times."
    REFERENCE   "[IEEE 802.3 Std.], 30.3.4.2,
                 aPAUSEMACCtrlFramesTransmitted."
    ::= { acEnetStatsEntry 27 }

acEnetStatsPkts1519to1522Octets  OBJECT-TYPE
    SYNTAX  Counter64
    MAX-ACCESS  read-only
    STATUS      current
    DESCRIPTION
    "The total number of packets transmitted and received on this 
    interface which were between 1519 and 1522 bytes in length, 
    expressed as a 64bit integer.  This allows us to support the 
    RMON mib."

    ::= { acEnetStatsEntry 28 }

 --
 -- Ethernet Configuration Record
 --
acEnetCfgTable  OBJECT-TYPE
    SYNTAX  SEQUENCE OF AcEnetCfgEntry
    MAX-ACCESS  not-accessible
    STATUS      current
    DESCRIPTION
    "A table of configuration instances for Ethernet Access ports.  This 
    table is automatically created based on what hardware is installed in the 
    slot."

    ::= { acEnet 2 }

acEnetCfgEntry OBJECT-TYPE
    SYNTAX  AcEnetCfgEntry
    MAX-ACCESS  not-accessible
    STATUS      current
    DESCRIPTION
    "A row which contains the configuration parameters for an Ethernet Access
    port.  These rows must be created by the EMS or CLI, and are not
    automatically instantiated by default."

    INDEX { acEnetCfgNodeId, acEnetCfgSlot, acEnetCfgPort }

    ::= { acEnetCfgTable 1 }

    AcEnetCfgEntry ::=
        SEQUENCE {
            acEnetCfgNodeId                     AcNodeId,
            acEnetCfgSlot                       AcSlotNumber,
            acEnetCfgPort                       AcPortNumber,
            acEnetCfgAdminStatus                AcAdminStatus,
            acEnetCfgOpStatus                   AcOpStatus,
            acEnetCfgOpCode                     INTEGER,
            acEnetCfgStatsReset                 TruthValue,
            acEnetCfgMediaType                  INTEGER,
            acEnetCfgPhysicalAddress            PhysAddress,
            acEnetCfgActiveMediaSlot            AcSlotNumber,
            acEnetCfgStandbyMediaSlot           AcSlotNumber,
            acEnetCfgMultiServiceEnable         TruthValue,
            acEnetCfgSpeed                      AcEnetSpeed,
            acEnetCfgDuplexity                  AcEnetDuplexity,
            acEnetCfgCurrentSpeed               AcEnetSpeed,
            acEnetCfgCurrentDuplexity           AcEnetDuplexity,
            acEnetCfgInterfaceName              DisplayString,
            acEnetCfgLinkState                  AcEnetLinkState,
            acEnetCfgAutoNegotiate              TruthValue,
            acEnetCfgPauseAdminMode             INTEGER,
            acEnetCfgPauseOperMode              INTEGER
        }
--
-- Ethernet Access Entries
--

acEnetCfgNodeId  OBJECT-TYPE
    SYNTAX  AcNodeId
    MAX-ACCESS  accessible-for-notify
    STATUS  current
    DESCRIPTION
    "The node id is the id for this specific node in the OSAP ring."

    ::= { acEnetCfgEntry 1 }

acEnetCfgSlot  OBJECT-TYPE
    SYNTAX  AcSlotNumber
    MAX-ACCESS  accessible-for-notify
    STATUS      current
    DESCRIPTION
    "The physical I/O slot where this access port is located."
    
    ::= { acEnetCfgEntry 2 }

acEnetCfgPort  OBJECT-TYPE
    SYNTAX  AcPortNumber
    MAX-ACCESS  accessible-for-notify
    STATUS      current
    DESCRIPTION
    "The physical connector on the I/O module for this Ethernet port."
    
    ::= { acEnetCfgEntry 3 }
    
acEnetCfgAdminStatus  OBJECT-TYPE
    SYNTAX  AcAdminStatus
    MAX-ACCESS  read-create
    STATUS      current
    DESCRIPTION
    "Appian Administrative Status attribute used to set the provisioning
    state as either activate(1), inactivate(2) or delete(3).  Refer to
    the Appian-SMI.mib file for additional information.

    Setting acEnetCfgAdminStatus to inactivate(2) disables the ethernet
    port."
    
    DEFVAL { inactivate }
    
    ::= { acEnetCfgEntry 4 }

acEnetCfgOpStatus  OBJECT-TYPE     
    SYNTAX  AcOpStatus
    MAX-ACCESS  read-only
    STATUS      current
    DESCRIPTION
    "The current operational status for the Ethernet module controlling 
    this port."

    ::= { acEnetCfgEntry 5 }
    
acEnetCfgOpCode  OBJECT-TYPE     
    SYNTAX  INTEGER
    MAX-ACCESS  read-only
    STATUS      current
    DESCRIPTION
    "Provides a detailed status code which can be used to isolate a problem
    or state condition reported in acEnetCfgOpStatus."

    ::= { acEnetCfgEntry 6 }

acEnetCfgStatsReset    OBJECT-TYPE
    SYNTAX  TruthValue
    MAX-ACCESS  read-create
    STATUS      current
    DESCRIPTION
    "Setting this attribute to True(1) will force all statistics for this
    row to be cleared and set to zero (0) values.  Used for debugging, 
    clearing statistics can trouble with trending and long term statistics
    collection by AppianVista or 3rd party trending tools.
    
    Note:  Reading this attribute will always return false()."

    DEFVAL { false }
    
    ::= { acEnetCfgEntry 7 }

acEnetCfgMediaType OBJECT-TYPE
    SYNTAX  INTEGER {
                unknown(0),
                mbe(1), 
                gbe(2)
            }
    MAX-ACCESS  read-only
    STATUS      current
    DESCRIPTION
    "Attribute to determine if this module is a 10mb/100mb or 1gb interface."
    
    ::= { acEnetCfgEntry 8 }

acEnetCfgPhysicalAddress  OBJECT-TYPE
    SYNTAX  PhysAddress (SIZE (0..13))
    MAX-ACCESS  read-only
    STATUS      current
    DESCRIPTION
    "The physical address (MAC Address) assigned to this physical Ethernet
    port."
    
    ::= { acEnetCfgEntry 9 }

acEnetCfgActiveMediaSlot  OBJECT-TYPE
    SYNTAX  AcSlotNumber
    MAX-ACCESS  read-only
    STATUS      current
    DESCRIPTION
    "This object identifies the slot in the chassis carrying the active media
    board for this port."

    ::= { acEnetCfgEntry 10 }

acEnetCfgStandbyMediaSlot  OBJECT-TYPE
    SYNTAX  AcSlotNumber
    MAX-ACCESS  read-only
    STATUS      current
    DESCRIPTION
    "This object identifies the slot in the chassis carrying the standby media
    board for this port."
    
    ::= { acEnetCfgEntry 11 }

acEnetCfgMultiServiceEnable OBJECT-TYPE
    SYNTAX  TruthValue
    MAX-ACCESS  read-create
    STATUS      current
    DESCRIPTION
    "Flag used to enable or disable multi-service for this Ethernet access
    port.  When set to True(2), the port is used for multi-service."

    DEFVAL { false }
    
    ::= { acEnetCfgEntry 12 }

acEnetCfgSpeed OBJECT-TYPE
    SYNTAX  AcEnetSpeed
    MAX-ACCESS  read-create
    STATUS      current
    DESCRIPTION
    "The desired configured speed of the physical interface."

    DEFVAL { mb100 }

    ::= { acEnetCfgEntry 13 }

acEnetCfgDuplexity OBJECT-TYPE
    SYNTAX  AcEnetDuplexity
    MAX-ACCESS  read-create
    STATUS      current
    DESCRIPTION
    "The desired configured duplexity mode.  By default set to full(1) but for
    interfacing to some older hubs, which do not perform link duplexity 
    negotiation properly, manual configuration may be necessary."

    DEFVAL { full }

    ::= { acEnetCfgEntry 14 }

acEnetCfgCurrentSpeed  OBJECT-TYPE
    SYNTAX  AcEnetSpeed
    MAX-ACCESS  read-only
    STATUS      current
    DESCRIPTION
    "The current operational interface speed for this Ethernet port as
    determined by the MAC PHY interface.  If using Auto Negotiation, the 
    current speed may be different than the configured speed."

    ::= { acEnetCfgEntry 15 }

acEnetCfgCurrentDuplexity  OBJECT-TYPE
    SYNTAX  AcEnetDuplexity
    MAX-ACCESS  read-only
    STATUS      current
    DESCRIPTION
    "The current operational duplexity mode for this Ethernet port as
    determined by the MAC PHY interface.  If using Auto Negotiation, the 
    current duplexity may be different than the configured duplexity."

    ::= { acEnetCfgEntry 16 }
    
acEnetCfgInterfaceName  OBJECT-TYPE
    SYNTAX  DisplayString (SIZE(0..64))
    MAX-ACCESS  read-create
    STATUS      current
    DESCRIPTION
    "The user configurable interface name which is an ASCII string up to
    64 characters in length."

    DEFVAL { "Ethernet Interface" }
    
    ::= { acEnetCfgEntry 17 }

acEnetCfgLinkState OBJECT-TYPE
    SYNTAX  AcEnetLinkState
    MAX-ACCESS  read-only
    STATUS      current
    DESCRIPTION
    "The link state for this physical interface.  Link state is determined
    by the Ethernet PHY logic and indicates whether or not the cable is
    properly connected and signal is present."
    
    ::= { acEnetCfgEntry 18 }

acEnetCfgAutoNegotiate    OBJECT-TYPE
    SYNTAX  TruthValue
    MAX-ACCESS  read-create
    STATUS      current
    DESCRIPTION
    "Setting this attribute to True(1) will force this interface to 
    use Auto Negotiation to determine interface speed and duplexity.
    When set in this mode, the values of acEnetCfgSpeed and 
    acEnetCfgDuplexity will be ignored. The interface shall advertise 
    the ability to run at 10M and 100M, and will advertise both half 
    and full duplex capabilities. When this attribute is set to False(0), 
    the interface will be configured according to the values in the 
    acEnetCfgSpeed and acEnetCfgDuplexity attributes."
    
    DEFVAL { true }
    
    ::= { acEnetCfgEntry 19 }

acEnetCfgPauseAdminMode OBJECT-TYPE
    SYNTAX      INTEGER {
                    disabled(1),
                    enabledXmit(2),
                    enabledRcv(3),
                    enabledXmitAndRcv(4)
                 }
    MAX-ACCESS  read-write
    STATUS      current
    DESCRIPTION "This object is used to configure the default
                 administrative PAUSE mode for this interface.

                 This object represents the
                 administratively-configured PAUSE mode for this
                 interface.  If auto-negotiation is not enabled
                 or is not implemented for the active MAU
                 attached to this interface, the value of this
                 object determines the operational PAUSE mode
                 of the interface whenever it is operating in
                 full-duplex mode.  In this case, a set to this
                 object will force the interface into the
                 specified mode.

                 If auto-negotiation is implemented and enabled
                 for the MAU attached to this interface, the
                 PAUSE mode for this interface is determined by
                 auto-negotiation, and the value of this object
                 denotes the mode to which the interface will
                 automatically revert if/when auto-negotiation is
                 later disabled.

                 Note that the value of this object is ignored
                 when the interface is not operating in
                 full-duplex mode.

                 An attempt to set this object to
                 'enabledXmit(2)' or 'enabledRcv(3)' will fail
                 on interfaces that do not support operation
                 at greater than 100 Mb/s."

    DEFVAL { disabled }

    ::= { acEnetCfgEntry 20 }

acEnetCfgPauseOperMode OBJECT-TYPE
    SYNTAX      INTEGER {
                    disabled(1),
                    enabledXmit(2),
                    enabledRcv(3),
                    enabledXmitAndRcv(4)
                }
    MAX-ACCESS  read-only
    STATUS      current
    DESCRIPTION "This object reflects the PAUSE mode currently
                 in use on this interface, as determined by
                 either (1) the result of the auto-negotiation
                 function or (2) if auto-negotiation is not
                 enabled or is not implemented for the active MAU
                 attached to this interface, by the value of
                 acPauseAdminMode.  Interfaces operating at
                 100 Mb/s or less will never return
                 'enabledXmit(2)' or 'enabledRcv(3)'.  Interfaces
                 operating in half-duplex mode will always return
                 'disabled(1)'.  Interfaces on which
                 auto-negotiation is enabled but not yet
                 completed should return the value
                 'disabled(1)'."
    ::= { acEnetCfgEntry 21 }

-- 
-- Ethernet Trap Definitions
--
--

acEnetTraps   OBJECT IDENTIFIER ::= { acEnet 0 }

acEnetLinkDownTrap  NOTIFICATION-TYPE
    OBJECTS { acChassisCurrentTime, acChassisRingId, acEnetCfgNodeId, 
              acEnetCfgSlot, acEnetCfgPort } 
    STATUS  current
    DESCRIPTION
    "The physical cable for this Ethernet interface has been detected as
    disconnected."
    
    ::= { acEnetTraps 1 }
    

acEnetLinkUpTrap  NOTIFICATION-TYPE
    OBJECTS { acChassisCurrentTime, acChassisRingId, acEnetCfgNodeId, 
              acEnetCfgSlot, acEnetCfgPort }     
    STATUS  current
    DESCRIPTION
    "The physical cable for this Ethernet interface has been detected as
    connected."
        
    ::= { acEnetTraps 2 }


acEnetStatsResetTrap  NOTIFICATION-TYPE 
    OBJECTS { acChassisCurrentTime, acChassisRingId, acEnetCfgNodeId, 
              acEnetCfgSlot, acEnetCfgPort }     
    STATUS  current
    DESCRIPTION
    "The Ethernet statistics for this interface have been reset to zero (0) 
    which may effect long term trending functions monitoring this interface."
    
    ::= { acEnetTraps 3 }


acEnetFailoverTrap  NOTIFICATION-TYPE 
    OBJECTS { acChassisCurrentTime, acChassisRingId, acEnetCfgNodeId, 
              acEnetCfgSlot, acEnetCfgPort, acEnetCfgOpCode } 
    STATUS  current
    DESCRIPTION
    "A failover condition has been detected.  Control has been changed to the
    standby Ethernet media module.  Refer to acEnetCfgActiveMediaSlot and
    acEnetCfgStandbyMediaSlot for active and standby configuration."
    
    ::= { acEnetTraps 4 }


acEnetCfgErrorTrap  NOTIFICATION-TYPE 
    OBJECTS { acChassisCurrentTime, acChassisRingId, acEnetCfgNodeId, 
              acEnetCfgSlot, acEnetCfgPort, acEnetCfgOpCode } 
    STATUS  current
    DESCRIPTION
    "A configuration request to the Ethernet configuration table for an 
    interface has been detected as invalid or corrupt."
    
    ::= { acEnetTraps 5 }
    
--
-- End Appian Ethernet MIB
--

END
