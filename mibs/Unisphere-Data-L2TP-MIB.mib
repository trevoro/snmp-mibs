-- *****************************************************************************
-- Unisphere-Data-L2TP-MIB
--
-- Unisphere Networks Inc. Enterprise MIB
-- Layer Two Tunneling Protocol (L2TP) MIB
--
-- Copyright (c) 2000, 2001 Unisphere Networks, Inc.  All Rights Reserved.
-- *****************************************************************************

Unisphere-Data-L2TP-MIB DEFINITIONS ::= BEGIN

IMPORTS
    MODULE-IDENTITY, OBJECT-TYPE, Integer32, Counter32, Gauge32, Unsigned32,
    IpAddress
        FROM SNMPv2-SMI
    TEXTUAL-CONVENTION, DisplayString, RowStatus, TruthValue
        FROM SNMPv2-TC
    OBJECT-GROUP, MODULE-COMPLIANCE
        FROM SNMPv2-CONF
    InterfaceIndex, InterfaceIndexOrZero
        FROM IF-MIB
    usDataMibs
        FROM Unisphere-Data-MIBs
    UsdEnable
        FROM Unisphere-Data-TC;

usdL2tpMIB MODULE-IDENTITY
    LAST-UPDATED "200110171451Z"  -- 17-Oct-01 10:51 AM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The L2TP MIB for the Unisphere Networks enterprise."
    -- Revision History
    REVISION    "200110171451Z"  -- 17-Oct-01 10:51 AM EDT  - RX 3.3
    DESCRIPTION
        "Added new objects
            usdL2tpSysConfigTunnelSwitchingEnabled,
            usdL2tpSysConfigControlRetransmissions,
            usdL2tpSysConfigTunnelIdleTimeout."
    REVISION    "200110171355Z"  -- 17-Oct-01 09:55 AM EDT  - RX 3.2
    DESCRIPTION
        "Added usdL2tpSysConfigReceiveDataSequencingIgnore."
    REVISION    "200106182000Z"  -- 18-Jun-01 04:00 PM EDT  - RX 3.0
    DESCRIPTION
        "Added usdL2tpSessionStatusLacTunneledIfIndex as long-term
        replacement for usdL2tpSessionStatusLacPppIfIndex.

        Added new objects
            usdL2tpTunnelStatusCumEstabTime,
            usdL2tpSessionStatusCumEstabTime,
            usdL2tpSessionStatPayLostPackets.
        Changed range of usdL2tpSysConfigDestructTimeout to 10-3600."
    REVISION    "200002110000Z"  -- 11-Feb-00               - RX 2.0
    DESCRIPTION
        "Initial revision, based in part on IETF L2TP Working Group
        draft-ietf-l2tpext-l2tp-mib-01."
    ::= { usDataMibs 35 }


-- ++++++++++++++++++++++++++++++++++++++++++++++++++++++++++++++++++++++
-- Textual conventions
-- ++++++++++++++++++++++++++++++++++++++++++++++++++++++++++++++++++++++

UsdL2tpTunnelId ::= TEXTUAL-CONVENTION
    STATUS      current
    DESCRIPTION
        "An L2TP Tunnel ID. Implementation constraints may
        restrict the range of values actually used."
    SYNTAX      Integer32(0..65535)

UsdL2tpSessionId ::= TEXTUAL-CONVENTION
    STATUS      current
    DESCRIPTION
        "An L2TP Session ID. Implementation constraints may restrict the range
        of values actually used."
    SYNTAX      Integer32(0..65535)

UsdL2tpAdminState ::= TEXTUAL-CONVENTION
    STATUS      current
    DESCRIPTION
        "The administrative state exerted on L2TP tunnels sessions at some scope
        of control.

            enabled     New tunnels/sessions may be instantiated.
            disabled    All tunnels/sessions are terminated.
            drain       No new tunnels/sessions may be instantiated, but any
                        existing tunnels/sessions may persist until they expire
                        by other means.

        The DESCRIPTION clause of an object defined to have this syntax must
        describe the scope of control that object exerts (e.g., all
        tunnels/sessions across the system, sessions within a single tunnel,
        etc.)."
    SYNTAX      INTEGER {
                    enabled(0),
                    disabled(1),
                    drain(2)
                }

UsdL2tpTransport ::= TEXTUAL-CONVENTION
    STATUS      current
    DESCRIPTION
        "Transport type over which L2TP is carried."
    SYNTAX      INTEGER {
                    other(0),
                    udpIp(1)
                }

-- ++++++++++++++++++++++++++++++++++++++++++++++++++++++++++++++++++++++
-- Managed object groups
-- ++++++++++++++++++++++++++++++++++++++++++++++++++++++++++++++++++++++

usdL2tpTraps           OBJECT IDENTIFIER  ::= { usdL2tpMIB 0 }
usdL2tpObjects         OBJECT IDENTIFIER  ::= { usdL2tpMIB 1 }
usdL2tpTrapControl     OBJECT IDENTIFIER  ::= { usdL2tpMIB 2 }
usdL2tpConformance     OBJECT IDENTIFIER  ::= { usdL2tpMIB 3 }

--
-- Major subtrees
--
usdL2tpSystem          OBJECT IDENTIFIER  ::= { usdL2tpObjects 1 }
usdL2tpDestination     OBJECT IDENTIFIER  ::= { usdL2tpObjects 2 }
usdL2tpTunnel          OBJECT IDENTIFIER  ::= { usdL2tpObjects 3 }
usdL2tpSession         OBJECT IDENTIFIER  ::= { usdL2tpObjects 4 }
usdL2tpTransport       OBJECT IDENTIFIER  ::= { usdL2tpObjects 5 }


-- ......................................................................
-- L2TP System Group
-- ......................................................................

usdL2tpSystemConfig      OBJECT IDENTIFIER   ::= { usdL2tpSystem 1 }
usdL2tpSystemStatus      OBJECT IDENTIFIER   ::= { usdL2tpSystem 2 }

--
-- L2TP System-level Configuration
--
usdL2tpSysConfigAdminState OBJECT-TYPE
    SYNTAX      UsdL2tpAdminState
    MAX-ACCESS  read-write
    STATUS      current
    DESCRIPTION
        "Exerts control over all L2TP tunnels/sessions in the system."
    ::= { usdL2tpSystemConfig 1 }

usdL2tpSysConfigDestructTimeout OBJECT-TYPE
    SYNTAX      Integer32(10..3600)
    UNITS       "seconds"
    MAX-ACCESS  read-write
    STATUS      current
    DESCRIPTION
        "The amount of time, in seconds, to preserve dynamic tunnels/sessions
        after they become inactive, e.g. to poll their statistics."
    ::= { usdL2tpSystemConfig 2 }

usdL2tpSysConfigIpChecksumEnable OBJECT-TYPE
    SYNTAX      UsdEnable
    MAX-ACCESS  read-write
    STATUS      current
    DESCRIPTION
        "Enable/disable IP checksumming for tunnels with UDP/IP transport."
    ::= { usdL2tpSystemConfig 3 }

usdL2tpSysConfigTunnelSwitchingEnabled OBJECT-TYPE
    SYNTAX      UsdEnable
    MAX-ACCESS  read-write
    STATUS      current
    DESCRIPTION
        "Tunnel switching enabled/disable."
    DEFVAL { disable }
    ::= { usdL2tpSystemConfig 4 }

usdL2tpSysConfigControlRetransmissions OBJECT-TYPE
    SYNTAX      Integer32(3..7)
    MAX-ACCESS  read-write
    STATUS      current
    DESCRIPTION
        "The number of retransmission retries allowed before control session
         goes down."
    DEFVAL { 5 }
    ::= { usdL2tpSystemConfig 5 }

usdL2tpSysConfigTunnelIdleTimeout OBJECT-TYPE
    SYNTAX      Integer32(0..86400)
    UNITS       "seconds"
    MAX-ACCESS  read-write
    STATUS      current
    DESCRIPTION
        "Idle tunnel remains active for the specified amount of time;
         value 0 disables the timer i.e. tunnel becomes persistent."
    DEFVAL { 60 }
    ::= { usdL2tpSystemConfig 6 }

usdL2tpSysConfigReceiveDataSequencingIgnore OBJECT-TYPE
    SYNTAX      UsdEnable
    MAX-ACCESS  read-write
    STATUS      current
    DESCRIPTION
        "Enable/disable ignoring of receive sequencing of L2TP data packets."
    ::= { usdL2tpSystemConfig 7 }

--
-- L2TP System-level Status and Statistics
--

usdL2tpSysStatusProtocolVersion OBJECT-TYPE
    SYNTAX      OCTET STRING (SIZE(2..256))
    MAX-ACCESS  read-only
    STATUS      current
    DESCRIPTION
        "Vector of supported L2TP protocol version and revision numbers.
        Supported versions are identified via a two octet pairing where the
        first octet indicates the version and the second octet contains the
        revision."
    ::= { usdL2tpSystemStatus 1 }

usdL2tpSysStatusVendorName OBJECT-TYPE
    SYNTAX      DisplayString
    MAX-ACCESS  read-only
    STATUS      current
    DESCRIPTION
        "Vendor name of the L2TP protocol stack."
    ::= { usdL2tpSystemStatus 2 }

usdL2tpSysStatusFirmwareRev OBJECT-TYPE
    SYNTAX      Integer32
    MAX-ACCESS  read-only
    STATUS      current
    DESCRIPTION
        "Firmware revision for the L2TP protocol stack."
    ::= { usdL2tpSystemStatus 3 }

usdL2tpSysStatusTotalDestinations OBJECT-TYPE
    SYNTAX      Counter32
    MAX-ACCESS  read-only
    STATUS      current
    DESCRIPTION
        "Number of destination creations attempted."
    ::= { usdL2tpSystemStatus 4 }

usdL2tpSysStatusFailedDestinations OBJECT-TYPE
    SYNTAX      Counter32
    MAX-ACCESS  read-only
    STATUS      current
    DESCRIPTION
        "Number of destination creation attempts that failed."
    ::= { usdL2tpSystemStatus 5 }

usdL2tpSysStatusActiveDestinations OBJECT-TYPE
    SYNTAX      Gauge32
    MAX-ACCESS  read-only
    STATUS      current
    DESCRIPTION
        "Number of destinations having at least one active tunnel."
    ::= { usdL2tpSystemStatus 6 }

usdL2tpSysStatusTotalTunnels OBJECT-TYPE
    SYNTAX      Counter32
    MAX-ACCESS  read-only
    STATUS      current
    DESCRIPTION
        "Number of tunnel creations attempted."
    ::= { usdL2tpSystemStatus 7 }

usdL2tpSysStatusFailedTunnels OBJECT-TYPE
    SYNTAX      Counter32
    MAX-ACCESS  read-only
    STATUS      current
    DESCRIPTION
        "Number of tunnel creation attempts that failed to reach the established
        state."
    ::= { usdL2tpSystemStatus 8 }

usdL2tpSysStatusFailedTunnelAuthens OBJECT-TYPE
    SYNTAX      Counter32
    MAX-ACCESS  read-only
    STATUS      current
    DESCRIPTION
        "Number of tunnel creation attempts that failed authentication."
    ::= { usdL2tpSystemStatus 9 }

usdL2tpSysStatusActiveTunnels OBJECT-TYPE
    SYNTAX      Gauge32
    MAX-ACCESS  read-only
    STATUS      current
    DESCRIPTION
        "Number of tunnels currently established."
    ::= { usdL2tpSystemStatus 10 }

usdL2tpSysStatusTotalSessions OBJECT-TYPE
    SYNTAX      Counter32
    MAX-ACCESS  read-only
    STATUS      current
    DESCRIPTION
        "Number of session creations attempted."
    ::= { usdL2tpSystemStatus 11 }

usdL2tpSysStatusFailedSessions OBJECT-TYPE
    SYNTAX      Counter32
    MAX-ACCESS  read-only
    STATUS      current
    DESCRIPTION
        "Number of session creation attempts that failed to reach the
        established state."
    ::= { usdL2tpSystemStatus 12 }

usdL2tpSysStatusActiveSessions OBJECT-TYPE
    SYNTAX      Gauge32
    MAX-ACCESS  read-only
    STATUS      current
    DESCRIPTION
        "Number of sessions currently established."
    ::= { usdL2tpSystemStatus 13 }

-- ......................................................................
-- L2TP Destination Group
-- ......................................................................

usdL2tpDestConfig      OBJECT IDENTIFIER   ::= { usdL2tpDestination 1 }
usdL2tpDestStatus      OBJECT IDENTIFIER   ::= { usdL2tpDestination 2 }
usdL2tpDestStatistics  OBJECT IDENTIFIER   ::= { usdL2tpDestination 3 }

--
-- Destination-level Configuration
--

-- { usdL2tpDestConfig 1 } reserved for "next ifIndex" acquisition

usdL2tpDestConfigTable   OBJECT-TYPE
    SYNTAX      SEQUENCE OF UsdL2tpDestConfigEntry
    MAX-ACCESS  not-accessible
    STATUS      current
    DESCRIPTION
        "The L2TP destination configuration table.  Each entry in this table has
        a corresponding entry in the Interfaces MIB ifTable, and in
        usdL2tpDestStatsTable."
    ::= { usdL2tpDestConfig 2 }

usdL2tpDestConfigEntry   OBJECT-TYPE
    SYNTAX      UsdL2tpDestConfigEntry
    MAX-ACCESS  not-accessible
    STATUS      current
    DESCRIPTION
        "Describes the configuration attributes of an L2TP destination."
    INDEX { usdL2tpDestConfigIfIndex }
    ::= { usdL2tpDestConfigTable 1 }

UsdL2tpDestConfigEntry ::= SEQUENCE {
    usdL2tpDestConfigIfIndex
        InterfaceIndex,
    usdL2tpDestConfigRowStatus
        RowStatus,
    usdL2tpDestConfigAdminState
        UsdL2tpAdminState
    }

usdL2tpDestConfigIfIndex OBJECT-TYPE
    SYNTAX      InterfaceIndex
    MAX-ACCESS  not-accessible
    STATUS      current
    DESCRIPTION
        "Same value as ifIndex for the corresponding entry in Interfaces MIB
        ifTable."
    ::= { usdL2tpDestConfigEntry 1 }

usdL2tpDestConfigRowStatus  OBJECT-TYPE
    SYNTAX      RowStatus
    MAX-ACCESS  read-create
    STATUS      current
    DESCRIPTION
        "An implementation may choose not to support administrative
        configuration of tunnels."
    ::= { usdL2tpDestConfigEntry 2 }

usdL2tpDestConfigAdminState  OBJECT-TYPE
    SYNTAX      UsdL2tpAdminState
    MAX-ACCESS  read-create
    STATUS      current
    DESCRIPTION
        "The configured administrative state."
    DEFVAL { enabled }
    ::= { usdL2tpDestConfigEntry 3 }

--
-- Destination-level Status
--

usdL2tpDestStatusTable   OBJECT-TYPE
    SYNTAX      SEQUENCE OF UsdL2tpDestStatusEntry
    MAX-ACCESS  not-accessible
    STATUS      current
    DESCRIPTION
        "The L2TP destination status table.  Each entry in this table has a
        corresponding entry in the Interfaces MIB ifTable, and in
        usdL2tpDestConfigTable."
    ::= { usdL2tpDestStatus 1 }

usdL2tpDestStatusEntry   OBJECT-TYPE
    SYNTAX      UsdL2tpDestStatusEntry
    MAX-ACCESS  not-accessible
    STATUS      current
    DESCRIPTION
        "Describes the status attributes of an L2TP destination."
    INDEX { usdL2tpDestStatusIfIndex }
    ::= { usdL2tpDestStatusTable 1 }

UsdL2tpDestStatusEntry ::= SEQUENCE {
    usdL2tpDestStatusIfIndex
        InterfaceIndex,
    usdL2tpDestStatusTransport
        UsdL2tpTransport,
    usdL2tpDestStatusEffectiveAdminState
        UsdL2tpAdminState,
    usdL2tpDestStatusTotalTunnels
        Counter32,
    usdL2tpDestStatusFailedTunnels
        Counter32,
    usdL2tpDestStatusFailedTunnelAuthens
        Counter32,
    usdL2tpDestStatusActiveTunnels
        Gauge32,
    usdL2tpDestStatusTotalSessions
        Counter32,
    usdL2tpDestStatusFailedSessions
        Counter32,
    usdL2tpDestStatusActiveSessions
        Gauge32
    }

usdL2tpDestStatusIfIndex OBJECT-TYPE
    SYNTAX      InterfaceIndex
    MAX-ACCESS  not-accessible
    STATUS      current
    DESCRIPTION
        "Same value as ifIndex for the corresponding entry in Interfaces MIB
        ifTable."
    ::= { usdL2tpDestStatusEntry 1 }

usdL2tpDestStatusTransport OBJECT-TYPE
    SYNTAX      UsdL2tpTransport
    MAX-ACCESS  read-only
    STATUS      current
    DESCRIPTION
        "The underlying transport over which this
        L2TP destination is carried."
    ::= { usdL2tpDestStatusEntry 2 }

usdL2tpDestStatusEffectiveAdminState  OBJECT-TYPE
    SYNTAX      UsdL2tpAdminState
    MAX-ACCESS  read-only
    STATUS      current
    DESCRIPTION
        "The administrative state currently in effect.  This could be the
        configured admin state for this destination, or an overriding admin
        state exerted from a higher hierarchical level (system)."
    ::= { usdL2tpDestStatusEntry 3 }

usdL2tpDestStatusTotalTunnels OBJECT-TYPE
    SYNTAX      Counter32
    MAX-ACCESS  read-only
    STATUS      current
    DESCRIPTION
        "Number of tunnel creations attempted."
    ::= { usdL2tpDestStatusEntry 4 }

usdL2tpDestStatusFailedTunnels OBJECT-TYPE
    SYNTAX      Counter32
    MAX-ACCESS  read-only
    STATUS      current
    DESCRIPTION
        "Number of tunnel creation attempts that failed to reach the established
        state."
    ::= { usdL2tpDestStatusEntry 5 }

usdL2tpDestStatusFailedTunnelAuthens OBJECT-TYPE
    SYNTAX      Counter32
    MAX-ACCESS  read-only
    STATUS      current
    DESCRIPTION
        "Number of tunnel creation attempts that failed authentication."
    ::= { usdL2tpDestStatusEntry 6 }

usdL2tpDestStatusActiveTunnels OBJECT-TYPE
    SYNTAX      Gauge32
    MAX-ACCESS  read-only
    STATUS      current
    DESCRIPTION
        "Number of tunnels currently established."
    ::= { usdL2tpDestStatusEntry 7 }

usdL2tpDestStatusTotalSessions OBJECT-TYPE
    SYNTAX      Counter32
    MAX-ACCESS  read-only
    STATUS      current
    DESCRIPTION
        "Number of session creations attempted."
    ::= { usdL2tpDestStatusEntry 8 }

usdL2tpDestStatusFailedSessions OBJECT-TYPE
    SYNTAX      Counter32
    MAX-ACCESS  read-only
    STATUS      current
    DESCRIPTION
        "Number of session creation attempts that failed to reach the
        established state."
    ::= { usdL2tpDestStatusEntry 9 }

usdL2tpDestStatusActiveSessions OBJECT-TYPE
    SYNTAX      Gauge32
    MAX-ACCESS  read-only
    STATUS      current
    DESCRIPTION
        "Number of sessions currently established."
    ::= { usdL2tpDestStatusEntry 10 }

--
-- Destination-level Statistics
--

usdL2tpDestStatTable   OBJECT-TYPE
    SYNTAX      SEQUENCE OF UsdL2tpDestStatEntry
    MAX-ACCESS  not-accessible
    STATUS      current
    DESCRIPTION
        "The L2TP destination statistics table.  Describes the aggregate control
        and payload statistics for all L2TP tunnels configured on each
        destination.  Each entry in this table has a corresponding entry in the
        Interfaces MIB ifTable, and in usdL2tpDestConfigTable."
    ::= { usdL2tpDestStatistics 1 }

usdL2tpDestStatEntry   OBJECT-TYPE
    SYNTAX      UsdL2tpDestStatEntry
    MAX-ACCESS  not-accessible
    STATUS      current
    DESCRIPTION
        "Describes the aggregate L2TP control and payload statistics for all
        L2TP tunnels on an L2TP destination."
    INDEX { usdL2tpDestStatIfIndex }
    ::= { usdL2tpDestStatTable 1 }

UsdL2tpDestStatEntry ::= SEQUENCE {
    usdL2tpDestStatIfIndex
        InterfaceIndex,
    usdL2tpDestStatCtlRecvOctets
        Counter32,
    usdL2tpDestStatCtlRecvPackets
        Counter32,
    usdL2tpDestStatCtlRecvErrors
        Counter32,
    usdL2tpDestStatCtlRecvDiscards
        Counter32,
    usdL2tpDestStatCtlSendOctets
        Counter32,
    usdL2tpDestStatCtlSendPackets
        Counter32,
    usdL2tpDestStatCtlSendErrors
        Counter32,
    usdL2tpDestStatCtlSendDiscards
        Counter32,
    usdL2tpDestStatPayRecvOctets
        Counter32,
    usdL2tpDestStatPayRecvPackets
        Counter32,
    usdL2tpDestStatPayRecvErrors
        Counter32,
    usdL2tpDestStatPayRecvDiscards
        Counter32,
    usdL2tpDestStatPaySendOctets
        Counter32,
    usdL2tpDestStatPaySendPackets
        Counter32,
    usdL2tpDestStatPaySendErrors
        Counter32,
    usdL2tpDestStatPaySendDiscards
        Counter32
    }

usdL2tpDestStatIfIndex OBJECT-TYPE
    SYNTAX      InterfaceIndex
    MAX-ACCESS  not-accessible
    STATUS      current
    DESCRIPTION
        "Same value as ifIndex for the corresponding entry in Interfaces MIB
        ifTable."
    ::= { usdL2tpDestStatEntry 1 }

usdL2tpDestStatCtlRecvOctets OBJECT-TYPE
    SYNTAX      Counter32
    MAX-ACCESS  read-only
    STATUS      current
    DESCRIPTION
        "Number of control octets received."
    ::= { usdL2tpDestStatEntry 2 }

usdL2tpDestStatCtlRecvPackets OBJECT-TYPE
    SYNTAX      Counter32
    MAX-ACCESS  read-only
    STATUS      current
    DESCRIPTION
        "Number of control packets received."
    ::= { usdL2tpDestStatEntry 3 }

usdL2tpDestStatCtlRecvErrors OBJECT-TYPE
    SYNTAX      Counter32
    MAX-ACCESS  read-only
    STATUS      current
    DESCRIPTION
        "Number of control packets incurring reception errors."
    ::= { usdL2tpDestStatEntry 4 }

usdL2tpDestStatCtlRecvDiscards OBJECT-TYPE
    SYNTAX      Counter32
    MAX-ACCESS  read-only
    STATUS      current
    DESCRIPTION
        "Number of control packets discarded after reception."
    ::= { usdL2tpDestStatEntry 5 }

usdL2tpDestStatCtlSendOctets OBJECT-TYPE
    SYNTAX      Counter32
    MAX-ACCESS  read-only
    STATUS      current
    DESCRIPTION
        "Number of control octets sent."
    ::= { usdL2tpDestStatEntry 6 }

usdL2tpDestStatCtlSendPackets OBJECT-TYPE
    SYNTAX      Counter32
    MAX-ACCESS  read-only
    STATUS      current
    DESCRIPTION
        "Number of control packets sent."
    ::= { usdL2tpDestStatEntry 7 }

usdL2tpDestStatCtlSendErrors OBJECT-TYPE
    SYNTAX      Counter32
    MAX-ACCESS  read-only
    STATUS      current
    DESCRIPTION
        "Number of control packets incurring transmission errors."
    ::= { usdL2tpDestStatEntry 8 }

usdL2tpDestStatCtlSendDiscards OBJECT-TYPE
    SYNTAX      Counter32
    MAX-ACCESS  read-only
    STATUS      current
    DESCRIPTION
        "Number of control packets discarded before transmission."
    ::= { usdL2tpDestStatEntry 9 }

usdL2tpDestStatPayRecvOctets OBJECT-TYPE
    SYNTAX      Counter32
    MAX-ACCESS  read-only
    STATUS      current
    DESCRIPTION
        "Number of payload octets received."
    ::= { usdL2tpDestStatEntry 10 }

usdL2tpDestStatPayRecvPackets OBJECT-TYPE
    SYNTAX      Counter32
    MAX-ACCESS  read-only
    STATUS      current
    DESCRIPTION
        "Number of payload packets received."
    ::= { usdL2tpDestStatEntry 11 }

usdL2tpDestStatPayRecvErrors OBJECT-TYPE
    SYNTAX      Counter32
    MAX-ACCESS  read-only
    STATUS      current
    DESCRIPTION
        "Number of payload packets incurring reception errors."
    ::= { usdL2tpDestStatEntry 12 }

usdL2tpDestStatPayRecvDiscards OBJECT-TYPE
    SYNTAX      Counter32
    MAX-ACCESS  read-only
    STATUS      current
    DESCRIPTION
        "Number of payload packets discarded after reception."
    ::= { usdL2tpDestStatEntry 13 }

usdL2tpDestStatPaySendOctets OBJECT-TYPE
    SYNTAX      Counter32
    MAX-ACCESS  read-only
    STATUS      current
    DESCRIPTION
        "Number of payload octets sent."
    ::= { usdL2tpDestStatEntry 14 }

usdL2tpDestStatPaySendPackets OBJECT-TYPE
    SYNTAX      Counter32
    MAX-ACCESS  read-only
    STATUS      current
    DESCRIPTION
        "Number of payload packets sent."
    ::= { usdL2tpDestStatEntry 15 }

usdL2tpDestStatPaySendErrors OBJECT-TYPE
    SYNTAX      Counter32
    MAX-ACCESS  read-only
    STATUS      current
    DESCRIPTION
        "Number of payload packets incurring transmission errors."
    ::= { usdL2tpDestStatEntry 16 }

usdL2tpDestStatPaySendDiscards OBJECT-TYPE
    SYNTAX      Counter32
    MAX-ACCESS  read-only
    STATUS      current
    DESCRIPTION
        "Number of payload packets discarded before transmission."
    ::= { usdL2tpDestStatEntry 17 }

-- ......................................................................
-- L2TP Tunnel Group
-- ......................................................................

usdL2tpTunnelConfig      OBJECT IDENTIFIER   ::= { usdL2tpTunnel 1 }
usdL2tpTunnelStatus      OBJECT IDENTIFIER   ::= { usdL2tpTunnel 2 }
usdL2tpTunnelStatistics  OBJECT IDENTIFIER   ::= { usdL2tpTunnel 3 }
usdL2tpTunnelMap         OBJECT IDENTIFIER   ::= { usdL2tpTunnel 4 }

--
-- Tunnel-level Configuration
--

-- { usdL2tpTunnelConfig 1 } reserved for "next ifIndex" acquisition

usdL2tpTunnelConfigTable   OBJECT-TYPE
    SYNTAX      SEQUENCE OF UsdL2tpTunnelConfigEntry
    MAX-ACCESS  not-accessible
    STATUS      current
    DESCRIPTION
        "The L2TP tunnel configuration table.  Each entry in this table has a
        corresponding entry in the Interfaces MIB ifTable, and in
        usdL2tpTunnelStatsTable."
    ::= { usdL2tpTunnelConfig 2 }

usdL2tpTunnelConfigEntry   OBJECT-TYPE
    SYNTAX      UsdL2tpTunnelConfigEntry
    MAX-ACCESS  not-accessible
    STATUS      current
    DESCRIPTION
        "Describes the configuration attributes of an L2TP tunnel."
    INDEX { usdL2tpTunnelConfigIfIndex }
    ::= { usdL2tpTunnelConfigTable 1 }

UsdL2tpTunnelConfigEntry ::= SEQUENCE {
    usdL2tpTunnelConfigIfIndex
        InterfaceIndex,
    usdL2tpTunnelConfigRowStatus
        RowStatus,
    usdL2tpTunnelConfigAdminState
        UsdL2tpAdminState
    }

usdL2tpTunnelConfigIfIndex OBJECT-TYPE
    SYNTAX      InterfaceIndex
    MAX-ACCESS  not-accessible
    STATUS      current
    DESCRIPTION
        "Same value as ifIndex for the corresponding entry in Interfaces MIB
        ifTable."
    ::= { usdL2tpTunnelConfigEntry 1 }

usdL2tpTunnelConfigRowStatus  OBJECT-TYPE
    SYNTAX      RowStatus
    MAX-ACCESS  read-create
    STATUS      current
    DESCRIPTION
        "An implementation may choose not to support administrative
        configuration of tunnels."
    ::= { usdL2tpTunnelConfigEntry 2 }

usdL2tpTunnelConfigAdminState  OBJECT-TYPE
    SYNTAX      UsdL2tpAdminState
    MAX-ACCESS  read-create
    STATUS      current
    DESCRIPTION
        "The configured administrative state."
    DEFVAL { enabled }
    ::= { usdL2tpTunnelConfigEntry 3 }

--
-- Tunnel-level Status and Statistics
--
usdL2tpTunnelStatusTable    OBJECT-TYPE
    SYNTAX      SEQUENCE OF UsdL2tpTunnelStatusEntry
    MAX-ACCESS  not-accessible
    STATUS      current
    DESCRIPTION
        "The L2TP tunnel status and statistics table.  Each entry in this table
        has a corresponding entry in the Interfaces MIB ifTable, and in
        usdL2tpTunnelConfigTable."
    ::= { usdL2tpTunnelStatus 1 }

usdL2tpTunnelStatusEntry    OBJECT-TYPE
    SYNTAX      UsdL2tpTunnelStatusEntry
    MAX-ACCESS  not-accessible
    STATUS      current
    DESCRIPTION
        "An L2TP tunnel interface stats entry."
    INDEX { usdL2tpTunnelStatusIfIndex }
    ::= { usdL2tpTunnelStatusTable 1 }

UsdL2tpTunnelStatusEntry ::= SEQUENCE {
    usdL2tpTunnelStatusIfIndex
        InterfaceIndex,
    usdL2tpTunnelStatusTransport
        UsdL2tpTransport,
    usdL2tpTunnelStatusLocalTunnelId
        UsdL2tpTunnelId,
    usdL2tpTunnelStatusRemoteTunnelId
        UsdL2tpTunnelId,
    usdL2tpTunnelStatusEffectiveAdminState
        UsdL2tpAdminState,
    usdL2tpTunnelStatusState
        INTEGER,
    usdL2tpTunnelStatusInitiated
        INTEGER,
    usdL2tpTunnelStatusRemoteHostName
        DisplayString,
    usdL2tpTunnelStatusRemoteVendorName
        DisplayString,
    usdL2tpTunnelStatusRemoteFirmwareRevision
        Integer32,
    usdL2tpTunnelStatusRemoteProtocolVersion
        OCTET STRING,
    usdL2tpTunnelStatusRemoteBearerCapabilities
        INTEGER,
    usdL2tpTunnelStatusRemoteFramingCapabilities
        INTEGER,
    usdL2tpTunnelStatusRecvWindowSize
        Gauge32,
    usdL2tpTunnelStatusSendWindowSize
        Gauge32,
    usdL2tpTunnelStatusSendQueueDepth
        Gauge32,
    usdL2tpTunnelStatusRecvSeq
        Integer32,
    usdL2tpTunnelStatusRecvSeqAck
        Integer32,
    usdL2tpTunnelStatusSendSeq
        Integer32,
    usdL2tpTunnelStatusSendSeqAck
        Integer32,
    usdL2tpTunnelStatusTotalSessions
        Counter32,
    usdL2tpTunnelStatusFailedSessions
        Counter32,
    usdL2tpTunnelStatusActiveSessions
        Gauge32,
    usdL2tpTunnelStatusLastResultCode
        Integer32,
    usdL2tpTunnelStatusLastErrorCode
        Integer32,
    usdL2tpTunnelStatusLastErrorMessage
        DisplayString,
    usdL2tpTunnelStatusCumEstabTime
        Unsigned32
    }

usdL2tpTunnelStatusIfIndex  OBJECT-TYPE
    SYNTAX      InterfaceIndex
    MAX-ACCESS  not-accessible
    STATUS      current
    DESCRIPTION
        "Same as the value of ifIndex for the corresponding entry in Interfaces
        MIB ifTable."
    ::= { usdL2tpTunnelStatusEntry 1 }

usdL2tpTunnelStatusTransport OBJECT-TYPE
    SYNTAX      UsdL2tpTransport
    MAX-ACCESS  read-only
    STATUS      current
    DESCRIPTION
        "The underlying transport over which this L2TP tunnel is carried."
    ::= { usdL2tpTunnelStatusEntry 2 }

usdL2tpTunnelStatusLocalTunnelId OBJECT-TYPE
    SYNTAX      UsdL2tpTunnelId
    MAX-ACCESS  read-only
    STATUS      current
    DESCRIPTION
        "The local tunnel identifier."
    ::= { usdL2tpTunnelStatusEntry 3 }

usdL2tpTunnelStatusRemoteTunnelId OBJECT-TYPE
    SYNTAX      UsdL2tpTunnelId
    MAX-ACCESS  read-only
    STATUS      current
    DESCRIPTION
        "The remote tunnel identifier."
    ::= { usdL2tpTunnelStatusEntry 4 }

usdL2tpTunnelStatusEffectiveAdminState  OBJECT-TYPE
    SYNTAX      UsdL2tpAdminState
    MAX-ACCESS  read-only
    STATUS      current
    DESCRIPTION
        "The administrative state currently in effect.  This could be the
        configured admin state for this tunnel, or an overriding admin state
        exerted from a higher hierarchical level (system, destination)."
    ::= { usdL2tpTunnelStatusEntry 5 }

usdL2tpTunnelStatusState    OBJECT-TYPE
    SYNTAX      INTEGER {
                    idle(0),
                    connecting(1),
                    established(2),
                    disconnecting(3)
                }
    MAX-ACCESS  read-only
    STATUS      current
    DESCRIPTION
        "The current state of the tunnel."
    ::= { usdL2tpTunnelStatusEntry 6 }

usdL2tpTunnelStatusInitiated  OBJECT-TYPE
    SYNTAX      INTEGER {
                    none(0),
                    local(1),
                    remote(2)
                }
    MAX-ACCESS  read-only
    STATUS      current
    DESCRIPTION
        "Indicates whether the tunnel was initiated locally, or by the remote
        tunnel peer."
    ::= { usdL2tpTunnelStatusEntry 7 }

usdL2tpTunnelStatusRemoteHostName  OBJECT-TYPE
    SYNTAX      DisplayString
    MAX-ACCESS  read-only
    STATUS      current
    DESCRIPTION
        "The host name obtained during the tunnel establishment phase (via the
        Host Name AVP) of the L2TP peer.  If the tunnel is idle, this object
        should maintain its value from the last time it was connected, or a
        zero-length string if no name was previously known."
    ::= { usdL2tpTunnelStatusEntry 8 }

usdL2tpTunnelStatusRemoteVendorName  OBJECT-TYPE
    SYNTAX      DisplayString
    MAX-ACCESS  read-only
    STATUS      current
    DESCRIPTION
        "Identifies the vendor name of the peer's L2TP implementation. If the
        tunnel is idle, this object should maintain its value from the last time
        it was connected, of a zero-length string if no name was previously
        known."
    ::= { usdL2tpTunnelStatusEntry 9 }

usdL2tpTunnelStatusRemoteFirmwareRevision  OBJECT-TYPE
    SYNTAX      Integer32
    MAX-ACCESS  read-only
    STATUS      current
    DESCRIPTION
        "The tunnel peer's firmware revision number.  If the tunnel is idle,
        this object should maintain its value from the last time it was
        connected, or a zero value if no revision was previously known."
    ::= { usdL2tpTunnelStatusEntry 10 }

usdL2tpTunnelStatusRemoteProtocolVersion  OBJECT-TYPE
    SYNTAX      OCTET STRING (SIZE(2))
    MAX-ACCESS  read-only
    STATUS      current
    DESCRIPTION
        "The protocol version and revision of the tunnel peer's implementation.
        The first octet contains the protocol version.  The second octet
        contains the protocol revision."
    ::= { usdL2tpTunnelStatusEntry 11 }

usdL2tpTunnelStatusRemoteBearerCapabilities  OBJECT-TYPE
    SYNTAX      INTEGER {
                    none(0),
                    digital(1),
                    analog(2),
                    digitalAnalog(3)
                }
    MAX-ACCESS  read-only
    STATUS      current
    DESCRIPTION
        "The Bearer Capabilities of the tunnel peer.  If the tunnel is idle this
        object should maintain its value from the last time it was connected, or
        'none' if not previously known."
    ::= { usdL2tpTunnelStatusEntry 12 }

usdL2tpTunnelStatusRemoteFramingCapabilities  OBJECT-TYPE
    SYNTAX      INTEGER {
                    none(0),
                    sync(1),
                    async(2),
                    syncAsync(3)
                }
    MAX-ACCESS  read-only
    STATUS      current
    DESCRIPTION
        "The Framing Capabilities of the tunnel peer.  If the tunnel is idle
        this object should maintain its value from the last time it was
        connected, or 'none' if not previously known."
    ::= { usdL2tpTunnelStatusEntry 13 }

usdL2tpTunnelStatusRecvWindowSize  OBJECT-TYPE
    SYNTAX      Gauge32
    MAX-ACCESS  read-only
    STATUS      current
    DESCRIPTION
        "The receive window size."
    ::= { usdL2tpTunnelStatusEntry 14 }

usdL2tpTunnelStatusSendWindowSize  OBJECT-TYPE
    SYNTAX      Gauge32
    MAX-ACCESS  read-only
    STATUS      current
    DESCRIPTION
        "The tunnel peer's receive window size."
    ::= { usdL2tpTunnelStatusEntry 15 }

usdL2tpTunnelStatusSendQueueDepth  OBJECT-TYPE
    SYNTAX      Gauge32
    MAX-ACCESS  read-only
    STATUS      current
    DESCRIPTION
        "Number of control packets on transmit queue."
    ::= { usdL2tpTunnelStatusEntry 16 }

usdL2tpTunnelStatusRecvSeq  OBJECT-TYPE
    SYNTAX      Integer32 (0..65535)
    MAX-ACCESS  read-only
    STATUS      current
    DESCRIPTION
        "The next sequence number expected in a received control packet."
    ::= { usdL2tpTunnelStatusEntry 17 }

usdL2tpTunnelStatusRecvSeqAck  OBJECT-TYPE
    SYNTAX      Integer32 (0..65535)
    MAX-ACCESS  read-only
    STATUS      current
    DESCRIPTION
        "The last received sequence number that was acknowledged back to the
        tunnel peer."
    ::= { usdL2tpTunnelStatusEntry 18 }

usdL2tpTunnelStatusSendSeq  OBJECT-TYPE
    SYNTAX      Integer32 (0..65535)
    MAX-ACCESS  read-only
    STATUS      current
    DESCRIPTION
        "The next sequence number to be sent in a transmitted control packet."
    ::= { usdL2tpTunnelStatusEntry 19 }

usdL2tpTunnelStatusSendSeqAck  OBJECT-TYPE
    SYNTAX      Integer32 (0..65535)
    MAX-ACCESS  read-only
    STATUS      current
    DESCRIPTION
        "The send sequence number that the tunnel peer has acknowledged.
        The flow control state can be determined by subtracting the
        usdL2tpTunnelStatusSendSeq from usdL2tpTunnelStatusSendSeqAck and
        comparing this value to usdL2tpTunnelStatusSendWindowSize."
    ::= { usdL2tpTunnelStatusEntry 20 }

usdL2tpTunnelStatusTotalSessions  OBJECT-TYPE
    SYNTAX      Counter32
    MAX-ACCESS  read-only
    STATUS      current
    DESCRIPTION
        "The total number of sessions that this tunnel has successfully
        connected through to its tunnel peer since this tunnel was created,
        including those that have since terminated."
    ::= { usdL2tpTunnelStatusEntry 21 }

usdL2tpTunnelStatusFailedSessions  OBJECT-TYPE
    SYNTAX      Counter32
    MAX-ACCESS  read-only
    STATUS      current
    DESCRIPTION
        "The number of sessions that were initiated but failed to reach the
        established phase."
    ::= { usdL2tpTunnelStatusEntry 22 }

usdL2tpTunnelStatusActiveSessions  OBJECT-TYPE
    SYNTAX      Gauge32
    MAX-ACCESS  read-only
    STATUS      current
    DESCRIPTION
        "The current number of sessions in the established state."
    ::= { usdL2tpTunnelStatusEntry 23 }

usdL2tpTunnelStatusLastResultCode  OBJECT-TYPE
    SYNTAX      Integer32 (0..65535)
    MAX-ACCESS  read-only
    STATUS      current
    DESCRIPTION
        "The last value of the result code as described in the Result Code AVP
        which caused the tunnel to disconnect."
    ::= { usdL2tpTunnelStatusEntry 24 }

usdL2tpTunnelStatusLastErrorCode  OBJECT-TYPE
    SYNTAX      Integer32 (0..65535)
    MAX-ACCESS  read-only
    STATUS      current
    DESCRIPTION
        "The last value of the error code as described in the Result Code AVP
        which caused the tunnel to disconnect."
    ::= { usdL2tpTunnelStatusEntry 25 }

usdL2tpTunnelStatusLastErrorMessage  OBJECT-TYPE
    SYNTAX      DisplayString
    MAX-ACCESS  read-only
    STATUS      current
    DESCRIPTION
        "The last value of the optional message as described in the Result Code
        AVP which caused the tunnel to disconnect."
    ::= { usdL2tpTunnelStatusEntry 26 }

usdL2tpTunnelStatusCumEstabTime OBJECT-TYPE
    SYNTAX      Unsigned32
    UNITS       "seconds"
    MAX-ACCESS  read-only
    STATUS      current
    DESCRIPTION
        "The cumulative time in seconds that this tunnel, since first being
        created, has spent in the established state (which may be punctuated by
        intervals outside the established state)."
    ::= { usdL2tpTunnelStatusEntry 27 }

--
-- Tunnel-level Statistics
--

usdL2tpTunnelStatTable   OBJECT-TYPE
    SYNTAX      SEQUENCE OF UsdL2tpTunnelStatEntry
    MAX-ACCESS  not-accessible
    STATUS      current
    DESCRIPTION
        "The L2TP tunnel statistics table.  Describes the control and payload
        statistics for each L2TP tunnel.  Each entry in this table has a
        corresponding entry in the Interfaces MIB ifTable, and in
        usdL2tpTunnelConfigTable."
    ::= { usdL2tpTunnelStatistics 1 }

usdL2tpTunnelStatEntry   OBJECT-TYPE
    SYNTAX      UsdL2tpTunnelStatEntry
    MAX-ACCESS  not-accessible
    STATUS      current
    DESCRIPTION
        "Describes the L2TP control and payload statistics for an L2TP tunnel."
    INDEX { usdL2tpTunnelStatIfIndex }
    ::= { usdL2tpTunnelStatTable 1 }

UsdL2tpTunnelStatEntry ::= SEQUENCE {
    usdL2tpTunnelStatIfIndex
        InterfaceIndex,
    usdL2tpTunnelStatCtlRecvOctets
        Counter32,
    usdL2tpTunnelStatCtlRecvPackets
        Counter32,
    usdL2tpTunnelStatCtlRecvErrors
        Counter32,
    usdL2tpTunnelStatCtlRecvDiscards
        Counter32,
    usdL2tpTunnelStatCtlSendOctets
        Counter32,
    usdL2tpTunnelStatCtlSendPackets
        Counter32,
    usdL2tpTunnelStatCtlSendErrors
        Counter32,
    usdL2tpTunnelStatCtlSendDiscards
        Counter32,
    usdL2tpTunnelStatPayRecvOctets
        Counter32,
    usdL2tpTunnelStatPayRecvPackets
        Counter32,
    usdL2tpTunnelStatPayRecvErrors
        Counter32,
    usdL2tpTunnelStatPayRecvDiscards
        Counter32,
    usdL2tpTunnelStatPaySendOctets
        Counter32,
    usdL2tpTunnelStatPaySendPackets
        Counter32,
    usdL2tpTunnelStatPaySendErrors
        Counter32,
    usdL2tpTunnelStatPaySendDiscards
        Counter32,

    usdL2tpTunnelStatCtlRecvZLB
        Counter32,
    usdL2tpTunnelStatCtlRecvOutOfSequence
        Counter32,
    usdL2tpTunnelStatCtlRecvOutOfWindow
        Counter32,
    usdL2tpTunnelStatCtlSendZLB
        Counter32,
    usdL2tpTunnelStatCtlSendRetransmits
        Counter32
    }

usdL2tpTunnelStatIfIndex OBJECT-TYPE
    SYNTAX      InterfaceIndex
    MAX-ACCESS  not-accessible
    STATUS      current
    DESCRIPTION
        "Same value as ifIndex for the corresponding entry in Interfaces MIB
        ifTable."
    ::= { usdL2tpTunnelStatEntry 1 }

usdL2tpTunnelStatCtlRecvOctets OBJECT-TYPE
    SYNTAX      Counter32
    MAX-ACCESS  read-only
    STATUS      current
    DESCRIPTION
        "Number of control octets received."
    ::= { usdL2tpTunnelStatEntry 2 }

usdL2tpTunnelStatCtlRecvPackets OBJECT-TYPE
    SYNTAX      Counter32
    MAX-ACCESS  read-only
    STATUS      current
    DESCRIPTION
        "Number of control packets received."
    ::= { usdL2tpTunnelStatEntry 3 }

usdL2tpTunnelStatCtlRecvErrors OBJECT-TYPE
    SYNTAX      Counter32
    MAX-ACCESS  read-only
    STATUS      current
    DESCRIPTION
        "Number of control packets incurring reception errors."
    ::= { usdL2tpTunnelStatEntry 4 }

usdL2tpTunnelStatCtlRecvDiscards OBJECT-TYPE
    SYNTAX      Counter32
    MAX-ACCESS  read-only
    STATUS      current
    DESCRIPTION
        "Number of control packets discarded after reception."
    ::= { usdL2tpTunnelStatEntry 5 }

usdL2tpTunnelStatCtlSendOctets OBJECT-TYPE
    SYNTAX      Counter32
    MAX-ACCESS  read-only
    STATUS      current
    DESCRIPTION
        "Number of control octets sent."
    ::= { usdL2tpTunnelStatEntry 6 }

usdL2tpTunnelStatCtlSendPackets OBJECT-TYPE
    SYNTAX      Counter32
    MAX-ACCESS  read-only
    STATUS      current
    DESCRIPTION
        "Number of control packets sent."
    ::= { usdL2tpTunnelStatEntry 7 }

usdL2tpTunnelStatCtlSendErrors OBJECT-TYPE
    SYNTAX      Counter32
    MAX-ACCESS  read-only
    STATUS      current
    DESCRIPTION
        "Number of control packets incurring transmission errors."
    ::= { usdL2tpTunnelStatEntry 8 }

usdL2tpTunnelStatCtlSendDiscards OBJECT-TYPE
    SYNTAX      Counter32
    MAX-ACCESS  read-only
    STATUS      current
    DESCRIPTION
        "Number of control packets discarded before transmission."
    ::= { usdL2tpTunnelStatEntry 9 }

usdL2tpTunnelStatPayRecvOctets OBJECT-TYPE
    SYNTAX      Counter32
    MAX-ACCESS  read-only
    STATUS      current
    DESCRIPTION
        "Number of payload octets received."
    ::= { usdL2tpTunnelStatEntry 10 }

usdL2tpTunnelStatPayRecvPackets OBJECT-TYPE
    SYNTAX      Counter32
    MAX-ACCESS  read-only
    STATUS      current
    DESCRIPTION
        "Number of payload packets received."
    ::= { usdL2tpTunnelStatEntry 11 }

usdL2tpTunnelStatPayRecvErrors OBJECT-TYPE
    SYNTAX      Counter32
    MAX-ACCESS  read-only
    STATUS      current
    DESCRIPTION
        "Number of payload packets incurring reception errors."
    ::= { usdL2tpTunnelStatEntry 12 }

usdL2tpTunnelStatPayRecvDiscards OBJECT-TYPE
    SYNTAX      Counter32
    MAX-ACCESS  read-only
    STATUS      current
    DESCRIPTION
        "Number of payload packets discarded after reception."
    ::= { usdL2tpTunnelStatEntry 13 }

usdL2tpTunnelStatPaySendOctets OBJECT-TYPE
    SYNTAX      Counter32
    MAX-ACCESS  read-only
    STATUS      current
    DESCRIPTION
        "Number of payload octets sent."
    ::= { usdL2tpTunnelStatEntry 14 }

usdL2tpTunnelStatPaySendPackets OBJECT-TYPE
    SYNTAX      Counter32
    MAX-ACCESS  read-only
    STATUS      current
    DESCRIPTION
        "Number of payload packets sent."
    ::= { usdL2tpTunnelStatEntry 15 }

usdL2tpTunnelStatPaySendErrors OBJECT-TYPE
    SYNTAX      Counter32
    MAX-ACCESS  read-only
    STATUS      current
    DESCRIPTION
        "Number of payload packets incurring transmission errors."
    ::= { usdL2tpTunnelStatEntry 16 }

usdL2tpTunnelStatPaySendDiscards OBJECT-TYPE
    SYNTAX      Counter32
    MAX-ACCESS  read-only
    STATUS      current
    DESCRIPTION
        "Number of payload packets discarded before transmission."
    ::= { usdL2tpTunnelStatEntry 17 }

--
-- additional granularity
--
usdL2tpTunnelStatCtlRecvZLB  OBJECT-TYPE
    SYNTAX      Counter32
    MAX-ACCESS  read-only
    STATUS      current
    DESCRIPTION
        "Number of Zero Length Body control packet acknowledgement
        packets that were received."
    ::= { usdL2tpTunnelStatEntry 18 }

usdL2tpTunnelStatCtlRecvOutOfSequence  OBJECT-TYPE
    SYNTAX      Counter32
    MAX-ACCESS  read-only
    STATUS      current
    DESCRIPTION
        "Number of control packets not received in the
        correct sequence number order."
    ::= { usdL2tpTunnelStatEntry 19 }

usdL2tpTunnelStatCtlRecvOutOfWindow  OBJECT-TYPE
    SYNTAX      Counter32
    MAX-ACCESS  read-only
    STATUS      current
    DESCRIPTION
        "Number of control packets received outside the
        offered receive window."
    ::= { usdL2tpTunnelStatEntry 20 }

usdL2tpTunnelStatCtlSendZLB  OBJECT-TYPE
    SYNTAX      Counter32
    MAX-ACCESS  read-only
    STATUS      current
    DESCRIPTION
        "Number of Zero Length Body control packets sent."
    ::= { usdL2tpTunnelStatEntry 21 }

usdL2tpTunnelStatCtlSendRetransmits OBJECT-TYPE
    SYNTAX      Counter32
    MAX-ACCESS  read-only
    STATUS      current
    DESCRIPTION
        "Number of control packet send retransmissions."
    ::= { usdL2tpTunnelStatEntry 22 }

--
-- Tunnel Mappings
--

--
-- TunnelIf/SessionId -> SessionIf Mapping
--
usdL2tpMapTifSidToSifTable   OBJECT-TYPE
    SYNTAX      SEQUENCE OF UsdL2tpMapTifSidToSifEntry
    MAX-ACCESS  not-accessible
    STATUS      current
    DESCRIPTION
        "Table of TunnelIf/SessionId -> SessionIf mappings."
    ::= { usdL2tpTunnelMap 1 }

usdL2tpMapTifSidToSifEntry   OBJECT-TYPE
    SYNTAX      UsdL2tpMapTifSidToSifEntry
    MAX-ACCESS  not-accessible
    STATUS      current
    DESCRIPTION
        "A mapping of TunnelIf/SessionId to SessionIf."
    INDEX { usdL2tpMapTifSidToSifTunnelIfIndex, usdL2tpMapTifSidToSifLocalSessionId }
    ::= { usdL2tpMapTifSidToSifTable 1 }

UsdL2tpMapTifSidToSifEntry ::= SEQUENCE {
    usdL2tpMapTifSidToSifTunnelIfIndex
        InterfaceIndex,
    usdL2tpMapTifSidToSifLocalSessionId
        UsdL2tpSessionId,
    usdL2tpMapTifSidToSifSessionIfIndex
        InterfaceIndex
    }

usdL2tpMapTifSidToSifTunnelIfIndex OBJECT-TYPE
    SYNTAX      InterfaceIndex
    MAX-ACCESS  not-accessible
    STATUS      current
    DESCRIPTION
        "The ifIndex of a tunnel interface."
    ::= { usdL2tpMapTifSidToSifEntry 1 }

usdL2tpMapTifSidToSifLocalSessionId  OBJECT-TYPE
    SYNTAX      UsdL2tpSessionId
    MAX-ACCESS  not-accessible
    STATUS      current
    DESCRIPTION
        "A local session ID on the associated tunnel interface."
    ::= { usdL2tpMapTifSidToSifEntry 2 }

usdL2tpMapTifSidToSifSessionIfIndex OBJECT-TYPE
    SYNTAX      InterfaceIndex
    MAX-ACCESS  read-only
    STATUS      current
    DESCRIPTION
        "The ifIndex of the session interface identified by this entry's Tunnel
        ifIndex and local Session Id pair."
    ::= { usdL2tpMapTifSidToSifEntry 3 }

--
-- Tunnel ID -> Tunnel If
--
usdL2tpMapTidToTifTable OBJECT-TYPE
    SYNTAX      SEQUENCE OF UsdL2tpMapTidToTifEntry
    MAX-ACCESS  not-accessible
    STATUS      current
    DESCRIPTION
        "Map L2TP tunnel IDs to tunnel interfaces."
    ::= { usdL2tpTunnelMap 2 }

usdL2tpMapTidToTifEntry OBJECT-TYPE
    SYNTAX      UsdL2tpMapTidToTifEntry
    MAX-ACCESS  not-accessible
    STATUS      current
    DESCRIPTION
        "A mapping of L2TP tunnel ID to tunnel interface."
    INDEX { usdL2tpMapTidToTifLocalTunnelId }
    ::= { usdL2tpMapTidToTifTable 1 }

UsdL2tpMapTidToTifEntry ::= SEQUENCE {
    usdL2tpMapTidToTifLocalTunnelId
        UsdL2tpTunnelId,
    usdL2tpMapTidToTifIfIndex
        InterfaceIndex
    }

usdL2tpMapTidToTifLocalTunnelId OBJECT-TYPE
    SYNTAX      UsdL2tpTunnelId
    MAX-ACCESS  not-accessible
    STATUS      current
    DESCRIPTION
        "A local tunnel identifier."
    ::= { usdL2tpMapTidToTifEntry 1 }

usdL2tpMapTidToTifIfIndex  OBJECT-TYPE
    SYNTAX      InterfaceIndex
    MAX-ACCESS  read-only
    STATUS      current
    DESCRIPTION
        "The ifIndex of the tunnel interface having the associated tunnel
        identifier."
    ::= { usdL2tpMapTidToTifEntry 2 }

-- ......................................................................
-- L2TP Session Group
-- ......................................................................

usdL2tpSessionConfig     OBJECT IDENTIFIER   ::= { usdL2tpSession 1 }
usdL2tpSessionStatus     OBJECT IDENTIFIER   ::= { usdL2tpSession 2 }
usdL2tpSessionStatistics OBJECT IDENTIFIER   ::= { usdL2tpSession 3 }


--
-- Session-level Configuration
--

-- { usdL2tpSessionConfig 1 } reserved for "next ifIndex" acquisition

usdL2tpSessionConfigTable   OBJECT-TYPE
    SYNTAX      SEQUENCE OF UsdL2tpSessionConfigEntry
    MAX-ACCESS  not-accessible
    STATUS      current
    DESCRIPTION
        "The L2TP session configuration table.  Each entry in this table has a
        corresponding entry in the Interfaces MIB ifTable, and in
        usdL2tpSessionStatsTable."
    ::= { usdL2tpSessionConfig 2 }

usdL2tpSessionConfigEntry   OBJECT-TYPE
    SYNTAX      UsdL2tpSessionConfigEntry
    MAX-ACCESS  not-accessible
    STATUS      current
    DESCRIPTION
        "Describes the configuration attributes of an L2TP session."
    INDEX { usdL2tpSessionConfigIfIndex }
    ::= { usdL2tpSessionConfigTable 1 }

UsdL2tpSessionConfigEntry ::= SEQUENCE {
    usdL2tpSessionConfigIfIndex
        InterfaceIndex,
    usdL2tpSessionConfigRowStatus
        RowStatus,
    usdL2tpSessionConfigAdminState
        UsdL2tpAdminState
    }

usdL2tpSessionConfigIfIndex OBJECT-TYPE
    SYNTAX      InterfaceIndex
    MAX-ACCESS  not-accessible
    STATUS      current
    DESCRIPTION
        "Same value as ifIndex for the corresponding entry in Interfaces MIB
        ifTable."
    ::= { usdL2tpSessionConfigEntry 1 }

usdL2tpSessionConfigRowStatus  OBJECT-TYPE
    SYNTAX      RowStatus
    MAX-ACCESS  read-create
    STATUS      current
    DESCRIPTION
        "An implementation may choose not to support administrative
        configuration of tunnels."
    ::= { usdL2tpSessionConfigEntry 2 }

usdL2tpSessionConfigAdminState  OBJECT-TYPE
    SYNTAX      UsdL2tpAdminState
    MAX-ACCESS  read-create
    STATUS      current
    DESCRIPTION
        "The configured administrative state."
    DEFVAL { enabled }
    ::= { usdL2tpSessionConfigEntry 3 }


--
-- L2TP Session-level Status and Statistics
--
usdL2tpSessionStatusTable   OBJECT-TYPE
    SYNTAX      SEQUENCE OF UsdL2tpSessionStatusEntry
    MAX-ACCESS  not-accessible
    STATUS      current
    DESCRIPTION
        "The L2TP session status and statistics table."
    ::= { usdL2tpSessionStatus 1 }

usdL2tpSessionStatusEntry   OBJECT-TYPE
    SYNTAX      UsdL2tpSessionStatusEntry
    MAX-ACCESS  not-accessible
    STATUS      current
    DESCRIPTION
        "An L2TP session interface status and statistics entry."
    INDEX { usdL2tpSessionStatusIfIndex }
    ::= { usdL2tpSessionStatusTable 1 }

UsdL2tpSessionStatusEntry ::= SEQUENCE {
    usdL2tpSessionStatusIfIndex
        InterfaceIndex,
    usdL2tpSessionStatusLacPppIfIndex
        InterfaceIndexOrZero,
    usdL2tpSessionStatusLocalSessionId
        UsdL2tpSessionId,
    usdL2tpSessionStatusRemoteSessionId
        UsdL2tpSessionId,
    usdL2tpSessionStatusUserName
        DisplayString,
    usdL2tpSessionStatusEffectiveAdminState
        UsdL2tpAdminState,
    usdL2tpSessionStatusState
        INTEGER,
    usdL2tpSessionStatusCallType
        INTEGER,
    usdL2tpSessionStatusCallSerialNumber
        Integer32,
    usdL2tpSessionStatusTxConnectSpeed
        Integer32,
    usdL2tpSessionStatusRxConnectSpeed
        Integer32,
    usdL2tpSessionStatusCallBearerType
        INTEGER,
    usdL2tpSessionStatusFramingType
        INTEGER,
    usdL2tpSessionStatusPhysChanId
        Integer32,
    usdL2tpSessionStatusDnis
        DisplayString,
    usdL2tpSessionStatusClid
        DisplayString,
    usdL2tpSessionStatusSubAddress
        DisplayString,
    usdL2tpSessionStatusPrivateGroupId
        DisplayString,
    usdL2tpSessionStatusProxyLcp
        TruthValue,
    usdL2tpSessionStatusAuthMethod
        INTEGER,
    usdL2tpSessionStatusSequencingState
        INTEGER,
    usdL2tpSessionStatusSendSeq
        Integer32,
    usdL2tpSessionStatusRecvSeq
        Integer32,
    usdL2tpSessionStatusLacTunneledIfIndex
        InterfaceIndexOrZero,
    usdL2tpSessionStatusCumEstabTime
        Unsigned32
    }

usdL2tpSessionStatusIfIndex OBJECT-TYPE
    SYNTAX      InterfaceIndex
    MAX-ACCESS  not-accessible
    STATUS      current
    DESCRIPTION
        "The ifIndex of an L2TP session interface."
    ::= { usdL2tpSessionStatusEntry 1 }

usdL2tpSessionStatusLacPppIfIndex OBJECT-TYPE
    SYNTAX      InterfaceIndexOrZero
    MAX-ACCESS  read-only
    STATUS      deprecated
    DESCRIPTION
        "For pass-through PPP sessions (conventional LAC), the ifIndex of an
        associated local PPP interface through which the remote LAC client was
        connected.  If unknown, this object contains a value of zero.

        For locally originated PPP sessions (LNS-like), this object has a value
        of zero.

        This object is deprecated in favor of
        usdL2tpSessionStatusLacTunneledIfIndex."
    ::= { usdL2tpSessionStatusEntry 2 }

usdL2tpSessionStatusLocalSessionId  OBJECT-TYPE
    SYNTAX      UsdL2tpSessionId
    MAX-ACCESS  read-only
    STATUS      current
    DESCRIPTION
        "The local session ID for the session."
    ::= { usdL2tpSessionStatusEntry 3 }

usdL2tpSessionStatusRemoteSessionId  OBJECT-TYPE
    SYNTAX      UsdL2tpSessionId
    MAX-ACCESS  read-only
    STATUS      current
    DESCRIPTION
        "The remote session ID for the session."
    ::= { usdL2tpSessionStatusEntry 4 }

usdL2tpSessionStatusUserName  OBJECT-TYPE
    SYNTAX      DisplayString
    MAX-ACCESS  read-only
    STATUS      current
    DESCRIPTION
        "The peer session name on this interface, typically the login name of
        the remote user.  If the user name is unknown this object will contain a
        zero-length string."
    ::= { usdL2tpSessionStatusEntry 5 }

usdL2tpSessionStatusEffectiveAdminState  OBJECT-TYPE
    SYNTAX      UsdL2tpAdminState
    MAX-ACCESS  read-only
    STATUS      current
    DESCRIPTION
        "The administrative state currently in effect.  This could be the
        configured admin state for this session, or an overriding admin state
        exerted from a higher hierarchical level (system, destination, tunnel)."
    ::= { usdL2tpSessionStatusEntry 6 }

usdL2tpSessionStatusState   OBJECT-TYPE
    SYNTAX      INTEGER {
                    idle(0),
                    connecting(1),
                    established(2),
                    disconnecting(3)
                }
    MAX-ACCESS  read-only
    STATUS      current
    DESCRIPTION
        "The current state of the session."
    ::= { usdL2tpSessionStatusEntry 7 }

usdL2tpSessionStatusCallType  OBJECT-TYPE
    SYNTAX      INTEGER {
                    none(0),
                    lacIncoming(1),
                    lnsIncoming(2),
                    lacOutgoing(3),
                    lnsOutgoing(4)
                }
    MAX-ACCESS  read-only
    STATUS      current
    DESCRIPTION
        "The type of call and role this tunnel peer is providing for this
        session.  For example, lacIncoming(1) indicates this tunnel peer is
        acting as a LAC and generated a Incoming-Call-Request to the tunnel peer
        (the LNS).  Note that tunnel peers can be both LAC and LNS
        simultaneously."
    ::= { usdL2tpSessionStatusEntry 8 }

usdL2tpSessionStatusCallSerialNumber  OBJECT-TYPE
    SYNTAX      Integer32
    MAX-ACCESS  read-only
    STATUS      current
    DESCRIPTION
        "The serial number assigned to this  session."
    ::= { usdL2tpSessionStatusEntry 9 }

usdL2tpSessionStatusTxConnectSpeed  OBJECT-TYPE
    SYNTAX      Integer32
    MAX-ACCESS  read-only
    STATUS      current
    DESCRIPTION
        "The last known transmit baud rate for this session."
    ::= { usdL2tpSessionStatusEntry 10 }

usdL2tpSessionStatusRxConnectSpeed  OBJECT-TYPE
    SYNTAX      Integer32
    MAX-ACCESS  read-only
    STATUS      current
    DESCRIPTION
        "The last known receive baud rate for this session."
    ::= { usdL2tpSessionStatusEntry 11 }

usdL2tpSessionStatusCallBearerType    OBJECT-TYPE
    SYNTAX      INTEGER {
                    none(0),
                    digital(1),
                    analog(2)
                }
    MAX-ACCESS  read-only
    STATUS      current
    DESCRIPTION
        "The bearer type of this session."
    ::= { usdL2tpSessionStatusEntry 12 }

usdL2tpSessionStatusFramingType  OBJECT-TYPE
    SYNTAX      INTEGER {
                    none(0),
                    sync(1),
                    async(2)
                }
    MAX-ACCESS  read-only
    STATUS      current
    DESCRIPTION
        "The framing type of this session."
    ::= { usdL2tpSessionStatusEntry 13 }

usdL2tpSessionStatusPhysChanId   OBJECT-TYPE
    SYNTAX      Integer32
    MAX-ACCESS  read-only
    STATUS      current
    DESCRIPTION
        "The physical channel identifier for the session.

        For pass-through PPP sessions, typically the ifIndex of the access
        interface lying below the PPP interface identified by
        usdL2tpSessionStatusLacTunneledIfIndex."
    ::= { usdL2tpSessionStatusEntry 14 }

usdL2tpSessionStatusDnis    OBJECT-TYPE
    SYNTAX      DisplayString
    MAX-ACCESS  read-only
    STATUS      current
    DESCRIPTION
        "The Dialed Number Information String that the LAC obtained from the
        network for the session.  If no DNIS was provided, a zero-length string
        will be returned."
    ::= { usdL2tpSessionStatusEntry 15 }

usdL2tpSessionStatusClid    OBJECT-TYPE
    SYNTAX      DisplayString
    MAX-ACCESS  read-only
    STATUS      current
    DESCRIPTION
        "The Calling Line ID that the LAC obtained from the network for the
        session.  If no CLID was provided, a zero-length string will be
        returned."
    ::= { usdL2tpSessionStatusEntry 16 }

usdL2tpSessionStatusSubAddress  OBJECT-TYPE
    SYNTAX      DisplayString
    MAX-ACCESS  read-only
    STATUS      current
    DESCRIPTION
        "The SubAddress that the LAC obtained from the network for the session.
        If no SubAddress was provided, a zero-length string will be returned."
    ::= { usdL2tpSessionStatusEntry 17 }

usdL2tpSessionStatusPrivateGroupId  OBJECT-TYPE
    SYNTAX      DisplayString
    MAX-ACCESS  read-only
    STATUS      current
    DESCRIPTION
        "The Private Group Identifier used for this tunneled session.  If no
        Private Group Identifier was provided, a zero-length string will be
        returned."
    ::= { usdL2tpSessionStatusEntry 18 }

usdL2tpSessionStatusProxyLcp  OBJECT-TYPE
    SYNTAX      TruthValue
    MAX-ACCESS  read-only
    STATUS      current
    DESCRIPTION
        "Indicates whether the LAC performed proxy LCP for this session."
    ::= { usdL2tpSessionStatusEntry 19 }

usdL2tpSessionStatusAuthMethod  OBJECT-TYPE
    SYNTAX      INTEGER {
                    none(0),
                    pppChap(1),
                    pppPap(2),
                    pppMsChap(3)
                }
    MAX-ACCESS  read-only
    STATUS      current
    DESCRIPTION
        "The proxy authentication method employed by the LAC for the session.
        If usdL2tpSessionProxyLcp is false(2) this object reports a value of
        'none' and should be ignored."
    ::= { usdL2tpSessionStatusEntry 20 }

usdL2tpSessionStatusSequencingState  OBJECT-TYPE
    SYNTAX      INTEGER {
                    none(0),
                    remote(1),
                    local(2),
                    both(3)
                }
    MAX-ACCESS  read-only
    STATUS      current
    DESCRIPTION
        "Indicates which tunnel peers have requested payload sequencing."
    ::= { usdL2tpSessionStatusEntry 21 }

usdL2tpSessionStatusSendSeq OBJECT-TYPE
    SYNTAX      Integer32 (0..65535)
    MAX-ACCESS  read-only
    STATUS      current
    DESCRIPTION
        "The next send sequence number."
    ::= { usdL2tpSessionStatusEntry 22 }

usdL2tpSessionStatusRecvSeq OBJECT-TYPE
    SYNTAX      Integer32 (0..65535)
    MAX-ACCESS  read-only
    STATUS      current
    DESCRIPTION
        "The next receive sequence number expected."
    ::= { usdL2tpSessionStatusEntry 23 }

usdL2tpSessionStatusLacTunneledIfIndex OBJECT-TYPE
    SYNTAX      InterfaceIndexOrZero
    MAX-ACCESS  read-only
    STATUS      current
    DESCRIPTION
        "For pass-through remote client sessions (conventional LAC), the ifIndex
        of an associated local interface through which the remote LAC client was
        connected.  If unknown, this object contains a value of zero.

        For locally originated sessions (LNS-like), this object has a value of
        zero."
    ::= { usdL2tpSessionStatusEntry 24 }

usdL2tpSessionStatusCumEstabTime OBJECT-TYPE
    SYNTAX      Unsigned32
    UNITS       "seconds"
    MAX-ACCESS  read-only
    STATUS      current
    DESCRIPTION
        "The cumulative time in seconds that this session, since first being
        created, has spent in the established state (which may be punctuated by
        intervals outside the established state)."
    ::= { usdL2tpSessionStatusEntry 25 }


--
-- L2TP Session-level Statistics
--
usdL2tpSessionStatTable   OBJECT-TYPE
    SYNTAX      SEQUENCE OF UsdL2tpSessionStatEntry
    MAX-ACCESS  not-accessible
    STATUS      current
    DESCRIPTION
        "The L2TP session statistics table."
    ::= { usdL2tpSessionStatistics 1 }

usdL2tpSessionStatEntry   OBJECT-TYPE
    SYNTAX      UsdL2tpSessionStatEntry
    MAX-ACCESS  not-accessible
    STATUS      current
    DESCRIPTION
        "An L2TP session interface statistics entry."
    INDEX { usdL2tpSessionStatIfIndex }
    ::= { usdL2tpSessionStatTable 1 }

UsdL2tpSessionStatEntry ::= SEQUENCE {
    usdL2tpSessionStatIfIndex
        InterfaceIndex,
    usdL2tpSessionStatPayRecvOctets
        Counter32,
    usdL2tpSessionStatPayRecvPackets
        Counter32,
    usdL2tpSessionStatPayRecvErrors
        Counter32,
    usdL2tpSessionStatPayRecvDiscards
        Counter32,
    usdL2tpSessionStatPaySendOctets
        Counter32,
    usdL2tpSessionStatPaySendPackets
        Counter32,
    usdL2tpSessionStatPaySendErrors
        Counter32,
    usdL2tpSessionStatPaySendDiscards
        Counter32,

    usdL2tpSessionStatRecvOutOfSequence
        Counter32,
    usdL2tpSessionStatResequencingTimeouts
        Counter32,

    usdL2tpSessionStatPayLostPackets
        Unsigned32
    }

usdL2tpSessionStatIfIndex OBJECT-TYPE
    SYNTAX      InterfaceIndex
    MAX-ACCESS  not-accessible
    STATUS      current
    DESCRIPTION
        "The ifIndex of an L2TP session interface."
    ::= { usdL2tpSessionStatEntry 1 }

usdL2tpSessionStatPayRecvOctets OBJECT-TYPE
    SYNTAX      Counter32
    MAX-ACCESS  read-only
    STATUS      current
    DESCRIPTION
        "Number of payload octets received."
    ::= { usdL2tpSessionStatEntry 2 }

usdL2tpSessionStatPayRecvPackets OBJECT-TYPE
    SYNTAX      Counter32
    MAX-ACCESS  read-only
    STATUS      current
    DESCRIPTION
        "Number of payload packets received."
    ::= { usdL2tpSessionStatEntry 3 }

usdL2tpSessionStatPayRecvErrors OBJECT-TYPE
    SYNTAX      Counter32
    MAX-ACCESS  read-only
    STATUS      current
    DESCRIPTION
        "Number of payload packets incurring reception errors."
    ::= { usdL2tpSessionStatEntry 4 }

usdL2tpSessionStatPayRecvDiscards OBJECT-TYPE
    SYNTAX      Counter32
    MAX-ACCESS  read-only
    STATUS      current
    DESCRIPTION
        "Number of payload packets discarded after reception."
    ::= { usdL2tpSessionStatEntry 5 }

usdL2tpSessionStatPaySendOctets OBJECT-TYPE
    SYNTAX      Counter32
    MAX-ACCESS  read-only
    STATUS      current
    DESCRIPTION
        "Number of payload octets sent."
    ::= { usdL2tpSessionStatEntry 6 }

usdL2tpSessionStatPaySendPackets OBJECT-TYPE
    SYNTAX      Counter32
    MAX-ACCESS  read-only
    STATUS      current
    DESCRIPTION
        "Number of payload packets sent."
    ::= { usdL2tpSessionStatEntry 7 }

usdL2tpSessionStatPaySendErrors OBJECT-TYPE
    SYNTAX      Counter32
    MAX-ACCESS  read-only
    STATUS      current
    DESCRIPTION
        "Number of payload packets incurring transmission errors."
    ::= { usdL2tpSessionStatEntry 8 }

usdL2tpSessionStatPaySendDiscards OBJECT-TYPE
    SYNTAX      Counter32
    MAX-ACCESS  read-only
    STATUS      current
    DESCRIPTION
        "Number of payload packets discarded before transmission."
    ::= { usdL2tpSessionStatEntry 9 }

--
-- other
--
usdL2tpSessionStatRecvOutOfSequence  OBJECT-TYPE
    SYNTAX      Counter32
    MAX-ACCESS  read-only
    STATUS      current
    DESCRIPTION
        "The number of packets received out of sequence."
    ::= { usdL2tpSessionStatEntry 10 }

usdL2tpSessionStatResequencingTimeouts  OBJECT-TYPE
    SYNTAX      Counter32
    MAX-ACCESS  read-only
    STATUS      current
    DESCRIPTION
        "The number of reassembly timeouts that have occurred."
    ::= { usdL2tpSessionStatEntry 11 }


usdL2tpSessionStatPayLostPackets OBJECT-TYPE
    SYNTAX      Unsigned32
    MAX-ACCESS  read-only
    STATUS      current
    DESCRIPTION
        "When sequence numbers are enabled, this value represents the estimated
        number of payload packets lost, based on observed gaps in sequence
        numbers.  This estimate is subject to correction (decrement) upon
        receipt of out-of-sequence packets that fill previously observed gaps."
    ::= { usdL2tpSessionStatEntry 12 }


-- ......................................................................
-- L2TP Transport Group
-- ......................................................................

--
-- UDP/IP Transport
--
usdL2tpTransportUdpIp        OBJECT IDENTIFIER   ::= { usdL2tpTransport 1 }
usdL2tpUdpIpSystem           OBJECT IDENTIFIER   ::= { usdL2tpTransportUdpIp 1 }
usdL2tpUdpIpDestination      OBJECT IDENTIFIER   ::= { usdL2tpTransportUdpIp 2 }
usdL2tpUdpIpTunnel           OBJECT IDENTIFIER   ::= { usdL2tpTransportUdpIp 3 }
usdL2tpUdpIpSession          OBJECT IDENTIFIER   ::= { usdL2tpTransportUdpIp 4 }

--
-- UDP/IP Destination
--
usdL2tpUdpIpDestTable   OBJECT-TYPE
    SYNTAX      SEQUENCE OF UsdL2tpUdpIpDestEntry
    MAX-ACCESS  not-accessible
    STATUS      current
    DESCRIPTION
        "The L2TP UDP/IP destination table.  Reports the UDP/IP characteristics
        of a L2TP UDP/IP destination.

        A L2TP UDP/IP destination is associated with a local router, a local IP
        address, and with a remote IP address for the L2TP peer.  More specific
        UDP/IP detail per tunnel is reported in the usdL2tpUdpIpTunnelTable."
    ::= { usdL2tpUdpIpDestination 1 }

usdL2tpUdpIpDestEntry   OBJECT-TYPE
    SYNTAX      UsdL2tpUdpIpDestEntry
    MAX-ACCESS  not-accessible
    STATUS      current
    DESCRIPTION
        "Describes the UDP/IP attributes of an L2TP destination."
    INDEX { usdL2tpUdpIpDestIfIndex }
    ::= { usdL2tpUdpIpDestTable 1 }

UsdL2tpUdpIpDestEntry ::= SEQUENCE {
    usdL2tpUdpIpDestIfIndex
        InterfaceIndex,
    usdL2tpUdpIpDestRouterIndex
        Unsigned32,
    usdL2tpUdpIpDestLocalAddress
        IpAddress,
    usdL2tpUdpIpDestRemoteAddress
        IpAddress
    }

usdL2tpUdpIpDestIfIndex OBJECT-TYPE
    SYNTAX      InterfaceIndex
    MAX-ACCESS  not-accessible
    STATUS      current
    DESCRIPTION
        "Same value as ifIndex for the corresponding entry in Interfaces MIB
        ifTable."
    ::= { usdL2tpUdpIpDestEntry 1 }

usdL2tpUdpIpDestRouterIndex  OBJECT-TYPE
    SYNTAX      Unsigned32
    MAX-ACCESS  read-only
    STATUS      current
    DESCRIPTION
        "The index of an entry in the usdRouterTable for the local router with
        which this L2TP destination interface is associated."
    ::= { usdL2tpUdpIpDestEntry 2 }

usdL2tpUdpIpDestLocalAddress  OBJECT-TYPE
    SYNTAX      IpAddress
    MAX-ACCESS  read-only
    STATUS      current
    DESCRIPTION
        "This L2TP destination's local IP address."
    ::= { usdL2tpUdpIpDestEntry 3 }

usdL2tpUdpIpDestRemoteAddress  OBJECT-TYPE
    SYNTAX      IpAddress
    MAX-ACCESS  read-only
    STATUS      current
    DESCRIPTION
        "The IP address of the remote L2TP endpoint."
    ::= { usdL2tpUdpIpDestEntry 4 }


--
-- UDP/IP Tunnel
--
usdL2tpUdpIpTunnelTable    OBJECT-TYPE
    SYNTAX      SEQUENCE OF UsdL2tpUdpIpTunnelEntry
    MAX-ACCESS  not-accessible
    STATUS      current
    DESCRIPTION
        "The L2TP UDP/IP tunnel table.  Reports the UDP/IP characteristics of
        L2TP UDP/IP tunnels.

        A L2TP UDP/IP tunnel is defined in terms of the local and remote IP
        addresses and UDP ports."
    ::= { usdL2tpUdpIpTunnel 1 }

usdL2tpUdpIpTunnelEntry    OBJECT-TYPE
    SYNTAX      UsdL2tpUdpIpTunnelEntry
    MAX-ACCESS  not-accessible
    STATUS      current
    DESCRIPTION
        "An L2TP UDP/IP tunnel entry."
    INDEX { usdL2tpUdpIpTunnelIfIndex }
    ::= { usdL2tpUdpIpTunnelTable 1 }

UsdL2tpUdpIpTunnelEntry ::= SEQUENCE {
    usdL2tpUdpIpTunnelIfIndex
        InterfaceIndex,
    usdL2tpUdpIpTunnelRouterIndex
        Unsigned32,
    usdL2tpUdpIpTunnelLocalAddress
        IpAddress,
    usdL2tpUdpIpTunnelLocalPort
        Integer32,
    usdL2tpUdpIpTunnelRemoteAddress
        IpAddress,
    usdL2tpUdpIpTunnelRemotePort
        Integer32
    }

usdL2tpUdpIpTunnelIfIndex  OBJECT-TYPE
    SYNTAX      InterfaceIndex
    MAX-ACCESS  not-accessible
    STATUS      current
    DESCRIPTION
        "Same as the value of ifIndex for the corresponding entry in Interfaces
        MIB ifTable."
    ::= { usdL2tpUdpIpTunnelEntry 1 }

usdL2tpUdpIpTunnelRouterIndex  OBJECT-TYPE
    SYNTAX      Unsigned32
    MAX-ACCESS  read-only
    STATUS      current
    DESCRIPTION
        "The index of an entry in the usdRouterTable for the local router with
        which this L2TP tunnel interface is associated."
    ::= { usdL2tpUdpIpTunnelEntry 2 }

usdL2tpUdpIpTunnelLocalAddress OBJECT-TYPE
    SYNTAX      IpAddress
    MAX-ACCESS  read-only
    STATUS      current
    DESCRIPTION
        "The local IP address for this UDP/IP tunnel."
    ::= { usdL2tpUdpIpTunnelEntry 3 }

usdL2tpUdpIpTunnelLocalPort OBJECT-TYPE
    SYNTAX      Integer32
    MAX-ACCESS  read-only
    STATUS      current
    DESCRIPTION
        "The local UDP port for this UDP/IP tunnel."
    ::= { usdL2tpUdpIpTunnelEntry 4 }

usdL2tpUdpIpTunnelRemoteAddress OBJECT-TYPE
    SYNTAX      IpAddress
    MAX-ACCESS  read-only
    STATUS      current
    DESCRIPTION
        "The remote IP address for this UDP/IP tunnel."
    ::= { usdL2tpUdpIpTunnelEntry 5 }

usdL2tpUdpIpTunnelRemotePort OBJECT-TYPE
    SYNTAX      Integer32
    MAX-ACCESS  read-only
    STATUS      current
    DESCRIPTION
        "The remote UDP port for this UDP/IP tunnel."
    ::= { usdL2tpUdpIpTunnelEntry 6 }


-- ++++++++++++++++++++++++++++++++++++++++++++++++++++++++++++++++++++++
-- conformance information
-- ++++++++++++++++++++++++++++++++++++++++++++++++++++++++++++++++++++++

usdL2tpGroups      OBJECT IDENTIFIER ::= { usdL2tpConformance 1 }
usdL2tpCompliances OBJECT IDENTIFIER ::= { usdL2tpConformance 2 }

--
-- compliance statements
--

usdL2tpCompliance MODULE-COMPLIANCE
    STATUS      obsolete
    DESCRIPTION
        "Obsolete compliance statement for SNMPv2 entities which implement the
        L2TP MIB.  This statement became obsolete when
        usdL2tpTunnelStatusCumEstabTime, usdL2tpSessionStatusCumEstabTime and
        usdL2tpSessionStatPayLostPackets were added, and
        usdL2tpSessionStatusLacTunneledIfIndex replaced
        usdL2tpSessionStatusLacPppIfIndex."
    MODULE   -- this module
        -- unconditionally mandatory groups
        MANDATORY-GROUPS {
            usdL2tpConfigGroup,
            usdL2tpStatusGroup,
            usdL2tpStatGroup,
            usdL2tpMapGroup
        }
        -- conditionally mandatory group
        GROUP       usdL2tpUdpIpGroup
        DESCRIPTION
            "The usdL2tpUdpIp group is mandatory only when L2TP is running over
            UDP/IP."
    ::= { usdL2tpCompliances 1 }                                       -- RX 2.0

usdL2tpCompliance2 MODULE-COMPLIANCE
    STATUS      obsolete
    DESCRIPTION
        "Obsolete compliance statement for SNMPv2 entities which implement the
        L2TP MIB.  This statement became obsolete when a new object was added to
        the configuration group."
    MODULE   -- this module
        -- unconditionally mandatory groups
        MANDATORY-GROUPS {
            usdL2tpConfigGroup,
            usdL2tpStatusGroup2,
            usdL2tpStatGroup2,
            usdL2tpMapGroup
        }
        -- conditionally mandatory group
        GROUP       usdL2tpUdpIpGroup
        DESCRIPTION
            "The usdL2tpUdpIp group is mandatory only when L2TP is running over
            UDP/IP."
    ::= { usdL2tpCompliances 2 }                                       -- RX 3.0

usdL2tpCompliance3 MODULE-COMPLIANCE
    STATUS      obsolete
    DESCRIPTION
        "Obsolete compliance statement for SNMPv2 entities which implement the
        L2TP MIB.  This statement became obsolete when a new objects were added
        to the configuration group."
    MODULE   -- this module
        -- unconditionally mandatory groups
        MANDATORY-GROUPS {
            usdL2tpConfigGroup2,
            usdL2tpStatusGroup2,
            usdL2tpStatGroup2,
            usdL2tpMapGroup
        }
        -- conditionally mandatory group
        GROUP       usdL2tpUdpIpGroup
        DESCRIPTION
            "The usdL2tpUdpIp group is mandatory only when L2TP is running over
            UDP/IP."
    ::= { usdL2tpCompliances 3 }                                       -- RX 3.2

usdL2tpCompliance4 MODULE-COMPLIANCE
    STATUS          current
    DESCRIPTION
        "The compliance statement for SNMPv2 entities which implement the L2TP
        MIB."
    MODULE          -- this module
        -- unconditionally mandatory groups
        MANDATORY-GROUPS {
            usdL2tpConfigGroup3,
            usdL2tpStatusGroup2,
            usdL2tpStatGroup2,
            usdL2tpMapGroup
        }
        -- conditionally mandatory group
        GROUP   usdL2tpUdpIpGroup
        DESCRIPTION
            "The usdL2tpUdpIp group is mandatory only when L2TP is running over
            UDP/IP."
    ::= { usdL2tpCompliances 4 }                                       -- RX 3.3


-- units of conformance

usdL2tpConfigGroup OBJECT-GROUP
    OBJECTS {
        usdL2tpSysConfigAdminState,
        usdL2tpSysConfigDestructTimeout,
        usdL2tpSysConfigIpChecksumEnable,

        usdL2tpDestConfigRowStatus,
        usdL2tpDestConfigAdminState,

        usdL2tpTunnelConfigRowStatus,
        usdL2tpTunnelConfigAdminState,

        usdL2tpSessionConfigRowStatus,
        usdL2tpSessionConfigAdminState
    }
    STATUS          obsolete
    DESCRIPTION
        "Obsolete collection of objects providing configuration information of
        the L2TP protocol, tunnels and sessions.  This group became obsolete
        when usdL2tpSysConfigReceiveDataSequencingIgnore was added."
    ::= { usdL2tpGroups 1 }

usdL2tpStatusGroup OBJECT-GROUP
    OBJECTS {
        usdL2tpSysStatusProtocolVersion,
        usdL2tpSysStatusVendorName,
        usdL2tpSysStatusFirmwareRev,
        usdL2tpSysStatusTotalDestinations,
        usdL2tpSysStatusFailedDestinations,
        usdL2tpSysStatusActiveDestinations,
        usdL2tpSysStatusTotalTunnels,
        usdL2tpSysStatusFailedTunnels,
        usdL2tpSysStatusFailedTunnelAuthens,
        usdL2tpSysStatusActiveTunnels,
        usdL2tpSysStatusTotalSessions,
        usdL2tpSysStatusFailedSessions,
        usdL2tpSysStatusActiveSessions,

        usdL2tpDestStatusEffectiveAdminState,
        usdL2tpDestStatusTotalTunnels,
        usdL2tpDestStatusFailedTunnels,
        usdL2tpDestStatusFailedTunnelAuthens,
        usdL2tpDestStatusActiveTunnels,
        usdL2tpDestStatusTotalSessions,
        usdL2tpDestStatusFailedSessions,
        usdL2tpDestStatusActiveSessions,

        usdL2tpTunnelStatusEffectiveAdminState,
        usdL2tpTunnelStatusLocalTunnelId,
        usdL2tpTunnelStatusRemoteTunnelId,
        usdL2tpTunnelStatusState,
        usdL2tpTunnelStatusInitiated,
        usdL2tpTunnelStatusRemoteHostName,
        usdL2tpTunnelStatusRemoteVendorName,
        usdL2tpTunnelStatusRemoteFirmwareRevision,
        usdL2tpTunnelStatusRemoteProtocolVersion,
        usdL2tpTunnelStatusRemoteBearerCapabilities,
        usdL2tpTunnelStatusRemoteFramingCapabilities,
        usdL2tpTunnelStatusRecvWindowSize,
        usdL2tpTunnelStatusSendWindowSize,
        usdL2tpTunnelStatusSendQueueDepth,
        usdL2tpTunnelStatusRecvSeq,
        usdL2tpTunnelStatusRecvSeqAck,
        usdL2tpTunnelStatusSendSeq,
        usdL2tpTunnelStatusSendSeqAck,
        usdL2tpTunnelStatusTotalSessions,
        usdL2tpTunnelStatusFailedSessions,
        usdL2tpTunnelStatusActiveSessions,
        usdL2tpTunnelStatusLastResultCode,
        usdL2tpTunnelStatusLastErrorCode,
        usdL2tpTunnelStatusLastErrorMessage,

        usdL2tpSessionStatusLacPppIfIndex,
        usdL2tpSessionStatusLocalSessionId,
        usdL2tpSessionStatusRemoteSessionId,
        usdL2tpSessionStatusUserName,
        usdL2tpSessionStatusState,
        usdL2tpSessionStatusCallType,
        usdL2tpSessionStatusCallSerialNumber,
        usdL2tpSessionStatusTxConnectSpeed,
        usdL2tpSessionStatusRxConnectSpeed,
        usdL2tpSessionStatusCallBearerType,
        usdL2tpSessionStatusFramingType,
        usdL2tpSessionStatusPhysChanId,
        usdL2tpSessionStatusDnis,
        usdL2tpSessionStatusClid,
        usdL2tpSessionStatusSubAddress,
        usdL2tpSessionStatusPrivateGroupId,
        usdL2tpSessionStatusProxyLcp,
        usdL2tpSessionStatusAuthMethod,
        usdL2tpSessionStatusSequencingState,
        usdL2tpSessionStatusSendSeq,
        usdL2tpSessionStatusRecvSeq
    }
    STATUS          obsolete
    DESCRIPTION
        "Obsolete collection of objects providing status of the L2TP protocol at
        the system, destination, tunnel, and session levels.  This group became
        obsolete when new objects were added."
    ::= { usdL2tpGroups 2 }

usdL2tpStatGroup OBJECT-GROUP
    OBJECTS {
        usdL2tpDestStatCtlRecvOctets,
        usdL2tpDestStatCtlRecvPackets,
        usdL2tpDestStatCtlRecvErrors,
        usdL2tpDestStatCtlRecvDiscards,
        usdL2tpDestStatCtlSendOctets,
        usdL2tpDestStatCtlSendPackets,
        usdL2tpDestStatCtlSendErrors,
        usdL2tpDestStatCtlSendDiscards,
        usdL2tpDestStatPayRecvOctets,
        usdL2tpDestStatPayRecvPackets,
        usdL2tpDestStatPayRecvErrors,
        usdL2tpDestStatPayRecvDiscards,
        usdL2tpDestStatPaySendOctets,
        usdL2tpDestStatPaySendPackets,
        usdL2tpDestStatPaySendErrors,
        usdL2tpDestStatPaySendDiscards,

        usdL2tpTunnelStatCtlRecvOctets,
        usdL2tpTunnelStatCtlRecvPackets,
        usdL2tpTunnelStatCtlRecvErrors,
        usdL2tpTunnelStatCtlRecvDiscards,
        usdL2tpTunnelStatCtlSendOctets,
        usdL2tpTunnelStatCtlSendPackets,
        usdL2tpTunnelStatCtlSendErrors,
        usdL2tpTunnelStatCtlSendDiscards,
        usdL2tpTunnelStatPayRecvOctets,
        usdL2tpTunnelStatPayRecvPackets,
        usdL2tpTunnelStatPayRecvErrors,
        usdL2tpTunnelStatPayRecvDiscards,
        usdL2tpTunnelStatPaySendOctets,
        usdL2tpTunnelStatPaySendPackets,
        usdL2tpTunnelStatPaySendErrors,
        usdL2tpTunnelStatPaySendDiscards,
        usdL2tpTunnelStatCtlRecvZLB,
        usdL2tpTunnelStatCtlRecvOutOfSequence,
        usdL2tpTunnelStatCtlRecvOutOfWindow,
        usdL2tpTunnelStatCtlSendZLB,
        usdL2tpTunnelStatCtlSendRetransmits,

        usdL2tpSessionStatPayRecvOctets,
        usdL2tpSessionStatPayRecvPackets,
        usdL2tpSessionStatPayRecvErrors,
        usdL2tpSessionStatPayRecvDiscards,
        usdL2tpSessionStatPaySendOctets,
        usdL2tpSessionStatPaySendPackets,
        usdL2tpSessionStatPaySendErrors,
        usdL2tpSessionStatPaySendDiscards,
        usdL2tpSessionStatRecvOutOfSequence,
        usdL2tpSessionStatResequencingTimeouts
    }
    STATUS          obsolete
    DESCRIPTION
        "Obsolete collection of objects providing statistics of the L2TP
        protocol at the destination, tunnel, and session levels.  This group
        became obsolete when new objects were added."
    ::= { usdL2tpGroups 3 }

usdL2tpMapGroup OBJECT-GROUP
    OBJECTS {
        usdL2tpMapTifSidToSifSessionIfIndex,
        usdL2tpMapTidToTifIfIndex
    }
    STATUS          current
    DESCRIPTION
        "A collection of objects providing mapping associations among L2TP
        components."
    ::= { usdL2tpGroups 4 }

usdL2tpUdpIpGroup OBJECT-GROUP
    OBJECTS {
        usdL2tpUdpIpDestRouterIndex,
        usdL2tpUdpIpDestLocalAddress,
        usdL2tpUdpIpDestRemoteAddress,

        usdL2tpUdpIpTunnelRouterIndex,
        usdL2tpUdpIpTunnelLocalAddress,
        usdL2tpUdpIpTunnelLocalPort,
        usdL2tpUdpIpTunnelRemoteAddress,
        usdL2tpUdpIpTunnelRemotePort
    }
    STATUS          current
    DESCRIPTION
        "A collection of objects providing UDP/IP transport information for L2TP
        components."
    ::= { usdL2tpGroups 5 }

usdL2tpStatusGroup2 OBJECT-GROUP
    OBJECTS {
        usdL2tpSysStatusProtocolVersion,
        usdL2tpSysStatusVendorName,
        usdL2tpSysStatusFirmwareRev,
        usdL2tpSysStatusTotalDestinations,
        usdL2tpSysStatusFailedDestinations,
        usdL2tpSysStatusActiveDestinations,
        usdL2tpSysStatusTotalTunnels,
        usdL2tpSysStatusFailedTunnels,
        usdL2tpSysStatusFailedTunnelAuthens,
        usdL2tpSysStatusActiveTunnels,
        usdL2tpSysStatusTotalSessions,
        usdL2tpSysStatusFailedSessions,
        usdL2tpSysStatusActiveSessions,

        usdL2tpDestStatusTransport,
        usdL2tpDestStatusEffectiveAdminState,
        usdL2tpDestStatusTotalTunnels,
        usdL2tpDestStatusFailedTunnels,
        usdL2tpDestStatusFailedTunnelAuthens,
        usdL2tpDestStatusActiveTunnels,
        usdL2tpDestStatusTotalSessions,
        usdL2tpDestStatusFailedSessions,
        usdL2tpDestStatusActiveSessions,

        usdL2tpTunnelStatusTransport,
        usdL2tpTunnelStatusLocalTunnelId,
        usdL2tpTunnelStatusRemoteTunnelId,
        usdL2tpTunnelStatusEffectiveAdminState,
        usdL2tpTunnelStatusState,
        usdL2tpTunnelStatusInitiated,
        usdL2tpTunnelStatusRemoteHostName,
        usdL2tpTunnelStatusRemoteVendorName,
        usdL2tpTunnelStatusRemoteFirmwareRevision,
        usdL2tpTunnelStatusRemoteProtocolVersion,
        usdL2tpTunnelStatusRemoteBearerCapabilities,
        usdL2tpTunnelStatusRemoteFramingCapabilities,
        usdL2tpTunnelStatusRecvWindowSize,
        usdL2tpTunnelStatusSendWindowSize,
        usdL2tpTunnelStatusSendQueueDepth,
        usdL2tpTunnelStatusRecvSeq,
        usdL2tpTunnelStatusRecvSeqAck,
        usdL2tpTunnelStatusSendSeq,
        usdL2tpTunnelStatusSendSeqAck,
        usdL2tpTunnelStatusTotalSessions,
        usdL2tpTunnelStatusFailedSessions,
        usdL2tpTunnelStatusActiveSessions,
        usdL2tpTunnelStatusLastResultCode,
        usdL2tpTunnelStatusLastErrorCode,
        usdL2tpTunnelStatusLastErrorMessage,
        usdL2tpTunnelStatusCumEstabTime,

        -- usdL2tpSessionStatusLacPppIfIndex deprecated
        usdL2tpSessionStatusLocalSessionId,
        usdL2tpSessionStatusRemoteSessionId,
        usdL2tpSessionStatusUserName,
        usdL2tpSessionStatusEffectiveAdminState,
        usdL2tpSessionStatusState,
        usdL2tpSessionStatusCallType,
        usdL2tpSessionStatusCallSerialNumber,
        usdL2tpSessionStatusTxConnectSpeed,
        usdL2tpSessionStatusRxConnectSpeed,
        usdL2tpSessionStatusCallBearerType,
        usdL2tpSessionStatusFramingType,
        usdL2tpSessionStatusPhysChanId,
        usdL2tpSessionStatusDnis,
        usdL2tpSessionStatusClid,
        usdL2tpSessionStatusSubAddress,
        usdL2tpSessionStatusPrivateGroupId,
        usdL2tpSessionStatusProxyLcp,
        usdL2tpSessionStatusAuthMethod,
        usdL2tpSessionStatusSequencingState,
        usdL2tpSessionStatusSendSeq,
        usdL2tpSessionStatusRecvSeq,
        usdL2tpSessionStatusLacTunneledIfIndex,
        usdL2tpSessionStatusCumEstabTime
    }
    STATUS          current
    DESCRIPTION
        "A collection of objects providing status of the L2TP protocol at the
        system, destination, tunnel, and session levels."
    ::= { usdL2tpGroups 6 }

usdL2tpStatGroup2 OBJECT-GROUP
    OBJECTS {
        usdL2tpDestStatCtlRecvOctets,
        usdL2tpDestStatCtlRecvPackets,
        usdL2tpDestStatCtlRecvErrors,
        usdL2tpDestStatCtlRecvDiscards,
        usdL2tpDestStatCtlSendOctets,
        usdL2tpDestStatCtlSendPackets,
        usdL2tpDestStatCtlSendErrors,
        usdL2tpDestStatCtlSendDiscards,
        usdL2tpDestStatPayRecvOctets,
        usdL2tpDestStatPayRecvPackets,
        usdL2tpDestStatPayRecvErrors,
        usdL2tpDestStatPayRecvDiscards,
        usdL2tpDestStatPaySendOctets,
        usdL2tpDestStatPaySendPackets,
        usdL2tpDestStatPaySendErrors,
        usdL2tpDestStatPaySendDiscards,

        usdL2tpTunnelStatCtlRecvOctets,
        usdL2tpTunnelStatCtlRecvPackets,
        usdL2tpTunnelStatCtlRecvErrors,
        usdL2tpTunnelStatCtlRecvDiscards,
        usdL2tpTunnelStatCtlSendOctets,
        usdL2tpTunnelStatCtlSendPackets,
        usdL2tpTunnelStatCtlSendErrors,
        usdL2tpTunnelStatCtlSendDiscards,
        usdL2tpTunnelStatPayRecvOctets,
        usdL2tpTunnelStatPayRecvPackets,
        usdL2tpTunnelStatPayRecvErrors,
        usdL2tpTunnelStatPayRecvDiscards,
        usdL2tpTunnelStatPaySendOctets,
        usdL2tpTunnelStatPaySendPackets,
        usdL2tpTunnelStatPaySendErrors,
        usdL2tpTunnelStatPaySendDiscards,
        usdL2tpTunnelStatCtlRecvZLB,
        usdL2tpTunnelStatCtlRecvOutOfSequence,
        usdL2tpTunnelStatCtlRecvOutOfWindow,
        usdL2tpTunnelStatCtlSendZLB,
        usdL2tpTunnelStatCtlSendRetransmits,

        usdL2tpSessionStatPayRecvOctets,
        usdL2tpSessionStatPayRecvPackets,
        usdL2tpSessionStatPayRecvErrors,
        usdL2tpSessionStatPayRecvDiscards,
        usdL2tpSessionStatPaySendOctets,
        usdL2tpSessionStatPaySendPackets,
        usdL2tpSessionStatPaySendErrors,
        usdL2tpSessionStatPaySendDiscards,
        usdL2tpSessionStatRecvOutOfSequence,
        usdL2tpSessionStatResequencingTimeouts,
        usdL2tpSessionStatPayLostPackets
    }
    STATUS          current
    DESCRIPTION
        "A collection of objects providing statistics of the L2TP protocol at
        the destination, tunnel, and session levels."
    ::= { usdL2tpGroups 7 }

usdL2tpConfigGroup2 OBJECT-GROUP
    OBJECTS {
        usdL2tpSysConfigAdminState,
        usdL2tpSysConfigDestructTimeout,
        usdL2tpSysConfigIpChecksumEnable,
        usdL2tpSysConfigReceiveDataSequencingIgnore,

        usdL2tpDestConfigRowStatus,
        usdL2tpDestConfigAdminState,

        usdL2tpTunnelConfigRowStatus,
        usdL2tpTunnelConfigAdminState,
        
        usdL2tpSessionConfigRowStatus,
        usdL2tpSessionConfigAdminState
    }
    STATUS          obsolete
    DESCRIPTION
        "Obsolete collection of objects providing configuration information of
        the L2TP protocol, tunnels and sessions.  This group became obsolete
        when new objects were added."
    ::= { usdL2tpGroups 8 }

usdL2tpConfigGroup3 OBJECT-GROUP
    OBJECTS {
        usdL2tpSysConfigAdminState,
        usdL2tpSysConfigDestructTimeout,
        usdL2tpSysConfigIpChecksumEnable,
        usdL2tpSysConfigTunnelSwitchingEnabled,
        usdL2tpSysConfigControlRetransmissions,
        usdL2tpSysConfigTunnelIdleTimeout,
        usdL2tpSysConfigReceiveDataSequencingIgnore,

        usdL2tpDestConfigRowStatus,
        usdL2tpDestConfigAdminState,

        usdL2tpTunnelConfigRowStatus,
        usdL2tpTunnelConfigAdminState,
        
        usdL2tpSessionConfigRowStatus,
        usdL2tpSessionConfigAdminState
    }
    STATUS          current
    DESCRIPTION
        "A collection of objects providing configuration information of the L2TP
        protocol, tunnels and sessions."
    ::= { usdL2tpGroups 9 }

END
