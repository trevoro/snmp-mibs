--			Ascend mibredhm MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBREDHM-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibredHealthMonitoringProfile  OBJECT IDENTIFIER ::= { configuration 179}

	-- The mibredHealthMonitoringProfile table
	--
	-- This table contains parameters for the mibredHealthMonitoringProfile profile
	--

    mibredHealthMonitoringProfileTable	OBJECT-TYPE
	SYNTAX		SEQUENCE OF MibredHealthMonitoringProfileEntry
	ACCESS		not-accessible
	STATUS		mandatory
	DESCRIPTION	"A list of mibredHealthMonitoringProfile profile entries."
	::= { mibredHealthMonitoringProfile 1 }

    mibredHealthMonitoringProfileEntry	OBJECT-TYPE
	SYNTAX		MibredHealthMonitoringProfileEntry
	ACCESS		not-accessible
	STATUS		mandatory
	DESCRIPTION	"A mibredHealthMonitoringProfile entry containing objects that
			 maps to the parameters of mibredHealthMonitoringProfile profile."
	INDEX		{ redHealthMonitoringProfile-Index-o }
	::= { mibredHealthMonitoringProfileTable 1 }

    MibredHealthMonitoringProfileEntry ::=
	SEQUENCE {
	    redHealthMonitoringProfile-Index-o
		INTEGER,
	    redHealthMonitoringProfile-HmEnabled
		INTEGER,
	    redHealthMonitoringProfile-MaxWarningPrimary
		INTEGER,
	    redHealthMonitoringProfile-MaxWarningSecondary
		INTEGER,
	    redHealthMonitoringProfile-MaxWarningPerMinutePrimary
		INTEGER,
	    redHealthMonitoringProfile-MaxWarningPerMinuteSecondary
		INTEGER,
	    redHealthMonitoringProfile-MemoryThresholdPrimary
		INTEGER,
	    redHealthMonitoringProfile-MemoryThresholdSecondary
		INTEGER,
	    redHealthMonitoringProfile-MemoryAlertThresholdPrimary
		INTEGER,
	    redHealthMonitoringProfile-MemoryAlertThresholdSecondary
		INTEGER,
	    redHealthMonitoringProfile-MemoryAlertTimeoutPrimary
		INTEGER,
	    redHealthMonitoringProfile-MemoryAlertTimeoutSecondary
		INTEGER,
	    redHealthMonitoringProfile-ResetStuckPrimaryTimeout
		INTEGER,
	    redHealthMonitoringProfile-Action-o
		INTEGER
	}

    redHealthMonitoringProfile-Index-o	OBJECT-TYPE
	SYNTAX	INTEGER
	ACCESS	read-only
	STATUS	mandatory
	DESCRIPTION	""
	::= { mibredHealthMonitoringProfileEntry 1 }

    redHealthMonitoringProfile-HmEnabled	OBJECT-TYPE
	SYNTAX	INTEGER {
		    no (1),
		    yes (2)
		}
	ACCESS	read-write
	STATUS	mandatory
	DESCRIPTION	"Indicates whether health monitoring feature is enabled. Redundancy feature has to be enabled prior to this feature"
	::= { mibredHealthMonitoringProfileEntry 2 }

    redHealthMonitoringProfile-MaxWarningPrimary	OBJECT-TYPE
	SYNTAX	INTEGER
	ACCESS	read-write
	STATUS	mandatory
	DESCRIPTION	"Maximum of total warnings allowed for primary, When the total warnings exceeds this maximum, controller will reset."
	::= { mibredHealthMonitoringProfileEntry 3 }

    redHealthMonitoringProfile-MaxWarningSecondary	OBJECT-TYPE
	SYNTAX	INTEGER
	ACCESS	read-write
	STATUS	mandatory
	DESCRIPTION	"Maximum of total warnings allowed for secondary, When the total warnings exceeds this maximum, controller will reset. Secondary should have a more stringent value than primary."
	::= { mibredHealthMonitoringProfileEntry 4 }

    redHealthMonitoringProfile-MaxWarningPerMinutePrimary	OBJECT-TYPE
	SYNTAX	INTEGER
	ACCESS	read-write
	STATUS	mandatory
	DESCRIPTION	"Maximum of total warning per minute allowed for primary."
	::= { mibredHealthMonitoringProfileEntry 5 }

    redHealthMonitoringProfile-MaxWarningPerMinuteSecondary	OBJECT-TYPE
	SYNTAX	INTEGER
	ACCESS	read-write
	STATUS	mandatory
	DESCRIPTION	"Maximum of total warning per minute allowed for secondary. Secondary should have a more stringent value than primary."
	::= { mibredHealthMonitoringProfileEntry 6 }

    redHealthMonitoringProfile-MemoryThresholdPrimary	OBJECT-TYPE
	SYNTAX	INTEGER
	ACCESS	read-write
	STATUS	mandatory
	DESCRIPTION	"Percent threshold for available memory on primary, controller resets when memory is lower than the threshold."
	::= { mibredHealthMonitoringProfileEntry 7 }

    redHealthMonitoringProfile-MemoryThresholdSecondary	OBJECT-TYPE
	SYNTAX	INTEGER
	ACCESS	read-write
	STATUS	mandatory
	DESCRIPTION	"Percent threshold for available memory on secondary, controller resets when memory is lower than the threshold. Secondary should have a more stringent value than primary."
	::= { mibredHealthMonitoringProfileEntry 8 }

    redHealthMonitoringProfile-MemoryAlertThresholdPrimary	OBJECT-TYPE
	SYNTAX	INTEGER
	ACCESS	read-write
	STATUS	mandatory
	DESCRIPTION	"Percent threshold for memory alert polling on primary, when memory level is lower than the threshold, log message will be sent out."
	::= { mibredHealthMonitoringProfileEntry 9 }

    redHealthMonitoringProfile-MemoryAlertThresholdSecondary	OBJECT-TYPE
	SYNTAX	INTEGER
	ACCESS	read-write
	STATUS	mandatory
	DESCRIPTION	"Percent threshold for memory alert polling on secondary, when memory level is lower than the threshold, log message will be sent out."
	::= { mibredHealthMonitoringProfileEntry 10 }

    redHealthMonitoringProfile-MemoryAlertTimeoutPrimary	OBJECT-TYPE
	SYNTAX	INTEGER
	ACCESS	read-write
	STATUS	mandatory
	DESCRIPTION	"Maximum time (in sec) allowed for memory level stays continuously below memory-alert-threshold-primary."
	::= { mibredHealthMonitoringProfileEntry 11 }

    redHealthMonitoringProfile-MemoryAlertTimeoutSecondary	OBJECT-TYPE
	SYNTAX	INTEGER
	ACCESS	read-write
	STATUS	mandatory
	DESCRIPTION	"Maximum time (in sec) allowed for memory level stays continuously below memory-alert-threshold-secondary."
	::= { mibredHealthMonitoringProfileEntry 12 }

    redHealthMonitoringProfile-ResetStuckPrimaryTimeout	OBJECT-TYPE
	SYNTAX	INTEGER
	ACCESS	read-write
	STATUS	mandatory
	DESCRIPTION	"secondary resets primary if no response from primary exceeds this timeout (in seconds). Minimum is 3 seconds."
	::= { mibredHealthMonitoringProfileEntry 13 }

    redHealthMonitoringProfile-Action-o	OBJECT-TYPE
	SYNTAX	INTEGER {
		    noAction (1),
		    createProfile (2),
		    deleteProfile (3)
		}
	ACCESS	read-write
	STATUS	mandatory
	DESCRIPTION	""
	::= { mibredHealthMonitoringProfileEntry 14 }

END
