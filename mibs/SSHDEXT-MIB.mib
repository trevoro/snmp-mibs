SSHDEXT-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE
			FROM SNMPv2-SMI
		sshdExt
			FROM APENT-MIB;


    apSshdMib MODULE-IDENTITY
	   LAST-UPDATED "0004031500Z" -- Mon April 03 15:00:00 EST 1997
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for SSHD"
      ::= { sshdExt 1}


--arrowpoint
-- apmgmt
--   apSshdExt
--     apSshdExt Scalars

-- Secure Shell Server configuration information

apSshdKeepAlive OBJECT-TYPE
	SYNTAX      INTEGER {
                             disable(0),
                             enable(1)
                            }
	MAX-ACCESS  read-write
	STATUS      current
	DESCRIPTION
	       "Specifies whether the system should send keepalives to the other side"
	DEFVAL {enable}
	::= {sshdExt 2}


apSshdKeyRegenerationInterval OBJECT-TYPE
	SYNTAX      INTEGER    (1..1440)
	MAX-ACCESS  read-write
	STATUS      current
	DESCRIPTION
	       "Automatically regenerate server key after this many minutes
            (if it has been used.)"
	DEFVAL {60}
	::= {sshdExt 3}

apSshdPort OBJECT-TYPE
	SYNTAX      INTEGER    (22..65535)
	MAX-ACCESS  read-write
	STATUS      current
	DESCRIPTION
	       "Specifies the port number that server listens on"
	DEFVAL {22}
	::= {sshdExt 4}

apSshdServerKeyBits OBJECT-TYPE
	SYNTAX      INTEGER    (512..65535)
	MAX-ACCESS  read-write
	STATUS      current
	DESCRIPTION
	       "Defines the number of bits in the server key"
	DEFVAL {768}
	::= {sshdExt 5}

END
