-- *****************************************************************************
-- Unisphere-Data-Accounting-CONF
--
-- SNMP Agent Capabilities definitions for the Accounting MIBs.
--
-- Copyright (c) 2001 Unisphere Networks, Inc.  All rights reserved.
-- *****************************************************************************

Unisphere-Data-Accounting-CONF DEFINITIONS ::= BEGIN

IMPORTS
    MODULE-IDENTITY
        FROM SNMPv2-SMI
    AGENT-CAPABILITIES
        FROM SNMPv2-CONF
    usDataAgents
        FROM Unisphere-Data-Agents
    acctngSelectionType, acctngFileFormat, acctngFileCollectFailedAttempts,
    acctngFileMinAge, acctngBasicGroup
        FROM ACCOUNTING-CONTROL-MIB
    usdAcctngBasicGroup, usdAcctngBasicGroup2, usdAcctngBasicGroup3
        FROM Unisphere-Data-ACCOUNTING-MIB;

usdAccountingAgent MODULE-IDENTITY
    LAST-UPDATED "200111132001Z"  -- 13-Nov-01 03:01 PM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Accounting component of the
        SNMP agent in the Unisphere Routing Switch family of products."
    -- Revision History
    REVISION    "200111132001Z"  -- 13-Nov-01 03:01 PM EST  - RX 4.0
    DESCRIPTION
        "Added support for selection policy name and type objects."
    REVISION    "200111121555Z"  -- 12-Nov-01 10:55 AM EST  - RX 3.2
    DESCRIPTION
        "The initial release of this management information module."
    ::= { usDataAgents 2 }

usdAccountingAgentV1 AGENT-CAPABILITIES
    PRODUCT-RELEASE
        "Version 1 of the Accounting component of the Unisphere Routing Switch
        SNMP agent.  This version of the Accounting component was supported in
        the Unisphere RX 2.0 thru 3.1 system releases."
    STATUS      obsolete
    DESCRIPTION
        "The MIBs supported by the SNMP agent for the Accounting application in
        the Unisphere Routing Switch.  These capabilities became obsolete when
        the usdAcctngSelectionSubtreeType object was deprecated."
    SUPPORTS    ACCOUNTING-CONTROL-MIB
        INCLUDES  { acctngBasicGroup }
        VARIATION   acctngSelectionType
            DESCRIPTION
                "When Unisphere-Data-ACCOUNTING-MIB.rsAcctngSelectionType has
                the ietfAccountControl(0) bit turned off (set to '0'), the
                acctngSelectionType object is ignored."
        VARIATION   acctngFileCollectFailedAttempts
            DESCRIPTION
                "When Unisphere-Data-ACCOUNTING-MIB.rsAcctngSelectionType has
                the ietfAccountControl(0) bit turned off (set to '0'), the
                acctngFileCollectFailedAttempts object is meaningless."
        VARIATION   acctngFileMinAge
            DESCRIPTION
                "When Unisphere-Data-ACCOUNTING-MIB.rsAcctngSelectionType has
                the ietfAccountControl(0) bit turned off (set to '0'), the
                acctngFileMinAge object is meaningless."
        VARIATION   acctngFileFormat
            SYNTAX      INTEGER { other(1) }
            DEFVAL    { other }
            DESCRIPTION
                "The ber(2) encoding option is not supported."
    SUPPORTS    Unisphere-Data-ACCOUNTING-MIB
        INCLUDES  { usdAcctngBasicGroup }
    ::= { usdAccountingAgent 1 }

usdAccountingAgentV2 AGENT-CAPABILITIES
    PRODUCT-RELEASE
        "Version 2 of the Accounting component of the Unisphere Routing Switch
        SNMP agent.  This version of the Accounting component wass supported in
        the Unisphere RX 3.2 thru 3.x system releases."
    STATUS      obsolete
    DESCRIPTION
        "The MIBs supported by the SNMP agent for the Accounting application in
        the Unisphere Routing Switch.  These capabilities became obsolete when
        support was added to the Unisphere-Data-ACCOUNTING-MIB for selection
        policy name and type objects."
    SUPPORTS    ACCOUNTING-CONTROL-MIB
        INCLUDES  { acctngBasicGroup }
        VARIATION   acctngSelectionType
            DESCRIPTION
                "When Unisphere-Data-ACCOUNTING-MIB.rsAcctngSelectionType has
                the ietfAccountControl(0) bit turned off (set to '0'), the
                acctngSelectionType object is ignored."
        VARIATION   acctngFileCollectFailedAttempts
            DESCRIPTION
                "When Unisphere-Data-ACCOUNTING-MIB.rsAcctngSelectionType has
                the ietfAccountControl(0) bit turned off (set to '0'), the
                acctngFileCollectFailedAttempts object is meaningless."
        VARIATION   acctngFileMinAge
            DESCRIPTION
                "When Unisphere-Data-ACCOUNTING-MIB.rsAcctngSelectionType has
                the ietfAccountControl(0) bit turned off (set to '0'), the
                acctngFileMinAge object is meaningless."
        VARIATION   acctngFileFormat
            SYNTAX      INTEGER { other(1) }
            DEFVAL    { other }
            DESCRIPTION
                "The ber(2) encoding option is not supported."
     SUPPORTS   Unisphere-Data-ACCOUNTING-MIB
        INCLUDES  { usdAcctngBasicGroup2 }
    ::= { usdAccountingAgent 2 }

usdAccountingAgentV3 AGENT-CAPABILITIES
    PRODUCT-RELEASE
        "Version 3 of the Accounting component of the Unisphere Routing Switch
        SNMP agent.  This version of the Accounting component is supported in
        the Unisphere RX 4.0 and subsequent system releases."
    STATUS      current
    DESCRIPTION
        "The MIBs supported by the SNMP agent for the Accounting application in
        the Unisphere Routing Switch."
    SUPPORTS    ACCOUNTING-CONTROL-MIB
        INCLUDES  { acctngBasicGroup }
        VARIATION   acctngSelectionType
            DESCRIPTION
                "When Unisphere-Data-ACCOUNTING-MIB.rsAcctngSelectionType has
                the ietfAccountControl(0) bit turned off (set to '0'), the
                acctngSelectionType object is ignored."
        VARIATION   acctngFileCollectFailedAttempts
            DESCRIPTION
                "When Unisphere-Data-ACCOUNTING-MIB.rsAcctngSelectionType has
                the ietfAccountControl(0) bit turned off (set to '0'), the
                acctngFileCollectFailedAttempts object is meaningless."
        VARIATION   acctngFileMinAge
            DESCRIPTION
                "When Unisphere-Data-ACCOUNTING-MIB.rsAcctngSelectionType has
                the ietfAccountControl(0) bit turned off (set to '0'), the
                acctngFileMinAge object is meaningless."
        VARIATION   acctngFileFormat
            SYNTAX      INTEGER { other(1) }
            DEFVAL    { other }
            DESCRIPTION
                "The ber(2) encoding option is not supported."
    SUPPORTS    Unisphere-Data-ACCOUNTING-MIB
        INCLUDES  { usdAcctngBasicGroup3 }
    ::= { usdAccountingAgent 3 }

END
