-- extracted from draft-ietf-ipcdn-cable-gateway-tools-mib-00.txt
-- at Wed Jun 25 06:13:38 2003

   CABH-IETF-CTP-MIB DEFINITIONS ::= BEGIN 
    
   IMPORTS 
      MODULE-IDENTITY, 
      OBJECT-TYPE, 
      mib-2                  FROM SNMPv2-SMI 
    
      TimeStamp, 
      TruthValue             FROM SNMPv2-TC 
    
      OBJECT-GROUP, 
      MODULE-COMPLIANCE      FROM SNMPv2-CONF 
    
      InetAddressType, 
      InetAddress            FROM INET-ADDRESS-MIB; 
    
    
   cabhCtpMib MODULE-IDENTITY 
       LAST-UPDATED    "200306210000Z" -- Jun 21, 2003 
       ORGANIZATION    "IETF IPCDN Working Group" 
       CONTACT-INFO 
               "Kevin Luehrs 
               Postal: Cable Television Laboratories, Inc. 
               400 Centennial Parkway 
               Louisville, Colorado 80027-1266 
               U.S.A. 
               Phone:  +1 303-661-9100 
               Fax:    +1 303-661-9199 
               E-mail: k.luehrs@cablelabs.com; mibs@cablelabs.com 
    
               IETF IPCDN Working Group 
               General Discussion: ipcdn@ietf.org 
               Subscribe: http://www.ietf.org/mailman/listinfo/ipcdn 
               Archive: ftp://ftp.ietf.org/ietf-mail-archive/ipcdn 
               Co-chairs: Richard Woundy, 
                          Richard_Woundy@cable.comcast.com 
                          Jean-Francois Mule, jf.mule@cablelabs.com" 
       DESCRIPTION 
               "This MIB module defines the diagnostic controls offered 
               by the CableHome Test Portal (CTP). 
    
               Copyright (C) The Internet Society (2003). This version 
               of this MIB module is part of RFC xxxx; see the RFC 
               itself for full legal notices." 
       REVISION         "200306210000Z" -- Jun 21, 2003 
       DESCRIPTION 
               "Initial version, published as RFC xxxx." 
               -- RFC editor to assign xxxx 
       ::= { mib-2 1 }    
       -- xx to be assigned by IANA 
    
   -- Textual conventions 
    
    
   cabhCtpObjects      OBJECT IDENTIFIER ::= { cabhCtpMib 1 } 
   cabhCtpBase         OBJECT IDENTIFIER ::= { cabhCtpObjects 1 } 
   cabhCtpConnSpeed    OBJECT IDENTIFIER ::= { cabhCtpObjects 2 } 
   cabhCtpPing         OBJECT IDENTIFIER ::= { cabhCtpObjects 3 } 
    
   -- 
   --  The following group describes the base objects in the CableHome 
   --  Management Portal.  
   -- 
   cabhCtpSetToFactory    OBJECT-TYPE 
       SYNTAX        TruthValue 
       MAX-ACCESS    read-write 
       STATUS        current 
       DESCRIPTION     
               "Setting this object to true(1) causes all the tables in 
               the CTP MIB to be cleared, and all CTP MIB objects with 
               default values set back to those default values. 
               Reading this object always returns false(2)." 
       ::={cabhCtpBase 1} 
    
   cabhCtpLastSetToFactory    OBJECT-TYPE 
       SYNTAX      TimeStamp 
       MAX-ACCESS  read-only 
       STATUS      current 
       DESCRIPTION 
               "The value of sysUpTime when cabhCtpSetToFactory was 
               last set to true. Zero if never reset." 
       ::={cabhCtpBase 2} 
    
   -- 
   --    Parameter and results from Connection Speed Command 
   -- 
    
   cabhCtpConnSrcIpType    OBJECT-TYPE 
       SYNTAX        InetAddressType 
       MAX-ACCESS  read-write 
       STATUS      current 
       DESCRIPTION 
               "The IP Address type used as the source address for the  
               Connection Speed Test."   
       DEFVAL { ipv4 }  
   ::= { cabhCtpConnSpeed 1 } 
    
   cabhCtpConnSrcIp    OBJECT-TYPE 
       SYNTAX      InetAddress 
       MAX-ACCESS  read-write 
       STATUS      current 
       DESCRIPTION 
               "The IP Address used as the source address for the  
               Connection Speed Test. The type of this address is 
               specified by cabhCtpConnSrcIpType. The default value is 
               the value of cabhCdpServerRouter (192.168.0.1)." 
       REFERENCE 
           "CableHome Specification Section 6.4.4" 
       DEFVAL { 'c0a80001'h }    -- 192.168.0.1 
       ::= { cabhCtpConnSpeed 2 } 
    
   cabhCtpConnDestIpType    OBJECT-TYPE 
       SYNTAX        InetAddressType 
       MAX-ACCESS    read-write 
       STATUS        current 
       DESCRIPTION 
               "The IP Address Type for the CTP Connection Speed Tool  
               destination address. " 
       DEFVAL { ipv4 } 
       ::={ cabhCtpConnSpeed 3 } 
    
   cabhCtpConnDestIp    OBJECT-TYPE 
       SYNTAX      InetAddress 
       MAX-ACCESS  read-write 
       STATUS      current 
       DESCRIPTION 
               "The IP Address used as the destination address for the  
               Connection Speed Test. The type of this address is 
               specified by cabhCtpConnDestIpType" 
       ::= { cabhCtpConnSpeed 4 } 
    
   cabhCtpConnProto    OBJECT-TYPE 
       SYNTAX      INTEGER { 
                     udp(1), 
                     tcp(2) 
                   } 
       MAX-ACCESS  read-write 
       STATUS      current 
       DESCRIPTION 
               "The protocol used in the Connection Speed Test.  
               TCP testing is optional." 
       DEFVAL { udp } 
       ::= { cabhCtpConnSpeed 5 } 
    
   cabhCtpConnNumPkts    OBJECT-TYPE 
       SYNTAX      INTEGER (1..65535) 
       MAX-ACCESS  read-write 
       STATUS      current 
       DESCRIPTION 
               "The number of packets the CTP is to send when triggered 
               to execute the Connection Speed Tool." 
       DEFVAL { 100 } 
       ::= { cabhCtpConnSpeed 6 } 
    
   cabhCtpConnPktSize    OBJECT-TYPE 
       SYNTAX      INTEGER (64..1518) 
       MAX-ACCESS  read-write 
       STATUS      current 
       DESCRIPTION 
               "The size of the test frames." 
       REFERENCE 
           "" 
       DEFVAL { 1518 } 
       ::= { cabhCtpConnSpeed 7 } 
    
   cabhCtpConnTimeOut    OBJECT-TYPE 
       SYNTAX      INTEGER (0..600000) -- Max 10 minutes 
       UNITS        "milliseconds" 
       MAX-ACCESS  read-write 
       STATUS      current 
       DESCRIPTION 
               "The timeout value for the response.  A value of zero  
               indicates no time out and can be used for TCP only." 
       DEFVAL {30000}  -- 30 seconds 
       ::= { cabhCtpConnSpeed 8 } 
    
   cabhCtpConnControl    OBJECT-TYPE 
       SYNTAX      INTEGER { 
                       start(1), 
                       abort(2)     
                    } 
       MAX-ACCESS    read-write 
       STATUS        current 
       DESCRIPTION 
               "The control for the Connection Speed Tool. Setting this  
               object to start(1)  causes the Connection Speed Tool to  
               execute. Setting this object to abort(2) causes the  
               Connection Speed Tool to stop running. 
               This parameter should only be set via SNMP." 
       DEFVAL  {abort } 
       ::={ cabhCtpConnSpeed 9 } 
    
   cabhCtpConnStatus    OBJECT-TYPE 
       SYNTAX      INTEGER { 
                       notRun(1), 
                       running(2),     
                       complete(3), 
                       aborted(4), 
                       timedOut(5) 
                   } 
       MAX-ACCESS    read-only 
       STATUS        current 
       DESCRIPTION 
               "The status of the Connection Speed Tool." 
       DEFVAL   { notRun } 
       ::={ cabhCtpConnSpeed 10 } 
        
   cabhCtpConnPktsSent    OBJECT-TYPE 
       SYNTAX      INTEGER (0..65535) 
       MAX-ACCESS  read-only 
       STATUS      current 
       DESCRIPTION 
               "The number of packets the CTP sent after it was 
               triggered to execute the Connection Speed Tool." 
       ::= { cabhCtpConnSpeed 11 } 
    
   cabhCtpConnPktsRecv    OBJECT-TYPE 
       SYNTAX      INTEGER (0..65535) 
       MAX-ACCESS  read-only 
       STATUS      current 
       DESCRIPTION 
               "The number of packets the CTP received after it 
               executed the Connection Speed Tool." 
       ::= { cabhCtpConnSpeed 12 } 
    
   cabhCtpConnRTT    OBJECT-TYPE 
       SYNTAX      INTEGER (0..600000) 
       UNITS       "millisec" 
       MAX-ACCESS  read-only 
       STATUS      current 
       DESCRIPTION 
               "The resulting round trip time for the set of packets 
               sent to and received from the target LAN IP Device." 
       ::= { cabhCtpConnSpeed 13 } 
    
   cabhCtpConnThroughput    OBJECT-TYPE 
       SYNTAX      INTEGER (0..65535) 
       MAX-ACCESS  read-only 
       STATUS      current 
       DESCRIPTION 
               "The average round-trip throughput measured in kilobits 
               per second." 
       ::= { cabhCtpConnSpeed 14 } 
    
   -- 
   --    Parameters and Results for Ping Command 
   -- 
    
   cabhCtpPingSrcIpType    OBJECT-TYPE 
       SYNTAX        InetAddressType 
       MAX-ACCESS    read-write 
       STATUS        current 
       DESCRIPTION 
               "The IP Address Type for CTP Ping Tool source address." 
       DEFVAL { ipv4 } 
       ::={ cabhCtpPing 1 } 
    
   cabhCtpPingSrcIp    OBJECT-TYPE 
       SYNTAX      InetAddress 
       MAX-ACCESS  read-write 
       STATUS      current 
       DESCRIPTION 
               "The IP Address used as the source address for the Ping  
               Test.  The type of this address is  specified by  
               cabhCtpPingSrcIpType. The default value is the value of  
               CabhCdpServerRouter (192.168.0.1)." 
       REFERENCE 
               "CableHome 1.0 Specification Section 6.4.4" 
       DEFVAL { 'c0a80001'h }  
       ::= { cabhCtpPing 2 } 
    
   cabhCtpPingDestIpType    OBJECT-TYPE 
       SYNTAX        InetAddressType 
       MAX-ACCESS    read-write 
       STATUS        current 
       DESCRIPTION 
               "The IP Address Type for the CTP Ping Tool destination  
               address." 
       DEFVAL { ipv4 } 
       ::={ cabhCtpPing 3 } 
    
   cabhCtpPingDestIp    OBJECT-TYPE 
       SYNTAX      InetAddress 
       MAX-ACCESS  read-write 
       STATUS      current 
       DESCRIPTION 
               "The Destination IP Address used as the destination 
               address for the Ping Test." 
       ::= { cabhCtpPing 4 } 
    
   cabhCtpPingNumPkts    OBJECT-TYPE 
       SYNTAX        INTEGER (1..4) 
       MAX-ACCESS  read-write 
       STATUS      current 
       DESCRIPTION 
               "The number of packets to send to each host." 
       DEFVAL {1} 
       ::= { cabhCtpPing 5 } 
    
   cabhCtpPingPktSize    OBJECT-TYPE 
       SYNTAX      INTEGER (64..1518) 
       MAX-ACCESS  read-write 
       STATUS      current 
       DESCRIPTION 
               "The size of the test frames." 
       DEFVAL {64} 
       ::= { cabhCtpPing 6 } 
    
   cabhCtpPingTimeBetween    OBJECT-TYPE 
       SYNTAX      INTEGER (0..600000) 
       UNITS       "milliseconds" 
       MAX-ACCESS  read-write 
       STATUS      current 
       DESCRIPTION 
               "The time between sending one ping and the next." 
       DEFVAL { 1000 } 
       ::= { cabhCtpPing 7 } 
    
   cabhCtpPingTimeOut        OBJECT-TYPE 
       SYNTAX       INTEGER (1..600000) 
       UNITS        "milliseconds" 
       MAX-ACCESS   read-write 
       STATUS       current 
       DESCRIPTION 
               "The time out for ping response (ICMP reply) for a 
               single transmitted ping message (ICMP request)." 
       DEFVAL  { 1000 } -- 1 second 
       ::={ cabhCtpPing 8 } 
    
    
    
   cabhCtpPingControl    OBJECT-TYPE 
       SYNTAX      INTEGER { 
                       start(1), 
                       abort(2) 
                   } 
       MAX-ACCESS  read-write 
       STATUS      current 
       DESCRIPTION 
               "The control for the Ping Tool. Setting this object to  
               start(1) causes the Ping Tool to execute. Setting this  
               object to abort(2) causes the Ping Tool to stop running. 
               This parameter should only be set via SNMP." 
       DEFVAL  {abort } 
       ::={ cabhCtpPing 9 } 
    
    
   cabhCtpPingStatus    OBJECT-TYPE 
       SYNTAX      INTEGER { 
                       notRun(1), 
                       running(2),     
                       complete(3), 
                       aborted(4), 
                       timedOut(5) 
                    } 
       MAX-ACCESS    read-only 
       STATUS        current 
       DESCRIPTION 
               "The status of the Ping Tool." 
       DEFVAL   { notRun } 
       ::={ cabhCtpPing 10 } 

   cabhCtpPingNumSent     OBJECT-TYPE 
       SYNTAX      INTEGER (0..4) 
       MAX-ACCESS  read-only 
       STATUS      current 
       DESCRIPTION 
               "The number of Pings sent" 
       ::={ cabhCtpPing 11 } 
    
   cabhCtpPingNumRecv    OBJECT-TYPE 
       SYNTAX      INTEGER (0..255) 
       MAX-ACCESS  read-only 
       STATUS      current 
       DESCRIPTION 
               "The number of pings received." 
       ::= { cabhCtpPing 12 } 
    
   cabhCtpPingAvgRTT    OBJECT-TYPE 
       SYNTAX        INTEGER (0..600000) 
       UNITS         "millisec" 
       MAX-ACCESS    read-only 
       STATUS        current 
       DESCRIPTION 
               "The resulting average of round trip times for 
               acknowledged packets." 
       ::= { cabhCtpPing 13 } 
    
   cabhCtpPingMaxRTT    OBJECT-TYPE 
       SYNTAX        INTEGER (0..600000) 
       UNITS            "millisec" 
       MAX-ACCESS  read-only 
       STATUS      current 
       DESCRIPTION 
               "The resulting maximum of round trip times for 
               acknowledged packets." 
       ::= { cabhCtpPing 14 } 
    
   cabhCtpPingMinRTT    OBJECT-TYPE 
       SYNTAX      INTEGER (0..600000) 
       UNITS       "millisec" 
       MAX-ACCESS  read-only 
       STATUS      current 
       DESCRIPTION 
               "The resulting minimum of round trip times for 
               acknowledged packets." 
       ::= { cabhCtpPing 15 } 
    
   cabhCtpPingNumIcmpError    OBJECT-TYPE 
       SYNTAX        INTEGER (0..255) 
       MAX-ACCESS  read-only 
       STATUS      current 
       DESCRIPTION 
               "Number of ICMP errors." 
       ::= { cabhCtpPing 16 } 
    
   cabhCtpPingIcmpError    OBJECT-TYPE 
       SYNTAX      INTEGER (0..255) 
       MAX-ACCESS  read-only 
       STATUS      current 
       DESCRIPTION 
               "The last ICMP error." 
       ::= { cabhCtpPing 17 } 
    
   --============================================================== 
    
   -- 
   -- notification group is for future extension. 
   --  
    
   cabhCtpNotification   OBJECT IDENTIFIER ::= { cabhCtpMib 2  } 
   cabhCtpNotifications  OBJECT IDENTIFIER ::= { cabhCtpNotification 0 } 
   cabhCtpConformance    OBJECT IDENTIFIER ::= { cabhCtpMib 3 } 
   cabhCtpCompliances    OBJECT IDENTIFIER ::= { cabhCtpConformance 1 } 
   cabhCtpGroups         OBJECT IDENTIFIER ::= { cabhCtpConformance 2 } 
    
   -- 
   --  Notification Group 
   -- 
   -- 
   -- compliance statements 
    
   cabhCtpBasicCompliance MODULE-COMPLIANCE 
       STATUS     current 
       DESCRIPTION 
               "The compliance statement for devices that implement 
               Portal Service feature." 
       MODULE   --cabhCtpMib 
    
    
    
   -- unconditionally mandatory groups 
    
       MANDATORY-GROUPS { 
           cabhCtpGroup 
       } 
    
       OBJECT cabhCtpConnSrcIpType 
          SYNTAX InetAddressType { ipv4(1) } 
          DESCRIPTION 
              "An implementation is only required to support IPv4 
               addresses." 

       OBJECT cabhCtpConnSrcIp 
          SYNTAX  InetAddress (SIZE(4)) 
          DESCRIPTION 
              "An implementation is only required to support IPv4 
               addresses." 
    
       OBJECT cabhCtpConnDestIpType 
          SYNTAX InetAddressType { ipv4(1) } 
          DESCRIPTION 
              "An implementation is only required to support IPv4 
               addresses." 
    
       OBJECT cabhCtpConnDestIp 
          SYNTAX  InetAddress (SIZE(4)) 
          DESCRIPTION 
              "An implementation is only required to support IPv4 
               addresses." 
    
       OBJECT cabhCtpPingSrcIpType 
          SYNTAX InetAddressType { ipv4(1) } 
          DESCRIPTION 
              "An implementation is only required to support IPv4 
               addresses." 
    
       OBJECT cabhCtpPingSrcIp 
          SYNTAX  InetAddress (SIZE(4)) 
          DESCRIPTION 
              "An implementation is only required to support IPv4 
               addresses." 
    
       OBJECT cabhCtpPingDestIpType 
          SYNTAX InetAddressType { ipv4(1) } 
          DESCRIPTION 
              "An implementation is only required to support IPv4 
               addresses." 
    
       OBJECT cabhCtpPingDestIp 
          SYNTAX  InetAddress (SIZE(4)) 
          DESCRIPTION 
              "An implementation is only required to support IPv4 
               addresses." 
    
   ::= { cabhCtpCompliances 3 } 
    
    
   cabhCtpGroup OBJECT-GROUP 
       OBJECTS { 
                 
           cabhCtpSetToFactory, 
           cabhCtpLastSetToFactory, 
           cabhCtpConnSrcIpType, 
           cabhCtpConnSrcIp, 
           cabhCtpConnDestIpType, 
           cabhCtpConnDestIp, 
           cabhCtpConnProto, 
           cabhCtpConnNumPkts, 
           cabhCtpConnPktSize, 
           cabhCtpConnTimeOut, 
           cabhCtpConnControl, 
           cabhCtpConnStatus, 
           cabhCtpConnPktsSent, 
           cabhCtpConnPktsRecv, 
           cabhCtpConnRTT, 
           cabhCtpConnThroughput, 
            
           cabhCtpPingSrcIpType, 
           cabhCtpPingSrcIp, 
           cabhCtpPingDestIpType, 
           cabhCtpPingDestIp, 
           cabhCtpPingNumPkts, 
           cabhCtpPingPktSize, 
           cabhCtpPingTimeBetween, 
           cabhCtpPingTimeOut, 
           cabhCtpPingControl, 
           cabhCtpPingStatus, 
           cabhCtpPingNumSent, 
           cabhCtpPingNumRecv, 
           cabhCtpPingAvgRTT, 
           cabhCtpPingMinRTT, 
           cabhCtpPingMaxRTT, 
           cabhCtpPingNumIcmpError, 
           cabhCtpPingIcmpError 
       } 
       STATUS    current 
       DESCRIPTION 
               "Group of objects for CableHome CTP MIB." 
       ::= { cabhCtpGroups 1 }  
   END 

--  
--    Copyright (C) The Internet Society (2003). All Rights Reserved. 
--     
--    This document and translations of it may be copied and furnished to 
--    others, and derivative works that comment on or otherwise explain it 
--    or assist in its implementation may be prepared, copied, published 
--    and distributed, in whole or in part, without restriction of any 
--    kind, provided that the above copyright notice and this paragraph are 
--    included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE."
