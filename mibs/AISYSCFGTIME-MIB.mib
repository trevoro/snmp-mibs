AISYSCFGTIME-MIB DEFINITIONS ::= BEGIN

IMPORTS
    MODULE-IDENTITY, OBJECT-TYPE,
    Integer32, IpAddress,
    enterprises
					FROM SNMPv2-SMI
    DisplayString, TruthValue
					FROM SNMPv2-TC;

    aii OBJECT IDENTIFIER ::= {enterprises 539}
    aiSysCfg OBJECT IDENTIFIER ::= {aii 32}

aiSysCfgTime MODULE-IDENTITY
    LAST-UPDATED "200104301700Z"
    ORGANIZATION "Applied Innovation Inc."
    CONTACT-INFO
"		Engineering MIB Administrator
		Postal: Applied Innovation Inc.
			5800 Innovation Drive
			Dublin, Ohio 43017-3271

		Tel:	614-798-2000
		Fax:	614-798-1770
		Email:	snmp@aiinet.com"
    DESCRIPTION
	"MIB module for timekeeping."
    REVISION "200104301700Z"
    DESCRIPTION "The initial revision of this module."
    ::= { aiSysCfg 2 }

-- Object definitions (Using "aiSCTime" prefix)

aiSCTimeZone OBJECT-TYPE
    SYNTAX	DisplayString (SIZE (5..6))
    MAX-ACCESS	read-write
    STATUS	current
    DESCRIPTION
	"The current Time Zone of the system in the following format:
	<+|->HH:MM, where HH is the number of hours and MM is the
	number of minutes. <+/-> specifies the East/West direction.
	For example, EST would be displayed as: -05:00.  The ':' is
	optional, making this variable conform to ISO-8601"
    ::= { aiSysCfgTime 1 }

aiSCDaylightSavingEnabled OBJECT-TYPE
    SYNTAX	TruthValue
    MAX-ACCESS	read-write
    STATUS	current
    DESCRIPTION
	"Indicates whether Daylight saving is enabled."
    ::= { aiSysCfgTime 2 }

aiSCDaylightSavingStatus OBJECT-TYPE
    SYNTAX	INTEGER { disabled(1), active(2), inactive(3) }
    MAX-ACCESS	read-write
    STATUS	current
    DESCRIPTION
	"If aiSCDaylightSavingEnabled is disabled(1), then that is
	also the value of this object.  Otherwise,
	aiSCDaylightSavingStatus is active(2) if we are currently
	observing Daylight Savings Time and inactive(3) otherwise."
    ::= { aiSysCfgTime 3 }

aiSCTimeSntpEnabled OBJECT-TYPE
    SYNTAX	TruthValue
    MAX-ACCESS	read-write
    STATUS	current
    DESCRIPTION
	"Indicates whether the SNTP client is enabled on this system."
    ::= { aiSysCfgTime 4 }

aiSCTimeSntpPollInterval OBJECT-TYPE
    SYNTAX	Integer32 (1..9999)
    MAX-ACCESS	read-write
    STATUS	current
    DESCRIPTION
	"SNTP poll interval in minutes"
    ::= { aiSysCfgTime 5 }

aiSCTimeNtpServerTable OBJECT-TYPE
    SYNTAX	SEQUENCE OF AiSCTimeNtpServerEntry
    MAX-ACCESS	not-accessible
    STATUS	current
    DESCRIPTION
	"A table of information on each NTP server."
    ::= { aiSysCfgTime 6 }

aiSCTimeNtpServerEntry OBJECT-TYPE
    SYNTAX	AiSCTimeNtpServerEntry
    MAX-ACCESS	not-accessible
    STATUS	current
    DESCRIPTION
	"Information on a given NTP server."
    INDEX { aiSCTimeNtpServerIndex }
    ::= { aiSCTimeNtpServerTable 1 }

AiSCTimeNtpServerEntry ::=
    SEQUENCE {
	aiSCTimeNtpServerIndex		Integer32,
	aiSCTimeNtpServerAddress	IpAddress
    }

aiSCTimeNtpServerIndex OBJECT-TYPE
    SYNTAX	Integer32 (1..2147483647)
    MAX-ACCESS	read-only
    STATUS	current
    DESCRIPTION
	"Self referential index in this table."
    ::= { aiSCTimeNtpServerEntry 1 }

aiSCTimeNtpServerAddress OBJECT-TYPE
    SYNTAX	IpAddress
    MAX-ACCESS	read-write
    STATUS	current
    DESCRIPTION
	"IP address of the primary NTP Server"
    ::= { aiSCTimeNtpServerEntry 2 }

END
