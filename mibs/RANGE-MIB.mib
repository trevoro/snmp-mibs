-- File: raty00.mi2
-- 
-- SNMP range processing tests for Integer32.
--

RANGE-MIB DEFINITIONS ::= BEGIN

IMPORTS
    MODULE-IDENTITY, OBJECT-TYPE, Integer32
        FROM SNMPv2-SMI;

rangeTestMIB MODULE-IDENTITY
    LAST-UPDATED "9512090000Z"
    ORGANIZATION "MIB Test Group"
    CONTACT-INFO 
            "     Test Dept
                   
                  MIB Test Group"
    DESCRIPTION
            "Range Test MIB"
    ::= { 1 1 1 }

rangeObj OBJECT IDENTIFIER ::= { 1 1 2 }


obj01 OBJECT-TYPE
    SYNTAX      Integer32
    MAX-ACCESS  read-only
    STATUS      current
    DESCRIPTION "description"
    ::= { rangeObj 1 }

obj02 OBJECT-TYPE
    SYNTAX      Integer32(1)
    MAX-ACCESS  read-only
    STATUS      current
    DESCRIPTION "description"
    ::= { rangeObj 2 }

obj03 OBJECT-TYPE
    SYNTAX      Integer32(2147483647)
    MAX-ACCESS  read-only
    STATUS      current
    DESCRIPTION "description"
    ::= { rangeObj 3 }

obj04 OBJECT-TYPE
    SYNTAX      Integer32(-1)
    MAX-ACCESS  read-only
    STATUS      current
    DESCRIPTION "description"
    ::= { rangeObj 4 }

obj05 OBJECT-TYPE
    SYNTAX      Integer32(-2147483648)
    MAX-ACCESS  read-only
    STATUS      current
    DESCRIPTION "description"
    ::= { rangeObj 5 }

obj06 OBJECT-TYPE
    SYNTAX      Integer32(0)
    MAX-ACCESS  read-only
    STATUS      current
    DESCRIPTION "description"
    ::= { rangeObj 6 }

obj07 OBJECT-TYPE
    SYNTAX      Integer32(0 | 10)
    MAX-ACCESS  read-only
    STATUS      current
    DESCRIPTION "description"
    ::= { rangeObj 7 }

obj08 OBJECT-TYPE
    SYNTAX      Integer32(10 | 0)
    MAX-ACCESS  read-only
    STATUS      current
    DESCRIPTION "description"
    ::= { rangeObj 8 }

obj09 OBJECT-TYPE
    SYNTAX      Integer32(0 | 10 | 2147483647)
    MAX-ACCESS  read-only
    STATUS      current
    DESCRIPTION "description"
    ::= { rangeObj 9 }

obj10 OBJECT-TYPE
    SYNTAX      Integer32(2147483647 | 0 | 10)
    MAX-ACCESS  read-only
    STATUS      current
    DESCRIPTION "description"
    ::= { rangeObj 10 }

obj11 OBJECT-TYPE
    SYNTAX      Integer32(-1 | 10)
    MAX-ACCESS  read-only
    STATUS      current
    DESCRIPTION "description"
    ::= { rangeObj 11 }

obj12 OBJECT-TYPE
    SYNTAX      Integer32(10 | -1)
    MAX-ACCESS  read-only
    STATUS      current
    DESCRIPTION "description"
    ::= { rangeObj 12 }

obj13 OBJECT-TYPE
    SYNTAX      Integer32(-2147483648 | -1)
    MAX-ACCESS  read-only
    STATUS      current
    DESCRIPTION "description"
    ::= { rangeObj 13 }

obj14 OBJECT-TYPE
    SYNTAX      Integer32(-1 | -2147483648)
    MAX-ACCESS  read-only
    STATUS      current
    DESCRIPTION "description"
    ::= { rangeObj 14 }

obj15 OBJECT-TYPE
    SYNTAX      Integer32(-2147483648 | -1 | 10 | 0)
    MAX-ACCESS  read-only
    STATUS      current
    DESCRIPTION "description"
    ::= { rangeObj 15 }


obj21 OBJECT-TYPE
    SYNTAX      Integer32(1..10)
    MAX-ACCESS  read-only
    STATUS      current
    DESCRIPTION "description"
    ::= { rangeObj 21}

obj22 OBJECT-TYPE
    SYNTAX      Integer32(0..10)
    MAX-ACCESS  read-only
    STATUS      current
    DESCRIPTION "description"
    ::= { rangeObj 22}

obj23 OBJECT-TYPE
    SYNTAX      Integer32(1..2147483647)
    MAX-ACCESS  read-only
    STATUS      current
    DESCRIPTION "description"
    ::= { rangeObj 23}

obj24 OBJECT-TYPE
    SYNTAX      Integer32(0..2147483647)
    MAX-ACCESS  read-only
    STATUS      current
    DESCRIPTION "description"
    ::= { rangeObj 24}

obj25 OBJECT-TYPE
    SYNTAX      Integer32(-2147483648..-1)
    MAX-ACCESS  read-only
    STATUS      current
    DESCRIPTION "description"
    ::= { rangeObj 25}

obj26 OBJECT-TYPE
    SYNTAX      Integer32(-2147483648..0)
    MAX-ACCESS  read-only
    STATUS      current
    DESCRIPTION "description"
    ::= { rangeObj 26}

obj27 OBJECT-TYPE
    SYNTAX      Integer32(-10..10)
    MAX-ACCESS  read-only
    STATUS      current
    DESCRIPTION "description"
    ::= { rangeObj 27 }

obj28 OBJECT-TYPE
    SYNTAX      Integer32(-2147483648..2147483647)
    MAX-ACCESS  read-only
    STATUS      current
    DESCRIPTION "description"
    ::= { rangeObj 28 }



obj31 OBJECT-TYPE
    SYNTAX      Integer32(0 | 1..10)
    MAX-ACCESS  read-only
    STATUS      current
    DESCRIPTION "description"
    ::= { rangeObj 31 }

obj32 OBJECT-TYPE
    SYNTAX      Integer32(1..10 | 0)
    MAX-ACCESS  read-only
    STATUS      current
    DESCRIPTION "description"
    ::= { rangeObj 32}

obj33 OBJECT-TYPE
    SYNTAX      Integer32(-2147483648..-1 | 1..2147483647)
    MAX-ACCESS  read-only
    STATUS      current
    DESCRIPTION "description"
    ::= { rangeObj 33 }

obj34 OBJECT-TYPE
    SYNTAX      Integer32(1..2147483647 | -2147483648..-1)
    MAX-ACCESS  read-only
    STATUS      current
    DESCRIPTION "description"
    ::= { rangeObj 34 }

obj35 OBJECT-TYPE
    SYNTAX      Integer32(-100..-60 | -40..-5 | -1..3 | 5..10 | 100..400)
    MAX-ACCESS  read-only
    STATUS      current
    DESCRIPTION "description"
    ::= { rangeObj 35 }

obj36 OBJECT-TYPE
    SYNTAX      Integer32(
                -200 | 200 |
                -199 | 199 |
                -198 | 198 |
                -197 | 197 |
                -196 | 196 |
                -195 | 195 |
                -194 | 194 |
                -193 | 193 |
                -192 | 192 |
                -191 | 191 |
                -190 | 190)
    MAX-ACCESS  read-only
    STATUS      current
    DESCRIPTION "description"
    ::= { rangeObj 36 }

obj37 OBJECT-TYPE
    SYNTAX      Integer32(
                -200..-190 |
                 190..200  |
                -170..-160 |
                 160..170  |
                -150..-140 |
                 140..150  |
                -120..-100 |
                 100..120)
    MAX-ACCESS  read-only
    STATUS      current
    DESCRIPTION "description"
    ::= { rangeObj 37 }

END
