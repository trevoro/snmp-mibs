-- *****************************************************************
-- CISCO-CAT6K-CROSSBAR-CAPABILITY.my:
-- Cisco CISCO-CAT6K-CROSSBAR-MIB AGENT-CAPABILITIES
--
-- April 2004, Padma Pullela 
--
-- Copyright (c) 2004, 2005, 2007 by Cisco Systems, Inc.
-- All rights reserved.
-- *****************************************************************

CISCO-CAT6K-CROSSBAR-CAPABILITY DEFINITIONS ::= BEGIN

IMPORTS
        MODULE-IDENTITY
                FROM SNMPv2-SMI
        AGENT-CAPABILITIES
                FROM SNMPv2-CONF
        ciscoAgentCapability
                FROM CISCO-SMI;

ciscoCat6kCrossbarCapability MODULE-IDENTITY
        LAST-UPDATED    "200701030000Z"
        ORGANIZATION    "Cisco Systems, Inc."
        CONTACT-INFO
                "       Cisco Systems
                        Customer Service

                Postal: 170 West Tasman Drive
                        San Jose, CA  95134
                        USA

                   Tel: +1 800 553-NETS

                E-mail: cs-cat6000@cisco.com"
        DESCRIPTION
                "The capabilities description of 
                 CISCO-CAT6K-CROSSBAR-MIB."

        REVISION        "200701030000Z"
        DESCRIPTION
                "Added capability statement
                 ccXbarCapCatOSV08R0601Cat6KSup32."
        REVISION        "200506220000Z"
        DESCRIPTION
                "Added capability statements  
                 ccXbarCapV12R0218SXFPCat6KSup2,
                 ccXbarCapV12R0218SXFPCat6KSup720,
                 and ccXbarCapV12R0218SXFPCat6KSup32."
 
        REVISION        "200505030000Z"
        DESCRIPTION
                "Added capability statements
                 ccXbarCapV12R012504EPCat6KSup1,
                 and ccXbarCapV12R012504EPCat6KSup2."

        REVISION        "200410190000Z"
        DESCRIPTION
                "Added capability statements
                 ccXbarCapV12R0119EPCat6KSup2,
                 ccXbarCapV12R0123E01PCat6KSup1,
                 and ccXbarCapV12R0123E01PCat6KSup2."  

        REVISION        "200404190000Z"
        DESCRIPTION
                "Added ccXbarCapV12R0218SXDCat6KSup720 and
                 ccXbarCapV12R0218SXDCat6KSup2."

        REVISION        "200404020000Z"
        DESCRIPTION
                "Initial version of this MIB module."

        ::= { ciscoAgentCapability 356 }

ccXbarCapV12R0108aEXCat6KSup2 AGENT-CAPABILITIES
    PRODUCT-RELEASE     "Cisco IOS 12.1(8a)EX on Catalyst 6000/6500
                         and Cisco 7600 series devices with 
                         Supervisor 2 present."
    STATUS              current
    DESCRIPTION         "CISCO-CAT6K-CROSSBAR-MIB capabilities."

    SUPPORTS            CISCO-CAT6K-CROSSBAR-MIB
       INCLUDES         { cc6kxbarModuleStatusGroup,
                          cc6kxbarChannelStatusGroup,
                          cc6kxbarChannelStatisticsGroup,
                          cc6kxbarBusOnlyAllowedGroup
                        }

    ::= { ciscoCat6kCrossbarCapability 1 }

ccXbarCapV12R0214SXCat6KSup720 AGENT-CAPABILITIES
    PRODUCT-RELEASE     "Cisco IOS 12.2(14)SX on Catalyst 6500 
                        and Cisco 7600 series devices with 
                        Supervisor 720 present."
    STATUS              current
    DESCRIPTION         "CISCO-CAT6K-CROSSBAR-MIB capabilities."

    SUPPORTS            CISCO-CAT6K-CROSSBAR-MIB
       INCLUDES         { cc6kxbarModuleStatusGroupVer1,
                          cc6kxbarChannelStatusGroup,
                          cc6kxbarChannelStatisticsGroupVer1,
                          cc6kxbarBusOnlyAllowedGroup,
                          cc6kxbarChannelUtilGroup,
                          cc6kxbarChannelSpeedGroup,
                          cc6kxbarSwBusGroup,
                          cc6kxbarSwBusNotifGroup
                        }

    ::= { ciscoCat6kCrossbarCapability 2 }

ccXbarCapCatOSV06R0301Cat6KSup2 AGENT-CAPABILITIES
    PRODUCT-RELEASE     "Cisco CatOS 6.3(1) on Catalyst 6000/6500
                         and Cisco 7600 series devices
                         with Supervisor 2 present."
    STATUS              current
    DESCRIPTION         "CISCO-CAT6K-CROSSBAR-MIB capabilities."

    SUPPORTS            CISCO-CAT6K-CROSSBAR-MIB
       INCLUDES         { cc6kxbarModuleStatusGroup,
                          cc6kxbarChannelStatusGroup,
                          cc6kxbarChannelStatisticsGroup,
                          cc6kxbarFallbackGroup
                        }

    ::= { ciscoCat6kCrossbarCapability 3 }

ccXbarCapCatOSV08R0101Cat6KSup2 AGENT-CAPABILITIES
    PRODUCT-RELEASE     "Cisco CatOS 8.1(1) on Catalyst 6000/6500
                         and Cisco 7600 series devices
                         with Supervisor 2 present."
    STATUS              current
    DESCRIPTION         "CISCO-CAT6K-CROSSBAR-MIB capabilities."

    SUPPORTS            CISCO-CAT6K-CROSSBAR-MIB
       INCLUDES         { cc6kxbarModuleStatusGroupVer1,
                          cc6kxbarChannelStatusGroup,
                          cc6kxbarChannelStatisticsGroupVer1,
                          cc6kxbarFallbackGroup,
                          cc6kxbarLcdBannerGroup,
                          cc6kxbarChannelUtilGroup,
                          cc6kxbarChannelSpeedGroup
                        }

    ::= { ciscoCat6kCrossbarCapability 4 }

ccXbarCapCatOSV08R0101Cat6KSup720 AGENT-CAPABILITIES
    PRODUCT-RELEASE     "Cisco CatOS 8.1(1) on  Catalyst 6500
                        and Cisco 7600 series devices with 
                        Supervisor 720 present."
    STATUS              current
    DESCRIPTION         "CISCO-CAT6K-CROSSBAR-MIB capabilities."

    SUPPORTS            CISCO-CAT6K-CROSSBAR-MIB
       INCLUDES         { cc6kxbarModuleStatusGroupVer1,
                          cc6kxbarChannelStatusGroup,
                          cc6kxbarChannelStatisticsGroupVer1,
                          cc6kxbarFallbackGroup,
                          cc6kxbarChannelUtilGroup,
                          cc6kxbarChannelSpeedGroup
                        }

    ::= { ciscoCat6kCrossbarCapability 5 }

ccXbarCapV12R0218SXDCat6KSup720 AGENT-CAPABILITIES
    PRODUCT-RELEASE     "Cisco IOS 12.2(18)SXD on Catalyst 6000/6500 
                        and Cisco 7600 series devices with 
                        Supervisor 720 present."
    STATUS              current
    DESCRIPTION         "CISCO-CAT6K-CROSSBAR-MIB capabilities."

    SUPPORTS            CISCO-CAT6K-CROSSBAR-MIB
       INCLUDES         { cc6kxbarModuleStatusGroupVer1,
                          cc6kxbarChannelStatusGroup,
                          cc6kxbarChannelStatisticsGroupVer1,
                          cc6kxbarBusOnlyAllowedGroup,
                          cc6kxbarChannelUtilGroup,
                          cc6kxbarChannelSpeedGroup,
                          cc6kxbarSwBusGroup,
                          cc6kxbarSwBusNotifGroup,
                          cc6kxbarTruncatedOperGroup
                        }

    ::= { ciscoCat6kCrossbarCapability 6 }

ccXbarCapV12R0218SXDCat6KSup2 AGENT-CAPABILITIES
    PRODUCT-RELEASE     "Cisco IOS 12.2(18)SXD on Catalyst 6000/6500 
                        and Cisco 7600 series devices with 
                        Supervisor 2 present."
    STATUS              current
    DESCRIPTION         "CISCO-CAT6K-CROSSBAR-MIB capabilities."

    SUPPORTS            CISCO-CAT6K-CROSSBAR-MIB
       INCLUDES         { cc6kxbarModuleStatusGroupVer1,
                          cc6kxbarChannelStatusGroup,
                          cc6kxbarChannelStatisticsGroupVer1,
                          cc6kxbarBusOnlyAllowedGroup,
                          cc6kxbarLcdBannerGroup,
                          cc6kxbarChannelUtilGroup,
                          cc6kxbarChannelSpeedGroup,
                          cc6kxbarSwBusGroup,
                          cc6kxbarSwBusNotifGroup,
                          cc6kxbarTruncatedOperGroup
                        }

    ::= { ciscoCat6kCrossbarCapability 7 }

ccXbarCapV12R0119EPCat6KSup2 AGENT-CAPABILITIES
    PRODUCT-RELEASE     "Cisco IOS 12.1(19)E on Catalyst 6000/6500
                         and Cisco 7600 series devices with 
                         Supervisor 2 present."
    STATUS              current
    DESCRIPTION         "CISCO-CAT6K-CROSSBAR-MIB capabilities."

    SUPPORTS            CISCO-CAT6K-CROSSBAR-MIB
       INCLUDES         { cc6kxbarModuleStatusGroup,
                          cc6kxbarChannelStatusGroup,
                          cc6kxbarChannelStatisticsGroup,
                          cc6kxbarBusOnlyAllowedGroup,
                          cc6kxbarSwBusGroup,
                          cc6kxbarSwBusNotifGroup
                        }

    ::= { ciscoCat6kCrossbarCapability 8 }

ccXbarCapV12R0123E01PCat6KSup1 AGENT-CAPABILITIES
    PRODUCT-RELEASE     "Cisco IOS 12.1(23)E1 on Catalyst 6000/6500 
                        series devices with Supervisor 1 present."
    STATUS              current
    DESCRIPTION         "CISCO-CAT6K-CROSSBAR-MIB capabilities."

    SUPPORTS            CISCO-CAT6K-CROSSBAR-MIB
       INCLUDES         { cc6kxbarIntBusNotifControlGroup,
                          cc6kxbarIntBusCRCErrNotifGroup
                        }
    
    ::= { ciscoCat6kCrossbarCapability 9 }

ccXbarCapV12R0123E01PCat6KSup2 AGENT-CAPABILITIES
    PRODUCT-RELEASE     "Cisco IOS 12.1(23)E1 on Catalyst 6000/6500
                         and Cisco 7600 series devices with 
                         Supervisor 2 present."
    STATUS              current
    DESCRIPTION         "CISCO-CAT6K-CROSSBAR-MIB capabilities."

    SUPPORTS            CISCO-CAT6K-CROSSBAR-MIB
       INCLUDES         { cc6kxbarModuleStatusGroup,
                          cc6kxbarChannelStatusGroup,
                          cc6kxbarChannelStatisticsGroup,
                          cc6kxbarBusOnlyAllowedGroup,
                          cc6kxbarSwBusGroup,
                          cc6kxbarSwBusNotifGroup,
                          cc6kxbarIntBusNotifControlGroup,
                          cc6kxbarIntBusCRCErrNotifGroup
                        }

    ::= { ciscoCat6kCrossbarCapability 10 }

ccXbarCapV12R012504EPCat6KSup1 AGENT-CAPABILITIES
    PRODUCT-RELEASE     "Cisco IOS 12.1(25.04)E on Catalyst 6000/6500 
                        series devices with Supervisor 1 present."
    STATUS              current
    DESCRIPTION         "CISCO-CAT6K-CROSSBAR-MIB capabilities."

    SUPPORTS            CISCO-CAT6K-CROSSBAR-MIB
       INCLUDES         { cc6kxbarIntBusNotifControlGroup,
                          cc6kxbarIntBusCRCErrNotifGroup,
                          cc6kxbarIntBusCRCErrGroup 
                        }
    
    ::= { ciscoCat6kCrossbarCapability 11 }

ccXbarCapV12R012504EPCat6KSup2 AGENT-CAPABILITIES
    PRODUCT-RELEASE     "Cisco IOS 12.1(25.04)E on Catalyst 6000/6500
                         and Cisco 7600 series devices with 
                         Supervisor 2 present."
    STATUS              current
    DESCRIPTION         "CISCO-CAT6K-CROSSBAR-MIB capabilities."

    SUPPORTS            CISCO-CAT6K-CROSSBAR-MIB
       INCLUDES         { cc6kxbarModuleStatusGroup,
                          cc6kxbarChannelStatusGroup,
                          cc6kxbarChannelStatisticsGroup,
                          cc6kxbarBusOnlyAllowedGroup,
                          cc6kxbarSwBusGroup,
                          cc6kxbarSwBusNotifGroup,
                          cc6kxbarIntBusNotifControlGroup,
                          cc6kxbarIntBusCRCErrNotifGroup,
                          cc6kxbarIntBusCRCErrGroup
                        }

    ::= { ciscoCat6kCrossbarCapability 12 }

ccXbarCapV12R0218SXFPCat6KSup2 AGENT-CAPABILITIES
    PRODUCT-RELEASE     "Cisco IOS 12.2(18)SXF on Catalyst 6000/6500 
                        and Cisco 7600 series devices with 
                        Supervisor 2 present."
    STATUS              current
    DESCRIPTION         "CISCO-CAT6K-CROSSBAR-MIB capabilities."

    SUPPORTS            CISCO-CAT6K-CROSSBAR-MIB
       INCLUDES         { cc6kxbarModuleStatusGroupVer1,
                          cc6kxbarChannelStatusGroup,
                          cc6kxbarChannelStatisticsGroupVer1,
                          cc6kxbarBusOnlyAllowedGroup,
                          cc6kxbarLcdBannerGroup,
                          cc6kxbarChannelUtilGroup,
                          cc6kxbarChannelSpeedGroup,
                          cc6kxbarSwBusGroup,
                          cc6kxbarSwBusNotifGroup,
                          cc6kxbarTruncatedOperGroup,
                          cc6kxbarIntBusNotifControlGroup,
                          cc6kxbarIntBusCRCErrNotifGroup,
                          cc6kxbarIntBusCRCErrGroup
                        }

    ::= { ciscoCat6kCrossbarCapability 13 }

ccXbarCapV12R0218SXFPCat6KSup720 AGENT-CAPABILITIES
    PRODUCT-RELEASE     "Cisco IOS 12.2(18)SXF on Catalyst 6000/6500 
                        and Cisco 7600 series devices with 
                        Supervisor 720 present."
    STATUS              current
    DESCRIPTION         "CISCO-CAT6K-CROSSBAR-MIB capabilities."

    SUPPORTS            CISCO-CAT6K-CROSSBAR-MIB
       INCLUDES         { cc6kxbarModuleStatusGroupVer1,
                          cc6kxbarChannelStatusGroup,
                          cc6kxbarChannelStatisticsGroupVer1,
                          cc6kxbarBusOnlyAllowedGroup,
                          cc6kxbarChannelUtilGroup,
                          cc6kxbarChannelSpeedGroup,
                          cc6kxbarSwBusGroup,
                          cc6kxbarSwBusNotifGroup,
                          cc6kxbarTruncatedOperGroup,
                          cc6kxbarIntBusNotifControlGroup,
                          cc6kxbarIntBusCRCErrNotifGroup,
                          cc6kxbarIntBusCRCErrGroup
                        }

    ::= { ciscoCat6kCrossbarCapability 14 }

ccXbarCapV12R0218SXFPCat6KSup32 AGENT-CAPABILITIES
    PRODUCT-RELEASE     "Cisco IOS 12.2(18)SXF on Catalyst 6000/6500 
                        and Cisco 7600 series devices with 
                        Supervisor 32 present."
    STATUS              current
    DESCRIPTION         "CISCO-CAT6K-CROSSBAR-MIB capabilities."

    SUPPORTS            CISCO-CAT6K-CROSSBAR-MIB
       INCLUDES         { cc6kxbarIntBusNotifControlGroup,
                          cc6kxbarIntBusCRCErrNotifGroup,
                          cc6kxbarIntBusCRCErrGroup
                        }

    ::= { ciscoCat6kCrossbarCapability 15 }

ccXbarCapCatOSV08R0601Cat6KSup32 AGENT-CAPABILITIES
    PRODUCT-RELEASE     "Cisco CatOS 8.6(1) on Catalyst 6500
                        series devices with Supervisor 32 present."
    STATUS              current
    DESCRIPTION         "CISCO-CAT6K-CROSSBAR-MIB capabilities."

    SUPPORTS            CISCO-CAT6K-CROSSBAR-MIB
       INCLUDES         { cc6kxbarFlowCtrlNotifCtrlGroup,
                          cc6kxbarFlowCtrlBusThreshGroup,
                          cc6kxbarFlowCtrlBusThrNotifGroup 
                        }

    ::= { ciscoCat6kCrossbarCapability 16 }

END
