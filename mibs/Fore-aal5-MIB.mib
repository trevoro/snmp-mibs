-- 
-- Copyright 1999 by Fore Systems, Inc. 
-- Converted to SMIv2 rfc 2578,2579,2580 - STD 58
--

-- Copyright 1997 by Fore Systems, Inc.
--
-- This file contains definitions for management information for
-- AAL5 configuration and statistics, including interface
-- specific and connection specific tables. Objects in the interface
-- specific table are in addition to the ifEntry maintained for
-- every pseudo port of the AAL5 driver. The following is the mapping of the
-- ifEntry objects into the AAL5 domain. Note that terms ingress and egress
-- are used from the ATM domain perspective, that is ingress means path from
-- aal5 pdus to cells (segmentation), and egress means path from cells to
-- aal5 pdus (reassembly). Furthermore, standard object names containing
-- 'Out' will refer to reassembly (egress), and standard object names
-- containing 'In' will refer to segmentation (ingress)
--
-- ifType - value is 49 (as per rfc1573 for AAL5 interfaces)
--
-- ifMtu - is the same for both directions, it reflects maximum AAL5
--       SDU size allowed over this interface
--
-- ifSpeed - should be set to the theoretical maximum physical
--         segmentation/reassembly rate of the interface, expressed in
--         bits per second (every cell is presumed to carry 53 bytes of
--         information)              
--
-- ifPhysAddress - usually this interface is not addressable, so this object
--               is set to be an octet string of zero length
--
-- ifAdminStatus - as per rfc1573
--
-- ifOperStatus - as per rfc1573, note that manipulating higher hierarchy
--                level objects (say, netmod status) may cause this object
--                to change its value
--
-- ifLastChange - system time when this interface was initialized;
--
-- ifOutOctets
-- ifInOctets - total number of octets received and transmitted over
--             this interface, atm cell headers excluded for all but
--             OAM cells
--
-- ifOutUcastPkts
-- ifInUcastPkts - total number of PDUs segmented and reassembled over
--                this interface, OAM cells are considered to be packets
--
-- ifOutNUcastPkts
-- ifInNUcastPkts - these objects when requested return 0
--
-- ifOutDiscards - total number of PDUs discarded over this interface
--               in egress direction, which is an aggregate of discards due
--               to different reassembly errors - i.e. length errors, crc
--               errors, oversized pdus
--
-- ifInDiscards - total number of AAL5 PDUs discarded over this
--               interface in ingress direction, for instance due to
--               exceeding maximum pdu size 
--
-- ifOutErrors - will return the same value as ifOutDiscards
--
-- ifOutUnknownProtos - will always be returned as 0
--
-- ifInErrors - will return the same value as ifInDiscards
--
-- ifInQLen - not supported
--
-- ifSpecific - not supported
--
-- IMPORTANT: This MIB requires a subset of RFC 1573 MIB, namely interface
--              table entry
--
--    LIST ALL IMPLEMENTATION ISSUES HERE
--   
--
------------------------------------------------------------------------------


Fore-aal5-MIB DEFINITIONS ::= BEGIN

    IMPORTS
          Integer32, Counter32,
          OBJECT-TYPE, 
          MODULE-IDENTITY                   FROM SNMPv2-SMI
          InterfaceIndex                    FROM IF-MIB
          frameInternetworking              FROM Fore-Common-MIB;

      aal5 MODULE-IDENTITY
          LAST-UPDATED    "9706100906Z"
          ORGANIZATION    "FORE"
          CONTACT-INFO    "
                  Postal: FORE Systems Inc.
                          1000 FORE Drive
                          Warrendale, PA 15086-7502
                  Tel:    +1 724 742 6900
                  Email:  nm_mibs@fore.com
                  Web:    http://www.fore.com"
          DESCRIPTION
             "This MIB module defines the FORE Systems AAL5 and EPD/PPD
              management interface of the Mercury netmod (FUNI FR/ATM
              interworking )"
      ::= { frameInternetworking 5 }


------------------------------------------------------------------

-- AAL5 Virtual Channel Connection Performance Statistics Group
--
-- This group contains the AAL5 performance statistics of a VCC at the
-- SAR interface
    aal5VccTable                            OBJECT-TYPE 
         SYNTAX                             SEQUENCE OF Aal5VccEntry
         MAX-ACCESS                         not-accessible
         STATUS                             current
         DESCRIPTION
         "This table contains AAL5 VCC performance parameters."
         ::= { aal5 1 }

    aal5VccEntry                            OBJECT-TYPE 
         SYNTAX                             Aal5VccEntry 
         MAX-ACCESS                         not-accessible
         STATUS                             current
         DESCRIPTION
         "This list contains the AAL5 VCC performance parameters. Entries in
          this table are indexed by ifIndex assigned to this interface and
          vpi/vci pairs assigned to this connection by either provisioning
          or signalling. Since this entry is associated with the
          netmod/fabric interface, indexes are fabric VPI/VCI and fabric
          service if index"
         INDEX { aal5VccAtmFabServiceIfIndex, aal5VccFabVpi, aal5VccFabVci }
         ::= { aal5VccTable 1 }

         Aal5VccEntry ::= SEQUENCE {
              aal5VccAtmFabServiceIfIndex         InterfaceIndex,
              aal5VccFabVpi                       Integer32,
              aal5VccFabVci                       Integer32,
              aal5VccCrcErrs                      Counter32,
              aal5VccSarTimeOuts                  Counter32,
              aal5VccOverSizedPDUs                Counter32,
              aal5VccLengthErrPDUs                Counter32,
              aal5VccCPIErrs                      Counter32,
              aal5VccInPDUs                       Counter32,
              aal5VccOutPDUs                      Counter32,
              aal5VccInOctets                     Counter32,
              aal5VccOutOctets                    Counter32
              } 

    aal5VccAtmFabServiceIfIndex             OBJECT-TYPE 
         SYNTAX                             InterfaceIndex 
         MAX-ACCESS                         read-only
         STATUS                             current
         DESCRIPTION "ifIndex assigned to this interface."
         ::= { aal5VccEntry 1 }

    aal5VccFabVpi                           OBJECT-TYPE 
         SYNTAX                             Integer32 
         MAX-ACCESS                         read-only
         STATUS                             current
         DESCRIPTION "vpi assigned to this interface."
         ::= { aal5VccEntry 2 }

    aal5VccFabVci                           OBJECT-TYPE 
         SYNTAX                             Integer32 
         MAX-ACCESS                             read-only
         STATUS                             current
         DESCRIPTION "vci assigned to this interface."
         ::= { aal5VccEntry 3 }

    aal5VccCrcErrs                          OBJECT-TYPE 
         SYNTAX                             Counter32
         MAX-ACCESS                             read-only
         STATUS                             current
         DESCRIPTION
         "The number of AAL5 CPCS PDUs received with CRC-32 errors on this
          AAL5 VCC at the interface associated with this AAL5 entity."
         ::= { aal5VccEntry 4 }

    aal5VccSarTimeOuts                      OBJECT-TYPE 
         SYNTAX                             Counter32
         MAX-ACCESS                             read-only
         STATUS                             current
         DESCRIPTION
         " The number of timeouts at the SAR level, waiting for a CPCS
          trailer"
         ::= { aal5VccEntry 5 }

    aal5VccOverSizedPDUs                    OBJECT-TYPE 
         SYNTAX                             Counter32
         MAX-ACCESS                             read-only
         STATUS                             current
         DESCRIPTION
         "The number of AAL5 CPCS PDUs discarded on this ATM VCC at the
          interface associated with an AAL5 entity due to the AAL5 PDUs
          being too large."
         ::= { aal5VccEntry 6 }

    aal5VccLengthErrPDUs                    OBJECT-TYPE 
         SYNTAX                             Counter32
         MAX-ACCESS                             read-only
         STATUS                             current
         DESCRIPTION
         "The number of AAL5 CPCS PDUs discarded on this ATM VCC at the
          interface associated with an AAL5 entity due to the AAL5 PDU
          length errors."
         ::= { aal5VccEntry 7 }

    aal5VccCPIErrs                          OBJECT-TYPE 
         SYNTAX                             Counter32
         MAX-ACCESS                             read-only
         STATUS                             current
         DESCRIPTION
         "The number of CPI ( Common Part Indicator ) current errors "
         ::= { aal5VccEntry 8 }

    aal5VccInPDUs                           OBJECT-TYPE 
         SYNTAX                             Counter32
         MAX-ACCESS                             read-only
         STATUS                             current
         DESCRIPTION
         "The number of AAL-5 PDU's transmitted by the interworking function
          on this ATM VCC."
         ::= { aal5VccEntry 9 }

    aal5VccOutPDUs                          OBJECT-TYPE 
         SYNTAX                             Counter32
         MAX-ACCESS                             read-only
         STATUS                             current
         DESCRIPTION
         "The number of AAL-5 PDU's received by the interworking function on
          this ATM VCC."
         ::= { aal5VccEntry 10 }

    aal5VccInOctets                         OBJECT-TYPE 
         SYNTAX                             Counter32
         MAX-ACCESS                             read-only
         STATUS                             current
         DESCRIPTION
         "The number of AAL-5 octets transmitted by the interworking
          function on this ATM VCC."
         ::= { aal5VccEntry 11 }

    aal5VccOutOctets                        OBJECT-TYPE 
         SYNTAX                             Counter32
         MAX-ACCESS                             read-only
         STATUS                             current
         DESCRIPTION
         "The number of AAL-5 octets received by the interworking function
          on this ATM VCC."
         ::= { aal5VccEntry 12 }

-------------------------------------------------------------------
-- the following three tables incorporate current, interval and total 
-- statistics gathered by the aal5 entity within the device under 
-- management. All three tables have similar set of statistics gathered, so 
-- that is why only current table's objects have comprehensive description of 
-- their usage. In case some of the parameters can not be supported by the 
-- device hardware, 0 is supposed to be returned when that counter is
-- inquired. These tables are accumulated per WAN side indices

    aal5CpcsCurrTable                       OBJECT-TYPE 
         SYNTAX                             SEQUENCE OF Aal5CpcsCurrEntry
         MAX-ACCESS                             not-accessible
         STATUS                             current
         DESCRIPTION
         "This table holds current ( within the last 15 minutes interval's
          statistics of AAL5 CPCS sublayer"
         ::= { aal5 2 }

    aal5CpcsCurrEntry                       OBJECT-TYPE 
         SYNTAX                             Aal5CpcsCurrEntry 
         MAX-ACCESS                             not-accessible
         STATUS                             current
         DESCRIPTION
         "Entry in the table of current statistics of AAL5 CPCS sublayer"
         INDEX { aal5CpcsFabServiceIfIndex }
         ::= { aal5CpcsCurrTable 1 }


         Aal5CpcsCurrEntry ::= SEQUENCE {
              aal5CpcsFabServiceIfIndex           InterfaceIndex,
              aal5CpcsCurrCRCErrs                 Counter32,
              aal5CpcsCurrSarTimeOuts             Counter32,
              aal5CpcsCurrOverSizedPDUs           Counter32,
              aal5CpcsCurrLengthErrs              Counter32,
              aal5CpcsCurrCPIErrs                 Counter32
              } 

    aal5CpcsFabServiceIfIndex               OBJECT-TYPE 
         SYNTAX                             InterfaceIndex 
         MAX-ACCESS                             read-only
         STATUS                             current
         DESCRIPTION "ifIndex assigned to this entry."
         ::= { aal5CpcsCurrEntry 1 }

    aal5CpcsCurrCRCErrs                     OBJECT-TYPE 
         SYNTAX                             Counter32
         MAX-ACCESS                             read-only
         STATUS                             current
         DESCRIPTION
         "The CRC current errors"
         ::= { aal5CpcsCurrEntry 2 }

    aal5CpcsCurrSarTimeOuts                 OBJECT-TYPE 
         SYNTAX                             Counter32
         MAX-ACCESS                             read-only
         STATUS                             current
         DESCRIPTION
         "The current number of Timeouts in the CPCS level, waiting for a
          CPCS trailer "
         ::= { aal5CpcsCurrEntry 3 }

    aal5CpcsCurrOverSizedPDUs               OBJECT-TYPE 
         SYNTAX                             Counter32
         MAX-ACCESS                             read-only
         STATUS                             current
         DESCRIPTION
         "The User Payload current errors"
         ::= { aal5CpcsCurrEntry 4 }

    aal5CpcsCurrLengthErrs                  OBJECT-TYPE 
         SYNTAX                             Counter32
         MAX-ACCESS                             read-only
         STATUS                             current
         DESCRIPTION
         "The Length current errors"
         ::= { aal5CpcsCurrEntry 5 }

    aal5CpcsCurrCPIErrs                     OBJECT-TYPE 
         SYNTAX                             Counter32
         MAX-ACCESS                             read-only
         STATUS                             current
         DESCRIPTION
         "The CPI ( Common Part Indicator ) current errors "
         ::= { aal5CpcsCurrEntry 6 }

-----------------------------------------------------------------------
-- This table provides the information about the time interval for 
-- gathering the related statistics on the CPCS level

    aal5CpcsIntvlTable                      OBJECT-TYPE 
         SYNTAX                             SEQUENCE OF Aal5CpcsIntvlEntry
         MAX-ACCESS                             not-accessible
         STATUS                             current
         DESCRIPTION
         "This table holds interval statistics of AAL5 CPCS sublayer for 8
          hour worth 15 minutes intervals. The table is indexed by the
          service ifIndex as well as interval number in range of 1..32"
         ::= { aal5 3 }

    aal5CpcsIntvlEntry                      OBJECT-TYPE 
         SYNTAX                             Aal5CpcsIntvlEntry 
         MAX-ACCESS                             not-accessible
         STATUS                             current
         DESCRIPTION
         "Entry in the table of interval statistics of AAL5 CPCS sublayer"
         INDEX { aal5CpcsIntvlFabServiceIfIndex, aal5CpcsIntvlNumber }
         ::= { aal5CpcsIntvlTable 1 }

         Aal5CpcsIntvlEntry ::= SEQUENCE {
              aal5CpcsIntvlFabServiceIfIndex      InterfaceIndex,
              aal5CpcsIntvlNumber                 Integer32,
              aal5CpcsIntvlCRCErrs                Counter32,
              aal5CpcsIntvlSarTimeOuts            Counter32,
              aal5CpcsIntvlOverSizedPDUs          Counter32,
              aal5CpcsIntvlLengthErrs             Counter32,
              aal5CpcsIntvlCPIErrs                Counter32
              } 

    aal5CpcsIntvlFabServiceIfIndex          OBJECT-TYPE 
         SYNTAX                             InterfaceIndex 
         MAX-ACCESS                         read-only
         STATUS                             current
         DESCRIPTION "ifIndex assigned to this entry."
         ::= { aal5CpcsIntvlEntry 1 }

    aal5CpcsIntvlNumber                     OBJECT-TYPE 
         SYNTAX                             Integer32 ( 1..32 )
         MAX-ACCESS                             read-only
         STATUS                             current
         DESCRIPTION
         "A number between 1 and 32, where 1 is the most recently completed
          15 minute interval and 32 is the least recently completed 15
          minutes interval ( assuming that all 32 intervals are valid ) ."
         ::= { aal5CpcsIntvlEntry 2 }

    aal5CpcsIntvlCRCErrs                    OBJECT-TYPE 
         SYNTAX                             Counter32
         MAX-ACCESS                             read-only
         STATUS                             current
         DESCRIPTION
         "The CRC interval errors"
         ::= { aal5CpcsIntvlEntry 3 }

    aal5CpcsIntvlSarTimeOuts                OBJECT-TYPE 
         SYNTAX                             Counter32
         MAX-ACCESS                             read-only
         STATUS                             current
         DESCRIPTION
         "The interval number of Timeouts in the CPCS level, waiting for a
          CPCS trailer "
         ::= { aal5CpcsIntvlEntry 4 }

    aal5CpcsIntvlOverSizedPDUs              OBJECT-TYPE 
         SYNTAX                             Counter32
         MAX-ACCESS                             read-only
         STATUS                             current
         DESCRIPTION
         "The User Payload interval errors"
         ::= { aal5CpcsIntvlEntry 5 }

    aal5CpcsIntvlLengthErrs                 OBJECT-TYPE 
         SYNTAX                             Counter32
         MAX-ACCESS                             read-only
         STATUS                             current
         DESCRIPTION
         "The Length interval errors"
         ::= { aal5CpcsIntvlEntry 6 }

    aal5CpcsIntvlCPIErrs                    OBJECT-TYPE 
         SYNTAX                             Counter32
         MAX-ACCESS                             read-only
         STATUS                             current
         DESCRIPTION
         "The CPI ( Common Part Indicator ) interval errors "
         ::= { aal5CpcsIntvlEntry 7 }

-- the AAL5 CPCS Total

-- The AAL5 CPCS Total Table contains the cumulative sum of the various
-- statistics for the 8 hour period preceding the current interval.

    aal5CpcsTotalTable                      OBJECT-TYPE 
         SYNTAX                             SEQUENCE OF Aal5CpcsTotalEntry
         MAX-ACCESS                             not-accessible
         STATUS                             current
         DESCRIPTION
         "This table holds cumulative statistics of AAL5 CPCS sublayer"
         ::= { aal5 4 }

    aal5CpcsTotalEntry                      OBJECT-TYPE 
         SYNTAX                             Aal5CpcsTotalEntry 
         MAX-ACCESS                             not-accessible
         STATUS                             current
         DESCRIPTION
         "Entry in the table of cumulative statistics of AAL5 CPCS sublayer"
         INDEX { aal5CpcsTotalFabServiceIfIndex }
         ::= { aal5CpcsTotalTable 1 }

         Aal5CpcsTotalEntry ::= SEQUENCE {
              aal5CpcsTotalFabServiceIfIndex      InterfaceIndex,
	      aal5CpcsTotalValidIntervals         Integer32,
              aal5CpcsTotalCRCErrs                Counter32,
              aal5CpcsTotalSarTimeOuts            Counter32,
              aal5CpcsTotalOverSizedPDUs          Counter32,
              aal5CpcsTotalLengthErrs             Counter32,
              aal5CpcsTotalCPIErrs                Counter32
              } 

    aal5CpcsTotalFabServiceIfIndex          OBJECT-TYPE 
         SYNTAX                             InterfaceIndex 
         MAX-ACCESS                             read-only
         STATUS                             current
         DESCRIPTION "ifIndex assigned to this entry."
         ::= { aal5CpcsTotalEntry 1 }

    aal5CpcsTotalValidIntervals             OBJECT-TYPE 
         SYNTAX                             Integer32 
         MAX-ACCESS                             read-only
         STATUS                             current
         DESCRIPTION
         "The number of previous intervals for which valid data was
          collected. The value will be 32 unless the interface was brought
          on-line within the last 8 hours, in which case the value will be
          the number of complete 15 minute intervals since the interface has
          been online."
         ::= { aal5CpcsTotalEntry 2 }

    aal5CpcsTotalCRCErrs                    OBJECT-TYPE 
         SYNTAX                             Counter32
         MAX-ACCESS                             read-only
         STATUS                             current
         DESCRIPTION
         "The CRC total errors"
         ::= { aal5CpcsTotalEntry 3 }

    aal5CpcsTotalSarTimeOuts                OBJECT-TYPE 
         SYNTAX                             Counter32
         MAX-ACCESS                             read-only
         STATUS                             current
         DESCRIPTION
         "The total number of Timeouts in the CPCS level, waiting for a CPCS
          trailer "
         ::= { aal5CpcsTotalEntry 4 }

    aal5CpcsTotalOverSizedPDUs              OBJECT-TYPE 
         SYNTAX                             Counter32
         MAX-ACCESS                             read-only
         STATUS                             current
         DESCRIPTION
         "The User Payload total errors"
         ::= { aal5CpcsTotalEntry 5 }

    aal5CpcsTotalLengthErrs                 OBJECT-TYPE 
         SYNTAX                             Counter32
         MAX-ACCESS                             read-only
         STATUS                             current
         DESCRIPTION
         "The Length total errors"
         ::= { aal5CpcsTotalEntry 6 }

    aal5CpcsTotalCPIErrs                    OBJECT-TYPE 
         SYNTAX                             Counter32
         MAX-ACCESS                             read-only
         STATUS                             current
         DESCRIPTION
         "The CPI ( Common Part Indicator ) total errors "
         ::= { aal5CpcsTotalEntry 7 }

------------------------------------------------------------------------
-- the following table contains statistics and a reference to the EPD/PPD
-- profile associated with the ATM connection.

    aal5EpdPpdVccTable                      OBJECT-TYPE 
         SYNTAX                             SEQUENCE OF Aal5EpdPpdVccEntry
         MAX-ACCESS                             not-accessible
         STATUS                             current
         DESCRIPTION
         "A table of statistical information associated with the EPD/PPD
          controller on a per connection basis."
         ::= { aal5 5 }

    aal5EpdPpdVccEntry                      OBJECT-TYPE 
         SYNTAX                             Aal5EpdPpdVccEntry 
         MAX-ACCESS                             not-accessible
         STATUS                             current
         DESCRIPTION
         "An entry in the FRAM netmod EPD/PPD statistic information table on
          a per connection basis"
         INDEX { aal5EpdPpdAtmFabServiceIfIndex, aal5EpdPpdVccFabVpi, aal5EpdPpdVccFabVci
              }
         ::= { aal5EpdPpdVccTable 1 }

         Aal5EpdPpdVccEntry ::= SEQUENCE {
              aal5EpdPpdAtmFabServiceIfIndex      InterfaceIndex,
              aal5EpdPpdVccFabVpi                 Integer32,
              aal5EpdPpdVccFabVci                 Integer32,
              aal5EpdPpdVccDroppedCellsClp1       Counter32,
              aal5EpdPpdVccForwardedCellsClp1     Counter32,
              aal5EpdPpdVccDroppedCellsClp0       Counter32,
              aal5EpdPpdVccForwardedCellsClp0     Counter32
              } 

    aal5EpdPpdAtmFabServiceIfIndex          OBJECT-TYPE 
         SYNTAX                             InterfaceIndex 
         MAX-ACCESS                             read-only
         STATUS                             current
         DESCRIPTION "ifIndex assigned to this entry."
         ::= { aal5EpdPpdVccEntry 1 }

    aal5EpdPpdVccFabVpi                     OBJECT-TYPE 
         SYNTAX                             Integer32 
         MAX-ACCESS                             read-only
         STATUS                             current
         DESCRIPTION "vpi assigned to this entry."
         ::= { aal5EpdPpdVccEntry 2 }

    aal5EpdPpdVccFabVci                     OBJECT-TYPE 
         SYNTAX                             Integer32 
         MAX-ACCESS                             read-only
         STATUS                             current
         DESCRIPTION "vci assigned to this entry."
         ::= { aal5EpdPpdVccEntry 3 }

    aal5EpdPpdVccDroppedCellsClp1           OBJECT-TYPE 
         SYNTAX                             Counter32
         MAX-ACCESS                             read-only
         STATUS                             current
         DESCRIPTION
         "The total number of dropped cells with CLP=1 by the EPD/PPD
          controller for a specific connection"
         ::= { aal5EpdPpdVccEntry 4 }

    aal5EpdPpdVccForwardedCellsClp1         OBJECT-TYPE 
         SYNTAX                             Counter32
         MAX-ACCESS                             read-only
         STATUS                             current
         DESCRIPTION
         "The total number of forwarded cells with CLP=1 by the EPD/PPD
          controller for a specific connection"
         ::= { aal5EpdPpdVccEntry 5 }

    aal5EpdPpdVccDroppedCellsClp0           OBJECT-TYPE 
         SYNTAX                             Counter32
         MAX-ACCESS                             read-only
         STATUS                             current
         DESCRIPTION
         "The total number of dropped cells with CLP=0 by the EPD/PPD
          controller for a specific connection"
         ::= { aal5EpdPpdVccEntry 6 }

    aal5EpdPpdVccForwardedCellsClp0         OBJECT-TYPE 
         SYNTAX                             Counter32
         MAX-ACCESS                             read-only
         STATUS                             current
         DESCRIPTION
         "The total number of forwarded cells with CLP=0 by the EPD/PPD
          controller for a specific connection"
         ::= { aal5EpdPpdVccEntry 7 }
END
