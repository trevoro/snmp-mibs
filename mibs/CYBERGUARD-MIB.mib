CYBERGUARD-MIB DEFINITIONS ::= BEGIN

	  -- SUBTREE: 1.3.6.1.4.1.23.1.13.25.1
	  -- iso.org.dod.internet.private.enterprises.novell.products.unixWare.CyberGuard

          IMPORTS
                  enterprises
                      FROM RFC1155-SMI
		TRAP-TYPE
			FROM RFC-1215
                  OBJECT-TYPE
                          FROM RFC-1212;

          -- textual conventions

          DisplayString ::=
              OCTET STRING
          -- This data type is used to model textual information taken
          -- from the NVT ASCII character set.  By convention, objects
          -- with this syntax are declared as having
          --
          --      SIZE (0..255)


	novell			OBJECT IDENTIFIER ::= { enterprises 23 }
	products		OBJECT IDENTIFIER ::= { novell 1 }
	unixWare		OBJECT IDENTIFIER ::= { products 13 }
	cyberGuard		OBJECT IDENTIFIER ::= { unixWare 25 }
	cgfwMIB			OBJECT IDENTIFIER ::= { cyberGuard 1 }
	cgfwEvent		OBJECT IDENTIFIER ::= { cgfwMIB 2 }

          cgAccessDeny OBJECT-TYPE
              SYNTAX  DisplayString (SIZE (0..255))
              ACCESS  read-only
              STATUS  mandatory
              DESCRIPTION
                      "A string containing the last snmp trap sent for access_deny via fw"
              ::= { cgfwEvent 1 }

          cgAccessGrant OBJECT-TYPE
              SYNTAX  DisplayString (SIZE (0..255))
              ACCESS  read-only
              STATUS  mandatory
              DESCRIPTION
                      "A string containing the last snmp trap sent for access_grant via fw"
              ::= { cgfwEvent 2 }

          cgDiskSpace OBJECT-TYPE
              SYNTAX  DisplayString (SIZE (0..255))
              ACCESS  read-only
              STATUS  mandatory
              DESCRIPTION
                      "A string containing the last snmp trap sent for disk_space via fw"
              ::= { cgfwEvent 3 }

          cgFailedLogin OBJECT-TYPE
              SYNTAX  DisplayString (SIZE (0..255))
              ACCESS  read-only
              STATUS  mandatory
              DESCRIPTION
                      "A string containing the last snmp trap sent for failed_login via fw"
              ::= { cgfwEvent 4 }

          cgHostLimit OBJECT-TYPE
              SYNTAX  DisplayString (SIZE (0..255))
              ACCESS  read-only
              STATUS  mandatory
              DESCRIPTION
                      "A string containing the last snmp trap sent for host_limit via fw"
              ::= { cgfwEvent 5 }

          cgForwardAttack OBJECT-TYPE
              SYNTAX  DisplayString (SIZE (0..255))
              ACCESS  read-only
              STATUS  mandatory
              DESCRIPTION
                      "A string containing the last snmp trap sent for forward_attack via fw"
              ::= { cgfwEvent 6 }

          cgLandAttack OBJECT-TYPE
              SYNTAX  DisplayString (SIZE (0..255))
              ACCESS  read-only
              STATUS  mandatory
              DESCRIPTION
                      "A string containing the last snmp trap sent for land_attack via fw"
              ::= { cgfwEvent 7 }

          cgPingOfDeath OBJECT-TYPE
              SYNTAX  DisplayString (SIZE (0..255))
              ACCESS  read-only
              STATUS  mandatory
              DESCRIPTION
                      "A string containing the last snmp trap sent for pingOdDeath via fw"
              ::= { cgfwEvent 8 }

          cgTcpSynFlood OBJECT-TYPE
              SYNTAX  DisplayString (SIZE (0..255))
              ACCESS  read-only
              STATUS  mandatory
              DESCRIPTION
                      "A string containing the last snmp trap sent for tcp_syn_flood via fw"
              ::= { cgfwEvent 9 }

          cgIntfSpoof OBJECT-TYPE
              SYNTAX  DisplayString (SIZE (0..255))
              ACCESS  read-only
              STATUS  mandatory
              DESCRIPTION
                      "A string containing the last snmp trap sent for interface_spoof via fw"
              ::= { cgfwEvent 10 }

          cgMacViolation OBJECT-TYPE
              SYNTAX  DisplayString (SIZE (0..255))
              ACCESS  read-only
              STATUS  mandatory
              DESCRIPTION
                      "A string containing the last snmp trap sent for mac_violation via fw"
              ::= { cgfwEvent 11 }

          cgPortScan OBJECT-TYPE
              SYNTAX  DisplayString (SIZE (0..255))
              ACCESS  read-only
              STATUS  mandatory
              DESCRIPTION
                      "A string containing the last snmp trap sent for port_scan via fw"
              ::= { cgfwEvent 12 }

          cgBlockedFile OBJECT-TYPE
              SYNTAX  DisplayString (SIZE (0..255))
              ACCESS  read-only
              STATUS  mandatory
              DESCRIPTION
                      "A string containing the last snmp trap sent for blocked_file via fw"
              ::= { cgfwEvent 13 }

          cgHaTransition OBJECT-TYPE
              SYNTAX  DisplayString (SIZE (0..255))
              ACCESS  read-only
              STATUS  mandatory
              DESCRIPTION
                      "A string containing the last snmp trap sent for ha_transition via fw"
              ::= { cgfwEvent 14 }

          cgHaNoHB OBJECT-TYPE
              SYNTAX  DisplayString (SIZE (0..255))
              ACCESS  read-only
              STATUS  mandatory
              DESCRIPTION
                      "A string containing the last snmp trap sent for ha_nohb via fw"
              ::= { cgfwEvent 15 }

          cgSwUpdate OBJECT-TYPE
              SYNTAX  DisplayString (SIZE (0..255))
              ACCESS  read-only
              STATUS  mandatory
              DESCRIPTION
                      "A string containing the last snmp trap sent for sw_update via fw"
              ::= { cgfwEvent 16 }

          cgPlatformSensor OBJECT-TYPE
              SYNTAX  DisplayString (SIZE (0..255))
              ACCESS  read-only
              STATUS  mandatory
              DESCRIPTION
                      "A string containing the last snmp trap sent for platform_sensor via fw"
              ::= { cgfwEvent 17 }

          cgAuditArchive OBJECT-TYPE
              SYNTAX  DisplayString (SIZE (0..255))
              ACCESS  read-only
              STATUS  mandatory
              DESCRIPTION
                      "A string containing the last snmp trap sent for audit_archive via fw"
              ::= { cgfwEvent 18 }

--	cgfwTrap TRAP-TYPE
--		ENTERPRISE	cgfwEvent
--		VARIABLES	{ xxxx }
--		DESCRIPTION
--			"CyberGuard FireWall SNMP trap"
--		::= 0

END
