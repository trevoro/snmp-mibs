-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : ipapps.def
 --
 -- DESCRIPTION : This is the Sonoma IP Applications MIB for TFTP/BOOTP.
 --
 -- ARCHIVE : $Archive:   M:\pvcs\pvcsproj\sonoma3\src\mib\ipapps.dev  $
 -- REVISION: $Revision:   1.5  $
 -- AUTHOR  : $Author:   FREEVE  $
 -- DATE    : $Date:   Nov 13 1998 10:33:36  $

      SONOMASYSTEMS-SONOMA-IPAPPS-MIB DEFINITIONS ::= BEGIN

      IMPORTS
        IpAddress
        FROM RFC1155-SMI
        OBJECT-TYPE
        FROM RFC-1212
        sonomaApplications 
        FROM SONOMASYSTEMS-SONOMA-MIB;

        --
        -- Hierarchy for these groups
        -- enterprises OBJECT IDENTIFIER ::= { private 4 }
        -- sonomaSystems OBJECT IDENTIFIER ::= {  enterprises 2926 }
        -- sonomaSeries OBJECT IDENTIFIER ::= { sonomaSystems 25 }
        -- sonomaApplications OBJECT IDENTIFIER ::= { sonomaSeries 8 }
        ipApplications OBJECT IDENTIFIER ::= { sonomaApplications 1 }

        bootpGroup OBJECT IDENTIFIER ::= { ipApplications 1 }
        pingGroup  OBJECT IDENTIFIER ::= { ipApplications 2 }

        --  Textual conventions
        -- This data type is used to model textual information taken
        -- from the NVT ASCII character set.  By convention, objects
        -- with this syntax are declared as having
        --
        --      SIZE (0..255)
        DisplayString  ::= OCTET STRING

    -- The following objects are used for File transfers between this unit and
    -- a Bootp/TFTP server.
    -- The files can be image or parameter files.
    --

    tftpFileServerIpAddress  OBJECT-TYPE
        SYNTAX  IpAddress
        ACCESS  read-write
        STATUS  mandatory
        DESCRIPTION
           "The IP Address of the file server to use for image and
            parameter file downloads and uploads."
        ::= { bootpGroup 1 }

    tftpFileName  OBJECT-TYPE
        SYNTAX  DisplayString (SIZE (0..127))
        ACCESS  read-write
        STATUS  mandatory
        DESCRIPTION
           "The path and name of the file to be uploaded or downloaded. This string
            is 128 charachters long, any longer causes problems fro Windown NT or 
            Windows 95. This length is recommended in RFC 1542."
         ::= { bootpGroup 2 }


    tftpImageNumber  OBJECT-TYPE
        SYNTAX  INTEGER {
                image1 (1),
                image2 (2),
                image3 (3),
                image4 (4),
                image5 (5),
                image6 (6),
                image7 (7),
                image8 (8)
                }
        ACCESS  read-write
        STATUS  mandatory
        DESCRIPTION
           "The Image number (1 - 8) for the operational image file to 
            be downloaded to. In the case of BOOTP the image will be stored
            in the BOOTP/ directory in flash"
        DEFVAL { image1 }
        ::= { bootpGroup 3 }

     tftpFileAction  OBJECT-TYPE
        SYNTAX  INTEGER {
                    noAction (1),
                    startBootPImageDownload (2),
                    startTFTPImageDownload (3),
                    startPrimaryImageTFTPDownload (4),
                    startSecondaryImageTFTPDownload (5),
                    startTFTPParameterBinDownload (6),
                    startTFTPParameterTextDownload (7),
                    startTFTPParameterBinUpload (8),
                    startTFTPParameterTextUpload (9),
                    startTFTPProfileDownload (10)
                    }
        ACCESS  read-write
        STATUS  mandatory
        DESCRIPTION
            "This object is used to initiate file transfer between this
             unit and the file server identified by
             tftpFileServerIpAddress.
             A download indicates that the file transfer is from the
             file server (down) to the device. An upload indicates a
             file transfer from the device (up) to the server.
             This object can be used to initiate either image or
             parameter file downloads and a parameter file upload.
             There is no image file upload feature.
             An image file can be downloaded via either a BootP request
             (where the image filename and the BootP server's IP Address
             is unknown) or via a TFTP request where the user has
             configured the tftpFileName object with the path and
             name of the file.
             BootP cannot be used to download or upload a parameter
             file.
             An attempt to set this object to one of the following
             values: startTFTPImageDownload, startTFTPParameterDownload
             or startTFTPParameterUpload, will fail if either the
             tftpFileName or tftpFileServerIpAddress object has
             not bee configured.
             The tftpFileName and tftpFileServerIpAddress
             objects are ignored for BootP requests.
             A value of noAction is always returned to a GetRequest.
             Seting this object with a value of noAction has no effect.
             The startPrimaryImageTFTPDownload is used to initiate the
             download of the primary boot image. This image is only downloaded
             when there is a new revision of the basic boot mechanism or
             changes to the flash or CMOS sub-systems."
          DEFVAL { noAction }
          ::= { bootpGroup 4 }

    tftpFileTransferStatus  OBJECT-TYPE
        SYNTAX  INTEGER {
                    idle (1),
                    downloading(2),
                    uploading (3),
                    programmingflash (4),
                    failBootpNoServer (5),
                    failTFTPNoFile (6),
                    errorServerResponse (7),
                    failTFTPInvalidFile (8),
                    failNetworkTimeout (9),
                    failFlashProgError (10),
                    failFlashChksumError (11),
                    errorServerData (12),
                    uploadResultUnknown (13),
                    uploadSuccessful (14),
                    downloadSuccessful (15),
                    generalFailure (16),
                    failCannotOverwriteActiveImage (17),
                    failCannotOverwriteActiveParam (18)
                    }
        ACCESS  read-only
        STATUS  mandatory
        DESCRIPTION
           "This is the current status of the file transfer process."
        ::= { bootpGroup 5 }

    --
    -- The Ping Group
    --

         pingIpAddress  OBJECT-TYPE
            SYNTAX  IpAddress
            ACCESS  read-write
            STATUS  mandatory
            DESCRIPTION
               " The IP Address to Ping"
            ::= { pingGroup 1 }

         pingTimeout  OBJECT-TYPE
            SYNTAX  INTEGER
            ACCESS  read-write
            STATUS  mandatory
            DESCRIPTION
                 "This is the timeout, in seconds, for a ping."
            DEFVAL { 0 }
            ::= { pingGroup 2 }

         pingRetries  OBJECT-TYPE
            SYNTAX  INTEGER
            ACCESS  read-write
            STATUS  mandatory
            DESCRIPTION
                 " This value indicates the number of times, to ping.
                   A value of 1 is the default and insicates that
                   the unit will send one pingp. 0 means no action."
            DEFVAL { 1 }
            ::= { pingGroup 3 }

         pingStatus  OBJECT-TYPE
            SYNTAX  DisplayString (SIZE (0..256))
            ACCESS  read-only
            STATUS  mandatory
            DESCRIPTION
                 " A text string which indicates the result or status of 
                   the last ping which the unit sent."
            ::= { pingGroup 4 }

        pingAction  OBJECT-TYPE
            SYNTAX  INTEGER {
                    start (1),
                    stop  (2),
                    noAction (3)
                    }
            ACCESS  read-write
            STATUS  mandatory
            DESCRIPTION
               "Indicates whether to stop or start a ping. This
                always returns the value noAction to a Get Request."
            DEFVAL { noAction }
            ::= { pingGroup 5 }

END
