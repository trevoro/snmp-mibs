-- *****************************************************************
-- CISCO-IE1000-MIB
--
--
-- ****************************************************************

CISCO-IE1000-MIB DEFINITIONS ::= BEGIN

IMPORTS
    MODULE-IDENTITY,
    OBJECT-IDENTITY
        FROM SNMPv2-SMI
    ciscoMgmt
        FROM CISCO-SMI;

ciscoIE1000MIB MODULE-IDENTITY
    LAST-UPDATED "201605180000Z"
    ORGANIZATION
        "Cisco Systems, Inc"
    CONTACT-INFO
        "Cisco Systems, Inc
         Customer Service
         Postal: 170 W Tasman Drive
         San Jose, CA 95134
         USA
         Tel: +1 800 553-NETS
         E-mail: cs-core-mibs@cisco.com"
    DESCRIPTION
        "The collection of MIBs relating to Cisco IE1000"
    REVISION    "201605180000Z"
    DESCRIPTION
        "Initial version"
    ::= { ciscoMgmt  832 }

cie1000SwitchMgmt OBJECT-IDENTITY
    STATUS          current
    DESCRIPTION
        "switchMgmt is the root OBJECT IDENTIFIER from
         which object id values are assigned."
    ::= { ciscoIE1000MIB 1 }

END
