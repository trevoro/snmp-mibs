ChrComPmEthETH-Day-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmEth				FROM  Chromatis-MIB
	chrComIfifIndex					FROM  ChrComIfifTable-MIB
	TruthValue				FROM  ChrTyp-MIB
	Gauge32				FROM  SNMPv2-SMI;

-- chrComPmEthETH-Day Table

chrComPmEthETH-DayTable		OBJECT-TYPE
	SYNTAX		SEQUENCE OF ChrComPmEthETH-DayEntry
	MAX-ACCESS	not-accessible
	STATUS		current
	DESCRIPTION
	""
	::= { chrComPmEth 11}

chrComPmEthETH-DayEntry		OBJECT-TYPE
	SYNTAX		ChrComPmEthETH-DayEntry
	MAX-ACCESS	not-accessible
	STATUS		current
	DESCRIPTION
	""
	INDEX  {  chrComIfifIndex, chrComPmEthDayNumber }

--DEFAULT  get-function-async  MNIL_GetRoutine
--DEFAULT  set-function-async  MNIL_SetRoutine
--DEFAULT  next-function-async MNIL_NextRoutine
--DEFAULT  test-function-async MNIL_TestRoutine
--DEFAULT  cookie "ETH-Day"
	::= { chrComPmEthETH-DayTable  1 }

ChrComPmEthETH-DayEntry  ::=
	SEQUENCE  {
	chrComPmEthDayNumber		Unsigned32	(1..2),
	chrComPmEthSuspectedInterval	TruthValue,
	chrComPmEthElapsedTime		Unsigned32	(0..4294967295),
	chrComPmEthSuppressedIntrvls	Gauge32			(0..4294967295),
	chrComPmEthdot3StatsFCSErrors	Gauge32			(0..4294967295),
	chrComPmEthdot3StatsLateCollisions	Gauge32			(0..4294967295),
	chrComPmEthdot3StatsFrameTooLongs	Gauge32			(0..4294967295),
	chrComPmEthdot3StatsInternalMacReceiveErrors Gauge32			(0..4294967295),
	chrComPmEthifInOctets		Gauge32			(0..4294967295),
	chrComPmEthifInUcastPkts		Gauge32			(0..4294967295),
	chrComPmEthifInDiscards		Gauge32			(0..4294967295),
	chrComPmEthifInErrors		Gauge32			(0..4294967295),
	chrComPmEthifOutOctets		Gauge32			(0..4294967295),
	chrComPmEthifOutUcastPkts		Gauge32			(0..4294967295),
	chrComPmEthifInMulticastPkts	Gauge32			(0..4294967295),
	chrComPmEthifInBroadcastPkts	Gauge32			(0..4294967295),
	chrComPmEthifOutMulticastPkts	Gauge32			(0..4294967295),
	chrComPmEthifOutBroadcastPkts	Gauge32			(0..4294967295),
	chrComPmEthchrFrames64Bytes	Gauge32			(0..4294967295),
	chrComPmEthchrFrames65to127Bytes	Gauge32			(0..4294967295),
	chrComPmEthchrFrames128to256Bytes	Gauge32			(0..4294967295),
	chrComPmEthchrFrames257to512Bytes	Gauge32			(0..4294967295),
	chrComPmEthchrFrames513to1024Bytes	Gauge32			(0..4294967295),
	chrComPmEthchrFrames1024toMaxBytes	Gauge32			(0..4294967295),
	chrComPmEthResetPmCountersAction	TruthValue
}

chrComPmEthDayNumber 	OBJECT-TYPE
	SYNTAX		Unsigned32	(1..2)
	MAX-ACCESS 	read-only
	STATUS 		current
	DESCRIPTION
	""
	::= { chrComPmEthETH-DayEntry  1 }

chrComPmEthSuspectedInterval 	OBJECT-TYPE
	SYNTAX		TruthValue
	MAX-ACCESS 	read-only
	STATUS 		current
	DESCRIPTION
	""
	::= { chrComPmEthETH-DayEntry  2 }

chrComPmEthElapsedTime 	OBJECT-TYPE
	SYNTAX		Unsigned32	(0..4294967295)
	MAX-ACCESS 	read-only
	STATUS 		current
	DESCRIPTION
	""
	::= { chrComPmEthETH-DayEntry  3 }

chrComPmEthSuppressedIntrvls 	OBJECT-TYPE
	SYNTAX		Gauge32			(0..4294967295)
	MAX-ACCESS 	read-only
	STATUS 		current
	DESCRIPTION
	""
	::= { chrComPmEthETH-DayEntry  4 }

chrComPmEthdot3StatsFCSErrors 	OBJECT-TYPE
	SYNTAX		Gauge32			(0..4294967295)
	MAX-ACCESS 	read-only
	STATUS 		current
	DESCRIPTION
	""
	::= { chrComPmEthETH-DayEntry  5 }

chrComPmEthdot3StatsLateCollisions 	OBJECT-TYPE
	SYNTAX		Gauge32			(0..4294967295)
	MAX-ACCESS 	read-only
	STATUS 		current
	DESCRIPTION
	""
	::= { chrComPmEthETH-DayEntry  6 }

chrComPmEthdot3StatsFrameTooLongs 	OBJECT-TYPE
	SYNTAX		Gauge32			(0..4294967295)
	MAX-ACCESS 	read-only
	STATUS 		current
	DESCRIPTION
	""
	::= { chrComPmEthETH-DayEntry  7 }

chrComPmEthdot3StatsInternalMacReceiveErrors 	OBJECT-TYPE
	SYNTAX		Gauge32			(0..4294967295)
	MAX-ACCESS 	read-only
	STATUS 		current
	DESCRIPTION
	""
	::= { chrComPmEthETH-DayEntry  8 }

chrComPmEthifInOctets 	OBJECT-TYPE
	SYNTAX		Gauge32			(0..4294967295)
	MAX-ACCESS 	read-only
	STATUS 		current
	DESCRIPTION
	""
	::= { chrComPmEthETH-DayEntry  9 }

chrComPmEthifInUcastPkts 	OBJECT-TYPE
	SYNTAX		Gauge32			(0..4294967295)
	MAX-ACCESS 	read-only
	STATUS 		current
	DESCRIPTION
	""
	::= { chrComPmEthETH-DayEntry  10 }

chrComPmEthifInDiscards 	OBJECT-TYPE
	SYNTAX		Gauge32			(0..4294967295)
	MAX-ACCESS 	read-only
	STATUS 		current
	DESCRIPTION
	""
	::= { chrComPmEthETH-DayEntry  11 }

chrComPmEthifInErrors 	OBJECT-TYPE
	SYNTAX		Gauge32			(0..4294967295)
	MAX-ACCESS 	read-only
	STATUS 		current
	DESCRIPTION
	""
	::= { chrComPmEthETH-DayEntry  12 }

chrComPmEthifOutOctets 	OBJECT-TYPE
	SYNTAX		Gauge32			(0..4294967295)
	MAX-ACCESS 	read-only
	STATUS 		current
	DESCRIPTION
	""
	::= { chrComPmEthETH-DayEntry  13 }

chrComPmEthifOutUcastPkts 	OBJECT-TYPE
	SYNTAX		Gauge32			(0..4294967295)
	MAX-ACCESS 	read-only
	STATUS 		current
	DESCRIPTION
	""
	::= { chrComPmEthETH-DayEntry  14 }

chrComPmEthifInMulticastPkts 	OBJECT-TYPE
	SYNTAX		Gauge32			(0..4294967295)
	MAX-ACCESS 	read-only
	STATUS 		current
	DESCRIPTION
	""
	::= { chrComPmEthETH-DayEntry  15 }

chrComPmEthifInBroadcastPkts 	OBJECT-TYPE
	SYNTAX		Gauge32			(0..4294967295)
	MAX-ACCESS 	read-only
	STATUS 		current
	DESCRIPTION
	""
	::= { chrComPmEthETH-DayEntry  16 }

chrComPmEthifOutMulticastPkts 	OBJECT-TYPE
	SYNTAX		Gauge32			(0..4294967295)
	MAX-ACCESS 	read-only
	STATUS 		current
	DESCRIPTION
	""
	::= { chrComPmEthETH-DayEntry  17 }

chrComPmEthifOutBroadcastPkts 	OBJECT-TYPE
	SYNTAX		Gauge32			(0..4294967295)
	MAX-ACCESS 	read-only
	STATUS 		current
	DESCRIPTION
	""
	::= { chrComPmEthETH-DayEntry  18 }

chrComPmEthchrFrames64Bytes 	OBJECT-TYPE
	SYNTAX		Gauge32			(0..4294967295)
	MAX-ACCESS 	read-only
	STATUS 		current
	DESCRIPTION
	""
	::= { chrComPmEthETH-DayEntry  19 }

chrComPmEthchrFrames65to127Bytes 	OBJECT-TYPE
	SYNTAX		Gauge32			(0..4294967295)
	MAX-ACCESS 	read-only
	STATUS 		current
	DESCRIPTION
	""
	::= { chrComPmEthETH-DayEntry  20 }

chrComPmEthchrFrames128to256Bytes 	OBJECT-TYPE
	SYNTAX		Gauge32			(0..4294967295)
	MAX-ACCESS 	read-only
	STATUS 		current
	DESCRIPTION
	""
	::= { chrComPmEthETH-DayEntry  21 }

chrComPmEthchrFrames257to512Bytes 	OBJECT-TYPE
	SYNTAX		Gauge32			(0..4294967295)
	MAX-ACCESS 	read-only
	STATUS 		current
	DESCRIPTION
	""
	::= { chrComPmEthETH-DayEntry  22 }

chrComPmEthchrFrames513to1024Bytes 	OBJECT-TYPE
	SYNTAX		Gauge32			(0..4294967295)
	MAX-ACCESS 	read-only
	STATUS 		current
	DESCRIPTION
	""
	::= { chrComPmEthETH-DayEntry  23 }

chrComPmEthchrFrames1024toMaxBytes 	OBJECT-TYPE
	SYNTAX		Gauge32			(0..4294967295)
	MAX-ACCESS 	read-only
	STATUS 		current
	DESCRIPTION
	""
	::= { chrComPmEthETH-DayEntry  24 }

chrComPmEthResetPmCountersAction 	OBJECT-TYPE
	SYNTAX		TruthValue
	MAX-ACCESS 	read-write
	STATUS 		current
	DESCRIPTION
	""
	::= { chrComPmEthETH-DayEntry  25 }


END
