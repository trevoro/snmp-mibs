--	$Id: Periphonicsv2.mib,v 1.2 1998/12/21 14:22:29 john Exp $
--
--	Copyright (c) 1994 by
--	Periphonics Corporation
--	4000 Veterans Memorial Hwy
--	Bohemia, NY 11716
--	
--	This software is furnished under a license and may be used and
--	copied only in accordance with the terms of such license and with
--	the inclusion of the above copyright notice. This software or any
--	other copies thereof, may not be provided or otherwise made
--	available to anyone other than the licensee. Title to and ownership
--	of this software remains with the Periphonics Corporation.
--	
--	The information in this document is subject to change without
--	notice and should not be construed as a commitment by Periphonics.
--	
--	Periphonics assumes no responsibility for the use or reliability of
--	its software on equipment that is not supplied by Periphonics.
--	
--	File Name:	$RCSfile: Periphonicsv2.mib,v $
--	
--	Description:	Defines periphonics enterprise subtree and defines the
--			organization of Periphonics subtree.
--
--	$Log: Periphonicsv2.mib,v $
--	Revision 1.2  1998/12/21 14:22:29  john
--	Added media server subtree.
--	
--

PERIPHONICS-MIB DEFINITIONS ::= BEGIN

IMPORTS
	MODULE-IDENTITY, enterprises
		FROM SNMPv2-SMI
	;

periphonics MODULE-IDENTITY
	LAST-UPDATED "9607010000Z"
	ORGANIZATION "Periphonics Corporation"
	CONTACT-INFO
		""
	DESCRIPTION
		"Periphonics enterprise MIB module."
	::= { enterprises 1357 }

vruNetwork	OBJECT IDENTIFIER ::= { periphonics 1 }
nmsIntegration	OBJECT IDENTIFIER ::= { periphonics 3 }
periMsMIB	OBJECT IDENTIFIER ::= { periphonics 5 }	-- Media Server MIB

END
