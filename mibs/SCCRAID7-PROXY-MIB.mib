SCCRAID7-PROXY-MIB DEFINITIONS ::= BEGIN

--
--  Definitions of Managed Objects for Storage Computer Corporation
--                     RAID7 Proxy Agent
--
--                  Name:    scc-raid7-proxy-mib-v1-0.txt
--                  Version: 1.0
--                  Date:    
--                  Company: Storage Computer Corporation
--                  Mail:    raid7@world.std.com
--  
--  Inquiries about the contents and use of this MIB may be sent to 
--  raid7@world.std.com
--
--  This MIB module defines objects that describe the status of the SNMP
--  proxy agent for the SCC RAID7 and the communcation between the RAID7
--  and the proxy.
--
--  The  objects  defined  in  this   MIB   are   located   under   the
--  private.enterprises subtree as shown below:
--
--                    iso(1).org(3).dod(6).internet(1)
--                                 |
--                              private(4)
--                                 |
--                              enterprises(1)
--                                 |
--                              scc(1386)
--                                 |
--                 .________________________________.
--                 |                                |
--              products(1)             .___________.___________.
--                 |                    |                       |
--                                      |                       |
--                                    raid7(1)              raid7proxy(2)
--
--
--  All objects within this MIB are prefixed with the OBJECT IDENTIFIER
--
--      iso(1).org(3).dod(6).internet(1).private(4).enterprises(1).
--          scc(1386).sccMibs(2).raid7Proxy(2)
--
--  or, 1.3.6.1.4.1.1386.2.2
--

IMPORTS
    Gauge, Counter
        FROM RFC1155-SMI
    OBJECT-TYPE
        FROM RFC-1212
    TRAP-TYPE
        FROM RFC-1215
    DisplayString
        FROM RFC1213-MIB
    raid7proxy
        FROM SCC-ENTERPRISE-MIB;

--
-- Groups within this MIB
--

raid7Agent OBJECT IDENTIFIER ::= { raid7proxy 1 }
raid7Link  OBJECT IDENTIFIER ::= { raid7proxy 2 }

raid7proxyMibVersion OBJECT-TYPE
        SYNTAX INTEGER
        ACCESS read-only
        STATUS mandatory
        DESCRIPTION
           "The version of this proxy MIB."

        ::= { raid7Agent 1 }

raid7proxyAgentVersion OBJECT-TYPE
        SYNTAX INTEGER
        ACCESS read-only
        STATUS mandatory
        DESCRIPTION
           "The version of the Proxy Agent software"

        ::= { raid7Agent 2 }

raid7CacheLifetime OBJECT-TYPE
        SYNTAX Gauge
        ACCESS read-only
        STATUS mandatory
        DESCRIPTION
           "The time in seconds that the agent will treat a value from the 
            RAID7 as valid.  When this time is exceeded for any object,
            the value of that object will be considered invalid and will 
            return GenError (NoSuchObject will be returned only for oids
            that are never valid)."

        ::= { raid7Agent 3 }

raid7CacheTimeouts OBJECT-TYPE
        SYNTAX Counter
        ACCESS read-only
        STATUS mandatory
        DESCRIPTION
           "The number of times that an error has been returned for an
            SNMP operation because the raid7CacheLifetime has been
            exceeded for some object."

        ::= { raid7Agent 4 }

raid7BadValues OBJECT-TYPE
        SYNTAX Counter
        ACCESS read-only
        STATUS mandatory
        DESCRIPTION
           "This counts the number of times that the agent has discarded a 
            data value from the RAID7 because it was out of range.  This
            may indicate a version incompatibility between the agent and 
            the array, or a serial link problem."

        ::= { raid7Agent 5 }

--
-- Proxy Link Group
--
--    These objects provide information intended to aid in the detection
--    of communication or compatibility problems on the link between the 
--    RAID7 and the proxy agent device.
-- 

raid7LinkName OBJECT-TYPE
        SYNTAX DisplayString (SIZE (0..31))
        ACCESS read-only
        STATUS mandatory
        DESCRIPTION
           "The device name on the proxy agent platform for the link
            between the proxy agent and the RAID7."

        ::= { raid7Link 1 }

raid7LinkStatus OBJECT-TYPE
        SYNTAX INTEGER {
               operational(1),
               openfailed(2),
               quiet(3)
               }
        ACCESS read-only
        STATUS mandatory
        DESCRIPTION
           "This object indicates the status of the serial link to the 
            RAID7:
                operational indicates that the device is open and
                            frames are being received from the RAID7.
                openfailed  indicates that there is a problem local
                            to the agent that is preventing the agent
                            process from opening; see the log file on
                            the agent system.
                quiet       indicates that the port was opened, but 
                            no data is being received from the RAID7."

        ::= { raid7Link 2 }

raid7LinkUp TRAP-TYPE
        ENTERPRISE raid7proxy
        VARIABLES { raid7LinkName, raid7LinkStatus }
        DESCRIPTION 
           "This trap is sent whenever the link becomes operational." 

        ::= 1
        
raid7LinkDown TRAP-TYPE
        ENTERPRISE raid7proxy
        VARIABLES { raid7LinkName, raid7LinkStatus }
        DESCRIPTION 
           "This trap is sent whenever the link status changes from
            operational to quiet." 

        ::= 2
        
raid7LinkInactivityTime OBJECT-TYPE
        SYNTAX Gauge
        ACCESS read-only
        STATUS mandatory
        DESCRIPTION
           "The number of seconds allowed between characters received
            from the RAID7 before the raid7LinkStatus is changed to quiet."

        ::= { raid7Link 3 }

raid7LinkRcvBytes OBJECT-TYPE
        SYNTAX Counter
        ACCESS read-only
        STATUS mandatory
        DESCRIPTION
           "Number of bytes received from the RAID7; this includes those
            bytes later discarded due to errors, and counts both bytes of
            an escaped value sequence."

        ::= { raid7Link 4 }

raid7LinkXmtBytes OBJECT-TYPE
        SYNTAX Counter
        ACCESS read-only
        STATUS mandatory
        DESCRIPTION
           "Number of bytes sent to the RAID7; this counts both bytes of
            an escaped value sequence."

        ::= { raid7Link 5 }

raid7LinkRcvFrames OBJECT-TYPE
        SYNTAX Counter
        ACCESS read-only
        STATUS mandatory
        DESCRIPTION
           "Number of frames recognized from the RAID7; this includes those
            frames later discarded due to errors counted below."

        ::= { raid7Link 6 }

--
-- Frame reject counters; these are mutually exclusive - a given frame 
-- will be discarded at the first of these errors detected, and will not
-- count any other error even if it is present.
-- 

raid7LinkXmtFrames OBJECT-TYPE
        SYNTAX Counter
        ACCESS read-only
        STATUS mandatory
        DESCRIPTION
           "Number of framees sent to the RAID7."

        ::= { raid7Link 7 }

raid7LinkFramingErrors OBJECT-TYPE
        SYNTAX Counter
        ACCESS read-only
        STATUS mandatory
        DESCRIPTION
           "This counts frames from the RAID7 discarded by the agent 
            because the length received did not match the message length
            field in the header."

        ::= { raid7Link 8 }

raid7LinkChecksumErrors OBJECT-TYPE
        SYNTAX Counter
        ACCESS read-only
        STATUS mandatory
        DESCRIPTION
           "This counts frames from the RAID7 discarded by the agent 
            because the checksum was not correct."

        ::= { raid7Link 9 }

raid7LinkBadVersions OBJECT-TYPE
        SYNTAX Counter
        ACCESS read-only
        STATUS mandatory
        DESCRIPTION
           "This counts frames from the RAID7 discarded by the agent 
            because the protocol version number in the header was not 
            a version supported by the proxy software."

        ::= { raid7Link 10 }

raid7LinkBadIds OBJECT-TYPE
        SYNTAX Counter
        ACCESS read-only
        STATUS mandatory
        DESCRIPTION
           "This counts frames from the RAID7 discarded by the agent 
            because the type/class/group header field was not a value
            supported by the proxy software."

        ::= { raid7Link 11 }

raid7LinkBadInstances OBJECT-TYPE
        SYNTAX Counter
        ACCESS read-only
        STATUS mandatory
        DESCRIPTION
           "This counts frames from the RAID7 discarded by the agent 
            because the instance header field was out of range."

        ::= { raid7Link 12 }

END
