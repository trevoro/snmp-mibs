-- *****************************************************************
-- tiaranet-ghdlc.mib:  Tiara Networks Enterprise SMI
--
-- July,1st 1999, Kumar
--
-- Copyright (c) 1998-2005 by Tiara Networks, Inc.
-- All rights reserved.
--
-- *****************************************************************

TIARA-GENERIC-HDLC-MIB DEFINITIONS ::= BEGIN

IMPORTS
	MODULE-IDENTITY, OBJECT-TYPE, 
		 Integer32, Counter32  FROM SNMPv2-SMI
	bundleId		FROM 	TIARA-BUNDLE-MIB
	tiaraMgmt FROM TIARA-NETWORKS-SMI;


tiaraGenHdlcMib MODULE-IDENTITY
	LAST-UPDATED "9907010000Z" 
	ORGANIZATION "Tiara Networks Inc."
	CONTACT-INFO
		 "       Tiara Networks
                         Customer Service

                	 Postal: 525 Race Street, Suite 100,
                         San Jose, CA 95126
                         USA

        	           Tel: +1 408-216-4700
                           Fax: +1 408-216-4701

                	   E-mail: support@tiaranetworks.com"

	DESCRIPTION
		"The MIB defines objects for configuring generic HDLC
        bundles and thier monitoring"

	 ::= { tiaraMgmt 15 } 


-- Generic Hdlc Table definition

genHdlcTable 	OBJECT-TYPE
	SYNTAX		SEQUENCE OF GenHdlcTableEntry
	MAX-ACCESS	not-accessible
	STATUS 		current
	DESCRIPTION
		"All the parameters pertinent to HDLC encapsulation on 
		a bundle are defined in this table."
	::= {tiaraGenHdlcMib 1}

genHdlcTableEntry	OBJECT-TYPE
	SYNTAX			GenHdlcTableEntry
	MAX-ACCESS		not-accessible
	STATUS			current
	DESCRIPTION
		"An entry in the GenHdlc Table"
	INDEX	{ bundleId }
	::= {genHdlcTable 1}

GenHdlcTableEntry ::= SEQUENCE {
        genHdlcKeepAlive    Integer32,
        genHdlcMtu    Integer32
	}
 

genHdlcKeepAlive	OBJECT-TYPE
	SYNTAX	Integer32(0..120)
	UNITS   "seconds"
	MAX-ACCESS	read-write
	STATUS	current
	DESCRIPTION 
		"The link's keep-alive interval.  Tiara system will send 
		messages once every chosen interval to check bundle's status."
	DEFVAL { 10 }
	::= { genHdlcTableEntry 1}

genHdlcMtu	OBJECT-TYPE
	SYNTAX	Integer32 -- RANGE
	MAX-ACCESS		read-write
	STATUS	current
	DESCRIPTION 
		"Maximum transmission unit ie. the maximum packet size to 
		be sent."
	DEFVAL { 1500 }
	::= { genHdlcTableEntry 2}

-- GenHdlcStats Table Definition

genHdlcStatsTable 	OBJECT-TYPE
	SYNTAX		SEQUENCE OF GenHdlcStatsTableEntry
	MAX-ACCESS	not-accessible
	STATUS 		current
	DESCRIPTION
		"All the statistics parameters pertinent to HDLC encapsulation 
		on a bundle are defined in this table."
	::= {tiaraGenHdlcMib 2}

genHdlcStatsTableEntry	OBJECT-TYPE
	SYNTAX			GenHdlcStatsTableEntry
	MAX-ACCESS		not-accessible
	STATUS			current
	DESCRIPTION
		"An entry in the genHdlcStats Table"
	INDEX	{ bundleId }
	::= {genHdlcStatsTable 1}

GenHdlcStatsTableEntry ::= SEQUENCE {
        genHdlcStatsBytesRxLastBootClear    Counter32,
        genHdlcStatsBytesTxLastBootClear    Counter32,
        genHdlcStatsPktsRxLastBootClear  Counter32,
        genHdlcStatsPktsTxLastBootClear  Counter32,
        genHdlcStatsErrPktsRxLastBootClear  Counter32,
        genHdlcStatsUpDownStatesLastBootClear  Counter32,
        genHdlcStatsBytesRxLastFiveMins  Counter32,
        genHdlcStatsBytesTxLastFiveMins  Counter32,
        genHdlcStatsPktsRxLastFiveMins  Counter32,
        genHdlcStatsPktsTxLastFiveMins Counter32,
        genHdlcStatsErrPktsRxLastFiveMins  Counter32,
        genHdlcStatsUpDownStatesLastFiveMins Counter32
	}
	
genHdlcStatsBytesRxLastBootClear	OBJECT-TYPE
	SYNTAX	Counter32
	MAX-ACCESS	read-only
	STATUS	current
	DESCRIPTION 
		"Tiara-fill"
	::= { genHdlcStatsTableEntry 1 }

genHdlcStatsBytesTxLastBootClear	OBJECT-TYPE
	SYNTAX	Counter32
	MAX-ACCESS	read-only
	STATUS	current
	DESCRIPTION 
		"Tiara-fill"
	::= { genHdlcStatsTableEntry 2 }

genHdlcStatsPktsRxLastBootClear	OBJECT-TYPE
	SYNTAX	Counter32
	MAX-ACCESS	read-only
	STATUS	current
	DESCRIPTION 
		"Tiara-fill"
	::= { genHdlcStatsTableEntry 3 }

genHdlcStatsPktsTxLastBootClear	OBJECT-TYPE
	SYNTAX	Counter32
	MAX-ACCESS	read-only
	STATUS	current
	DESCRIPTION 
		"Tiara-fill"
	::= { genHdlcStatsTableEntry 4 }

genHdlcStatsErrPktsRxLastBootClear	OBJECT-TYPE
	SYNTAX	Counter32
	MAX-ACCESS	read-only
	STATUS	current
	DESCRIPTION 
		"Tiara-fill"
	::= { genHdlcStatsTableEntry 5 }

genHdlcStatsUpDownStatesLastBootClear	OBJECT-TYPE
	SYNTAX	Counter32
	MAX-ACCESS	read-only
	STATUS	current
	DESCRIPTION 
		"Tiara-fill"
	::= { genHdlcStatsTableEntry 6 }

genHdlcStatsBytesRxLastFiveMins	OBJECT-TYPE
	SYNTAX	Counter32
	MAX-ACCESS	read-only
	STATUS	current
	DESCRIPTION 
		"Tiara-fill"
	::= { genHdlcStatsTableEntry 7 }

genHdlcStatsBytesTxLastFiveMins	OBJECT-TYPE
	SYNTAX	Counter32
	MAX-ACCESS	read-only
	STATUS	current
	DESCRIPTION 
		"Tiara-fill"
	::= { genHdlcStatsTableEntry 8 }

genHdlcStatsPktsRxLastFiveMins	OBJECT-TYPE
	SYNTAX	Counter32
	MAX-ACCESS	read-only
	STATUS	current
	DESCRIPTION 
		"Tiara-fill"
	::= { genHdlcStatsTableEntry 9 }

genHdlcStatsPktsTxLastFiveMins	OBJECT-TYPE
	SYNTAX	Counter32
	MAX-ACCESS	read-only
	STATUS	current
	DESCRIPTION 
		"Tiara-fill"
	::= { genHdlcStatsTableEntry 10 }

genHdlcStatsErrPktsRxLastFiveMins	OBJECT-TYPE
	SYNTAX	Counter32
	MAX-ACCESS	read-only
	STATUS	current
	DESCRIPTION 
		"Tiara-fill"
	::= { genHdlcStatsTableEntry 11 }

genHdlcStatsUpDownStatesLastFiveMins	OBJECT-TYPE
	SYNTAX	Counter32
	MAX-ACCESS	read-only
	STATUS	current
	DESCRIPTION 
		"Tiara-fill"
	::= { genHdlcStatsTableEntry 12 }

END
