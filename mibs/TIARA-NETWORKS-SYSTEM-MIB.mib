-- *****************************************************************
-- tiaranet-system.mib:  Tiara Networks System MIB file
--
-- April,1st 1998, Shyla
--
--
-- Copyright (c) 1998-2005 by Tiara Networks, Inc.
-- All rights reserved.
-- 
-- *****************************************************************
--
TIARA-NETWORKS-SYSTEM-MIB 


DEFINITIONS ::= BEGIN

IMPORTS
        OBJECT-TYPE,
        IpAddress,
        Counter32,
        MODULE-IDENTITY
                FROM SNMPv2-SMI
        DisplayString,TruthValue
                FROM SNMPv2-TC
        TRAP-TYPE
                FROM RFC-1215
	tiaraMgmt
	        FROM TIARA-NETWORKS-SMI;

tiaraSystemMib MODULE-IDENTITY 
  	LAST-UPDATED "0008180000Z"
  	ORGANIZATION "Tiara Networks, Inc."
  	CONTACT-INFO
                "       Tiara Networks
                        Customer Support

                		525 Race Street, Suite 100,
                        San Jose, CA 95126
                        USA

                  	Tel: +1 408-216-4700
                   	Fax: +1 408-216-4701

                		Email: support@tiaranetworks.com"

  	DESCRIPTION
  		"System group for Tiara Networks products."
  	REVISION      "0008180000Z"
  	DESCRIPTION
  		"Initial version of this MIB module."
        ::= { tiaraMgmt 1}

SntpEnabled ::= TEXTUAL-CONVENTION
    STATUS  current
    DESCRIPTION
   	"Enabled flag for sntp client."
    SYNTAX INTEGER 
    {
    not-enabled(1),
    enabled(2)
    }   
    
    
systemObjects 		OBJECT IDENTIFIER ::= { tiaraSystemMib 1 }
dnsGroup 			OBJECT IDENTIFIER ::= { tiaraSystemMib 2 }
systemEnableNotification	OBJECT IDENTIFIER ::= { tiaraSystemMib 3 }
systemNotifications	OBJECT IDENTIFIER ::= { tiaraSystemMib 4 }
userAdminGroup		OBJECT IDENTIFIER ::= { tiaraSystemMib 5 }
ethernetFailOverGroup   OBJECT IDENTIFIER ::= { tiaraSystemMib 6 }
failOverEnableNotifications   OBJECT IDENTIFIER ::= { tiaraSystemMib 7 }
failOverNotifications   OBJECT IDENTIFIER ::= { tiaraSystemMib 8 }
vlanGroup			OBJECT IDENTIFIER ::= { tiaraSystemMib 9 }
sntpGroup              OBJECT IDENTIFIER ::= { tiaraSystemMib 10 }
sntpNotificationEnables OBJECT IDENTIFIER ::= { tiaraSystemMib 11 }
sntpNotifications       OBJECT IDENTIFIER ::= { tiaraSystemMib 12 }
vlanInterfaceGroup		OBJECT IDENTIFIER ::= { tiaraSystemMib 13 }
enableBgpNotifications          OBJECT IDENTIFIER ::= { tiaraSystemMib 14 }


sysIpAddr OBJECT-TYPE
        SYNTAX        IpAddress
        MAX-ACCESS        read-only
        STATUS        current
        DESCRIPTION   "This entity's IP address."
        ::= { systemObjects 1 }

sysNetMask 			OBJECT-TYPE
      SYNTAX        	IpAddress
      MAX-ACCESS    	read-only
      STATUS        	current
      DESCRIPTION   "This entity's subnet mask."
        ::= { systemObjects 2 }

sysBroadcast 		OBJECT-TYPE
      SYNTAX        	IpAddress
      MAX-ACCESS    	read-only
      STATUS        	current
      DESCRIPTION   "This entity's broadcast address."
        ::= { systemObjects 3 }

sysVersion 			OBJECT-TYPE
	SYNTAX  		DisplayString (SIZE (0..64))
	MAX-ACCESS      	read-only
      STATUS        	current
      DESCRIPTION
            "This variable contains a printable octet
             string that contains the system bootstrap
             and software version identification."
        ::= { systemObjects 4 }

sysHostName 		OBJECT-TYPE
	SYNTAX  		DisplayString (SIZE (0..64))
	MAX-ACCESS      	read-write
	STATUS          	current
	DESCRIPTION
		"
		Hostname of the system.
		"
	::= { systemObjects 6 }

sysDomainName 		OBJECT-TYPE
	SYNTAX  		DisplayString (SIZE (0..64))
	MAX-ACCESS  	read-write
	STATUS  		current
	DESCRIPTION
		"
		Domain name of the host.
		"
	::= { systemObjects 7 }

sysAlarmStatus 		OBJECT-TYPE
      SYNTAX        	INTEGER {
		clear(1),
		minor(2),
		major(3)
                                }
      MAX-ACCESS    	read-only
      STATUS        	current
   	DESCRIPTION   
			"This variable is set to major when the summary LED 
			on the system is illuminated. This happens when any 
			of the WAN physical interfaces have at least one 
			alarm."
      ::= { systemObjects 8 }

sysReset 			OBJECT-TYPE
     	SYNTAX        	INTEGER {
		other(1),   -- none of the following
		reset(2)    -- do systemreset
                                }
     	MAX-ACCESS   	read-write
     	STATUS        	current
     	DESCRIPTION   "
		      Writing a 2 to this object resets the system.
		      "
        ::= { systemObjects 10 }


sysDateTime 		OBJECT-TYPE
     	SYNTAX    		OCTET STRING(SIZE(10))
     	MAX-ACCESS    	read-write
     	STATUS        	current
     	DESCRIPTION   "
		      System date/time
--    A date-time specification.
--    
--     field  octets  contents                  range
--     =====  ======  ========                  =====
--       1       1    direction from UTC        '+' / '-'
--       2       1    hours from UTC            0..23
--       3       1    minutes from UTC          0..59

--       4       1    month                     1..12
--       5       1    day                       1..31
--       6       2    year                      1970..2100

--       7       1    hour                      0..23
--       8       1    minutes                   0..59
--       9       1    seconds                   0..60
--                    (use 60 for leap-second)

--    
--    For example, Tuesday May 26, 1992 at 1:30:15 PM
--    EDT would be displayed as:
--    
--                1992-5-26,13:30:15.0,-4:0
--    
--    Note that if only local time is known, then
--    time zone information (fields 8-10) is not
--    present.

		      "
        ::= { systemObjects 11 }

arpClearAtTable 		OBJECT-TYPE
	SYNTAX  		INTEGER
	MAX-ACCESS  	read-write
	STATUS  		current
	DESCRIPTION
		"Perform a clearing of the entire ARP address translation 
		 table. MIB II address translation table can be used to 
		 delete an individual entry.
		"
	::= { systemObjects 12 }


ipClearRouteTable 	OBJECT-TYPE
	SYNTAX  		INTEGER
	MAX-ACCESS  	read-write
	STATUS  		current
	DESCRIPTION
		"Perform a clearing of the entire Routing table.
		 MIB II routing table can be used to delete an individual 
		 entry.
		"
	::= { systemObjects 13 }
--
-- the DNS group using this MIB group an a DNS server can be configured 
-- or deleted if is is already configured.
--

dnsEnable 			OBJECT-TYPE
   	SYNTAX		INTEGER 	{ 
				enabled(1), 
				disabled(2) 
				}
    	MAX-ACCESS		read-write
     	STATUS        	current
    	DESCRIPTION   "Indicates if the DNS feature is enabled or 
			   disabled."
    	DEFVAL { disabled }
      ::= { dnsGroup 1}

dnsServerTable 		OBJECT-TYPE
      SYNTAX        	SEQUENCE OF DnsServerEntry
      MAX-ACCESS   	not-accessible
      STATUS        	current
      DESCRIPTION 	"This table lists a maximum of 3 DNS servers
		      	dnsEntryStatus variable is used to add an 
				entry or remove an entry from table. The first
		      	added entry will be used first. If it is not
		      	reachable, the next entry in the list will be 
		      	tried, and the next one, and so on.

                      	When creating a row, send oids for both 
                      	dnsServerEntryType dnsServerAddr in the same 
				snmp SET request. A row creation request for 
				a secondary request should return a failure 
				unless a primary name server has already been 
				configured."
      ::= { dnsGroup 2 }

dnsServerEntry 		OBJECT-TYPE
    	SYNTAX        	DnsServerEntry
     	MAX-ACCESS    	not-accessible
     	STATUS        	current
     	DESCRIPTION   "A DNS server table entry."
     	INDEX         	{ dnsServerAddr }
     	::= { dnsServerTable 1 }

DnsServerEntry ::= SEQUENCE {
		dnsServerEntryType INTEGER,
                dnsServerAddr		IpAddress
                }

dnsServerEntryType 	OBJECT-TYPE
     	SYNTAX        	INTEGER {
                       	invalid(1),   -- remove this entry
                       	primary(2),   -- the primary entry
                        other(3)      -- a lower priority entry
                         }
    	MAX-ACCESS   	read-write
   	STATUS        	current
    	DESCRIPTION   	"To add a new entry to the dnsServerTable, set 
				this object to primary(2) or other(3) for an 
				IP address that is not already in the table. 
				The primary entry will be used first, if it 
				is reachable. Otherwise, one of the other 
				entries will be used. Setting one entry to
                        primary(2) causes any previous primary entry
                        to change to other(3). To remove an entry 
				from the table, set this object to 
				invalid(1). "
      ::= { dnsServerEntry 1 }

dnsServerAddr 		OBJECT-TYPE
  	SYNTAX        	IpAddress
     	MAX-ACCESS    	read-write
    	STATUS        	current
   	DESCRIPTION   	"The IP address of a DNS server."
    	::= { dnsServerEntry 2 }

--
-- the userAdminGroup is used to administer the user accounts, etc.
--
userName 			OBJECT-TYPE
	SYNTAX  		DisplayString (SIZE (0..64))
	MAX-ACCESS  	not-accessible
	STATUS  		current
	DESCRIPTION
		"
		Name of the user.
		"
	::= { userAdminGroup 1 }


--
-- the ethernetFailOverGroup.
--
tiaraEthernetFailOverTable	OBJECT-TYPE
  	SYNTAX             	SEQUENCE OF TiaraEthernetFailOverEntry
   	MAX-ACCESS         	not-accessible
   	STATUS               	current
    	DESCRIPTION

            "A table maintaining failover and holdDown for Ethernet 
            interfaces:

                  tiaraFailOverIndex       = Ethernet index
                  tiaraFailOverEnable      = Enable Failover
                  tiaraHoldDownTime        = Holddown Time "

                           ::= { ethernetFailOverGroup 1 }

tiaraEthernetFailOverEntry 	OBJECT-TYPE
      SYNTAX                 	TiaraEthernetFailOverEntry
      MAX-ACCESS             	not-accessible
      STATUS                  current
      DESCRIPTION

           "A failover entry for each Ethernet."

      INDEX               {  tiaraFailOverIndex }
                           ::= { tiaraEthernetFailOverTable 1 }

TiaraEthernetFailOverEntry ::= SEQUENCE {
        tiaraFailOverIndex  	INTEGER,
        tiaraFailOverEnable  	TruthValue,
        tiaraHoldDownTime    	INTEGER
        }


tiaraFailOverIndex                      OBJECT-TYPE
        SYNTAX                          INTEGER 
        MAX-ACCESS                      not-accessible
        STATUS                          current
        DESCRIPTION

            "A numeric index for an ethernet. This value is the same
            as the ifIndex for ethernet ."

                           ::= { tiaraEthernetFailOverEntry 1 }


tiaraFailOverEnable         	OBJECT-TYPE
    	SYNTAX               	TruthValue
    	MAX-ACCESS           	read-write
    	STATUS              	current
    	DESCRIPTION

            "This object toggles the failover enable mode for a 
            particular Ethernet interface. The default mode is
            failover disabled. At present this is only applicable
            for data using source forwarding on an Ethernet 
		interface. If failover is enabled on a particular
            Ethernet interface and the Ethernet interface link 
            goes down, source forwarded traffic will switch 
            over to the other Ethernet interface." 


                           ::= { tiaraEthernetFailOverEntry 2 }

tiaraHoldDownTime        	OBJECT-TYPE
    	SYNTAX              	INTEGER (3..900)
    	MAX-ACCESS           	read-write
    	STATUS               	current
    	DESCRIPTION

            "The time, in seconds, that an Ethernet interface should 
		be in holdDown when it receives an up signal. In other 
		words, no source forwarding traffic should be sent on the 
		Ethernet interface during the holdDown time period. The 
		default is 3 seconds and the maximum is 900 seconds 
		(15 minutes). This applies when failover is enabled on 
		the interface and traffic has switched over to the other
            Ethernet interface ."

                           ::= { tiaraEthernetFailOverEntry 3 }

                       
--
-- failOverNotification contains the managed objects to enable the 
-- notifications for Ethernet fail over and when fail over fails.
-- 

enableFailOverNotification 	OBJECT-TYPE
    	SYNTAX          		TruthValue
    	MAX-ACCESS      		read-write
    	STATUS          		current
    	DESCRIPTION
               "Indicates whether the system produces the
                failOverNotification trap. The default is yes.
                "
 	DEFVAL { true }
    	::= { failOverEnableNotifications 1 }

enableFailOverFailNotification 	OBJECT-TYPE
    	SYNTAX          			TruthValue
     	MAX-ACCESS      			read-write
    	STATUS          			current
    	DESCRIPTION
               "Indicates whether the system produces the
                failOverFailNotification trap. The default is yes.
                "
    	DEFVAL { true }
    	::= { failOverEnableNotifications 2 }

--
-- failOverNotifications group is used to define notifications.
--

failOverNotification TRAP-TYPE
    	ENTERPRISE failOverNotifications
    	VARIABLES {tiaraFailOverIndex}
    	DESCRIPTION
                "
                A failOverNotification is sent on a successful fail
                over.
                "
             --#TYPE "Failover success notification"
             --#SUMMARY "Failover success notification for index: %s"
             --#ARGUMENTS {0}
             --#SEVERITY NORMAL            
        ::= 1

failOverFailNotification TRAP-TYPE
    	ENTERPRISE failOverNotifications
    	VARIABLES {tiaraFailOverIndex}
    	DESCRIPTION
                "
                A failOverFailNotification is sent when a fail over
                to the other port fails. 
                "
             --#TYPE "Failover failure notification"
             --#SUMMARY "Failover failure notification for index: %s"
             --#ARGUMENTS {0}
             --#SEVERITY MAJOR                        
        ::= 2

--
-- BgpNotification contains the managed objects to enable the
-- notifications for Bgp Peer establishment and backward transition.
--

enableBgpEstablishedNotification      OBJECT-TYPE
        SYNTAX                          TruthValue
        MAX-ACCESS                      read-write
        STATUS                          current
        DESCRIPTION
               "Indicates whether the system produces the
                bgpEstablished trap. The default is yes.
                "
        DEFVAL { true }
        ::= { enableBgpNotifications 1 }

enableBgpBackwardNotification  OBJECT-TYPE
        SYNTAX                                  TruthValue
        MAX-ACCESS                              read-write
        STATUS                                  current
        DESCRIPTION
               "Indicates whether the system produces the
                bgpBackwardTransition trap. The default is yes.
                "
        DEFVAL { true }
        ::= { enableBgpNotifications 2 }

  
--
-- VLAN table. 
-- 
-- 

vlanType 			OBJECT-TYPE
   	SYNTAX        	INTEGER 
    	MAX-ACCESS    	read-only
    	STATUS        	current
    	DESCRIPTION   	"VLAN Type."
    	::= { vlanGroup 1 }

vlanStatsTable 		OBJECT-TYPE
   	SYNTAX         	SEQUENCE OF VlanStatsEntry
   	MAX-ACCESS     	not-accessible
    	STATUS         	current
   	DESCRIPTION  	"VLAN Table."
   	::= { vlanGroup 2 }

vlanStatsEntry 		OBJECT-TYPE
    	SYNTAX        	VlanStatsEntry
    	MAX-ACCESS    	not-accessible
   	STATUS      	current
    	DESCRIPTION 	"A VLAN table entry."
    	INDEX         	{ vlanTag }
    	::= { vlanStatsTable 1 }

VlanStatsEntry ::= SEQUENCE {
	vlanTag 		INTEGER,
	vlanInterfaceList	DisplayString,
	vlanTxPkts		Counter32,
	vlanTxBytes      	DisplayString,
	vlanRxPkts		Counter32,
	vlanRxBytes      	DisplayString,
	vlanDroppedPkts	        Counter32,               
	vlanDropBytes    	DisplayString
			                }

vlanTag 			OBJECT-TYPE
     	SYNTAX        	INTEGER 
    	MAX-ACCESS    	read-only
    	STATUS        	current
    	DESCRIPTION   	"VLAN ID (Tag)."
    	::= { vlanStatsEntry 1 }

vlanInterfaceList 	OBJECT-TYPE
    	SYNTAX        	DisplayString 
    	MAX-ACCESS    	read-only
    	STATUS        	current
     	DESCRIPTION   	"VLAN Interface List."
     	::= { vlanStatsEntry 2 }

vlanTxPkts 			OBJECT-TYPE
     	SYNTAX        	Counter32 
     	MAX-ACCESS    	read-only
    	STATUS        	current
     	DESCRIPTION   	"Packets transmitted on this VLAN."
      ::= { vlanStatsEntry 3 }

vlanTxBytes             OBJECT-TYPE
    	SYNTAX        	DisplayString 
    	MAX-ACCESS    	read-only
    	STATUS        	current
     	DESCRIPTION   	"Bytes transmitted on this VLAN."
     	::= { vlanStatsEntry 4 }

vlanRxPkts 			OBJECT-TYPE
      SYNTAX        	Counter32 
      MAX-ACCESS    	read-only
      STATUS        	current
      DESCRIPTION   	"Packets received on this VLAN."
      ::= { vlanStatsEntry 5 }

vlanRxBytes             OBJECT-TYPE
    	SYNTAX        	DisplayString 
    	MAX-ACCESS    	read-only
    	STATUS        	current
     	DESCRIPTION   	"Bytes received on this VLAN."
     	::= { vlanStatsEntry 6 }

vlanDroppedPkts 	OBJECT-TYPE
      SYNTAX        	Counter32 
      MAX-ACCESS    	read-only
      STATUS        	current
      DESCRIPTION   	"Packets dropped on this VLAN."
      ::= { vlanStatsEntry 7 }

vlanDropBytes           OBJECT-TYPE
    	SYNTAX        	DisplayString 
    	MAX-ACCESS    	read-only
    	STATUS        	current
     	DESCRIPTION   	"Bytes dropped on this VLAN."
     	::= { vlanStatsEntry 8 }


--
-- VLAN interface stats table. 
-- 
-- 

vlanInterfaceStatsTable 		OBJECT-TYPE
   	SYNTAX         	SEQUENCE OF VlanInterfaceStatsEntry
   	MAX-ACCESS     	not-accessible
    	STATUS         	current
   	DESCRIPTION  	"VLAN Interface statistics Table."
   	::= { vlanInterfaceGroup 1 }

vlanInterfaceStatsEntry 		OBJECT-TYPE
    	SYNTAX        	VlanInterfaceStatsEntry
    	MAX-ACCESS    	not-accessible
   	STATUS      	current
    	DESCRIPTION 	"A VLAN interface stats table entry."
    	INDEX         	{ vlanInterfaceIndex }
    	::= { vlanInterfaceStatsTable 1 }

VlanInterfaceStatsEntry ::= SEQUENCE {
	vlanInterfaceIndex    	INTEGER,
	vlanInterfaceName     	DisplayString,
	vlanTagID 	        INTEGER,
	vlanTaggedPkts 		INTEGER,
	vlanTaggedBytes      	DisplayString,
	vlanUnTaggedPkts 	INTEGER,
	vlanUnTaggedBytes      	DisplayString
			        }

vlanInterfaceIndex	OBJECT-TYPE
     	SYNTAX          INTEGER	
     	MAX-ACCESS    	not-accessible
    	STATUS        	current
     	DESCRIPTION   	"VLAN interface index for the table"
      ::= { vlanInterfaceStatsEntry 1 }

vlanInterfaceName           OBJECT-TYPE
    	SYNTAX        	DisplayString 
    	MAX-ACCESS    	read-only
    	STATUS        	current
     	DESCRIPTION   	"VLAN interface name."                  
     	::= { vlanInterfaceStatsEntry 2 }

vlanTagID            OBJECT-TYPE
     	SYNTAX          INTEGER	
     	MAX-ACCESS    	read-only
    	STATUS        	current
     	DESCRIPTION   	"VLAN tagging ID of the interface."
      ::= { vlanInterfaceStatsEntry 3 }

vlanTaggedPkts 			OBJECT-TYPE
     	SYNTAX          INTEGER	
     	MAX-ACCESS    	read-only
    	STATUS        	current
     	DESCRIPTION   	"Packets tagged on this VLAN interface."
      ::= { vlanInterfaceStatsEntry 4 }

vlanTaggedBytes             OBJECT-TYPE
    	SYNTAX        	DisplayString 
    	MAX-ACCESS    	read-only
    	STATUS        	current
     	DESCRIPTION   	"Bytes tagged on this VLAN interface."
     	::= { vlanInterfaceStatsEntry 5 }

vlanUnTaggedPkts 			OBJECT-TYPE
     	SYNTAX          INTEGER	
     	MAX-ACCESS    	read-only
    	STATUS        	current
     	DESCRIPTION   	"Packets un-tagged on this VLAN interface."
      ::= { vlanInterfaceStatsEntry 6 }

vlanUnTaggedBytes             OBJECT-TYPE
    	SYNTAX        	DisplayString 
    	MAX-ACCESS    	read-only
    	STATUS        	current
     	DESCRIPTION   	"Bytes un-tagged on this VLAN interface."
     	::= { vlanInterfaceStatsEntry 7 }


--
-- sntpGroup
--
sntpClientEnabled OBJECT-TYPE
	SYNTAX		SntpEnabled
	MAX-ACCESS	read-create
	STATUS		current
	DESCRIPTION	"Sntp Client Enabled Flag."
        DEFVAL          { not-enabled }
	::= { sntpGroup 1 }    
            
sntpServerAddr OBJECT-TYPE
        SYNTAX          DisplayString (SIZE (0..30))
        MAX-ACCESS      read-create
        STATUS          current
        DESCRIPTION
            "The IP address or host name of an SNTP/NTP server.
             It can be set only when set along with the
             sntpClientEnabled object.
            "
        ::= { sntpGroup 2 }

                       
sntpTimeout OBJECT-TYPE
        SYNTAX           INTEGER 
        MAX-ACCESS       read-create
        STATUS           current
        DESCRIPTION
            "The timeout value for the sntp client.
             It can be set only when set along with the
             sntpClientEnabled object.
            "
        DEFVAL           { 1024 }
        ::= { sntpGroup 3 }

--
-- sntp mib objects
--

enableSntpNotification OBJECT-TYPE
        SYNTAX          TruthValue
        MAX-ACCESS      read-write
        STATUS          current
        DESCRIPTION
               "Indicates whether the system produces the
                sntpNotification. Default is yes.
                "
        DEFVAL         { true }
        ::= { sntpNotificationEnables 1 }

sntpEnableNotification TRAP-TYPE
        ENTERPRISE sntpNotifications
        VARIABLES { sntpServerAddr,
                    sntpTimeout 
                  }
        DESCRIPTION
                "
                A sntpNotification is sent when an sntp client
                is enabled.
                "
        ::= 1

sntpDisableNotification TRAP-TYPE
        ENTERPRISE sntpNotifications
        VARIABLES { sntpServerAddr,
                    sntpTimeout 
                  }
        DESCRIPTION
                "
                A sntpNotification is sent when an sntp client
                is disabled.
                "
        ::= 2

sntpSuccessNotification TRAP-TYPE
       ENTERPRISE sntpNotifications
       VARIABLES { sntpServerAddr,
                   sntpTimeout 
                 }
       DESCRIPTION
               "
               A sntpSuccessNotification is sent when an sntp client
               is successful in receiving time from the server.
               "
       ::= 3

sntpErrorNotification TRAP-TYPE
       ENTERPRISE sntpNotifications
       VARIABLES { sntpServerAddr,
                   sntpTimeout 
                 }
       DESCRIPTION
               "
               A sntpErrorNotification is sent when an sntp client
               has error in receiving time from the server.
               "
       ::= 4       


--
-- systemNotification contains the managed objects to enable the 
-- notifications if system is shutdown for reasons.
-- 

enableSysShutDownNotification OBJECT-TYPE
  	SYNTAX 	    		TruthValue
      MAX-ACCESS   		read-write
      STATUS     			current
      DESCRIPTION
            "Indicates whether the system produces the 
		shutDownNotification TRAP. The default is yes.
		"
      DEFVAL { true }
      ::= { systemEnableNotification 1 }

enableUserLoginNotification 	OBJECT-TYPE
     	SYNTAX 	    		TruthValue
      MAX-ACCESS      		read-write
      STATUS      		current
      DESCRIPTION
            "Indicates whether the system produces the 
		userLoginNotification TRAP. The default is yes.
		"
      DEFVAL { true }
      ::= { systemEnableNotification 2 }

enableUserLogOffNotification 	OBJECT-TYPE
      SYNTAX 	    		TruthValue
      MAX-ACCESS      		read-write
      STATUS      		current
      DESCRIPTION
            "Indicates whether the system produces the 
		userLoginOffNotification TRAP. The default is yes.
		"
      DEFVAL { true }
      ::= { systemEnableNotification 3 }

enableUserLoginFailNotification 	OBJECT-TYPE
      SYNTAX 	    			TruthValue
      MAX-ACCESS      			read-write
      STATUS      			current
      DESCRIPTION
            "Indicates whether the system produces the 
		userLoginFailNotification TRAP. the default is yes.
		"
      DEFVAL { true }
      ::= { systemEnableNotification 4 }

--
-- sysNotifications group is used to define notifications.
--

shutDownNotification TRAP-TYPE
    	ENTERPRISE systemNotifications
--     	VARIABLES {sysRestartReason}
	DESCRIPTION
		"
		A shutDownNotification is sent for the reboot command.
		"
             --#TYPE "System shutdown notification"
             --#SUMMARY "System shutdown notification"
             --#SEVERITY NORMAL                       
	::= 1

userLoginNotification TRAP-TYPE
    	ENTERPRISE systemNotifications
    	VARIABLES { userName }
	DESCRIPTION
		"
		A userAccessNotification is sent when a user logs in 
		successfully.
		"
             --#TYPE "User login successful"
             --#SUMMARY "User: %s login successful"
             --#ARGUMENTS {0}
             --#SEVERITY NORMAL                        
	::= 2

userLogOffNotification TRAP-TYPE
    	ENTERPRISE systemNotifications
    	VARIABLES { userName }
	DESCRIPTION
		"
		A userAccessNotification is sent when a user logs off.
		"
             --#TYPE "User logoff"
             --#SUMMARY "User: %s logoff"
             --#ARGUMENTS {0}
             --#SEVERITY NORMAL            
	::= 3
userLoginFailNotification TRAP-TYPE
    	ENTERPRISE systemNotifications
    	VARIABLES { userName }
	DESCRIPTION
		"
		A userAccessNotification is sent when a user login fails.
		"
             --#TYPE "User login failure"
             --#SUMMARY "User: %s login failure"
             --#ARGUMENTS {0}
             --#SEVERITY MINOR            
	::= 4
END
