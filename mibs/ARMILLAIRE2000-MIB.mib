-- *************************************************************************** 
-- (c) Copyright, Armillaire Tecnologies, Inc.
-- ALL RIGHTS RESERVED 
--
--   Armillaire Technologies, Inc.
--   6707 Democracy Blvd, Suite 200
--   Bethesda, MD 20817, USA 
--
--
-- Description    Armillaire MSSC MIB  (SNMPv1)
--
-- ****************************************************************************


ARMILLAIRE2000-MIB DEFINITIONS ::= BEGIN
IMPORTS
	TRAP-TYPE FROM RFC-1215
enterprises, Counter, Gauge, IpAddress, TimeTicks
	FROM RFC1155-SMI
OBJECT-TYPE
	FROM RFC-1212
DisplayString
	FROM RFC1213-MIB;
armillaire     OBJECT IDENTIFIER ::= { enterprises 4618 }
RowStatus	::=  INTEGER { 
			createandwait( 5),
			destroy( 6),
			active( 1),
			notinservice( 2),
			notready( 3),
			modified( 17),
			up( 22),
			down( 23),
			outofservice( 18)}

LrnRowStatus	::=  INTEGER { 
			createandwait( 5),
			destroy( 6),
			active( 1),
			notinservice( 2),
			notready( 3),
			outofservice( 18)}

CktRowStatus	::=  INTEGER { 
			createandwait( 5),
			destroy( 6),
			active( 1),
			notinservice( 2),
			notready( 3),
			modified( 17),
			up( 22),
			down( 23),
			modifytimer( 99),
			outofservice( 18),
			block( 20)}

TmrRowStatus	::=  INTEGER { 
			modifytimer( 99),
			active( 1),
			notinservice( 2),
			notready( 3),
			modified( 17),
			up( 22),
			down( 23),
			outofservice( 18)}

UserLoginStatus	::=  INTEGER { 
			login( 1),
			logininvalid( 2),
			adduser( 3),
			deleteuser( 4)}

UserLoginPriority	::=  INTEGER { 
			admin( 1),
			cts( 2),
			user( 8738)}

ProcessStatus	::=  INTEGER { 
			down( 1),
			active( 34),
			standby( 51),
			outofservice( 170),
			switchingover( 3),
			unknown( 172)}

IsdnPriority	::=  INTEGER { 
			primary( 0),
			secondary( 1),
			bearing( 2)}

IsdnType	::=  INTEGER { 
			nfas( 1),
			fas( 0)}

OpStatus	::=  INTEGER { 
			active( 1),
			down( 23)}

LinkOpStatus	::=  INTEGER { 
			active( 1),
			down( 23),
			inhibit( 19)}

LinkSetOpStatus	::=  INTEGER { 
			active( 1),
			deactive( 23)}

CktOpStatus	::=  INTEGER { 
			active( 1),
			down( 23),
			block( 20)}

IsdnTrnkOpStatus	::=  INTEGER { 
			active( 1),
			down( 23),
			disable( 21)}

ModifyTmrStatus	::=  INTEGER { 
			modifytimer( 99),
			noaction( 0)}

IfType	::=  INTEGER { 
			interface-t1( 0),
			interface-t3( 1),
			interface-ut3( 2),
			interface-oc3( 3),
			interface-ut3cp( 4),
			interface-oc3cp( 5),
			interface-e1( 8),
			interface-hde1( 9),
			interface-une3( 10),
			interface-stm( 11),
			interface-oc3aps( 12),
			interface-stm1aps( 13)}

AtmIfType	::=  INTEGER { 
			interface-t1( 0),
			interface-e1( 8)}

ConnectionType	::=  INTEGER { 
			t3( 1),
			ut3( 2),
			e3( 10)}

EnableStatus	::=  INTEGER { 
			yes( 1),
			no( 2)}

Ss7RouteType	::=  INTEGER { 
			load( 0)}

AddrIdentifier	::=  INTEGER { 
			unknown( 2),
			nationalnumber( 3)}

AddrType	::=  INTEGER { 
			callpartynum( 1),
			transitnetwork( 2)}

NumPlan	::=  INTEGER { 
			nonumber( 0),
			isdnnumplan( 1)}

Direction	::=  INTEGER { 
			in( 0),
			out( 1),
			both( 2)}

EnableOperation	::=  INTEGER { 
			enable( 16),
			disable( 17)}

IsdnChnlMgtOperation	::=  INTEGER { 
			enable( 11),
			disable( 12)}

IsdnTrnkMgtOperation	::=  INTEGER { 
			enable( 9),
			disable( 10)}

BlockOperation	::=  INTEGER { 
			block( 5),
			unblock( 6),
			noaction( 0)}

Level	::=  INTEGER { 
			level1( 1),
			level2( 2)}

ModemResetStatus	::=  INTEGER { 
			yes( 1),
			no( 0)}

ModemEnableStatus	::=  INTEGER { 
			enable( 1),
			disable( 0)}

MeasEnableStatus	::=  INTEGER { 
			enable( 1),
			disable( 0)}

EthernetConnStatus	::=  INTEGER { 
			up( 1),
			down( 2)}

Standard	::=  INTEGER { 
			ansi( 65),
			itu( 73),
			telmex( 84)}

TrunkType	::=  INTEGER { 
			ss7( 34),
			isdn( 17)}

RouteType	::=  INTEGER { 
			ss7RouteType( 1),
			isdnRouteType( 2)}

AuditType	::=  INTEGER { 
			ansi( 65),
			itu( 73)}

AuditOperation	::=  INTEGER { 
			audit( 1),
			noaction( 0)}

Controlstatus	::=  INTEGER { 
			blockckt( 5),
			unblock( 6),
			enablechnl( 11),
			disablechnl( 12),
			noaction( 0)}

LinkControlStatus	::=  INTEGER { 
			inhibitlink( 1),
			uninhibitlink( 2),
			noaction( 0)}

LinkSetControlStatus	::=  INTEGER { 
			activatelnkset( 3),
			deactivatelnkset( 4),
			noaction( 0)}

CircuitControlStatus	::=  INTEGER { 
			blockcic( 7),
			unblockcic( 8),
			queryckt( 13),
			validateckt( 14),
			resetckt( 15),
			noaction( 0)}

IsdnControlstatus	::=  INTEGER { 
			enabletrnk( 9),
			disabletrnk( 10),
			noaction( 0)}

MtpRteState	::=  INTEGER { 
			rteavail( 1),
			rteunaval( 0)}

Bool	::=  INTEGER { 
			yes( 1),
			no( 0)}

LoadBalance	::=  INTEGER { 
			disable( 0),
			enable( 1)}

TrnkGrpType	::=  INTEGER { 
			ss7( 32),
			isdn( 33)}

ActiveAlarmAckStatus	::=  INTEGER { 
			clear( 0),
			noaction( 1)}

EventType	::=  INTEGER { 
			alarm( 1),
			emergency( 2),
			audit( 3),
			diagnostics( 4),
			security( 5),
			maintenance( 6)}

AlarmEvent	::=  INTEGER { 
			general( 1),
			device( 2),
			protocol( 3),
			mfd( 4),
			cdr( 5),
			measurement( 6),
			log( 7),
			ig( 8),
			faultTolerance( 9),
			nomainevent( 0)}

AlarmSubEvent	::=  INTEGER { 
			administration( 1),
			nosubevent( 0),
			operation( 2),
			mssc( 3),
			xconnect( 4),
			hub( 5),
			ss7lnk( 6),
			ss7Br( 7),
			isdn( 8),
			atm( 9)}

AlarmSeverity	::=  INTEGER { 
			critical( 1),
			major( 2),
			minor( 3),
			informational( 4)}

RoffType	::=  INTEGER { 
			le( 1),
			tandem( 2),
			intlgateway( 3)}

NameString ::=  DisplayString(SIZE(1..24))
AddrString ::=  DisplayString(SIZE(1..24))
CdrFlag	::=  INTEGER { 
			noCdr( 0),
			ic( 1),
			og( 2),
			bi( 3)}

DSPCardType	::=  INTEGER { 
			dsp2B( 1),
			dsp2C( 2)}

VoicePcm	::=  INTEGER { 
			alaw( 101),
			ulaw( 102)}

TGFeature	::=  INTEGER { 
			enable( 1),
			disable( 0)}

FTswitchOver	::=  INTEGER { 
			ftsig( 0),
			fticc( 1),
			ftisdn( 2),
			ftsphr( 3),
			ftlm( 4)}

LogFileAttr	::=  INTEGER { 
			alarmlog( 3),
			auditlog( 2),
			measlog( 7),
			diaglog( 1),
			scrtylog( 4),
			eventlog( 5),
			billlog( 8),
			emplog( 6)}

LogFileEnDis	::=  INTEGER { 
			alarmlog( 3),
			auditlog( 2),
			measlog( 7),
			diaglog( 1),
			scrtylog( 4),
			eventlog( 5),
			billlog( 8),
			emplog( 6),
			logall( 11),
			noaction( 0)}

SwitchType	::=  INTEGER { 
			national( 0),
			international( 1)}

LinkType	::=  INTEGER { 
			speed-56K( 53),
			speed-64K( 54)}

LogType	::=  INTEGER { 
			on( 49),
			off( 48)}

EnableTrace	::=  INTEGER { 
			enable( 1),
			disable( 0)}

TrunkState	::=  INTEGER { 
			idle( 0),
			unEquipped( 255),
			cP-Busy( 1),
			maintainance-Busy( 2)}

MeasPurgeFlag	::=  INTEGER { 
			autoOff( 0),
			autoOn( 1)}

E1MultiFrame	::=  INTEGER { 
			cas( 1),
			ccs( 2)}

E1CRC4	::=  INTEGER { 
			enabled( 1),
			disabled( 2)}

TransClkSrc	::=  INTEGER { 
			loopTiming( 1),
			localTiming( 2)}

DS1LineType	::=  INTEGER { 
			esF( 1),
			d4( 2)}

DS1LineCoding	::=  INTEGER { 
			b8zs( 1),
			ami( 2)}

DS1LBO	::=  INTEGER { 
			upTo133Feet( 1),
			upTo266Feet( 2),
			upTo399Feet( 3),
			upTo533Feet( 4),
			upTo655Feet( 5),
			negative7-5Db( 6),
			negative15Db( 7),
			negative22-5Db( 8)}

DS3LineType	::=  INTEGER { 
			cbitParity( 1),
			clearChannel( 2)}

DS3LBO	::=  INTEGER { 
			short( 1),
			long( 2)}

DS3ATMCellMap	::=  INTEGER { 
			plcp( 1),
			directMapping( 2)}

TimerType	::=  INTEGER { 
			ansi( 1),
			itu( 2)}


products		OBJECT IDENTIFIER   ::=	{ armillaire	 1 }

services		OBJECT IDENTIFIER   ::=	{ armillaire	 2 }

armillaire2000		OBJECT IDENTIFIER   ::=	{ products	 2 }

 -- *************************************************     
 -- MSSC group
 -- *************************************************     

switchInfo		OBJECT IDENTIFIER   ::=	{ armillaire2000	 1 }

switchConfig		OBJECT IDENTIFIER   ::=	{ armillaire2000	 2 }

switchMeas		OBJECT IDENTIFIER   ::=	{ armillaire2000	 3 }

switchCdr		OBJECT IDENTIFIER   ::=	{ armillaire2000	 4 }

switchFeature		OBJECT IDENTIFIER   ::=	{ armillaire2000	 5 }

switchMaintenance		OBJECT IDENTIFIER   ::=	{ armillaire2000	 6 }

switchTrap		OBJECT IDENTIFIER   ::=	{ armillaire2000	 7 }

 -- *************************************************     
 -- Switch Information Group
 -- *************************************************     

switchGenInfoGrp		OBJECT IDENTIFIER   ::=	{ switchInfo	 1 }

switchPcInfo		OBJECT IDENTIFIER   ::=	{ switchInfo	 2 }

switchUsrInfo		OBJECT IDENTIFIER   ::=	{ switchInfo	 3 }

switchVersionGrp		OBJECT IDENTIFIER   ::=	{ switchInfo	 4 }

 -- *************************************************     
 -- Switch Configuration Group
 -- *************************************************     

ss7		OBJECT IDENTIFIER   ::=	{ switchConfig	 1 }

isdn		OBJECT IDENTIFIER   ::=	{ switchConfig	 2 }

trnkGrp		OBJECT IDENTIFIER   ::=	{ switchConfig	 3 }

rt		OBJECT IDENTIFIER   ::=	{ switchConfig	 4 }

xconnect		OBJECT IDENTIFIER   ::=	{ switchConfig	 5 }

enableGroup		OBJECT IDENTIFIER   ::=	{ switchConfig	 6 }

 -- *************************************************     
 -- Switch Measurement Group
 -- *************************************************     

measFile		OBJECT IDENTIFIER   ::=	{ switchMeas	 1 }

measSwitch		OBJECT IDENTIFIER   ::=	{ switchMeas	 2 }

measTrnkGrp		OBJECT IDENTIFIER   ::=	{ switchMeas	 3 }

measLnk		OBJECT IDENTIFIER   ::=	{ switchMeas	 4 }

 -- *************************************************     
 -- Switch Features Group
 -- *************************************************     

modemFaultDetection		OBJECT IDENTIFIER   ::=	{ switchFeature	 1 }

lnp		OBJECT IDENTIFIER   ::=	{ switchFeature	 2 }

switchDSP		OBJECT IDENTIFIER   ::=	{ switchFeature	 3 }

switchTGFeature		OBJECT IDENTIFIER   ::=	{ switchFeature	 4 }

 -- *************************************************     
 -- Switch Maintenance Group
 -- *************************************************     

ft		OBJECT IDENTIFIER   ::=	{ switchMaintenance	 1 }

log		OBJECT IDENTIFIER   ::=	{ switchMaintenance	 2 }

trace		OBJECT IDENTIFIER   ::=	{ switchMaintenance	 3 }

processStatus		OBJECT IDENTIFIER   ::=	{ switchMaintenance	 4 }

ethernetConnStatusInfo		OBJECT IDENTIFIER   ::=	{ switchMaintenance	 5 }

audit		OBJECT IDENTIFIER   ::=	{ switchMaintenance	 6 }

 -- *************************************************     
 -- Switch Trap Group
 -- *************************************************     

trapObjects		OBJECT IDENTIFIER   ::=	{ switchTrap	 1 }

alarmGrp		OBJECT IDENTIFIER   ::=	{ switchTrap	 2 }

 -- *************************************************     
 -- Switch Maintenance Group [ FT ]
 -- *************************************************     

ftSwitchOverInfo		OBJECT IDENTIFIER   ::=	{ ft	 1 }

 -- *************************************************     
 -- Switch Maintenance Group [LOG ]
 -- *************************************************     

logFileInfo		OBJECT IDENTIFIER   ::=	{ log	 1 }

logFileGenEnable		OBJECT IDENTIFIER   ::=	{ log	 2 }

logFileAttribute		OBJECT IDENTIFIER   ::=	{ log	 3 }

 -- *************************************************     
 -- Switch Maintenance Group [Audit ]
 -- *************************************************     

auditInfo		OBJECT IDENTIFIER   ::=	{ audit	 1 }

 -- *************************************************     
 -- Switch Maintenance Group [Trace ]
 -- *************************************************     

ss7LnkTrace		OBJECT IDENTIFIER   ::=	{ trace	 1 }

ss7RouteTrace		OBJECT IDENTIFIER   ::=	{ trace	 2 }

isdnTrnkTrace		OBJECT IDENTIFIER   ::=	{ trace	 3 }

 -- *************************************************     
 -- Switch Maintenance Group [ProcessStatus ]
 -- *************************************************     

processStatusInfo		OBJECT IDENTIFIER   ::=	{ processStatus	 1 }

 -- *************************************************     
 -- SS7 Configuration Group
 -- *************************************************     

ss7Sig		OBJECT IDENTIFIER   ::=	{ ss7	 1 }

ss7Br		OBJECT IDENTIFIER   ::=	{ ss7	 2 }

mtp2		OBJECT IDENTIFIER   ::=	{ ss7	 3 }

mtp3		OBJECT IDENTIFIER   ::=	{ ss7	 4 }

isup		OBJECT IDENTIFIER   ::=	{ ss7	 5 }

ss7Route		OBJECT IDENTIFIER   ::=	{ ss7	 6 }

 -- *************************************************     
 -- mtp3 gen Timer
 -- *************************************************     

mtp3GenTmrCfgGroup		OBJECT IDENTIFIER   ::=	{ mtp3	 1 }

 -- *************************************************     
 -- ISUP group
 -- *************************************************     

switchName		OBJECT-TYPE
			SYNTAX	NameString
			ACCESS	read-write
			STATUS	mandatory
			DESCRIPTION 
	"The switch Name. Can be any combination of alphanumeric 
	characters. Spaces are not allowed and cannot exceed 24 characters "
			::= {	switchGenInfoGrp   1 }

switchDescr		OBJECT-TYPE
			SYNTAX	DisplayString(SIZE(1..255))
			ACCESS	read-write
			STATUS	mandatory
			DESCRIPTION 
	"Description of the Switch. Can be any combination of alphanumeric 
	characters. Spaces are allowed and cannot exceed 255 characters. "
			::= {	switchGenInfoGrp   2 }

switchLocation		OBJECT-TYPE
			SYNTAX	DisplayString(SIZE(1..255))
			ACCESS	read-write
			STATUS	mandatory
			DESCRIPTION 
	"Location of the Switch. Can be any combination of alphanumeric 
	characters. Spaces are allowed and cannot exceed 255 characters. "
			::= {	switchGenInfoGrp   3 }

switchContact		OBJECT-TYPE
			SYNTAX	DisplayString(SIZE(1..24))
			ACCESS	read-write
			STATUS	mandatory
			DESCRIPTION 
	"Contact information about the Switch. Can be any combination of alphanumeric 
	characters. Spaces are allowed and cannot exceed 24 characters. "
			::= {	switchGenInfoGrp   4 }

switchIPAddr		OBJECT-TYPE
			SYNTAX	IpAddress
			ACCESS	read-only
			STATUS	mandatory
			DESCRIPTION 
	"Switch IP address. In xxx.xxx.xxx.xxx format. "
			::= {	switchGenInfoGrp   5 }

switchUpTime		OBJECT-TYPE
			SYNTAX	TimeTicks
			ACCESS	read-only
			STATUS	mandatory
			DESCRIPTION 
	"The Time (in Seconds) since last restart of the Switch "
			::= {	switchGenInfoGrp   6 }

switchVersion		OBJECT-TYPE
			SYNTAX	DisplayString(SIZE(1..24))
			ACCESS	read-only
			STATUS	mandatory
			DESCRIPTION 
	"The version of current Switch "
			::= {	switchGenInfoGrp   7 }

switchVerDescr		OBJECT-TYPE
			SYNTAX	DisplayString(SIZE(1..255))
			ACCESS	read-only
			STATUS	mandatory
			DESCRIPTION 
	"The description of switch version "
			::= {	switchGenInfoGrp   8 }

systemDescr		OBJECT-TYPE
			SYNTAX	DisplayString(SIZE(1..255))
			ACCESS	read-only
			STATUS	mandatory
			DESCRIPTION 
	"The description of the System "
			::= {	switchGenInfoGrp   9 }

switchType		OBJECT-TYPE
			SYNTAX	SwitchType
			ACCESS	read-only
			STATUS	mandatory
			DESCRIPTION 
	"The Switch Type : (National/International) "
			::= {	switchGenInfoGrp   10 }

switchNameStatus		OBJECT-TYPE
			SYNTAX	RowStatus
			ACCESS	read-write
			STATUS	mandatory
			DESCRIPTION 
	"Current Status (configurational Status) of this Switch Name. 
	To Configure this Link, the only option is 'CREATEANDWAIT' 
	To Delete this Link, the only option is 'DESTROY' 
	For the GET Operation, the possible options are 
	1) active 
	2) notinservice 
	3) no"
			::= {	switchGenInfoGrp   11 }

 -- *************************************************     
 -- switch pointcode information
 -- *************************************************     

switchPcInfoTable		OBJECT-TYPE
			SYNTAX   SEQUENCE OF SwitchPcEntry
			ACCESS	not-accessible
			STATUS	mandatory
			DESCRIPTION 
	"Switch Point code Information Table.The index of this 
	table is switchPc (Integer). "
			::= { switchPcInfo	 1 }

switchPcEntry		OBJECT-TYPE
			SYNTAX	SwitchPcEntry
			ACCESS	not-accessible
			STATUS	mandatory
			DESCRIPTION 
	"The Current Entry Containes all the objects for this Table. 
	This object is not-accessible, but the user can access all 
	the objects in this table at the next level. "
			INDEX { switchPc }
			::= {	switchPcInfoTable   1 }

SwitchPcEntry		::= SEQUENCE {
			switchPc		INTEGER,
			switchPcMode		Standard,
			switchPcStatus		RowStatus
			}

switchPc		OBJECT-TYPE
			SYNTAX	INTEGER(1..16777215)
			ACCESS	read-write
			STATUS	mandatory
			DESCRIPTION 
	"Point Code for the switch (the Integer Value). 
	The Point Code should be converted into its Integer 
	equivalent. For Example: 
	0-1-1 is converted as 257 (for ANSI) 
	0-1-2 is converted as 10 (for ITU) "
			::= {	switchPcEntry   1 }

switchPcMode		OBJECT-TYPE
			SYNTAX	Standard
			ACCESS	read-write
			STATUS	mandatory
			DESCRIPTION 
	"Point Code type (ANSI/ITU) "
			::= {	switchPcEntry   2 }

switchPcStatus		OBJECT-TYPE
			SYNTAX	RowStatus
			ACCESS	read-write
			STATUS	mandatory
			DESCRIPTION 
	"Current Status (configurational Status) of this Switch Point Code. 
	To Configure this Link, the only option is 'CREATEANDWAIT' 
	To Delete this Link, the only option is 'DESTROY' 
	For the 'GET' Operation, the possible options are 
	1) active 
	2) notinservic"
			::= {	switchPcEntry   3 }

 -- *************************************************     
 -- switch User information Table
 -- *************************************************     

switchUserCfgTable		OBJECT-TYPE
			SYNTAX   SEQUENCE OF SwitchUserCfgEntry
			ACCESS	not-accessible
			STATUS	mandatory
			DESCRIPTION 
	"This Table is to maintain the User information 
	and providing Validation Checks for Authorised users 
	for Configuration.The index of this table is switchUserId (Integer). 
	CURRENTLY NOT APPLICABLE "
			::= { switchUsrInfo	 1 }

switchUserCfgEntry		OBJECT-TYPE
			SYNTAX	SwitchUserCfgEntry
			ACCESS	not-accessible
			STATUS	mandatory
			DESCRIPTION 
	"The Current Entry Containes all the objects for this Table. 
	This object is not-accessible, but the user can access all 
	the objects in this table at the next level. 
	CURRENTLY NOT APPLICABLE "
			INDEX { switchUserId }
			::= {	switchUserCfgTable   1 }

SwitchUserCfgEntry		::= SEQUENCE {
			switchUserId		INTEGER,
			switchUserName		NameString,
			switchUserPassword		NameString,
			switchUserPriority		UserLoginPriority,
			switchUserStatus		UserLoginStatus
			}

switchUserId		OBJECT-TYPE
			SYNTAX	INTEGER
			ACCESS	read-write
			STATUS	mandatory
			DESCRIPTION 
	"The Id of the Switch User. The user can only 'SET' User Id. 
	If user tries to 'GET' the user Id, incorrect value would be displayed. 
	This Feature is CURRENTLY NOT APPLICABLE  "
			::= {	switchUserCfgEntry   1 }

switchUserName		OBJECT-TYPE
			SYNTAX	NameString
			ACCESS	read-write
			STATUS	mandatory
			DESCRIPTION 
	"The NAME of the Switch User. The user can only 'SET' User NAME. 
	If user tries to 'GET' the user Id, incorrect value would be displayed. 
	This Feature is CURRENTLY NOT APPLICABLE  "
			::= {	switchUserCfgEntry   2 }

switchUserPassword		OBJECT-TYPE
			SYNTAX	NameString
			ACCESS	read-write
			STATUS	mandatory
			DESCRIPTION 
	"The PASSWORD of the Switch User. This is in an encrypted format. 
	This is not visible to user.The user can only set password . 
	This Feature is CURRENTLY NOT APPLICABLE  "
			::= {	switchUserCfgEntry   3 }

switchUserPriority		OBJECT-TYPE
			SYNTAX	UserLoginPriority
			ACCESS	read-write
			STATUS	mandatory
			DESCRIPTION 
	"The PRIORITY of the Switch User. User Priority by default is ADMINISTRATOR. 
	This Feature is CURRENTLY NOT APPLICABLE  "
			::= {	switchUserCfgEntry   4 }

switchUserStatus		OBJECT-TYPE
			SYNTAX	UserLoginStatus
			ACCESS	read-write
			STATUS	mandatory
			DESCRIPTION 
	"Checks whether user is a valid user. 
	Only the user with administrative privilege can login. 
	This Feature is CURRENTLY NOT APPLICABLE  "
			::= {	switchUserCfgEntry   5 }

 -- *************************************************     
 -- switch Version group
 -- *************************************************     

switchVerLM		OBJECT-TYPE
			SYNTAX	DisplayString
			ACCESS	read-only
			STATUS	mandatory
			DESCRIPTION 
	"Switch's Process LM Version number  "
			::= {	switchVersionGrp   1 }

switchVerMTP2		OBJECT-TYPE
			SYNTAX	DisplayString
			ACCESS	read-only
			STATUS	mandatory
			DESCRIPTION 
	"Switch's Process MPT2 Version number  "
			::= {	switchVersionGrp   2 }

switchVerICC		OBJECT-TYPE
			SYNTAX	DisplayString
			ACCESS	read-only
			STATUS	mandatory
			DESCRIPTION 
	"Switch's Process ICC Version number  "
			::= {	switchVersionGrp   3 }

switchVerSIG		OBJECT-TYPE
			SYNTAX	DisplayString
			ACCESS	read-only
			STATUS	mandatory
			DESCRIPTION 
	"Switch's Process SIG Version number  "
			::= {	switchVersionGrp   4 }

switchVerISDN		OBJECT-TYPE
			SYNTAX	DisplayString
			ACCESS	read-only
			STATUS	mandatory
			DESCRIPTION 
	"Switch's Process ISDN Version number  "
			::= {	switchVersionGrp   5 }

switchVerSPHR		OBJECT-TYPE
			SYNTAX	DisplayString
			ACCESS	read-only
			STATUS	mandatory
			DESCRIPTION 
	"Switch's Process SPHR Version number  "
			::= {	switchVersionGrp   6 }

 -- *************************************************     
 -- ss7 link configuration table
 -- *************************************************     

ss7LinkCfgTable		OBJECT-TYPE
			SYNTAX   SEQUENCE OF Ss7LinkCfgEntry
			ACCESS	not-accessible
			STATUS	mandatory
			DESCRIPTION 
	"SS7 Link Table. Information about the SS7 Link(s) in MSSC are 
	provided in this table. The index of this table is ss7LinkName (String) "
			::= { ss7Sig	 1 }

ss7LinkCfgEntry		OBJECT-TYPE
			SYNTAX	Ss7LinkCfgEntry
			ACCESS	not-accessible
			STATUS	mandatory
			DESCRIPTION 
	"The Current Entry Containes all the objects for this Table. 
	This object is not-accessible, but the user can access all 
	the objects in this table at the next level. "
			INDEX { ss7LinkName }
			::= {	ss7LinkCfgTable   1 }

Ss7LinkCfgEntry		::= SEQUENCE {
			ss7LinkName		NameString,
			ss7LinkId		INTEGER,
			ss7LinkTrunkId		INTEGER,
			ss7LinkChannel		INTEGER,
			ss7LinkSlc		INTEGER,
			ss7LinkSpeed		LinkType,
			ss7LinkMode		Standard,
			ss7LinkRowStatus		RowStatus,
			ss7LinkOpStatus		LinkOpStatus
			}

ss7LinkName		OBJECT-TYPE
			SYNTAX	NameString
			ACCESS	read-write
			STATUS	mandatory
			DESCRIPTION 
	"Link name. Can be any combination of alphanumeric characters. 
	Spaces are not allowed and cannot exceed 15 characters. "
			::= {	ss7LinkCfgEntry   1 }

ss7LinkId		OBJECT-TYPE
			SYNTAX	INTEGER(1..65535)
			ACCESS	read-write
			STATUS	mandatory
			DESCRIPTION 
	"User assigned Link id. Can be any integer 1-65535. "
			::= {	ss7LinkCfgEntry   2 }

ss7LinkTrunkId		OBJECT-TYPE
			SYNTAX	INTEGER(1..65535)
			ACCESS	read-write
			STATUS	mandatory
			DESCRIPTION 
	"User assigned Trunk id.  "
			::= {	ss7LinkCfgEntry   3 }

ss7LinkChannel		OBJECT-TYPE
			SYNTAX	INTEGER(1..65535)
			ACCESS	read-write
			STATUS	mandatory
			DESCRIPTION 
	"User assigned channel.  "
			::= {	ss7LinkCfgEntry   4 }

ss7LinkSlc		OBJECT-TYPE
			SYNTAX	INTEGER(0..15)
			ACCESS	read-write
			STATUS	mandatory
			DESCRIPTION 
	"Link Selection Code. Can be any integer 0-15. "
			::= {	ss7LinkCfgEntry   5 }

ss7LinkSpeed		OBJECT-TYPE
			SYNTAX	LinkType
			ACCESS	read-only
			STATUS	mandatory
			DESCRIPTION 
	"SS7 Link Speed: Possible Values are: 
	56k or 64k. 
	Default Value is 64K "
			::= {	ss7LinkCfgEntry   6 }

ss7LinkMode		OBJECT-TYPE
			SYNTAX	Standard
			ACCESS	read-write
			STATUS	mandatory
			DESCRIPTION 
	"Link Mode(ANSI/ITU) "
			::= {	ss7LinkCfgEntry   7 }

ss7LinkRowStatus		OBJECT-TYPE
			SYNTAX	RowStatus
			ACCESS	read-write
			STATUS	mandatory
			DESCRIPTION 
	"Current Status (configurational Status) of this Link. 
	To Configure this Link, the only option is 'CREATEANDWAIT' 
	To Delete this Link, the only option is 'DESTROY' 
	For the 'GET' Operation, the possible options are 
	1) active 
	2) notinservice 
	3) notread"
			::= {	ss7LinkCfgEntry   8 }

ss7LinkOpStatus		OBJECT-TYPE
			SYNTAX	LinkOpStatus
			ACCESS	read-only
			STATUS	mandatory
			DESCRIPTION 
	"Current Status (Operational Status) of this SS7 Link. 
	'SET' Operation is NOT APPLICABLE. 
	For the 'GET' Operation, the possible options are 
	1) active 
	2) down 
	3) inhibit "
			::= {	ss7LinkCfgEntry   9 }

 -- *************************************************     
 -- ATM link config table
 -- *************************************************     

ss7AtmLinkCfgTable		OBJECT-TYPE
			SYNTAX   SEQUENCE OF Ss7AtmLinkCfgEntry
			ACCESS	not-accessible
			STATUS	mandatory
			DESCRIPTION 
	"SS7 Atm Link Table. Information about the Atm Link(s) in MSSC are 
	provided in this table. This table has two indices. The indices are 
	ss7AtmVpi and ss7AtmVci (both Integer). "
			::= { ss7Sig	 2 }

ss7AtmLinkCfgEntry		OBJECT-TYPE
			SYNTAX	Ss7AtmLinkCfgEntry
			ACCESS	not-accessible
			STATUS	mandatory
			DESCRIPTION 
	"The Current Entry Containes all the objects for this Table. 
	This object is not-accessible, but the user can access all 
	the objects in this table at the next level. "
			INDEX { ss7AtmVpi, ss7AtmVci }
			::= {	ss7AtmLinkCfgTable   1 }

Ss7AtmLinkCfgEntry		::= SEQUENCE {
			ss7AtmVpi		INTEGER,
			ss7AtmVci		INTEGER,
			ss7AtmLnkId		INTEGER,
			ss7AtmXconnectId		INTEGER,
			ss7AtmSlotId		INTEGER,
			ss7AtmPortId		INTEGER,
			ss7AtmChnlId		INTEGER,
			ss7AtmTrnkId		INTEGER,
			ss7AtmPhyType		AtmIfType,
			ss7AtmLinkRowStatus		RowStatus,
			ss7AtmLinkOpStatus		LinkOpStatus
			}

ss7AtmVpi		OBJECT-TYPE
			SYNTAX	INTEGER(1..65535)
			ACCESS	read-write
			STATUS	mandatory
			DESCRIPTION 
	"Atmlink Virtual Path Identifier.  "
			::= {	ss7AtmLinkCfgEntry   1 }

ss7AtmVci		OBJECT-TYPE
			SYNTAX	INTEGER(1..65535)
			ACCESS	read-write
			STATUS	mandatory
			DESCRIPTION 
	"Atmlink Virtual Channel Identifier.  "
			::= {	ss7AtmLinkCfgEntry   2 }

ss7AtmLnkId		OBJECT-TYPE
			SYNTAX	INTEGER(1..65535)
			ACCESS	read-write
			STATUS	mandatory
			DESCRIPTION 
	"Atmlink Id.  "
			::= {	ss7AtmLinkCfgEntry   3 }

ss7AtmXconnectId		OBJECT-TYPE
			SYNTAX	INTEGER(1..65535)
			ACCESS	read-write
			STATUS	mandatory
			DESCRIPTION 
	"Xconnect Id.  "
			::= {	ss7AtmLinkCfgEntry   4 }

ss7AtmSlotId		OBJECT-TYPE
			SYNTAX	INTEGER(1..65535)
			ACCESS	read-write
			STATUS	mandatory
			DESCRIPTION 
	"Slot Id.  "
			::= {	ss7AtmLinkCfgEntry   5 }

ss7AtmPortId		OBJECT-TYPE
			SYNTAX	INTEGER(1..65535)
			ACCESS	read-write
			STATUS	mandatory
			DESCRIPTION 
	"Port Id. "
			::= {	ss7AtmLinkCfgEntry   6 }

ss7AtmChnlId		OBJECT-TYPE
			SYNTAX	INTEGER(1..65535)
			ACCESS	read-write
			STATUS	mandatory
			DESCRIPTION 
	"Channel Id.  "
			::= {	ss7AtmLinkCfgEntry   7 }

ss7AtmTrnkId		OBJECT-TYPE
			SYNTAX	INTEGER(1..65535)
			ACCESS	read-write
			STATUS	mandatory
			DESCRIPTION 
	"Atm Trunk Id.  "
			::= {	ss7AtmLinkCfgEntry   8 }

ss7AtmPhyType		OBJECT-TYPE
			SYNTAX	AtmIfType
			ACCESS	read-write
			STATUS	mandatory
			DESCRIPTION 
	"SS7 ATM Physical interface type. The value of this object could be 1) T1 (interface - t1) 2) E1 (interface - e1)."
			::= {	ss7AtmLinkCfgEntry   9 }

ss7AtmLinkRowStatus		OBJECT-TYPE
			SYNTAX	RowStatus
			ACCESS	read-write
			STATUS	mandatory
			DESCRIPTION 
	"Current ATM Status (configurational Status) of this Link. 
	To Configure this Link, the only option is 'CREATEANDWAIT' 
	To Delete this Link, the only option is 'DESTROY' 
	For the 'GET' Operation, the possible options are 
	1) active 
	2) notinservice 
	3) not"
			::= {	ss7AtmLinkCfgEntry   10 }

ss7AtmLinkOpStatus		OBJECT-TYPE
			SYNTAX	LinkOpStatus
			ACCESS	read-only
			STATUS	mandatory
			DESCRIPTION 
	"Current Status (Operational Status) of this SS7 Atm Link. 
	'SET' Operation is NOT APPLICABLE. 
	For the 'GET' Operation, the possible options are 
	1) active 
	2) down 
	3) inhibit "
			::= {	ss7AtmLinkCfgEntry   11 }

 -- *************************************************     
 -- SS7 linkset config table
 -- *************************************************     

ss7LinksetCfgTable		OBJECT-TYPE
			SYNTAX   SEQUENCE OF Ss7LinksetCfgEntry
			ACCESS	not-accessible
			STATUS	mandatory
			DESCRIPTION 
	"SS7 Linkset Table. Information about the Linkset(s) in MSSC are 
	provided in this table. This table has the index ss7LinksetLinkId (Integer). "
			::= { ss7Sig	 3 }

ss7LinksetCfgEntry		OBJECT-TYPE
			SYNTAX	Ss7LinksetCfgEntry
			ACCESS	not-accessible
			STATUS	mandatory
			DESCRIPTION 
	"The Current Entry Containes all the objects for this Table. 
	This object is not-accessible, but the user can access all 
	the objects in this table at the next level. "
			INDEX { ss7LinksetLinkId }
			::= {	ss7LinksetCfgTable   1 }

Ss7LinksetCfgEntry		::= SEQUENCE {
			ss7LinksetLinkId		INTEGER,
			ss7LinksetId		INTEGER,
			ss7LinksetName		NameString,
			ss7LinksetAdjDpc		INTEGER,
			ss7LinksetMode		Standard,
			ss7LinksetRowStatus		RowStatus,
			ss7LinksetOpStatus		LinkSetOpStatus
			}

ss7LinksetLinkId		OBJECT-TYPE
			SYNTAX	INTEGER(1..65535)
			ACCESS	read-write
			STATUS	mandatory
			DESCRIPTION 
	"Link id. Can be any integer 1-65535. "
			::= {	ss7LinksetCfgEntry   1 }

ss7LinksetId		OBJECT-TYPE
			SYNTAX	INTEGER(1..128)
			ACCESS	read-write
			STATUS	mandatory
			DESCRIPTION 
	"Linkset id. Can be any integer 1-128. "
			::= {	ss7LinksetCfgEntry   2 }

ss7LinksetName		OBJECT-TYPE
			SYNTAX	NameString
			ACCESS	read-write
			STATUS	mandatory
			DESCRIPTION 
	"Linkset name. Can be any combination of alphanumeric characters. 
	Spaces are not allowed and cannot exceed 15 characters. "
			::= {	ss7LinksetCfgEntry   3 }

ss7LinksetAdjDpc		OBJECT-TYPE
			SYNTAX	INTEGER(1..16777215)
			ACCESS	read-write
			STATUS	mandatory
			DESCRIPTION 
	"Adjacent Point Code for this Linkset (the Integer value). 
	The Point Code should be converted into its Integer 
	equivalent. For Example: 
	0-1-1 is converted as 257 (for ANSI) 
	0-1-2 is converted as 10 (for ITU) "
			::= {	ss7LinksetCfgEntry   4 }

ss7LinksetMode		OBJECT-TYPE
			SYNTAX	Standard
			ACCESS	read-write
			STATUS	mandatory
			DESCRIPTION 
	"Linkset Type(ANSI/ITU) "
			::= {	ss7LinksetCfgEntry   5 }

ss7LinksetRowStatus		OBJECT-TYPE
			SYNTAX	RowStatus
			ACCESS	read-write
			STATUS	mandatory
			DESCRIPTION 
	"Current Status (configurational Status) of this Link. 
	To Configure this Link, the only option is 'CREATEANDWAIT' 
	To Delete this Link, the only option is 'DESTROY' 
	For the 'GET' Operation, the possible options are 
	1) active 
	2) notinservice 
	3) notread"
			::= {	ss7LinksetCfgEntry   6 }

ss7LinksetOpStatus		OBJECT-TYPE
			SYNTAX	LinkSetOpStatus
			ACCESS	read-only
			STATUS	mandatory
			DESCRIPTION 
	"Current Status (Operational Status) of this Link Set. 
	'SET' Operation is NOT APPLICABLE. 
	For the 'GET' Operation, the possible options are 
	1) active 
	2) deactive  "
			::= {	ss7LinksetCfgEntry   7 }

 -- *************************************************     
 -- SS7 linkset mangment table
 -- *************************************************     

ss7LinksetMgmtTable		OBJECT-TYPE
			SYNTAX   SEQUENCE OF Ss7LinksetMgmtEntry
			ACCESS	not-accessible
			STATUS	mandatory
			DESCRIPTION 
	"SS7 Linkset Management Table. The Management Commands for Linkset 
	in MSSC are provided in this table. This table has the index linksetId (Integer). "
			::= { ss7Sig	 4 }

ss7LinksetMgmtEntry		OBJECT-TYPE
			SYNTAX	Ss7LinksetMgmtEntry
			ACCESS	not-accessible
			STATUS	mandatory
			DESCRIPTION 
	"The Current Entry Containes all the objects for this Table. 
	This object is not-accessible, but the user can access all 
	the objects in this table at the next level. "
			INDEX { linksetId }
			::= {	ss7LinksetMgmtTable   1 }

Ss7LinksetMgmtEntry		::= SEQUENCE {
			linksetId		INTEGER,
			linksetLevel		Level,
			linksetMgmntCmd		LinkSetControlStatus
			}

linksetId		OBJECT-TYPE
			SYNTAX	INTEGER
			ACCESS	read-only
			STATUS	mandatory
			DESCRIPTION 
	"SS7 Linkset Id "
			::= {	ss7LinksetMgmtEntry   1 }

linksetLevel		OBJECT-TYPE
			SYNTAX	Level
			ACCESS	read-write
			STATUS	mandatory
			DESCRIPTION 
	"This option deactivates the linkset at level 1 or level 2. 
	Level 2 is for layer 2 only. 
	The option available are: 
	1) Level 1 (level-1) [Default] 
	2) Level 2 (level-2)  "
			::= {	ss7LinksetMgmtEntry   2 }

linksetMgmntCmd		OBJECT-TYPE
			SYNTAX	LinkSetControlStatus
			ACCESS	read-write
			STATUS	mandatory
			DESCRIPTION 
	"Management Command for Activing/DeActiving call on this linkset. 
	The possible options are : 
	1) Active 
	2) Deactive 
	3) Noaction [default] "
			::= {	ss7LinksetMgmtEntry   3 }

 -- *************************************************     
 -- SS7 link management table
 -- *************************************************     

ss7LinkMgmntTable		OBJECT-TYPE
			SYNTAX   SEQUENCE OF Ss7LinkMgmntEntry
			ACCESS	not-accessible
			STATUS	mandatory
			DESCRIPTION 
	"SS7 Link Management Table. The Management Commands for Link(s) 
	in MSSC are provided in this table. This table has the index linkName (String). "
			::= { ss7Sig	 5 }

ss7LinkMgmntEntry		OBJECT-TYPE
			SYNTAX	Ss7LinkMgmntEntry
			ACCESS	not-accessible
			STATUS	mandatory
			DESCRIPTION 
	"The Current Entry Containes all the objects for this Table. 
	This object is not-accessible, but the user can access all 
	the objects in this table at the next level. "
			INDEX { linkName }
			::= {	ss7LinkMgmntTable   1 }

Ss7LinkMgmntEntry		::= SEQUENCE {
			linkName		NameString,
			linkMgmntCmd		LinkControlStatus
			}

linkName		OBJECT-TYPE
			SYNTAX	NameString
			ACCESS	read-only
			STATUS	mandatory
			DESCRIPTION 
	"SS7 Link Name  "
			::= {	ss7LinkMgmntEntry   1 }

linkMgmntCmd		OBJECT-TYPE
			SYNTAX	LinkControlStatus
			ACCESS	read-write
			STATUS	mandatory
			DESCRIPTION 
	"Management Command for Inhibiting/UnInhibiting link. 
	The possible options are : 
	1) Inhibit 
	2) UnInhibit 
	3) Noaction [default]  "
			::= {	ss7LinkMgmntEntry   2 }

 -- *************************************************     
 -- SS7/isdn trunk group config table
 -- *************************************************     

trunkGrpCfgTable		OBJECT-TYPE
			SYNTAX   SEQUENCE OF TrunkGrpCfgEntry
			ACCESS	not-accessible
			STATUS	mandatory
			DESCRIPTION 
	"SS7/ISDN Trunk Group Table. The Information about Trunk Groups 
	in MSSC are provided in this table. This table has the index trunkGrpId (Integer). "
			::= { trnkGrp	 1 }

trunkGrpCfgEntry		OBJECT-TYPE
			SYNTAX	TrunkGrpCfgEntry
			ACCESS	not-accessible
			STATUS	mandatory
			DESCRIPTION 
	"The Current Entry Containes all the objects for this Table. 
	This object is not-accessible, but the user can access all 
	the objects in this table at the next level. "
			INDEX { trunkGrpId }
			::= {	trunkGrpCfgTable   1 }

TrunkGrpCfgEntry		::= SEQUENCE {
			trunkGrpId		INTEGER,
			trunkGrpName		DisplayString,
			trunkGrpCarrierId		INTEGER,
			trunkGrpType		TrnkGrpType,
			trunkGrpRoffName		NameString,
			trunkGrpRoffType		RoffType,
			trunkGrpCdrFlag		CdrFlag,
			trunkGrpNoOfTrunks		INTEGER,
			trunkGrpVoicePcm		VoicePcm,
			trunkGrpRowStatus		RowStatus,
			trunkGrpOpStatus		OpStatus
			}

trunkGrpId		OBJECT-TYPE
			SYNTAX	INTEGER(1..65535)
			ACCESS	read-write
			STATUS	mandatory
			DESCRIPTION 
	"Denotes Id for this trunk group. Range for Id is 1-65535. "
			::= {	trunkGrpCfgEntry   1 }

trunkGrpName		OBJECT-TYPE
			SYNTAX	DisplayString(SIZE(1..8))
			ACCESS	read-write
			STATUS	mandatory
			DESCRIPTION 
	"Denotes Name of this trunk group. 
	The Name is a string of length 8. The first two characters 
	of Name have to be alphabhets. The next 6 charecters are 
	numeric. An example a valid Trunk Group Name is ab123456. 
	NOTE: This format needs to be strictly foll"
			::= {	trunkGrpCfgEntry   2 }

trunkGrpCarrierId		OBJECT-TYPE
			SYNTAX	INTEGER(0..65535)
			ACCESS	read-write
			STATUS	mandatory
			DESCRIPTION 
	"Denotes Carrier id for this trunk group. 
	The Carrier id Field is an integer of length 4. 
	An example for Carried Id is: 1234 
	NOTE: The format for sertting the Carrier Id needs 
	to strictly followed. Failure to follow this format 
	will result in unsucces"
			::= {	trunkGrpCfgEntry   3 }

trunkGrpType		OBJECT-TYPE
			SYNTAX	TrnkGrpType
			ACCESS	read-write
			STATUS	mandatory
			DESCRIPTION 
	"Denotes Trunk group type. Possible values for Trunk group are: 
	1. ss7 
	2. isdn "
			::= {	trunkGrpCfgEntry   4 }

trunkGrpRoffName		OBJECT-TYPE
			SYNTAX	NameString
			ACCESS	read-write
			STATUS	mandatory
			DESCRIPTION 
	"Denotes Remote Office Name: 
	NOTE: Value for this object is NOT Valid if TrunkGrpType 
	is ISDN. Only Valid For SS7 TrunkGroup. If trunkGrpType 
	is ISDN and the USER sets the value for Remote Office 
	Name, then this Remote Office Name will be ignored when "
			::= {	trunkGrpCfgEntry   5 }

trunkGrpRoffType		OBJECT-TYPE
			SYNTAX	RoffType
			ACCESS	read-write
			STATUS	mandatory
			DESCRIPTION 
	"Denotes Remote Office Type: 
	NOTE: Value for this object is NOT Valid if TrunkGrpType 
	is ISDN. Remote Office Type is only Valid For SS7 
	TrunkGroup.If trunkGrpType is ISDN and the USER sets 
	the value for Remote Office Type, then this value is 
	ignored w"
			::= {	trunkGrpCfgEntry   6 }

trunkGrpCdrFlag		OBJECT-TYPE
			SYNTAX	CdrFlag
			ACCESS	read-write
			STATUS	mandatory
			DESCRIPTION 
	"Denotes Cdr Flag : Possible values are: 
	0) noCdr -> default (No CDR file is required) 
	1) IC -> for Incoming calls 
	2) OG -> for Outgoing calls 
	3) BI -> for both the Incoming and outgoing calls "
			::= {	trunkGrpCfgEntry   7 }

trunkGrpNoOfTrunks		OBJECT-TYPE
			SYNTAX	INTEGER(0..65535)
			ACCESS	read-only
			STATUS	mandatory
			DESCRIPTION 
	"Denotes the Number Of Trunks that are contained in this trunk Group "
			::= {	trunkGrpCfgEntry   8 }

trunkGrpVoicePcm		OBJECT-TYPE
			SYNTAX	VoicePcm
			ACCESS	read-write
			STATUS	mandatory
			DESCRIPTION 
			""
			::= {	trunkGrpCfgEntry   9 }

trunkGrpRowStatus		OBJECT-TYPE
			SYNTAX	RowStatus
			ACCESS	read-write
			STATUS	mandatory
			DESCRIPTION 
	"Current Status (configurational Status) of this Trunk Group. 
	To Configure this Link, the only option is 'CREATEANDWAIT' 
	To Delete this Link, the only option is 'DESTROY' 
	For the 'GET' Operation, the possible options are 
	1) active 
	2) notinservice 
	3) "
			::= {	trunkGrpCfgEntry   10 }

trunkGrpOpStatus		OBJECT-TYPE
			SYNTAX	OpStatus
			ACCESS	read-only
			STATUS	mandatory
			DESCRIPTION 
	"Current Status (Operational Status) of this Trunk Group. 
	'SET' Operation is NOT APPLICABLE. 
	For the 'GET' Operation, the possible options are 
	1) active 
	2) down  "
			::= {	trunkGrpCfgEntry   11 }

 -- *************************************************     
 -- SS7 trunk config table
 -- *************************************************     

ss7TrunkCfgTable		OBJECT-TYPE
			SYNTAX   SEQUENCE OF Ss7TrunkCfgEntry
			ACCESS	not-accessible
			STATUS	mandatory
			DESCRIPTION 
	"ISDN Trunk Table. The Information about ISDN Trunk(s) 
	in MSSC are provided in this table. 
	This table has the index ss7TrunkId (Integer). "
			::= { ss7Br	 1 }

ss7TrunkCfgEntry		OBJECT-TYPE
			SYNTAX	Ss7TrunkCfgEntry
			ACCESS	not-accessible
			STATUS	mandatory
			DESCRIPTION 
	"The Current Entry Containes all the objects for this Table. 
	This object is not-accessible, but the user can access all 
	the objects in this table at the next level. "
			INDEX { ss7TrunkId }
			::= {	ss7TrunkCfgTable   1 }

Ss7TrunkCfgEntry		::= SEQUENCE {
			ss7TrunkId		INTEGER,
			ss7TrunkName		NameString,
			ss7TrunkGrpId		INTEGER,
			ss7TrunkXconnectId		INTEGER,
			ss7TrunkSlotId		INTEGER,
			ss7TrunkPortId		INTEGER,
			ss7TrunkOpc		INTEGER,
			ss7TrunkDpc		INTEGER,
			ss7TrunkPhyType		IfType,
			ss7TrunkMode		Standard,
			ss7TrunkE1MultiFrame		E1MultiFrame,
			 ss7TrunkE1CRC4		E1CRC4,
			 ss7TrunkE1TransClk		TransClkSrc,
			 ss7TrunkDS1LineType		DS1LineType,
			 ss7TrunkDS1LineCoding		DS1LineCoding,
			 ss7TrunkDS1TransClkSrc		TransClkSrc,
			 ss7TrunkDS1LBO		DS1LBO,
			ss7TrunkDS3LineType		DS3LineType,
			 ss7TrunkDS3TransClkSrc		TransClkSrc,
			 ss7TrunkDS3LBO		DS3LBO,
			 ss7TrunkDS3DS1LineType		DS1LineType,
			 ss7TrunkDS3DS1TransClkSrc		TransClkSrc,
			 ss7TrunkOC3TransClkSrc		TransClkSrc,
			 ss7TrunkUNCHE3TransClkSrc		TransClkSrc,
			 ss7TrunkDS3ATMLineType		DS3LineType,
			 ss7TrunkDS3ATMCellMap		DS3ATMCellMap,
			 ss7TrunkDS3ATMTransClkSrc		TransClkSrc,
			 ss7TrunkDS3ATMLBO		DS3LBO,
			ss7TrunkRowStatus		RowStatus,
			ss7TrunkOpStatus		OpStatus
			}

ss7TrunkId		OBJECT-TYPE
			SYNTAX	INTEGER(1..65535)
			ACCESS	read-write
			STATUS	mandatory
			DESCRIPTION 
	"Id for the trunk. Can be any integer 1-65535. "
			::= {	ss7TrunkCfgEntry   1 }

ss7TrunkName		OBJECT-TYPE
			SYNTAX	NameString
			ACCESS	read-write
			STATUS	mandatory
			DESCRIPTION 
	"Name for the trunk. Can be any combination of alphanumeric characters. 
	Spaces are not allowed and cannot exceed 15 characters. "
			::= {	ss7TrunkCfgEntry   2 }

ss7TrunkGrpId		OBJECT-TYPE
			SYNTAX	INTEGER(1..65535)
			ACCESS	read-write
			STATUS	mandatory
			DESCRIPTION 
	"Id of the trunk group to which the trunk belongs. Can be any integer 1-65535. "
			::= {	ss7TrunkCfgEntry   3 }

ss7TrunkXconnectId		OBJECT-TYPE
			SYNTAX	INTEGER(1..65535)
			ACCESS	read-write
			STATUS	mandatory
			DESCRIPTION 
	"Xconnect id "
			::= {	ss7TrunkCfgEntry   4 }

ss7TrunkSlotId		OBJECT-TYPE
			SYNTAX	INTEGER(1..65535)
			ACCESS	read-write
			STATUS	mandatory
			DESCRIPTION 
	"Slot id "
			::= {	ss7TrunkCfgEntry   5 }

ss7TrunkPortId		OBJECT-TYPE
			SYNTAX	INTEGER(1..65535)
			ACCESS	read-write
			STATUS	mandatory
			DESCRIPTION 
	"Port id "
			::= {	ss7TrunkCfgEntry   6 }

ss7TrunkOpc		OBJECT-TYPE
			SYNTAX	INTEGER(1..16777215)
			ACCESS	read-write
			STATUS	mandatory
			DESCRIPTION 
	"Originating point code (the Integer value). 
	The Point Code should be converted into its Integer 
	equivalent. For Example: 
	0-1-1 is converted as 257 (for ANSI) 
	0-1-2 is converted as 10 (for ITU) "
			::= {	ss7TrunkCfgEntry   7 }

ss7TrunkDpc		OBJECT-TYPE
			SYNTAX	INTEGER(1..16777215)
			ACCESS	read-write
			STATUS	mandatory
			DESCRIPTION 
	"Destination point code ( the Integer Value). 
	The Point Code should be converted into its Integer 
	equivalent. For Example: 
	0-1-1 is converted as 257 (for ANSI) 
	0-1-2 is converted as 10 (for ITU) "
			::= {	ss7TrunkCfgEntry   8 }

ss7TrunkPhyType		OBJECT-TYPE
			SYNTAX	IfType
			ACCESS	read-write
			STATUS	mandatory
			DESCRIPTION 
	"Physical Interface Type 
	possible options are 
	1) T1 (interface-t1) 
	2) T3 (interface-t3) 
	3) Unchannelized T3 (interface-ut3) 
	4) OC3 (interface-oc3) 
	5) Unchannelized T3 with compression (interface-ut3cp) 
	6) OC3 with compression (interface-oc3cp) 
	7) E"
			::= {	ss7TrunkCfgEntry   9 }

ss7TrunkMode		OBJECT-TYPE
			SYNTAX	Standard
			ACCESS	read-write
			STATUS	mandatory
			DESCRIPTION 
	"Trunk mode - ANSI/ITU "
			::= {	ss7TrunkCfgEntry   10 }

ss7TrunkE1MultiFrame		OBJECT-TYPE
			SYNTAX	E1MultiFrame
			ACCESS	read-write
			STATUS	mandatory
			DESCRIPTION 
	"E1 multiFrame Type possible options are 1) CAS(1) 2) CCS(2)"
			::= {	ss7TrunkCfgEntry   11 }

 ss7TrunkE1CRC4		OBJECT-TYPE
			SYNTAX	E1CRC4
			ACCESS	read-write
			STATUS	mandatory
			DESCRIPTION 
	"E1 Cyclic Redundancy Code, possible options are 1) enabled(1) 2) disable(2)"
			::= {	ss7TrunkCfgEntry   12 }

 ss7TrunkE1TransClk		OBJECT-TYPE
			SYNTAX	TransClkSrc
			ACCESS	read-write
			STATUS	mandatory
			DESCRIPTION 
	"E1 Transmit Clock Source, possible options are 1) loopTiming(1) 2) localTiming(2)"
			::= {	ss7TrunkCfgEntry   13 }

 ss7TrunkDS1LineType		OBJECT-TYPE
			SYNTAX	DS1LineType
			ACCESS	read-write
			STATUS	mandatory
			DESCRIPTION 
	"DS1 Line Type possible options are 1) esF(1) 2) d4(2)"
			::= {	ss7TrunkCfgEntry   14 }

 ss7TrunkDS1LineCoding		OBJECT-TYPE
			SYNTAX	DS1LineCoding
			ACCESS	read-write
			STATUS	mandatory
			DESCRIPTION 
	"DS1 Line Coding, possible options are 1) b8zs(1) 2) ami(2)"
			::= {	ss7TrunkCfgEntry   15 }

 ss7TrunkDS1TransClkSrc		OBJECT-TYPE
			SYNTAX	TransClkSrc
			ACCESS	read-write
			STATUS	mandatory
			DESCRIPTION 
	"DS1 Transmit Clock Source, possible options are 1) loopTiming(1) 2) localTiming(2)"
			::= {	ss7TrunkCfgEntry   16 }

 ss7TrunkDS1LBO		OBJECT-TYPE
			SYNTAX	DS1LBO
			ACCESS	read-write
			STATUS	mandatory
			DESCRIPTION 
	"DS1 Line Build Out, possible options are 1) upTo133Feet(1) 2) upTo266Feet(2) 3) upTo399Feet(3) 4) upTo533Feet(4) 5) upTo655Feet(5) 6) negative7_5Db(6) 7) negative15Db(7) 8) negative22_5Db(8)"
			::= {	ss7TrunkCfgEntry   17 }

ss7TrunkDS3LineType		OBJECT-TYPE
			SYNTAX	DS3LineType
			ACCESS	read-write
			STATUS	mandatory
			DESCRIPTION 
	"DS3 Line Type possible options are 1) cbitParity(1) 2) clearChannel(2)"
			::= {	ss7TrunkCfgEntry   18 }

 ss7TrunkDS3TransClkSrc		OBJECT-TYPE
			SYNTAX	TransClkSrc
			ACCESS	read-write
			STATUS	mandatory
			DESCRIPTION 
	"DS3 Transmit Clock Source, possible options are 1) loopTiming(1) 2) localTiming(2)"
			::= {	ss7TrunkCfgEntry   19 }

 ss7TrunkDS3LBO		OBJECT-TYPE
			SYNTAX	DS3LBO
			ACCESS	read-write
			STATUS	mandatory
			DESCRIPTION 
	"DS3 Line Build Out possible options are 1) short(1) 2) long(2)"
			::= {	ss7TrunkCfgEntry   20 }

 ss7TrunkDS3DS1LineType		OBJECT-TYPE
			SYNTAX	DS1LineType
			ACCESS	read-write
			STATUS	mandatory
			DESCRIPTION 
	"DS3DS1 Line Type possible options are 1) esF(1) 2) d4(2)"
			::= {	ss7TrunkCfgEntry   21 }

 ss7TrunkDS3DS1TransClkSrc		OBJECT-TYPE
			SYNTAX	TransClkSrc
			ACCESS	read-write
			STATUS	mandatory
			DESCRIPTION 
	"DS3DS1ansmit Clock Source, possible options are 1) loopTiming(1) 2) localTiming(2)"
			::= {	ss7TrunkCfgEntry   22 }

 ss7TrunkOC3TransClkSrc		OBJECT-TYPE
			SYNTAX	TransClkSrc
			ACCESS	read-write
			STATUS	mandatory
			DESCRIPTION 
	"OC3 Transmit Clock Source, possible options are 1) loopTiming(1) 2) localTiming(2)"
			::= {	ss7TrunkCfgEntry   23 }

 ss7TrunkUNCHE3TransClkSrc		OBJECT-TYPE
			SYNTAX	TransClkSrc
			ACCESS	read-write
			STATUS	mandatory
			DESCRIPTION 
	"UNCHANNELIZED E3 Transmit Clock Source, possible options are 1) loopTiming(1) 2) localTiming(2)"
			::= {	ss7TrunkCfgEntry   24 }

 ss7TrunkDS3ATMLineType		OBJECT-TYPE
			SYNTAX	DS3LineType
			ACCESS	read-write
			STATUS	mandatory
			DESCRIPTION 
	"DS3-ATM Line Type possible options are 1) cbitParity(1) 2) clearChannel(2)"
			::= {	ss7TrunkCfgEntry   25 }

 ss7TrunkDS3ATMCellMap		OBJECT-TYPE
			SYNTAX	DS3ATMCellMap
			ACCESS	read-write
			STATUS	mandatory
			DESCRIPTION 
	"DS3-ATM Cell Mapping, possible options are 1) plcp(1) 2) directMapping(2)"
			::= {	ss7TrunkCfgEntry   26 }

 ss7TrunkDS3ATMTransClkSrc		OBJECT-TYPE
			SYNTAX	TransClkSrc
			ACCESS	read-write
			STATUS	mandatory
			DESCRIPTION 
	"DS3-ATM transmit Clock Source, possible options are 1) loopTiming(1) 2) localTiming(2)"
			::= {	ss7TrunkCfgEntry   27 }

 ss7TrunkDS3ATMLBO		OBJECT-TYPE
			SYNTAX	DS3LBO
			ACCESS	read-write
			STATUS	mandatory
			DESCRIPTION 
	"DS3-ATM Line Build Out possible options are 1) short(1) 2) long(2)"
			::= {	ss7TrunkCfgEntry   28 }

ss7TrunkRowStatus		OBJECT-TYPE
			SYNTAX	RowStatus
			ACCESS	read-write
			STATUS	mandatory
			DESCRIPTION 
	"Current Status (configurational Status) of this SS7 Trunk. 
	To Configure this Link, the only option is 'CREATEANDWAIT' 
	To Delete this Link, the only option is 'DESTROY' 
	For the 'GET' Operation, the possible options are 
	1) active 
	2) notinservice 
	3) no"
			::= {	ss7TrunkCfgEntry   29 }

ss7TrunkOpStatus		OBJECT-TYPE
			SYNTAX	OpStatus
			ACCESS	read-only
			STATUS	mandatory
			DESCRIPTION 
	"Current Status (Operational Status) of this SS7 Trunk. 
	'SET' Operation is NOT APPLICABLE. 
	For the 'GET' Operation, the possible options are 
	1) active 
	2) down  "
			::= {	ss7TrunkCfgEntry   30 }

 -- *************************************************     
 -- SS7 circuit config table
 -- *************************************************     

ss7CktCfgTable		OBJECT-TYPE
			SYNTAX   SEQUENCE OF Ss7CktCfgEntry
			ACCESS	not-accessible
			STATUS	mandatory
			DESCRIPTION 
	"SS7 Circuit Table. The Information about SS7 Circuit(s) 
	in MSSC are provided in this table. 
	This table has two indices: ss7CktTrunkId and ss7CktChnlId (both Integer). "
			::= { ss7Br	 2 }

ss7CktCfgEntry		OBJECT-TYPE
			SYNTAX	Ss7CktCfgEntry
			ACCESS	not-accessible
			STATUS	mandatory
			DESCRIPTION 
	"The Current Entry Containes all the objects for this Table. 
	This object is not-accessible, but the user can access all 
	the objects in this table at the next level. "
			INDEX { ss7CktTrunkId, ss7CktChnlId }
			::= {	ss7CktCfgTable   1 }

Ss7CktCfgEntry		::= SEQUENCE {
			ss7CktTrunkId		INTEGER,
			ss7CktChnlId		INTEGER,
			ss7CktId		INTEGER,
			ss7CktDpc		INTEGER,
			ss7CktCic		INTEGER,
			ss7CktDir		Direction,
			ss7CktPriority		INTEGER,
			ss7CktT3		INTEGER,
			ss7CktT12		INTEGER,
			ss7CktT13		INTEGER,
			ss7CktT14		INTEGER,
			ss7CktT15		INTEGER,
			ss7CktT16		INTEGER,
			ss7CktT17		INTEGER,
			ss7CktTVal		INTEGER,
			ss7CktRowStatus		CktRowStatus,
			ss7CktOpStatus		CktOpStatus
			}

ss7CktTrunkId		OBJECT-TYPE
			SYNTAX	INTEGER(1..65535)
			ACCESS	read-write
			STATUS	mandatory
			DESCRIPTION 
	"User Assigned Trunk id.  "
			::= {	ss7CktCfgEntry   1 }

ss7CktChnlId		OBJECT-TYPE
			SYNTAX	INTEGER(1..65535)
			ACCESS	read-write
			STATUS	mandatory
			DESCRIPTION 
	"User Assigned Channel id "
			::= {	ss7CktCfgEntry   2 }

ss7CktId		OBJECT-TYPE
			SYNTAX	INTEGER(1..4294967295)
			ACCESS	read-only
			STATUS	mandatory
			DESCRIPTION 
	"Circuit id. The Id assingned to each of the circuits for a particular Trunk.  "
			::= {	ss7CktCfgEntry   3 }

ss7CktDpc		OBJECT-TYPE
			SYNTAX	INTEGER(1..16777215)
			ACCESS	read-write
			STATUS	mandatory
			DESCRIPTION 
	"Destination Point Code (The Integer Value). 
	The Point Code should be converted into its Integer 
	equivalent. For Example: 
	0-1-1 is converted as 257 (for ANSI) 
	0-1-2 is converted as 10 (for ITU) "
			::= {	ss7CktCfgEntry   4 }

ss7CktCic		OBJECT-TYPE
			SYNTAX	INTEGER(1..16383)
			ACCESS	read-write
			STATUS	mandatory
			DESCRIPTION 
	"Circuit identifier code. Can be any integer from 
	1) 1-4095 for ITU 
	2) 1-16383 for ANSI "
			::= {	ss7CktCfgEntry   5 }

ss7CktDir		OBJECT-TYPE
			SYNTAX	Direction
			ACCESS	read-write
			STATUS	mandatory
			DESCRIPTION 
	"Traffic direction: Possible options are : 
	1) IN 
	2) OUT 
	3) BOTH  "
			::= {	ss7CktCfgEntry   6 }

ss7CktPriority		OBJECT-TYPE
			SYNTAX	INTEGER(1..65535)
			ACCESS	read-write
			STATUS	mandatory
			DESCRIPTION 
	"Traffic priority "
			::= {	ss7CktCfgEntry   7 }

ss7CktT3		OBJECT-TYPE
			SYNTAX	INTEGER(0..120)
			UNITS "sec"
			ACCESS	read-write
			STATUS	mandatory
			DESCRIPTION 
	"T3 timer. Default Value is 0 milliSeconds "
			DEFVAL { 0 }
			::= {	ss7CktCfgEntry   8 }

ss7CktT12		OBJECT-TYPE
			SYNTAX	INTEGER(4000..60000)
			UNITS "ms"
			ACCESS	read-write
			STATUS	mandatory
			DESCRIPTION 
	"T12 timer - blocking sent. Default Value is 40 milliSeconds "
			DEFVAL { 4000 }
			::= {	ss7CktCfgEntry   9 }

ss7CktT13		OBJECT-TYPE
			SYNTAX	INTEGER(60..900)
			UNITS "sec"
			ACCESS	read-write
			STATUS	mandatory
			DESCRIPTION 
	"T13 timer - initial blocking sent. Default Value is 600 milliSeconds "
			DEFVAL { 60 }
			::= {	ss7CktCfgEntry   10 }

ss7CktT14		OBJECT-TYPE
			SYNTAX	INTEGER(4000..60000)
			UNITS "ms"
			ACCESS	read-write
			STATUS	mandatory
			DESCRIPTION 
	"T14 timer - unblocking sent. Default Value is 40 milliSeconds "
			DEFVAL { 4000 }
			::= {	ss7CktCfgEntry   11 }

ss7CktT15		OBJECT-TYPE
			SYNTAX	INTEGER(60..900)
			UNITS "sec"
			ACCESS	read-write
			STATUS	mandatory
			DESCRIPTION 
	"T15 timer - initial unblocking sent. Default Value is 600 milliSeconds "
			DEFVAL { 60 }
			::= {	ss7CktCfgEntry   12 }

ss7CktT16		OBJECT-TYPE
			SYNTAX	INTEGER(4000..60000)
			UNITS "ms"
			ACCESS	read-write
			STATUS	mandatory
			DESCRIPTION 
	"T16 timer - reset sent. Default Value is 40 milliSeconds "
			DEFVAL { 4000 }
			::= {	ss7CktCfgEntry   13 }

ss7CktT17		OBJECT-TYPE
			SYNTAX	INTEGER(60..900)
			UNITS "sec"
			ACCESS	read-write
			STATUS	mandatory
			DESCRIPTION 
	"T17 timer - initial reset sent. Default Value is 600 milliSeconds "
			DEFVAL { 60 }
			::= {	ss7CktCfgEntry   14 }

ss7CktTVal		OBJECT-TYPE
			SYNTAX	INTEGER(10000)
			UNITS "ms"
			ACCESS	read-write
			STATUS	mandatory
			DESCRIPTION 
	"TVal timer - initial reset sent. Default Value is 100 milliSeconds "
			DEFVAL { 10000 }
			::= {	ss7CktCfgEntry   15 }

ss7CktRowStatus		OBJECT-TYPE
			SYNTAX	CktRowStatus
			ACCESS	read-write
			STATUS	mandatory
			DESCRIPTION 
	"Current Status (configurational Status) of this SS7 Circuit. 
	To Configure this circuit, the only option is 'CREATEANDWAIT'. 
	To Delete this circuit, the only option is 'DESTROY'. 
	To Modify any of the Circuit Timers, the only option is 'MODIFYTIMER'. 
	Fo"
			::= {	ss7CktCfgEntry   16 }

ss7CktOpStatus		OBJECT-TYPE
			SYNTAX	CktOpStatus
			ACCESS	read-only
			STATUS	mandatory
			DESCRIPTION 
	"Current Status (Operational Status) of this SS7 Circuit. 
	'SET' Operation is NOT APPLICABLE. 
	For the 'GET' Operation, the possible options are 
	1) active 
	2) down 
	3) block "
			::= {	ss7CktCfgEntry   17 }

 -- *************************************************     
 -- SS7 Cic timer table
 -- *************************************************     

ss7CICTimerTable		OBJECT-TYPE
			SYNTAX   SEQUENCE OF Ss7CicTmrEntry
			ACCESS	not-accessible
			STATUS	mandatory
			DESCRIPTION 
	"SS7 Circuit CIC Timer Table. The Information about SS7 Circuit(s) 
	Timers in MSSC are provided in this table.User can Modify any Timer(s) 
	in this table. This table has two indices: ss7CktTmrDpc and ss7CktTmrCic (both Integer). "
			::= { ss7Br	 3 }

ss7CicTmrEntry		OBJECT-TYPE
			SYNTAX	Ss7CicTmrEntry
			ACCESS	not-accessible
			STATUS	mandatory
			DESCRIPTION 
	"The Current Entry Containes all the objects for this Table. 
	This object is not-accessible, but the user can access all 
	the objects in this table at the next level. "
			INDEX { ss7CktTmrDpc, ss7CktTmrCic }
			::= {	ss7CICTimerTable   1 }

Ss7CicTmrEntry		::= SEQUENCE {
			ss7CktTmrDpc		INTEGER,
			ss7CktTmrCic		INTEGER,
			ss7CktTmrT3		INTEGER,
			ss7CktTmrT12		INTEGER,
			ss7CktTmrT13		INTEGER,
			ss7CktTmrT14		INTEGER,
			ss7CktTmrT15		INTEGER,
			ss7CktTmrT16		INTEGER,
			ss7CktTmrT17		INTEGER,
			ss7CktTmrTVal		INTEGER,
			ss7CktTmrRowStatus		ModifyTmrStatus
			}

ss7CktTmrDpc		OBJECT-TYPE
			SYNTAX	INTEGER(1..16777215)
			ACCESS	read-write
			STATUS	mandatory
			DESCRIPTION 
	"Destination Point Code (The Integer Value). 
	The Point Code should be converted into its Integer 
	equivalent. For Example: 
	0-1-1 is converted as 257 (for ANSI) 
	0-1-2 is converted as 10 (for ITU) "
			::= {	ss7CicTmrEntry   1 }

ss7CktTmrCic		OBJECT-TYPE
			SYNTAX	INTEGER(1..65535)
			ACCESS	read-write
			STATUS	mandatory
			DESCRIPTION 
	"Circuit identifier code. Can be any integer 1-65535. "
			::= {	ss7CicTmrEntry   2 }

ss7CktTmrT3		OBJECT-TYPE
			SYNTAX	INTEGER(1..65535)
			UNITS "ms"
			ACCESS	read-write
			STATUS	mandatory
			DESCRIPTION 
	"T3 timer. Default Value is 0 milliSeconds "
			DEFVAL { 0 }
			::= {	ss7CicTmrEntry   3 }

ss7CktTmrT12		OBJECT-TYPE
			SYNTAX	INTEGER(1..65535)
			UNITS "ms"
			ACCESS	read-write
			STATUS	mandatory
			DESCRIPTION 
	"T12 timer - blocking sent. Default Value is 40 milliSeconds "
			DEFVAL { 40 }
			::= {	ss7CicTmrEntry   4 }

ss7CktTmrT13		OBJECT-TYPE
			SYNTAX	INTEGER(1..65535)
			UNITS "ms"
			ACCESS	read-write
			STATUS	mandatory
			DESCRIPTION 
	"T13 timer - initial blocking sent. Default Value is 600 milliSeconds "
			DEFVAL { 600 }
			::= {	ss7CicTmrEntry   5 }

ss7CktTmrT14		OBJECT-TYPE
			SYNTAX	INTEGER(1..65535)
			UNITS "ms"
			ACCESS	read-write
			STATUS	mandatory
			DESCRIPTION 
	"T14 timer - unblocking sent. Default Value is 40 milliSeconds "
			DEFVAL { 40 }
			::= {	ss7CicTmrEntry   6 }

ss7CktTmrT15		OBJECT-TYPE
			SYNTAX	INTEGER(1..65535)
			UNITS "ms"
			ACCESS	read-write
			STATUS	mandatory
			DESCRIPTION 
	"T15 timer - initial unblocking sent. Default Value is 600 milliSeconds "
			DEFVAL { 600 }
			::= {	ss7CicTmrEntry   7 }

ss7CktTmrT16		OBJECT-TYPE
			SYNTAX	INTEGER(1..65535)
			UNITS "ms"
			ACCESS	read-write
			STATUS	mandatory
			DESCRIPTION 
	"T16 timer - reset sent. Default Value is 40 milliSeconds "
			DEFVAL { 40 }
			::= {	ss7CicTmrEntry   8 }

ss7CktTmrT17		OBJECT-TYPE
			SYNTAX	INTEGER(1..65535)
			UNITS "ms"
			ACCESS	read-write
			STATUS	mandatory
			DESCRIPTION 
	"T17 timer - initial reset sent. Default Value is 600 milliSeconds "
			DEFVAL { 600 }
			::= {	ss7CicTmrEntry   9 }

ss7CktTmrTVal		OBJECT-TYPE
			SYNTAX	INTEGER(1..65535)
			UNITS "ms"
			ACCESS	read-write
			STATUS	mandatory
			DESCRIPTION 
	"TVal timer - initial reset sent. Default Value is 100 milliSeconds "
			DEFVAL { 100 }
			::= {	ss7CicTmrEntry   10 }

ss7CktTmrRowStatus		OBJECT-TYPE
			SYNTAX	ModifyTmrStatus
			ACCESS	read-write
			STATUS	mandatory
			DESCRIPTION 
	"This is a command to MODIFY a Timer. A 'GET' operation on 
	this object will display the default value [no action]. 
	The possible option for 'SET' operation is: 
	1)modify "
			::= {	ss7CicTmrEntry   11 }

 -- *************************************************     
 -- SS7 broadband circuit table
 -- *************************************************     

ss7BCktCfgTable		OBJECT-TYPE
			SYNTAX   SEQUENCE OF Ss7BCktCfgEntry
			ACCESS	not-accessible
			STATUS	mandatory
			DESCRIPTION 
	"SS7 B-Circuit Table. The Information about SS7 B-Circuit(s) 
	in MSSC are provided in this table.This table has two indices: 
	ss7BCktVpi and ss7BCktVci (both Integer). "
			::= { ss7Br	 4 }

ss7BCktCfgEntry		OBJECT-TYPE
			SYNTAX	Ss7BCktCfgEntry
			ACCESS	not-accessible
			STATUS	mandatory
			DESCRIPTION 
	"The Current Entry Containes all the objects for this Table. 
	This object is not-accessible, but the user can access all 
	the objects in this table at the next level. "
			INDEX { ss7BCktVpi, ss7BCktVci }
			::= {	ss7BCktCfgTable   1 }

Ss7BCktCfgEntry		::= SEQUENCE {
			ss7BCktVpi		INTEGER,
			ss7BCktVci		INTEGER,
			ss7BCktTrunkId		INTEGER,
			ss7BCktDpc		INTEGER,
			ss7BCktCic		INTEGER,
			ss7BCktDir		Direction,
			ss7BCktPriority		INTEGER,
			ss7BCktT3		INTEGER,
			ss7BCktT12		INTEGER,
			ss7BCktT13		INTEGER,
			ss7BCktT14		INTEGER,
			ss7BCktT15		INTEGER,
			ss7BCktT16		INTEGER,
			ss7BCktT17		INTEGER,
			ss7BCktTVal		INTEGER,
			ss7BCktRowStatus		CktRowStatus,
			ss7BCktOpStatus		CktOpStatus
			}

ss7BCktVpi		OBJECT-TYPE
			SYNTAX	INTEGER(1..65535)
			ACCESS	read-write
			STATUS	mandatory
			DESCRIPTION 
	"Broadband Virtual Path Indentifier. Can be any integer 1-65535. "
			::= {	ss7BCktCfgEntry   1 }

ss7BCktVci		OBJECT-TYPE
			SYNTAX	INTEGER(1..65535)
			ACCESS	read-write
			STATUS	mandatory
			DESCRIPTION 
	"Broadband Virtual Channel Identifier. Can be any integer 1-65535. "
			::= {	ss7BCktCfgEntry   2 }

ss7BCktTrunkId		OBJECT-TYPE
			SYNTAX	INTEGER(1..65535)
			ACCESS	read-write
			STATUS	mandatory
			DESCRIPTION 
	"Trunk id. "
			::= {	ss7BCktCfgEntry   3 }

ss7BCktDpc		OBJECT-TYPE
			SYNTAX	INTEGER(1..16777215)
			ACCESS	read-write
			STATUS	mandatory
			DESCRIPTION 
	"Broadband Circuit Destination Point Code (The Integer Value). 
	The Point Code should be converted into its Integer 
	equivalent. For Example: 
	0-1-1 is converted as 257 (for ANSI) 
	0-1-2 is converted as 10 (for ITU) "
			::= {	ss7BCktCfgEntry   4 }

ss7BCktCic		OBJECT-TYPE
			SYNTAX	INTEGER(1..16383)
			ACCESS	read-write
			STATUS	mandatory
			DESCRIPTION 
	"Circuit identifier code. Can be any integer from : 
	1) 1-16383 for ANSI 
	2) 1-4095 for ITU "
			::= {	ss7BCktCfgEntry   5 }

ss7BCktDir		OBJECT-TYPE
			SYNTAX	Direction
			ACCESS	read-write
			STATUS	mandatory
			DESCRIPTION 
	"Denotes Traffic direction. Possible Values are: 
	1) in 
	2) out 
	3) both "
			::= {	ss7BCktCfgEntry   6 }

ss7BCktPriority		OBJECT-TYPE
			SYNTAX	INTEGER(1..65535)
			ACCESS	read-write
			STATUS	mandatory
			DESCRIPTION 
	"Traffic priority "
			::= {	ss7BCktCfgEntry   7 }

ss7BCktT3		OBJECT-TYPE
			SYNTAX	INTEGER(1..65535)
			UNITS "ms"
			ACCESS	read-write
			STATUS	mandatory
			DESCRIPTION 
	"T3 timer. Default Value is 0 milliSeconds "
			DEFVAL { 0 }
			::= {	ss7BCktCfgEntry   8 }

ss7BCktT12		OBJECT-TYPE
			SYNTAX	INTEGER(1..65535)
			UNITS "ms"
			ACCESS	read-write
			STATUS	mandatory
			DESCRIPTION 
	"T12 timer - blocking sent. Default Value is 40 milliSeconds "
			DEFVAL { 40 }
			::= {	ss7BCktCfgEntry   9 }

ss7BCktT13		OBJECT-TYPE
			SYNTAX	INTEGER(1..65535)
			UNITS "ms"
			ACCESS	read-write
			STATUS	mandatory
			DESCRIPTION 
	"T13 timer - initial blocking sent. Default Value is 600 milliSeconds "
			DEFVAL { 600 }
			::= {	ss7BCktCfgEntry   10 }

ss7BCktT14		OBJECT-TYPE
			SYNTAX	INTEGER(1..65535)
			UNITS "ms"
			ACCESS	read-write
			STATUS	mandatory
			DESCRIPTION 
	"T14 timer - unblocking sent. Default Value is 40 milliSeconds "
			DEFVAL { 40 }
			::= {	ss7BCktCfgEntry   11 }

ss7BCktT15		OBJECT-TYPE
			SYNTAX	INTEGER(1..65535)
			UNITS "ms"
			ACCESS	read-write
			STATUS	mandatory
			DESCRIPTION 
	"T15 timer - initial unblocking sent. Default Value is 600 milliSeconds "
			DEFVAL { 600 }
			::= {	ss7BCktCfgEntry   12 }

ss7BCktT16		OBJECT-TYPE
			SYNTAX	INTEGER(1..65535)
			UNITS "ms"
			ACCESS	read-write
			STATUS	mandatory
			DESCRIPTION 
	"T16 timer - reset sent. Default Value is 40 milliSeconds "
			DEFVAL { 40 }
			::= {	ss7BCktCfgEntry   13 }

ss7BCktT17		OBJECT-TYPE
			SYNTAX	INTEGER(1..65535)
			UNITS "ms"
			ACCESS	read-write
			STATUS	mandatory
			DESCRIPTION 
	"T17 timer - initial reset sent. Default Value is 600 milliSeconds "
			DEFVAL { 600 }
			::= {	ss7BCktCfgEntry   14 }

ss7BCktTVal		OBJECT-TYPE
			SYNTAX	INTEGER(1..65535)
			UNITS "ms"
			ACCESS	read-write
			STATUS	mandatory
			DESCRIPTION 
	"TVal timer - initial reset sent. Default Value is 100 milliSeconds "
			DEFVAL { 100 }
			::= {	ss7BCktCfgEntry   15 }

ss7BCktRowStatus		OBJECT-TYPE
			SYNTAX	CktRowStatus
			ACCESS	read-write
			STATUS	mandatory
			DESCRIPTION 
	"Current Status (configurational Status) of this SS7 B-Circuit. 
	To Configure this circuit, the only option is 'CREATEANDWAIT'. 
	To Modify any of the timers the only option is 'MODIFYTIMER' . 
	To Delete this circuit, the only option is 'DESTROY'. 
	For the "
			::= {	ss7BCktCfgEntry   16 }

ss7BCktOpStatus		OBJECT-TYPE
			SYNTAX	CktOpStatus
			ACCESS	read-only
			STATUS	mandatory
			DESCRIPTION 
	"Current Status (Operational Status) of this SS7 B-Circuit. 
	'SET' Operation is NOT APPLICABLE. 
	For the 'GET' Operation, the possible options are 
	1) active 
	2) down 
	3) block "
			::= {	ss7BCktCfgEntry   17 }

 -- *************************************************     
 -- SS7 circuit management Group
 -- *************************************************     

ss7CktMgmntGroup		OBJECT IDENTIFIER   ::=	{ ss7Br	 5 }

 -- *************************************************     
 -- SS7 circuit Managmant group
 -- *************************************************     

ss7CktMgmntTable		OBJECT-TYPE
			SYNTAX   SEQUENCE OF Ss7CktMgmntEntry
			ACCESS	not-accessible
			STATUS	mandatory
			DESCRIPTION 
	"SS7 Circuit Management Table. The Management Commands for SS7 Circuits(s) 
	in MSSC are provided in this table. 
	This table has two indices: ss7CktMgmntTrnkId and ss7CktMgmntChnlId (both Integer). "
			::= { ss7CktMgmntGroup	 1 }

ss7CktMgmntEntry		OBJECT-TYPE
			SYNTAX	Ss7CktMgmntEntry
			ACCESS	not-accessible
			STATUS	mandatory
			DESCRIPTION 
	"The Current Entry Containes all the objects for this Table. 
	This object is not-accessible, but the user can access all 
	the objects in this table at the next level. "
			INDEX { ss7CktMgmntTrnkId, ss7CktMgmntChnlId }
			::= {	ss7CktMgmntTable   1 }

Ss7CktMgmntEntry		::= SEQUENCE {
			ss7CktMgmntTrnkId		INTEGER,
			ss7CktMgmntChnlId		INTEGER,
			ss7CktMgmntRepNum		INTEGER,
			ss7CktMgmntCmd		BlockOperation
			}

ss7CktMgmntTrnkId		OBJECT-TYPE
			SYNTAX	INTEGER
			ACCESS	read-only
			STATUS	mandatory
			DESCRIPTION 
	"Trunk id. "
			::= {	ss7CktMgmntEntry   1 }

ss7CktMgmntChnlId		OBJECT-TYPE
			SYNTAX	INTEGER
			ACCESS	read-only
			STATUS	mandatory
			DESCRIPTION 
	"Channel id "
			::= {	ss7CktMgmntEntry   2 }

ss7CktMgmntRepNum		OBJECT-TYPE
			SYNTAX	INTEGER(1..65535)
			ACCESS	read-write
			STATUS	mandatory
			DESCRIPTION 
	"Repeat Number for this operation. 
	This option will allow consecutive CIC to be reset "
			::= {	ss7CktMgmntEntry   3 }

ss7CktMgmntCmd		OBJECT-TYPE
			SYNTAX	BlockOperation
			ACCESS	read-write
			STATUS	mandatory
			DESCRIPTION 
	"Management Command for Blocking/Unblocking any call setup 
	on the specified channel. The option of repnum is provided to allow 
	consecutive CIC to be blocked/unblocked 
	The possible options are : 
	1) Block 
	2) UnBlock 
	3) Noaction [default]  "
			::= {	ss7CktMgmntEntry   4 }

 -- *************************************************     
 -- SS7b Cic Management table
 -- *************************************************     

ss7CICMgmntTable		OBJECT-TYPE
			SYNTAX   SEQUENCE OF Ss7CICMgmntEntry
			ACCESS	not-accessible
			STATUS	mandatory
			DESCRIPTION 
	"SS7 Circuit CIC Management Table. The Management Commands for SS7 Circuits(s) 
	in MSSC are provided in this table. 
	This table has two indices: ss7CktMgmtDPC and ss7CktMgmtCIC (both Integer). "
			::= { ss7CktMgmntGroup	 2 }

ss7CICMgmntEntry		OBJECT-TYPE
			SYNTAX	Ss7CICMgmntEntry
			ACCESS	not-accessible
			STATUS	mandatory
			DESCRIPTION 
	"The Current Entry Containes all the objects for this Table. 
	This object is not-accessible, but the user can access all 
	the objects in this table at the next level. "
			INDEX { ss7CktMgmtDPC, ss7CktMgmtCIC }
			::= {	ss7CICMgmntTable   1 }

Ss7CICMgmntEntry		::= SEQUENCE {
			ss7CktMgmtDPC		INTEGER,
			ss7CktMgmtCIC		INTEGER,
			ss7CktRepNum		INTEGER,
			ss7CicRange		INTEGER,
			ss7CICMgmntCmd		CircuitControlStatus
			}

ss7CktMgmtDPC		OBJECT-TYPE
			SYNTAX	INTEGER
			ACCESS	read-only
			STATUS	mandatory
			DESCRIPTION 
	"Destination Point Code (The Integer Value). 
	The Point Code should be converted into its Integer 
	equivalent. For Example: 
	0-1-1 is converted as 257 (for ANSI) 
	0-1-2 is converted as 10 (for ITU) "
			::= {	ss7CICMgmntEntry   1 }

ss7CktMgmtCIC		OBJECT-TYPE
			SYNTAX	INTEGER
			ACCESS	read-only
			STATUS	mandatory
			DESCRIPTION 
	"Circuit identifier code. Can be any integer from 
	1) 1-4095 for ITU 
	2) 1-16383 for ANSI "
			::= {	ss7CICMgmntEntry   2 }

ss7CktRepNum		OBJECT-TYPE
			SYNTAX	INTEGER(1..65535)
			ACCESS	read-write
			STATUS	mandatory
			DESCRIPTION 
	"Repeat Number for this operation. 
	This option will allow consecutive CIC to be reset "
			::= {	ss7CICMgmntEntry   3 }

ss7CicRange		OBJECT-TYPE
			SYNTAX	INTEGER(1..65535)
			ACCESS	read-write
			STATUS	mandatory
			DESCRIPTION 
	"Range for this operation. 
	This option will allow consecutive CIC to be reset "
			::= {	ss7CICMgmntEntry   4 }

ss7CICMgmntCmd		OBJECT-TYPE
			SYNTAX	CircuitControlStatus
			ACCESS	read-write
			STATUS	mandatory
			DESCRIPTION 
	"Management Command for Blocking/Unblocking any call setup 
	on the specified channel. The option of repnum is provided to allow 
	consecutive CIC to be blocked/unblocked 
	The possible options are : 
	1) Block 
	2) UnBlock [default] "
			::= {	ss7CICMgmntEntry   5 }

 -- *************************************************     
 -- Mtp2 timer Configuration starts here
 -- *************************************************     

mtp2LinkTmrCfgTable		OBJECT-TYPE
			SYNTAX   SEQUENCE OF Mtp2LinkTmrCfgEntry
			ACCESS	not-accessible
			STATUS	mandatory
			DESCRIPTION 
	"MTP2 Link Timer Table. The Information about MTP2 Link Timers 
	in MSSC are provided in this table. User can Modify Timer(s) 
	from this table. 
	This table has one index: mtp2LinkId (Integer). "
			::= { mtp2	 1 }

mtp2LinkTmrCfgEntry		OBJECT-TYPE
			SYNTAX	Mtp2LinkTmrCfgEntry
			ACCESS	not-accessible
			STATUS	mandatory
			DESCRIPTION 
	"The Current Entry Containes all the objects for this Table. 
	This object is not-accessible, but the user can access all 
	the objects in this table at the next level. "
			INDEX { mtp2LinkId }
			::= {	mtp2LinkTmrCfgTable   1 }

Mtp2LinkTmrCfgEntry		::= SEQUENCE {
			mtp2LinkId		INTEGER,
			mtp2T1		INTEGER,
			mtp2T2		INTEGER,
			mtp2T3		INTEGER,
			mtp2T4n		INTEGER,
			mtp2T4e		INTEGER,
			mtp2T5		INTEGER,
			mtp2T6		INTEGER,
			mtp2T7		INTEGER,
			mtp2RowStatus		TmrRowStatus,
			mtp2OpStatus		OpStatus
			}

mtp2LinkId		OBJECT-TYPE
			SYNTAX	INTEGER(1..65535)
			ACCESS	read-write
			STATUS	mandatory
			DESCRIPTION 
	"Link id. Can be any integer 1-65535. "
			::= {	mtp2LinkTmrCfgEntry   1 }

mtp2T1		OBJECT-TYPE
			SYNTAX	INTEGER(13000..50000)
			UNITS "ms"
			ACCESS	read-write
			STATUS	mandatory
			DESCRIPTION 
	"t1 timer - for aligned ready condition 
	GR-606-CORE, ISSUE 1, June 1994. Default Value is 13000 milliSeconds "
			DEFVAL { 13000 }
			::= {	mtp2LinkTmrCfgEntry   2 }

mtp2T2		OBJECT-TYPE
			SYNTAX	INTEGER(5000..50000)
			UNITS "ms"
			ACCESS	read-write
			STATUS	mandatory
			DESCRIPTION 
	"t2 timer - Timer for out-of-alignment 
	GR-606-CORE, ISSUE 1, June 1994. Default Value is 11500 milliSeconds "
			DEFVAL { 11500 }
			::= {	mtp2LinkTmrCfgEntry   3 }

mtp2T3		OBJECT-TYPE
			SYNTAX	INTEGER(1000..15000)
			UNITS "ms"
			ACCESS	read-write
			STATUS	mandatory
			DESCRIPTION 
	"t3 timer - Timer for aligned condition 
	GR-606-CORE, ISSUE 1, June 1994. Default Value is 11500 milliSeconds "
			DEFVAL { 1000 }
			::= {	mtp2LinkTmrCfgEntry   4 }

mtp2T4n		OBJECT-TYPE
			SYNTAX	INTEGER(2070..9500)
			UNITS "ms"
			ACCESS	read-write
			STATUS	mandatory
			DESCRIPTION 
	"t4n timer - Normal proving period 
	GR-606-CORE, ISSUE 1, June 1994. Default Value is 2000 milliSeconds "
			DEFVAL { 2070 }
			::= {	mtp2LinkTmrCfgEntry   5 }

mtp2T4e		OBJECT-TYPE
			SYNTAX	INTEGER(400..600)
			UNITS "ms"
			ACCESS	read-write
			STATUS	mandatory
			DESCRIPTION 
	"t4e timer - Emergency proving period 
	GR-606-CORE, ISSUE 1, June 1994. Default Value is 500 milliSeconds "
			DEFVAL { 400 }
			::= {	mtp2LinkTmrCfgEntry   6 }

mtp2T5		OBJECT-TYPE
			SYNTAX	INTEGER(80..120)
			UNITS "ms"
			ACCESS	read-write
			STATUS	mandatory
			DESCRIPTION 
	"t5 timer - Busy status transmission interval 
	GR-606-CORE, ISSUE 1, June 1994. Default Value is 100 milliSeconds "
			DEFVAL { 80 }
			::= {	mtp2LinkTmrCfgEntry   7 }

mtp2T6		OBJECT-TYPE
			SYNTAX	INTEGER(3000..6000)
			UNITS "ms"
			ACCESS	read-write
			STATUS	mandatory
			DESCRIPTION 
	"t6 timer - Supervision of remote congestion timer 
	GR-606-CORE, ISSUE 1, June 1994. Default Value is 3000 milliSeconds "
			DEFVAL { 3000 }
			::= {	mtp2LinkTmrCfgEntry   8 }

mtp2T7		OBJECT-TYPE
			SYNTAX	INTEGER(500..2000)
			UNITS "ms"
			ACCESS	read-write
			STATUS	mandatory
			DESCRIPTION 
	"t7 timer - Excessive delay of ack 
	GR-606-CORE, ISSUE 1, June 1994. Default Value is 500 milliSeconds "
			DEFVAL { 500 }
			::= {	mtp2LinkTmrCfgEntry   9 }

mtp2RowStatus		OBJECT-TYPE
			SYNTAX	TmrRowStatus
			ACCESS	read-write
			STATUS	mandatory
			DESCRIPTION 
	"Current Status (configurational Status) of this MTP2 Link Timer. 
	To Modify any Timer for this link, the only option is 'MODIFYTIMER'. 
	For the 'GET' Operation, the possible options are 
	1) active 
	2) notinservice 
	3) notready 
	4) modified 
	5) up 
	6) down"
			::= {	mtp2LinkTmrCfgEntry   10 }

mtp2OpStatus		OBJECT-TYPE
			SYNTAX	OpStatus
			ACCESS	read-only
			STATUS	mandatory
			DESCRIPTION 
	"Current Status (Operational Status) of this MTP2 Link Timer. 
	'SET' Operation is NOT APPLICABLE. 
	For the 'GET' Operation, the possible options are 
	1) active 
	2) down  "
			::= {	mtp2LinkTmrCfgEntry   11 }

 -- *************************************************     
 -- mtp3 general timer configuration starts here
 -- *************************************************     

mtp3T15		OBJECT-TYPE
			SYNTAX	INTEGER(2000..3000)
			UNITS "ms"
			ACCESS	read-write
			STATUS	mandatory
			DESCRIPTION 
	"T15 timer - Signal route set congestion test interval 
	GR-606-CORE, ISSUE 1, June 1994. Default Value is 3000 milliSeconds "
			DEFVAL { 2000 }
			::= {	mtp3GenTmrCfgGroup   1 }

mtp3T16		OBJECT-TYPE
			SYNTAX	INTEGER(1400..2000)
			UNITS "ms"
			ACCESS	read-write
			STATUS	mandatory
			DESCRIPTION 
	"T16 timer - Transfer controlled update 
	GR-606-CORE, ISSUE 1, June 1994. Default Value is 1400 milliSeconds "
			DEFVAL { 2000 }
			::= {	mtp3GenTmrCfgGroup   2 }

mtp3T18		OBJECT-TYPE
			SYNTAX	INTEGER(0..65535)
			UNITS "ms"
			ACCESS	read-write
			STATUS	mandatory
			DESCRIPTION 
	"T18 timer - Timer for links to become available. 
	Not Applicable to ANSI. Default Value is 1400 milliSeconds "
			DEFVAL { 600 }
			::= {	mtp3GenTmrCfgGroup   3 }

mtp3T19		OBJECT-TYPE
			SYNTAX	INTEGER(67000..69000)
			UNITS "ms"
			ACCESS	read-write
			STATUS	mandatory
			DESCRIPTION 
	"T19 timer - Timer to receive all traffic restart. 
	Not Applicable to ANSI. Default Value is 0 "
			DEFVAL { 67000 }
			::= {	mtp3GenTmrCfgGroup   4 }

mtp3T20		OBJECT-TYPE
			SYNTAX	INTEGER(59000..61000)
			UNITS "ms"
			ACCESS	read-write
			STATUS	mandatory
			DESCRIPTION 
	"T20 timer - BroadCast traffic restart interval. 
	Not Applicable to ANSI. "
			DEFVAL { 590000 }
			::= {	mtp3GenTmrCfgGroup   5 }

mtp3T21		OBJECT-TYPE
			SYNTAX	INTEGER(63000..65000)
			UNITS "ms"
			ACCESS	read-write
			STATUS	mandatory
			DESCRIPTION 
	"T21 timer - Interval to restart traffic route through adjacent SP "
			DEFVAL { 63000 }
			::= {	mtp3GenTmrCfgGroup   6 }

mtp3T26		OBJECT-TYPE
			SYNTAX	INTEGER(12000..15000)
			UNITS "ms"
			ACCESS	read-write
			STATUS	mandatory
			DESCRIPTION 
	"T26 timer - Timer at restarting SP waiting to repeat TRW 
	GR-606-CORE, ISSUE 1, June 1994. Default Value is 13500 milliSeconds "
			DEFVAL { 12000 }
			::= {	mtp3GenTmrCfgGroup   7 }

mtp3T30		OBJECT-TYPE
			SYNTAX	INTEGER(30000..35000)
			UNITS "ms"
			ACCESS	read-only
			STATUS	mandatory
			DESCRIPTION 
	"T30 timer - Route Instance timer "
			DEFVAL { 30000 }
			::= {	mtp3GenTmrCfgGroup   8 }

mtp3GenTmrRowStatus		OBJECT-TYPE
			SYNTAX	ModifyTmrStatus
			ACCESS	read-write
			STATUS	mandatory
			DESCRIPTION 
	"This is a command to MODIFY a Timer. A 'GET' operation on 
	this object will display the default value [no action]. 
	The possible option for 'SET' operation is: 
	1)modify "
			::= {	mtp3GenTmrCfgGroup   9 }

 -- *************************************************     
 -- mtp3 link configuration table
 -- *************************************************     

mtp3LinkCfgTable		OBJECT-TYPE
			SYNTAX   SEQUENCE OF Mtp3LinkCfgEntry
			ACCESS	not-accessible
			STATUS	mandatory
			DESCRIPTION 
	"MTP3 Link Timer Table. The Information about MTP3 Link Timers 
	in MSSC are provided in this table. User can Modify Timer(s) 
	from this table. 
	This table has one index: mtp3LinkId (Integer). "
			::= { mtp3	 2 }

mtp3LinkCfgEntry		OBJECT-TYPE
			SYNTAX	Mtp3LinkCfgEntry
			ACCESS	not-accessible
			STATUS	mandatory
			DESCRIPTION 
	"The Current Entry Containes all the objects for this Table. 
	This object is not-accessible, but the user can access all 
	the objects in this table at the next level. "
			INDEX { mtp3LinkId }
			::= {	mtp3LinkCfgTable   1 }

Mtp3LinkCfgEntry		::= SEQUENCE {
			mtp3LinkId		INTEGER,
			mtp3T1		INTEGER,
			mtp3T2		INTEGER,
			mtp3T3		INTEGER,
			mtp3T4		INTEGER,
			mtp3T5		INTEGER,
			mtp3T6		INTEGER,
			mtp3T7		INTEGER,
			mtp3T12		INTEGER,
			mtp3T13		INTEGER,
			mtp3T14		INTEGER,
			mtp3T17		INTEGER,
			mtp3T22		INTEGER,
			mtp3T23		INTEGER,
			mtp3T24		INTEGER,
			mtp3T31		INTEGER,
			mtp3T32		INTEGER,
			mtp3T33		INTEGER,
			mtp3T34		INTEGER,
			mtp3T35		INTEGER,
			mtp3T36		INTEGER,
			mtp3T37		INTEGER,
			mtp3TFLC		INTEGER,
			mtp3TBND		INTEGER,
			mtp3RowStatus		TmrRowStatus,
			mtp3OpStatus		OpStatus
			}

mtp3LinkId		OBJECT-TYPE
			SYNTAX	INTEGER(1..65535)
			ACCESS	read-write
			STATUS	mandatory
			DESCRIPTION 
	"Link id GR-606-CORE, ISSUE 1, June 1994 "
			::= {	mtp3LinkCfgEntry   1 }

mtp3T1		OBJECT-TYPE
			SYNTAX	INTEGER(500..1200)
			UNITS "ms"
			ACCESS	read-write
			STATUS	mandatory
			DESCRIPTION 
	"T1 timer - Transmission delay following changeover 
	GR-606-CORE, ISSUE 1, June 1994. Default Value is 500 milliSeconds "
			DEFVAL { 1000 }
			::= {	mtp3LinkCfgEntry   2 }

mtp3T2		OBJECT-TYPE
			SYNTAX	INTEGER(700..2000)
			UNITS "ms"
			ACCESS	read-write
			STATUS	mandatory
			DESCRIPTION 
	"T2 timer - changeover ack timer 
	GR-606-CORE, ISSUE 1, June 1994. Default Value is 700 milliSeconds "
			DEFVAL { 1000 }
			::= {	mtp3LinkCfgEntry   3 }

mtp3T3		OBJECT-TYPE
			SYNTAX	INTEGER(500..1200)
			UNITS "ms"
			ACCESS	read-write
			STATUS	mandatory
			DESCRIPTION 
	"T3 timer - Transmission delay following changeback 
	GR-606-CORE, ISSUE 1, June 1994. Default Value is 500 milliSeconds "
			DEFVAL { 1000 }
			::= {	mtp3LinkCfgEntry   4 }

mtp3T4		OBJECT-TYPE
			SYNTAX	INTEGER(500..1200)
			UNITS "ms"
			ACCESS	read-write
			STATUS	mandatory
			DESCRIPTION 
	"T4 timer - Changeback ack timer (first attempt) 
	GR-606-CORE, ISSUE 1, June 1994. Default is 500 milliSeconds "
			DEFVAL { 1000 }
			::= {	mtp3LinkCfgEntry   5 }

mtp3T5		OBJECT-TYPE
			SYNTAX	INTEGER(500..1200)
			UNITS "ms"
			ACCESS	read-write
			STATUS	mandatory
			DESCRIPTION 
	"T5 timer - Changeback ack timer (subsequent attempt) 
	GR-606-CORE, ISSUE 1, June 1994. Default is 500 milliSeconds "
			DEFVAL { 1000 }
			::= {	mtp3LinkCfgEntry   6 }

mtp3T6		OBJECT-TYPE
			SYNTAX	INTEGER(500..1200)
			UNITS "ms"
			ACCESS	read-write
			STATUS	mandatory
			DESCRIPTION 
	"T6 timer - Controlled rerouting transmission delay 
	GR-606-CORE, ISSUE 1, June 1994. Default Value is 500 milliSeconds "
			DEFVAL { 500 }
			::= {	mtp3LinkCfgEntry   7 }

mtp3T7		OBJECT-TYPE
			SYNTAX	INTEGER(500..1200)
			UNITS "ms"
			ACCESS	read-only
			STATUS	mandatory
			DESCRIPTION 
	"T7 Timer - Link connection ack timer "
			::= {	mtp3LinkCfgEntry   8 }

mtp3T12		OBJECT-TYPE
			SYNTAX	INTEGER(800..1500)
			UNITS "ms"
			ACCESS	read-write
			STATUS	mandatory
			DESCRIPTION 
	"T12 timer - Uninhibit acknowledge timer 
	GR-606-CORE, ISSUE 1, June 1994. Default Value is 1000 milliSeconds "
			DEFVAL { 1000 }
			::= {	mtp3LinkCfgEntry   9 }

mtp3T13		OBJECT-TYPE
			SYNTAX	INTEGER(800..1500)
			UNITS "ms"
			ACCESS	read-write
			STATUS	mandatory
			DESCRIPTION 
	"T13 timer - Forced uninhibit ack timer 
	GR-606-CORE, ISSUE 1, June 1994. Default Value is 1000 milliSeconds. "
			DEFVAL { 1000 }
			::= {	mtp3LinkCfgEntry   10 }

mtp3T14		OBJECT-TYPE
			SYNTAX	INTEGER(2000..3000)
			UNITS "ms"
			ACCESS	read-write
			STATUS	mandatory
			DESCRIPTION 
	"T14 timer - Inhibit ack timer 
	GR-606-CORE, ISSUE 1, June 1994. Default Value is 3000 milliSeconds "
			DEFVAL { 3000 }
			::= {	mtp3LinkCfgEntry   11 }

mtp3T17		OBJECT-TYPE
			SYNTAX	INTEGER(800..1500)
			UNITS "ms"
			ACCESS	read-write
			STATUS	mandatory
			DESCRIPTION 
	"T17 timer - Timing to restart of initial alignment 
	GR-606-CORE, ISSUE 1, June 1994. Default Value is 1000 milliSeconds "
			DEFVAL { 1000 }
			::= {	mtp3LinkCfgEntry   12 }

mtp3T22		OBJECT-TYPE
			SYNTAX	INTEGER(180..360)
			UNITS "sec"
			ACCESS	read-write
			STATUS	mandatory
			DESCRIPTION 
	"T20 timer - Waiting to repeat local inhibit test. 
	Default Value is 10000 milliSeconds "
			DEFVAL { 180 }
			::= {	mtp3LinkCfgEntry   13 }

mtp3T23		OBJECT-TYPE
			SYNTAX	INTEGER(180..360)
			UNITS "sec"
			ACCESS	read-write
			STATUS	mandatory
			DESCRIPTION 
	"T21 timer - Waiting to repeat remote inhibit test. 
	Default Value is 10000 milliSeconds "
			DEFVAL { 180 }
			::= {	mtp3LinkCfgEntry   14 }

mtp3T24		OBJECT-TYPE
			SYNTAX	INTEGER(5000..5000)
			UNITS "ms"
			ACCESS	read-only
			STATUS	mandatory
			DESCRIPTION 
	"T24 timer - Stabilizing timer. "
			DEFVAL { 5000 }
			::= {	mtp3LinkCfgEntry   15 }

mtp3T31		OBJECT-TYPE
			SYNTAX	INTEGER(10..120)
			UNITS "sec"
			ACCESS	read-write
			STATUS	mandatory
			DESCRIPTION 
	"T31 timer - Timer to detect a link in false link congestion. 
	GR-606-CORE, ISSUE 1, June 1994. Default Value is 30000 milliSeconds "
			DEFVAL { 120 }
			::= {	mtp3LinkCfgEntry   16 }

mtp3T32		OBJECT-TYPE
			SYNTAX	INTEGER(4..12)
			UNITS "sec"
			ACCESS	read-write
			STATUS	mandatory
			DESCRIPTION 
	"T32 timer - SLT timer "
			DEFVAL { 4 }
			::= {	mtp3LinkCfgEntry   17 }

mtp3T33		OBJECT-TYPE
			SYNTAX	INTEGER(60..600)
			UNITS "sec"
			ACCESS	read-write
			STATUS	mandatory
			DESCRIPTION 
	"T33 timer - Timer to detect a link in false link congestion. 
	GR-606-CORE, ISSUE 1, June 1994. Default Value is 30000 milliSeconds "
			DEFVAL { 120 }
			::= {	mtp3LinkCfgEntry   18 }

mtp3T34		OBJECT-TYPE
			SYNTAX	INTEGER(30..90)
			UNITS "sec"
			ACCESS	read-write
			STATUS	mandatory
			DESCRIPTION 
	"T34 timer - Timer to detect a link in false link congestion. 
	GR-606-CORE, ISSUE 1, June 1994. Default Value is 30000 milliSeconds "
			DEFVAL { 30 }
			::= {	mtp3LinkCfgEntry   19 }

mtp3T35		OBJECT-TYPE
			SYNTAX	INTEGER(10..120)
			UNITS "sec"
			ACCESS	read-write
			STATUS	mandatory
			DESCRIPTION 
	"T35 timer - periodic signalling link test timer 
	GR-606-CORE, ISSUE 1, June 1994. Default Value is 30000 milliSeconds "
			DEFVAL { 120 }
			::= {	mtp3LinkCfgEntry   20 }

mtp3T36		OBJECT-TYPE
			SYNTAX	INTEGER(60..600)
			UNITS "sec"
			ACCESS	read-write
			STATUS	mandatory
			DESCRIPTION 
	"T36 timer - Probation timer for link oscillation. 
	Not in bellcore. Default Value is 30000 milliSeconds "
			DEFVAL { 120 }
			::= {	mtp3LinkCfgEntry   21 }

mtp3T37		OBJECT-TYPE
			SYNTAX	INTEGER(5..120)
			UNITS "sec"
			ACCESS	read-write
			STATUS	mandatory
			DESCRIPTION 
	"T37 timer - Suspension Timer for link oscillation. 
	Not in bellcore. Default Value is 30000 milliSeconds "
			DEFVAL { 120 }
			::= {	mtp3LinkCfgEntry   22 }

mtp3TFLC		OBJECT-TYPE
			SYNTAX	INTEGER(1..65535)
			UNITS "ms"
			ACCESS	read-write
			STATUS	mandatory
			DESCRIPTION 
	"TFLC timer - Flow control request timer. 
	Not in bellcore.  "
			DEFVAL { 5000 }
			::= {	mtp3LinkCfgEntry   23 }

mtp3TBND		OBJECT-TYPE
			SYNTAX	INTEGER(1..65535)
			UNITS "ms"
			ACCESS	read-write
			STATUS	mandatory
			DESCRIPTION 
	"TBND timer - Bind confirm wait timer. 
	Not in bellcore.  "
			DEFVAL { 20000 }
			::= {	mtp3LinkCfgEntry   24 }

mtp3RowStatus		OBJECT-TYPE
			SYNTAX	TmrRowStatus
			ACCESS	read-write
			STATUS	mandatory
			DESCRIPTION 
	"Current Status (configurational Status) of this MTP3 Link Timer. 
	To Modify any Timer for this link, the only option is 'MODIFYTIMER'. 
	For the 'GET' Operation, the possible options are 
	1) active 
	2) notinservice 
	3) notready 
	4) modified 
	5) up 
	6) down"
			::= {	mtp3LinkCfgEntry   25 }

mtp3OpStatus		OBJECT-TYPE
			SYNTAX	OpStatus
			ACCESS	read-only
			STATUS	mandatory
			DESCRIPTION 
	"Current Status (Operational Status) of this MTP3 Link Timer. 
	'SET' Operation is NOT APPLICABLE. 
	For the 'GET' Operation, the possible options are 
	1) active 
	2) down  "
			::= {	mtp3LinkCfgEntry   26 }

 -- *************************************************     
 -- ISUP general Timer configuration Group
 -- *************************************************     

isupTimerCfgTable		OBJECT-TYPE
			SYNTAX   SEQUENCE OF IsupTimerCfgEntry
			ACCESS	not-accessible
			STATUS	mandatory
			DESCRIPTION 
	"Isup Timer Table. The Information about ISUPTimers 
	in MSSC are provided in this table. User can Modify Timer(s) 
	from this table. 
	This table has one index: isupTmrSS7Type (TimerType). "
			::= { isup	 1 }

isupTimerCfgEntry		OBJECT-TYPE
			SYNTAX	IsupTimerCfgEntry
			ACCESS	not-accessible
			STATUS	mandatory
			DESCRIPTION 
	"The Current Entry Containes all the objects for this Table. 
	This object is not-accessible, but the user can access all 
	the objects in this table at the next level. "
			INDEX { isupTimerType }
			::= {	isupTimerCfgTable   1 }

IsupTimerCfgEntry		::= SEQUENCE {
			isupTimerType		TimerType,
			isupTmrT1		INTEGER,
			isupTmrT2		INTEGER,
			isupTmrT5		INTEGER,
			isupTmrT6		INTEGER,
			isupTmrT7		INTEGER,
			isupTmrT8		INTEGER,
			isupTmrT9		INTEGER,
			isupTmrT18		INTEGER,
			isupTmrT19		INTEGER,
			isupTmrT20		INTEGER,
			isupTmrT21		INTEGER,
			isupTmrT22		INTEGER,
			isupTmrT23		INTEGER,
			isupTmrT27		INTEGER,
			isupTmrT28		INTEGER,
			isupTmrT31		INTEGER,
			isupTmrT33		INTEGER,
			isupTmrT34		INTEGER,
			isupTmrT36		INTEGER,
			isupTmrTCCR		INTEGER,
			isupTmrTEX		INTEGER,
			isupTmrTCRM		INTEGER,
			isupTmrTCRA		INTEGER,
			isupTmrTCCRt		INTEGER,
			isupTmrTECt		INTEGER,
			isupTmrTGTCHG		INTEGER,
			isupTmrTGRES		INTEGER,
			isupTmrTFGR		INTEGER,
			isupTmrTRELRSP		INTEGER,
			isupTmrTFNLRELRS		INTEGER,
			isupTimerRowStatus		ModifyTmrStatus
			}

isupTimerType		OBJECT-TYPE
			SYNTAX	TimerType(1..2)
			ACCESS	read-write
			STATUS	mandatory
			DESCRIPTION 
	"Index for this IsupTimer Table, is an enumerated data type ansi(1), itu(2)"
			::= {	isupTimerCfgEntry   1 }

isupTmrT1		OBJECT-TYPE
			SYNTAX	INTEGER(4000..60000)
			UNITS "ms"
			ACCESS	read-write
			STATUS	mandatory
			DESCRIPTION 
	"T1 timer - release sent, 
	GR-246-CORE, Issue 2, December 1997. 
	Default Value is 4000 milliSeconds "
			DEFVAL { 4000 }
			::= {	isupTimerCfgEntry   2 }

isupTmrT2		OBJECT-TYPE
			SYNTAX	INTEGER(0..180)
			UNITS "sec"
			ACCESS	read-write
			STATUS	mandatory
			DESCRIPTION 
	"T2 timer - suspend received, 
	GR-246-CORE, Issue 2, December 1997. 
	Default Value is 0 milliSeconds "
			DEFVAL { 180 }
			::= {	isupTimerCfgEntry   3 }

isupTmrT5		OBJECT-TYPE
			SYNTAX	INTEGER(60..900)
			UNITS "sec"
			ACCESS	read-write
			STATUS	mandatory
			DESCRIPTION 
	"T5 timer - initial release sent 
	GR-246-CORE, Issue 2, December 1997. 
	Default Value is 60000 milliSeconds "
			DEFVAL { 300 }
			::= {	isupTimerCfgEntry   4 }

isupTmrT6		OBJECT-TYPE
			SYNTAX	INTEGER(10000..32000)
			UNITS "ms"
			ACCESS	read-write
			STATUS	mandatory
			DESCRIPTION 
	"T6 timer - suspend received 
	GR-246-CORE, Issue 2, December 1997. 
	Default Value is 10000 milliSeconds "
			DEFVAL { 10000 }
			::= {	isupTimerCfgEntry   5 }

isupTmrT7		OBJECT-TYPE
			SYNTAX	INTEGER(20000..30000)
			UNITS "ms"
			ACCESS	read-write
			STATUS	mandatory
			DESCRIPTION 
	"T7 timer - latest address sent 
	GR-246-CORE, Issue 2, December 1997. 
	Default Value is 20000 milliSeconds "
			DEFVAL { 20000 }
			::= {	isupTimerCfgEntry   6 }

isupTmrT8		OBJECT-TYPE
			SYNTAX	INTEGER(10000..15000)
			UNITS "ms"
			ACCESS	read-write
			STATUS	mandatory
			DESCRIPTION 
	"T8 - timer initial address received 
	GR-246-CORE, Issue 2, December 1997. 
	Default Value is 10000 milliSeconds "
			DEFVAL { 10000 }
			::= {	isupTimerCfgEntry   7 }

isupTmrT9		OBJECT-TYPE
			SYNTAX	INTEGER(120..240)
			UNITS "sec"
			ACCESS	read-write
			STATUS	mandatory
			DESCRIPTION 
	"T9 timer - latest address sent after ACM 
	GR-246-CORE, Issue 2, December 1997. 
	Default Value is 120000 milliSeconds "
			DEFVAL { 120 }
			::= {	isupTimerCfgEntry   8 }

isupTmrT18		OBJECT-TYPE
			SYNTAX	INTEGER(4000..60000)
			UNITS "ms"
			ACCESS	read-write
			STATUS	mandatory
			DESCRIPTION 
	"T18 timer - group blocking sent 
	GR-246-CORE, Issue 2, December 1997. 
	Default Value is 4000 milliSeconds "
			DEFVAL { 15000 }
			::= {	isupTimerCfgEntry   9 }

isupTmrT19		OBJECT-TYPE
			SYNTAX	INTEGER(60..900)
			UNITS "sec"
			ACCESS	read-write
			STATUS	mandatory
			DESCRIPTION 
	"T19 timer - initial group blocking sent 
	GR-246-CORE, Issue 2, December 1997. 
	Default Value is 60000 milliSeconds "
			DEFVAL { 300 }
			::= {	isupTimerCfgEntry   10 }

isupTmrT20		OBJECT-TYPE
			SYNTAX	INTEGER(4000..60000)
			UNITS "ms"
			ACCESS	read-write
			STATUS	mandatory
			DESCRIPTION 
	"T20 timer - group unblocking sent 
	GR-246-CORE, Issue 2, December 1997. 
	Default Value is 4000 milliSeconds "
			DEFVAL { 15000 }
			::= {	isupTimerCfgEntry   11 }

isupTmrT21		OBJECT-TYPE
			SYNTAX	INTEGER(60..900)
			UNITS "sec"
			ACCESS	read-write
			STATUS	mandatory
			DESCRIPTION 
	"T21 timer - initial group unblocking sent 
	GR-246-CORE, Issue 2, December 1997. 
	Default Value is 60000 milliSeconds "
			DEFVAL { 30 }
			::= {	isupTimerCfgEntry   12 }

isupTmrT22		OBJECT-TYPE
			SYNTAX	INTEGER(4000..60000)
			UNITS "ms"
			ACCESS	read-write
			STATUS	mandatory
			DESCRIPTION 
	"T22 timer - group reset sent 
	GR-246-CORE, Issue 2, December 1997. 
	Default Value is 4000 milliSeconds "
			DEFVAL { 15000 }
			::= {	isupTimerCfgEntry   13 }

isupTmrT23		OBJECT-TYPE
			SYNTAX	INTEGER(60..900)
			UNITS "sec"
			ACCESS	read-write
			STATUS	mandatory
			DESCRIPTION 
	"T23 timer - initial group reset sent 
	GR-246-CORE, Issue 2, December 1997. 
	Default Value is 60000 milliSeconds "
			DEFVAL { 300 }
			::= {	isupTimerCfgEntry   14 }

isupTmrT27		OBJECT-TYPE
			SYNTAX	INTEGER(18..24)
			UNITS "sec"
			ACCESS	read-write
			STATUS	mandatory
			DESCRIPTION 
	"T27 timer - waiting for continuity recheck 
	GR-246-CORE, Issue 2, December 1997. 
	Default Value is 200000 milliSeconds "
			DEFVAL { 18 }
			::= {	isupTimerCfgEntry   15 }

isupTmrT28		OBJECT-TYPE
			SYNTAX	INTEGER(10000..10000)
			UNITS "ms"
			ACCESS	read-write
			STATUS	mandatory
			DESCRIPTION 
	"T28 timer - circuit group query sent 
	GR-246-CORE, Issue 2, December 1997. 
	Default Value is 10000 milliSeconds "
			DEFVAL { 10000 }
			::= {	isupTimerCfgEntry   16 }

isupTmrT31		OBJECT-TYPE
			SYNTAX	INTEGER(360)
			UNITS "sec"
			ACCESS	read-write
			STATUS	mandatory
			DESCRIPTION 
	"T31 timer - call reference frozen period 
	GR-246-CORE, Issue 2, December 1997. 
	Default Value is 360000 milliSeconds "
			DEFVAL { 360 }
			::= {	isupTimerCfgEntry   17 }

isupTmrT33		OBJECT-TYPE
			SYNTAX	INTEGER(12000..15000)
			UNITS "ms"
			ACCESS	read-write
			STATUS	mandatory
			DESCRIPTION 
	"T33 timer - INR sent 
	GR-246-CORE, Issue 2, December 1997. 
	Default Value is 12000 milliSeconds "
			DEFVAL { 12000 }
			::= {	isupTimerCfgEntry   18 }

isupTmrT34		OBJECT-TYPE
			SYNTAX	INTEGER(10000..15000)
			UNITS "ms"
			ACCESS	read-write
			STATUS	mandatory
			DESCRIPTION 
	"T34 timer - currently unknown. Default Value is 10000 milliSeconds "
			DEFVAL { 10000 }
			::= {	isupTimerCfgEntry   19 }

isupTmrT36		OBJECT-TYPE
			SYNTAX	INTEGER(2000..4000)
			UNITS "ms"
			ACCESS	read-write
			STATUS	mandatory
			DESCRIPTION 
	"T36 timer - waiting for continuity after recheck, 
	in bellcore it is T34 GR-246-CORE, Issue 2, December 1997. 
	Default Value is 2000 milliSeconds "
			DEFVAL { 2000 }
			::= {	isupTimerCfgEntry   20 }

isupTmrTCCR		OBJECT-TYPE
			SYNTAX	INTEGER(20000..24000)
			UNITS "ms"
			ACCESS	read-write
			STATUS	mandatory
			DESCRIPTION 
	"tCCR timer - continuity recheck timer 
	GR-246-CORE, Issue 2, December 1997. 
	Default Value is 20000 milliSeconds "
			DEFVAL { 20000 }
			::= {	isupTimerCfgEntry   21 }

isupTmrTEX		OBJECT-TYPE
			SYNTAX	INTEGER(1..65535)
			UNITS "ms"
			ACCESS	read-only
			STATUS	mandatory
			DESCRIPTION 
	"TEX timer - Exit to be sent, currently not applicable "
			DEFVAL { 0 }
			::= {	isupTimerCfgEntry   22 }

isupTmrTCRM		OBJECT-TYPE
			SYNTAX	INTEGER(3000..4000)
			UNITS "ms"
			ACCESS	read-write
			STATUS	mandatory
			DESCRIPTION 
	"TCRM timer - circuit reservation message sent. 
	GR-246-CORE, Issue 2, December 1997. 
	Default Value is 3000 milliSeconds "
			DEFVAL { 3000 }
			::= {	isupTimerCfgEntry   23 }

isupTmrTCRA		OBJECT-TYPE
			SYNTAX	INTEGER(0..20000)
			UNITS "ms"
			ACCESS	read-write
			STATUS	mandatory
			DESCRIPTION 
	"TCRA timer - circuit reservation acknowledgement sent. 
	GR-246-CORE, Issue 2, December 1997. 
	Default Value is 20000 milliSeconds "
			DEFVAL { 0 }
			::= {	isupTimerCfgEntry   24 }

isupTmrTCCRt		OBJECT-TYPE
			SYNTAX	INTEGER(0..2000)
			UNITS "ms"
			ACCESS	read-write
			STATUS	mandatory
			DESCRIPTION 
	"TCCRt timer - tCCR timer (o/g side). 
	Default Value is 0 milliSeconds "
			DEFVAL { 0 }
			::= {	isupTimerCfgEntry   25 }

isupTmrTECt		OBJECT-TYPE
			SYNTAX	INTEGER(1..65535)
			UNITS "ms"
			ACCESS	read-only
			STATUS	mandatory
			DESCRIPTION 
	"tECT timer - Explicit Call Transfer -wait for loop prvnt rsp. 
	Default Value is 0 milliSeconds "
			DEFVAL { 0 }
			::= {	isupTimerCfgEntry   26 }

isupTmrTGTCHG		OBJECT-TYPE
			SYNTAX	INTEGER(1..65535)
			UNITS "ms"
			ACCESS	read-only
			STATUS	mandatory
			DESCRIPTION 
	"Timer tGTCHG - Awaiting charging extended acknowledgement after 
	having sent CHGE  "
			DEFVAL { 0 }
			::= {	isupTimerCfgEntry   27 }

isupTmrTGRES		OBJECT-TYPE
			SYNTAX	INTEGER(5000..5000)
			UNITS "ms"
			ACCESS	read-write
			STATUS	mandatory
			DESCRIPTION 
	"TGRS timer - at receipt of circuit group reset message, treat subsequent 
	circuit group reset messages new only on this timer expiration. "
			DEFVAL { 5000 }
			::= {	isupTimerCfgEntry   28 }

isupTmrTFGR		OBJECT-TYPE
			SYNTAX	INTEGER(10000..120000)
			UNITS "ms"
			ACCESS	read-only
			STATUS	mandatory
			DESCRIPTION 
	"TFGR timer - first group received timer 
	GR-246-CORE, Issue 2, December 1997 "
			DEFVAL { 0 }
			::= {	isupTimerCfgEntry   29 }

isupTmrTRELRSP		OBJECT-TYPE
			SYNTAX	INTEGER(1..65535)
			UNITS "ms"
			ACCESS	read-only
			STATUS	mandatory
			DESCRIPTION 
	"Time tRELRSP - Awaiting for release response. 
	Default Value is 0 milliSeconds  "
			DEFVAL { 0 }
			::= {	isupTimerCfgEntry   30 }

isupTmrTFNLRELRS		OBJECT-TYPE
			SYNTAX	INTEGER(1..65535)
			UNITS "ms"
			ACCESS	read-only
			STATUS	mandatory
			DESCRIPTION 
	"Time tFNLRELRSP - Awaiting for final release response. 
	Default Value is 0 milliSeconds "
			DEFVAL { 0 }
			::= {	isupTimerCfgEntry   31 }

isupTimerRowStatus		OBJECT-TYPE
			SYNTAX	ModifyTmrStatus
			ACCESS	read-write
			STATUS	mandatory
			DESCRIPTION 
	"This is a command to MODIFY a Timer. A 'GET' operation on 
	this object will display the default value [no action]. 
	The possible option for 'SET' operation is: 
	1)modify "
			::= {	isupTimerCfgEntry   32 }

 -- *************************************************     
 -- Ss7 DPC Route
 -- *************************************************     

ss7RtDpcTable		OBJECT-TYPE
			SYNTAX   SEQUENCE OF Ss7RtDpcEntry
			ACCESS	not-accessible
			STATUS	mandatory
			DESCRIPTION 
	"SS7 Route Dpc Table. The Information about Route(s) 
	in MSSC are provided in this table. 
	This table has one index: ss7RtDPC (Integer). "
			::= { ss7Route	 1 }

ss7RtDpcEntry		OBJECT-TYPE
			SYNTAX	Ss7RtDpcEntry
			ACCESS	not-accessible
			STATUS	mandatory
			DESCRIPTION 
	"The Current Entry Containes all the objects for this Table. 
	This object is not-accessible, but the user can access all 
	the objects in this table at the next level. "
			INDEX { ss7RtDPC }
			::= {	ss7RtDpcTable   1 }

Ss7RtDpcEntry		::= SEQUENCE {
			ss7RtDPC		INTEGER,
			ss7RtCmbLinksetId		INTEGER,
			ss7RtLoadShareType		Standard,
			ss7RtRowStatus		RowStatus,
			ss7RtOpStatus		OpStatus
			}

ss7RtDPC		OBJECT-TYPE
			SYNTAX	INTEGER(1..16777215)
			ACCESS	read-write
			STATUS	mandatory
			DESCRIPTION 
	"The Route Destination Point Code (The Integer Value). 
	The Point Code should be converted into its Integer 
	equivalent. For Example: 
	0-1-1 is converted as 257 (for ANSI) 
	0-1-2 is converted as 10 (for ITU) "
			::= {	ss7RtDpcEntry   1 }

ss7RtCmbLinksetId		OBJECT-TYPE
			SYNTAX	INTEGER(1..65535)
			ACCESS	read-write
			STATUS	mandatory
			DESCRIPTION 
	"SS7 Linkset Id which is already configured so far. 
	An incorrect Linkset Id will result a failure at 
	the time of 'CREATION' of the Route table for the specified DPC. "
			::= {	ss7RtDpcEntry   2 }

ss7RtLoadShareType		OBJECT-TYPE
			SYNTAX	Standard
			ACCESS	read-write
			STATUS	mandatory
			DESCRIPTION 
	"Load Share type(ANSI/ITU) "
			::= {	ss7RtDpcEntry   3 }

ss7RtRowStatus		OBJECT-TYPE
			SYNTAX	RowStatus
			ACCESS	read-write
			STATUS	mandatory
			DESCRIPTION 
	"Current Status (configurational Status) of this SS7 Route. 
	To Configure this Route, the only option is 'CREATEANDWAIT'. 
	To Delete this Route, the only option is 'DESTROY'. 
	For the 'GET' Operation, the possible options are 
	1) active 
	2) notinservice 
	3"
			::= {	ss7RtDpcEntry   4 }

ss7RtOpStatus		OBJECT-TYPE
			SYNTAX	OpStatus
			ACCESS	read-only
			STATUS	mandatory
			DESCRIPTION 
	"Current Status (Operational Status) of this SS7 Route. 
	'SET' Operation is NOT APPLICABLE. 
	For the 'GET' Operation, the possible options are 
	1) active 
	2) down  "
			::= {	ss7RtDpcEntry   5 }

 -- *************************************************     
 -- ISDN Trunk Timer config table
 -- *************************************************     

isdnTmrCfgTable		OBJECT-TYPE
			SYNTAX   SEQUENCE OF IsdnTmrCfgEntry
			ACCESS	not-accessible
			STATUS	mandatory
			DESCRIPTION 
	"ISDN Timer Table. The Information about ISDN Timers 
	in MSSC are provided in this table. User can Modify Timer(s) 
	from this table. 
	This table has one index: isdnTnkId (Integer). "
			::= { isdn	 1 }

isdnTmrCfgEntry		OBJECT-TYPE
			SYNTAX	IsdnTmrCfgEntry
			ACCESS	not-accessible
			STATUS	mandatory
			DESCRIPTION 
	"The Current Entry Containes all the objects for this Table. 
	This object is not-accessible, but the user can access all 
	the objects in this table at the next level. "
			INDEX { isdnTnkId }
			::= {	isdnTmrCfgTable   1 }

IsdnTmrCfgEntry		::= SEQUENCE {
			isdnTnkId		INTEGER,
			isdnTmrT301		INTEGER,
			isdnTmrT302		INTEGER,
			isdnTmrT303		INTEGER,
			isdnTmrT304		INTEGER,
			isdnTmrT305		INTEGER,
			isdnTmrT306		INTEGER,
			isdnTmrT307		INTEGER,
			isdnTmrT308		INTEGER,
			isdnTmrT310		INTEGER,
			isdnTmrT311		INTEGER,
			isdnTmrT312		INTEGER,
			isdnTmrT313		INTEGER,
			isdnTmrT316		INTEGER,
			isdnTmrT318		INTEGER,
			isdnTmrT319		INTEGER,
			isdnTmrT322		INTEGER,
			isdnTmrT316C		INTEGER,
			isdnTmrT330		INTEGER,
			isdnTmrT331		INTEGER,
			isdnTmrT332		INTEGER,
			isdnTmrTRST		INTEGER,
			isdnTmrTREST		INTEGER,
			isdnTmrTANS		INTEGER,
			isdnTmrT396		INTEGER,
			isdnTmrT397		INTEGER,
			isdnTrnkTmrRowStatus		TmrRowStatus,
			isdnTrnkTmrOpStatus		OpStatus
			}

isdnTnkId		OBJECT-TYPE
			SYNTAX	INTEGER(1..65535)
			ACCESS	read-write
			STATUS	mandatory
			DESCRIPTION 
	"Trunk id.  "
			::= {	isdnTmrCfgEntry   1 }

isdnTmrT301		OBJECT-TYPE
			SYNTAX	INTEGER(180..420)
			UNITS "sec"
			ACCESS	read-write
			STATUS	mandatory
			DESCRIPTION 
	"T301 timer - alert received 
	Recommandation Q.931, TABLE 9-1/Q931 "
			DEFVAL { 180 }
			::= {	isdnTmrCfgEntry   2 }

isdnTmrT302		OBJECT-TYPE
			SYNTAX	INTEGER(0..15000)
			UNITS "ms"
			ACCESS	read-write
			STATUS	mandatory
			DESCRIPTION 
	"T302 timer - SETUP ACK sent Receipt of INFO 
	Recommandation Q.931, TABLE 9-1/Q931 "
			DEFVAL { 0 }
			::= {	isdnTmrCfgEntry   3 }

isdnTmrT303		OBJECT-TYPE
			SYNTAX	INTEGER(1000..4000)
			UNITS "ms"
			ACCESS	read-write
			STATUS	mandatory
			DESCRIPTION 
	"T303 timer - setup sent 
	Recommandation Q.931, TABLE 9-1/Q931. 
	Default Value is 4000 milliSeconds "
			DEFVAL { 4000 }
			::= {	isdnTmrCfgEntry   4 }

isdnTmrT304		OBJECT-TYPE
			SYNTAX	INTEGER(0..20000)
			UNITS "ms"
			ACCESS	read-write
			STATUS	mandatory
			DESCRIPTION 
	"T304 timer - setup ack received info sent alert 
	Recommandation Q.931, TABLE 9-1/Q931. 
	Default Value is 20000 milliSeconds "
			DEFVAL { 0 }
			::= {	isdnTmrCfgEntry   5 }

isdnTmrT305		OBJECT-TYPE
			SYNTAX	INTEGER(2000..60000)
			UNITS "ms"
			ACCESS	read-write
			STATUS	mandatory
			DESCRIPTION 
	"T305 timer - disc w/ prog ind sent or disc sent 
	Recommandation Q.931, TABLE 9-1/Q931. 
	Default Value is 30000 milliSeconds "
			DEFVAL { 30000 }
			::= {	isdnTmrCfgEntry   6 }

isdnTmrT306		OBJECT-TYPE
			SYNTAX	INTEGER(30..150)
			UNITS "sec"
			ACCESS	read-write
			STATUS	mandatory
			DESCRIPTION 
	"T306 timer - disc without prog ind sent 
	Recommandation Q.931, TABLE 9-1/Q931. 
	Default Value is 30000 milliSeconds "
			DEFVAL { 30 }
			::= {	isdnTmrCfgEntry   7 }

isdnTmrT307		OBJECT-TYPE
			SYNTAX	INTEGER(0..180)
			UNITS "sec"
			ACCESS	read-write
			STATUS	mandatory
			DESCRIPTION 
	"T307 timer - iusp ack sent 
	Recommandation Q.931, TABLE 9-1/Q931. 
	Default Value is 180000 milliSeconds "
			DEFVAL { 0 }
			::= {	isdnTmrCfgEntry   8 }

isdnTmrT308		OBJECT-TYPE
			SYNTAX	INTEGER(2000..10000)
			UNITS "ms"
			ACCESS	read-write
			STATUS	mandatory
			DESCRIPTION 
	"T308 timer - release sent 
	Recommandation Q.931, TABLE 9-1/Q931. 
	Default Value is 4000 milliSeconds "
			DEFVAL { 4000 }
			::= {	isdnTmrCfgEntry   9 }

isdnTmrT310		OBJECT-TYPE
			SYNTAX	INTEGER(3000..10000)
			UNITS "ms"
			ACCESS	read-write
			STATUS	mandatory
			DESCRIPTION 
	"T310 timer - call proc received 
	Recommandation Q.931, TABLE 9-1/Q931. 
	Default Value is 10000 milliSeconds "
			DEFVAL { 10000 }
			::= {	isdnTmrCfgEntry   10 }

isdnTmrT311		OBJECT-TYPE
			SYNTAX	INTEGER(0..65535)
			UNITS "ms"
			ACCESS	read-only
			STATUS	mandatory
			DESCRIPTION 
	"T310 timer - call proc received, not in the network side "
			::= {	isdnTmrCfgEntry   11 }

isdnTmrT312		OBJECT-TYPE
			SYNTAX	INTEGER(0..6000)
			UNITS "ms"
			ACCESS	read-write
			STATUS	mandatory
			DESCRIPTION 
	"T312 timer - setup sent on broadcast 
	Recommandation Q.931, TABLE 9-1/Q931. 
	Default Value is 6000 milliSeconds "
			DEFVAL { 0 }
			::= {	isdnTmrCfgEntry   12 }

isdnTmrT313		OBJECT-TYPE
			SYNTAX	INTEGER(0..65535)
			UNITS "ms"
			ACCESS	read-write
			STATUS	mandatory
			DESCRIPTION 
	"T313 timer - conn sent, not in BellCore network side "
			DEFVAL { 0 }
			::= {	isdnTmrCfgEntry   13 }

isdnTmrT316		OBJECT-TYPE
			SYNTAX	INTEGER(10..120)
			UNITS "sec"
			ACCESS	read-write
			STATUS	mandatory
			DESCRIPTION 
	"T316 timer - restart sent interface 
	Recommandation Q.931, TABLE 9-1/Q931. Default Value is 120000 milliSeconds "
			DEFVAL { 30 }
			::= {	isdnTmrCfgEntry   14 }

isdnTmrT318		OBJECT-TYPE
			SYNTAX	INTEGER(0..65535)
			UNITS "ms"
			ACCESS	read-write
			STATUS	mandatory
			DESCRIPTION 
	"T318 timer - resume sent, not in bellcore network side "
			DEFVAL { 0 }
			::= {	isdnTmrCfgEntry   15 }

isdnTmrT319		OBJECT-TYPE
			SYNTAX	INTEGER(0..65535)
			UNITS "ms"
			ACCESS	read-write
			STATUS	mandatory
			DESCRIPTION 
	"T319 timer - suspend sent, not in Bellcore network side "
			DEFVAL { 0 }
			::= {	isdnTmrCfgEntry   16 }

isdnTmrT322		OBJECT-TYPE
			SYNTAX	INTEGER(2000..10000)
			UNITS "ms"
			ACCESS	read-write
			STATUS	mandatory
			DESCRIPTION 
	"T322 timer - stat enq sent 
	Recommandation Q.931, TABLE 9-1/Q931. 
	Default Value is 4000 milliSeconds "
			DEFVAL { 4000 }
			::= {	isdnTmrCfgEntry   17 }

isdnTmrT316C		OBJECT-TYPE
			SYNTAX	INTEGER(30..120)
			UNITS "sec"
			ACCESS	read-only
			STATUS	mandatory
			DESCRIPTION 
	"T316c Timer -Restart sent to individual channel "
			DEFVAL { 30 }
			::= {	isdnTmrCfgEntry   18 }

isdnTmrT330		OBJECT-TYPE
			SYNTAX	INTEGER(0..65535)
			UNITS "ms"
			ACCESS	read-write
			STATUS	mandatory
			DESCRIPTION 
	"T330 Timer - Congestion with Upper "
			DEFVAL { 0 }
			::= {	isdnTmrCfgEntry   19 }

isdnTmrT331		OBJECT-TYPE
			SYNTAX	INTEGER(0..65535)
			UNITS "ms"
			ACCESS	read-write
			STATUS	mandatory
			DESCRIPTION 
	"T331 Timer - Congestion with lower "
			DEFVAL { 0 }
			::= {	isdnTmrCfgEntry   20 }

isdnTmrT332		OBJECT-TYPE
			SYNTAX	INTEGER(0..65535)
			UNITS "ms"
			ACCESS	read-write
			STATUS	mandatory
			DESCRIPTION 
	"T332 Timer - Service request sent "
			DEFVAL { 0 }
			::= {	isdnTmrCfgEntry   21 }

isdnTmrTRST		OBJECT-TYPE
			SYNTAX	INTEGER(30..600)
			UNITS "sec"
			ACCESS	read-only
			STATUS	mandatory
			DESCRIPTION 
	"TRst Timer - Disconnect indication sent while restarting interface "
			DEFVAL { 120 }
			::= {	isdnTmrCfgEntry   22 }

isdnTmrTREST		OBJECT-TYPE
			SYNTAX	INTEGER(30..600)
			UNITS "sec"
			ACCESS	read-write
			STATUS	mandatory
			DESCRIPTION 
	"TREST Timer - Disconnect indication sent while NI2 restarting interface "
			DEFVAL { 120 }
			::= {	isdnTmrCfgEntry   23 }

isdnTmrTANS		OBJECT-TYPE
			SYNTAX	INTEGER(1..65553)
			UNITS "ms"
			ACCESS	read-only
			STATUS	mandatory
			DESCRIPTION 
	"TAns Timer - Answer timer "
			::= {	isdnTmrCfgEntry   24 }

isdnTmrT396		OBJECT-TYPE
			SYNTAX	INTEGER(0..65535)
			UNITS "ms"
			ACCESS	read-write
			STATUS	mandatory
			DESCRIPTION 
	"T396 Timer - t303 expired "
			DEFVAL { 0 }
			::= {	isdnTmrCfgEntry   25 }

isdnTmrT397		OBJECT-TYPE
			SYNTAX	INTEGER(0..65535)
			UNITS "ms"
			ACCESS	read-write
			STATUS	mandatory
			DESCRIPTION 
	"T397 Timer - Information sent on permanent signal "
			DEFVAL { 0 }
			::= {	isdnTmrCfgEntry   26 }

isdnTrnkTmrRowStatus		OBJECT-TYPE
			SYNTAX	TmrRowStatus
			ACCESS	read-write
			STATUS	mandatory
			DESCRIPTION 
	"Current Status (configurational Status) of this Isdn Trunk Timer. 
	To Modify any Timer for this Trunk, the only option is 'MODIFYTIMER'. 
	For the 'GET' Operation, the possible options are 
	1) active 
	2) notinservice 
	3) notready 
	4) modified 
	5) up 
	6) do"
			::= {	isdnTmrCfgEntry   27 }

isdnTrnkTmrOpStatus		OBJECT-TYPE
			SYNTAX	OpStatus
			ACCESS	read-only
			STATUS	mandatory
			DESCRIPTION 
	"Current Status (Operational Status) of this Isdn Timer. 
	'SET' Operation is NOT APPLICABLE. 
	For the 'GET' Operation, the possible options are 
	1) active 
	2) down  "
			::= {	isdnTmrCfgEntry   28 }

 -- *************************************************     
 -- ISDN Trunk Config Table
 -- *************************************************     

isdnTrunkCfgTable		OBJECT-TYPE
			SYNTAX   SEQUENCE OF IsdnTrunkCfgEntry
			ACCESS	not-accessible
			STATUS	mandatory
			DESCRIPTION 
	"ISDN Trunk Table. Information about the ISDN Trunk(s) in MSSC are 
	provided in this table. The index of this table is isdnTrunkId (Integer) "
			::= { isdn	 2 }

isdnTrunkCfgEntry		OBJECT-TYPE
			SYNTAX	IsdnTrunkCfgEntry
			ACCESS	not-accessible
			STATUS	mandatory
			DESCRIPTION 
	"The Current Entry Containes all the objects for this Table. 
	This object is not-accessible, but the user can access all 
	the objects in this table at the next level. "
			INDEX { isdnTrunkId }
			::= {	isdnTrunkCfgTable   1 }

IsdnTrunkCfgEntry		::= SEQUENCE {
			isdnTrunkId		INTEGER,
			isdnTrunkName		NameString,
			isdnTrunkGrpId		INTEGER,
			isdnDchnlId		INTEGER,
			isdnTrunkType		IsdnType,
			isdnXconnectId		INTEGER,
			isdnSlotId		INTEGER,
			isdnPortId		INTEGER,
			isdnDirection		Direction,
			isdnPriority		IsdnPriority,
			isdnDurthreshold		INTEGER,
			isdnCntthreshold		INTEGER,
			isdnPhyIntfType		IfType,
			isdnDchnlTimeSlot		INTEGER,
			isdnE1MultiFrame		E1MultiFrame,
			isdnE1CRC4		E1CRC4,
			isdnE1TransClk		TransClkSrc,
			isdnDS1LineType		DS1LineType,
			isdnDS1LineCoding		DS1LineCoding,
			isdnDS1TransClkSrc		TransClkSrc,
			isdnDS1LBO		DS1LBO,
			isdnDS3LineType		DS3LineType,
			isdnDS3TransClkSrc		TransClkSrc,
			isdnDS3LBO		DS3LBO,
			isdnDS3DS1LineType		DS1LineType,
			isdnDS3DS1TransClkSrc		TransClkSrc,
			isdnTrunkRowStatus		RowStatus,
			isdnTrunkOpStatus		IsdnTrnkOpStatus
			}

isdnTrunkId		OBJECT-TYPE
			SYNTAX	INTEGER(1..65535)
			ACCESS	read-write
			STATUS	mandatory
			DESCRIPTION 
	"Trunk id. Can be any integer 1-65535. "
			::= {	isdnTrunkCfgEntry   1 }

isdnTrunkName		OBJECT-TYPE
			SYNTAX	NameString
			ACCESS	read-write
			STATUS	mandatory
			DESCRIPTION 
	"Trunk name. Can be any combinaton of alphanumeric characters. 
	Spaces are not allowed.  "
			::= {	isdnTrunkCfgEntry   2 }

isdnTrunkGrpId		OBJECT-TYPE
			SYNTAX	INTEGER(1..65535)
			ACCESS	read-write
			STATUS	mandatory
			DESCRIPTION 
	"Trunk Group id to which the trunk belongs. Can be any integer 1-65535. "
			::= {	isdnTrunkCfgEntry   3 }

isdnDchnlId		OBJECT-TYPE
			SYNTAX	INTEGER(1..65535)
			ACCESS	read-write
			STATUS	mandatory
			DESCRIPTION 
	"D-Channel Id "
			::= {	isdnTrunkCfgEntry   4 }

isdnTrunkType		OBJECT-TYPE
			SYNTAX	IsdnType
			ACCESS	read-write
			STATUS	mandatory
			DESCRIPTION 
	"Trunk Type (nfas/fas). "
			::= {	isdnTrunkCfgEntry   5 }

isdnXconnectId		OBJECT-TYPE
			SYNTAX	INTEGER(1..65535)
			ACCESS	read-write
			STATUS	mandatory
			DESCRIPTION 
	"Xconnect id "
			::= {	isdnTrunkCfgEntry   6 }

isdnSlotId		OBJECT-TYPE
			SYNTAX	INTEGER(1..65535)
			ACCESS	read-write
			STATUS	mandatory
			DESCRIPTION 
	"Slot id "
			::= {	isdnTrunkCfgEntry   7 }

isdnPortId		OBJECT-TYPE
			SYNTAX	INTEGER(1..65535)
			ACCESS	read-write
			STATUS	mandatory
			DESCRIPTION 
	"Port id "
			::= {	isdnTrunkCfgEntry   8 }

isdnDirection		OBJECT-TYPE
			SYNTAX	Direction
			ACCESS	read-write
			STATUS	mandatory
			DESCRIPTION 
	"Traffic direction. 
	possible options are 
	1) in 
	2) out 
	3) both "
			::= {	isdnTrunkCfgEntry   9 }

isdnPriority		OBJECT-TYPE
			SYNTAX	IsdnPriority
			ACCESS	read-write
			STATUS	mandatory
			DESCRIPTION 
	"Traffic priority "
			::= {	isdnTrunkCfgEntry   10 }

isdnDurthreshold		OBJECT-TYPE
			SYNTAX	INTEGER(1..65535)
			ACCESS	read-write
			STATUS	mandatory
			DESCRIPTION 
	"Bad Call Duration Threshold "
			::= {	isdnTrunkCfgEntry   11 }

isdnCntthreshold		OBJECT-TYPE
			SYNTAX	INTEGER(1..65535)
			ACCESS	read-write
			STATUS	mandatory
			DESCRIPTION 
	"Bad Call Count Threshold "
			::= {	isdnTrunkCfgEntry   12 }

isdnPhyIntfType		OBJECT-TYPE
			SYNTAX	IfType
			ACCESS	read-write
			STATUS	mandatory
			DESCRIPTION 
	"Isdn Physical Interface Type 
	possible options are 
	1) T1 (interface-t1) 
	2) T3 (interface-t3) 
	3) Unchannelized T3 (interface-ut3) 
	4) OC3 (interface-oc3) 
	5) Unchannelized T3 with compression (interface-ut3cp) 
	6) OC3 with compression (interface-oc3cp) "
			::= {	isdnTrunkCfgEntry   13 }

isdnDchnlTimeSlot		OBJECT-TYPE
			SYNTAX	INTEGER(1..65535)
			ACCESS	read-write
			STATUS	mandatory
			DESCRIPTION 
	"D-Channel Time slot "
			::= {	isdnTrunkCfgEntry   14 }

isdnE1MultiFrame		OBJECT-TYPE
			SYNTAX	E1MultiFrame
			ACCESS	read-write
			STATUS	mandatory
			DESCRIPTION 
	"E1 multiFrame Type possible options are 1) CAS(1) 2) CCS(2)"
			::= {	isdnTrunkCfgEntry   15 }

isdnE1CRC4		OBJECT-TYPE
			SYNTAX	E1CRC4
			ACCESS	read-write
			STATUS	mandatory
			DESCRIPTION 
	"E1 Cyclic Redundancy Code, possible options are 1) enabled(1) 2) disable(2)"
			::= {	isdnTrunkCfgEntry   16 }

isdnE1TransClk		OBJECT-TYPE
			SYNTAX	TransClkSrc
			ACCESS	read-write
			STATUS	mandatory
			DESCRIPTION 
	"E1 Transmit Clock Source, possible options are 1) loopTiming(1) 2) localTiming(2)"
			::= {	isdnTrunkCfgEntry   17 }

isdnDS1LineType		OBJECT-TYPE
			SYNTAX	DS1LineType
			ACCESS	read-write
			STATUS	mandatory
			DESCRIPTION 
	"DS1 Line Type possible options are 1) esF(1) 2) d4(2)"
			::= {	isdnTrunkCfgEntry   18 }

isdnDS1LineCoding		OBJECT-TYPE
			SYNTAX	DS1LineCoding
			ACCESS	read-write
			STATUS	mandatory
			DESCRIPTION 
	"DS1 Line Coding, possible options are 1) b8zs(1) 2) ami(2)"
			::= {	isdnTrunkCfgEntry   19 }

isdnDS1TransClkSrc		OBJECT-TYPE
			SYNTAX	TransClkSrc
			ACCESS	read-write
			STATUS	mandatory
			DESCRIPTION 
	"DS1 Transmit Clock Source, possible options are 1) loopTiming(1) 2) localTiming(2)"
			::= {	isdnTrunkCfgEntry   20 }

isdnDS1LBO		OBJECT-TYPE
			SYNTAX	DS1LBO
			ACCESS	read-write
			STATUS	mandatory
			DESCRIPTION 
	"DS1 Line Build Out, possible options are 1) upTo133Feet(1) 2) upTo266Feet(2) 3) upTo399Feet(3) 4) upTo533Feet(4) 5) upTo655Feet(5) 6) negative7_5Db(6) 7) negative15Db(7) 8) negative22_5Db(8)"
			::= {	isdnTrunkCfgEntry   21 }

isdnDS3LineType		OBJECT-TYPE
			SYNTAX	DS3LineType
			ACCESS	read-write
			STATUS	mandatory
			DESCRIPTION 
	"DS3 Line Type possible options are 1) cbitParity(1) 2) clearChannel(2)"
			::= {	isdnTrunkCfgEntry   22 }

isdnDS3TransClkSrc		OBJECT-TYPE
			SYNTAX	TransClkSrc
			ACCESS	read-write
			STATUS	mandatory
			DESCRIPTION 
	"DS3 Transmit Clock Source, possible options are 1) loopTiming(1) 2) localTiming(2)"
			::= {	isdnTrunkCfgEntry   23 }

isdnDS3LBO		OBJECT-TYPE
			SYNTAX	DS3LBO
			ACCESS	read-write
			STATUS	mandatory
			DESCRIPTION 
	"DS3 Line Build Out possible options are 1) short(1) 2) long(2)"
			::= {	isdnTrunkCfgEntry   24 }

isdnDS3DS1LineType		OBJECT-TYPE
			SYNTAX	DS1LineType
			ACCESS	read-write
			STATUS	mandatory
			DESCRIPTION 
	"DS3DS1 Line Type possible options are 1) esF(1) 2) d4(2)"
			::= {	isdnTrunkCfgEntry   25 }

isdnDS3DS1TransClkSrc		OBJECT-TYPE
			SYNTAX	TransClkSrc
			ACCESS	read-write
			STATUS	mandatory
			DESCRIPTION 
	"DS3DS1 Transmit Clock Source, possible options are 1) loopTiming(1) 2) localTiming(2)"
			::= {	isdnTrunkCfgEntry   26 }

isdnTrunkRowStatus		OBJECT-TYPE
			SYNTAX	RowStatus
			ACCESS	read-write
			STATUS	mandatory
			DESCRIPTION 
	"Current Status (configurational Status) of this ISDN TRUNK. 
	To Configure this Link, the only option is 'CREATEANDWAIT' 
	To Delete this Link, the only option is 'DESTROY' 
	For the 'GET' Operation, the possible options are 
	1) active 
	2) notinservice 
	3) n"
			::= {	isdnTrunkCfgEntry   27 }

isdnTrunkOpStatus		OBJECT-TYPE
			SYNTAX	IsdnTrnkOpStatus
			ACCESS	read-only
			STATUS	mandatory
			DESCRIPTION 
	"Current Status (Operational Status) of this ISDN Trunk. 
	'SET' Operation is NOT APPLICABLE. 
	For the 'GET' Operation, the possible options are 
	1) active 
	2) down 
	3) disable "
			::= {	isdnTrunkCfgEntry   28 }

 -- *************************************************     
 -- ISDN Channel status Table
 -- *************************************************     

isdnChnlStatusTable		OBJECT-TYPE
			SYNTAX   SEQUENCE OF IsdnChnlStatusCfgEntry
			ACCESS	not-accessible
			STATUS	mandatory
			DESCRIPTION 
	"ISDN Channel Status Table. Information about the DS0 
	Channel(s) Status in MSSC are provided in this table. 
	The index of this table is isdnStatusTrunkId (Integer) "
			::= { isdn	 3 }

isdnChnlStatusCfgEntry		OBJECT-TYPE
			SYNTAX	IsdnChnlStatusCfgEntry
			ACCESS	not-accessible
			STATUS	mandatory
			DESCRIPTION 
	"The Current Entry Containes all the objects for this Table. 
	This object is not-accessible, but the user can access all 
	the objects in this table at the next level. "
			INDEX { isdnStatusTrunkId, isdnStatusChnlId }
			::= {	isdnChnlStatusTable   1 }

IsdnChnlStatusCfgEntry		::= SEQUENCE {
			isdnStatusTrunkId		INTEGER,
			isdnStatusChnlId		INTEGER,
			isdnStatusChnlState		TrunkState,
			isdnStatusChnlAllocMeth		INTEGER,
			isdnStatusChnlSuConnId		INTEGER
			}

isdnStatusTrunkId		OBJECT-TYPE
			SYNTAX	INTEGER(1..65535)
			ACCESS	read-only
			STATUS	mandatory
			DESCRIPTION 
			""
			::= {	isdnChnlStatusCfgEntry   1 }

isdnStatusChnlId		OBJECT-TYPE
			SYNTAX	INTEGER(1..65535)
			ACCESS	read-only
			STATUS	mandatory
			DESCRIPTION 
	"Channel id. "
			::= {	isdnChnlStatusCfgEntry   2 }

isdnStatusChnlState		OBJECT-TYPE
			SYNTAX	TrunkState
			ACCESS	read-only
			STATUS	mandatory
			DESCRIPTION 
	"Isdn Channel String. "
			::= {	isdnChnlStatusCfgEntry   3 }

isdnStatusChnlAllocMeth		OBJECT-TYPE
			SYNTAX	INTEGER(1..65535)
			ACCESS	read-only
			STATUS	mandatory
			DESCRIPTION 
	"Isdn Channel AllocMeth. "
			::= {	isdnChnlStatusCfgEntry   4 }

isdnStatusChnlSuConnId		OBJECT-TYPE
			SYNTAX	INTEGER(1..65535)
			ACCESS	read-only
			STATUS	mandatory
			DESCRIPTION 
	"Isdn Channel SuConnId. "
			::= {	isdnChnlStatusCfgEntry   5 }

 -- *************************************************     
 -- Isdn mangment command Group
 -- *************************************************     

isdnMgmntGroup		OBJECT IDENTIFIER   ::=	{ isdn	 4 }

 -- *************************************************     
 -- Isdn Trunk management table
 -- *************************************************     

isdnTrnkMgmntTable		OBJECT-TYPE
			SYNTAX   SEQUENCE OF IsdnTrnkMgmntEntry
			ACCESS	not-accessible
			STATUS	mandatory
			DESCRIPTION 
	"ISDN Trunk Management Table. The Management Commands for ISDN Trunk(s) 
	in MSSC are provided in this table. This table has the index isdnTrnkMgmntId (Integer). "
			::= { isdnMgmntGroup	 1 }

isdnTrnkMgmntEntry		OBJECT-TYPE
			SYNTAX	IsdnTrnkMgmntEntry
			ACCESS	not-accessible
			STATUS	mandatory
			DESCRIPTION 
	"The Current Entry Containes all the objects for this Table. 
	This object is not-accessible, but the user can access all 
	the objects in this table at the next level. "
			INDEX { isdnTrnkMgmntId }
			::= {	isdnTrnkMgmntTable   1 }

IsdnTrnkMgmntEntry		::= SEQUENCE {
			isdnTrnkMgmntId		INTEGER,
			isdnTrnkMgmntCmd		IsdnTrnkMgtOperation
			}

isdnTrnkMgmntId		OBJECT-TYPE
			SYNTAX	INTEGER
			ACCESS	read-only
			STATUS	mandatory
			DESCRIPTION 
	"Trunk id. "
			::= {	isdnTrnkMgmntEntry   1 }

isdnTrnkMgmntCmd		OBJECT-TYPE
			SYNTAX	IsdnTrnkMgtOperation
			ACCESS	read-write
			STATUS	mandatory
			DESCRIPTION 
	"Management Command for Enabling/Disabling the specified 
	trunk group. This command will make all the channels in this 
	trunk available 
	The possible options are : 
	1) Enable 
	2) Disable [default] "
			::= {	isdnTrnkMgmntEntry   2 }

 -- *************************************************     
 -- Isdn Channel management Table
 -- *************************************************     

isdnChnlMgmntTable		OBJECT-TYPE
			SYNTAX   SEQUENCE OF IsdnChnlMgmntEntry
			ACCESS	not-accessible
			STATUS	mandatory
			DESCRIPTION 
	"ISDN Trunk Channel Management Table. The Management Commands for ISDN Trunk(s) 
	in MSSC are provided in this table. This table has the index isdnTrunkMgmntId (Integer). "
			::= { isdnMgmntGroup	 2 }

isdnChnlMgmntEntry		OBJECT-TYPE
			SYNTAX	IsdnChnlMgmntEntry
			ACCESS	not-accessible
			STATUS	mandatory
			DESCRIPTION 
	"The Current Entry Containes all the objects for this Table. 
	This object is not-accessible, but the user can access all 
	the objects in this table at the next level. "
			INDEX { isdnTrunkMgmntId, isdnChnlMgmntId }
			::= {	isdnChnlMgmntTable   1 }

IsdnChnlMgmntEntry		::= SEQUENCE {
			isdnTrunkMgmntId		INTEGER,
			isdnChnlMgmntId		INTEGER,
			isdnChnlMgmntCmd		IsdnChnlMgtOperation
			}

isdnTrunkMgmntId		OBJECT-TYPE
			SYNTAX	INTEGER
			ACCESS	read-only
			STATUS	mandatory
			DESCRIPTION 
	"Trunk id. "
			::= {	isdnChnlMgmntEntry   1 }

isdnChnlMgmntId		OBJECT-TYPE
			SYNTAX	INTEGER
			ACCESS	read-only
			STATUS	mandatory
			DESCRIPTION 
	"Channel id. "
			::= {	isdnChnlMgmntEntry   2 }

isdnChnlMgmntCmd		OBJECT-TYPE
			SYNTAX	IsdnChnlMgtOperation
			ACCESS	read-write
			STATUS	mandatory
			DESCRIPTION 
	"Management Command for Enabling/Disabling the specified 
	Channel in the specified trunk. 
	The possible options are : 
	1) Enable 
	2) Disable [default] "
			::= {	isdnChnlMgmntEntry   3 }

 -- *************************************************     
 -- MFD Managment table
 -- *************************************************     

mfdMgmntTable		OBJECT-TYPE
			SYNTAX   SEQUENCE OF MfdMgmntEntry
			ACCESS	not-accessible
			STATUS	mandatory
			DESCRIPTION 
	"Modem Fault Management Table. The Management Commands for Modem(s) in MSSC 
	are provided in this table. This table has the index isdnTnkMgmntId (Integer). "
			::= { isdnMgmntGroup	 3 }

mfdMgmntEntry		OBJECT-TYPE
			SYNTAX	MfdMgmntEntry
			ACCESS	not-accessible
			STATUS	mandatory
			DESCRIPTION 
	"The Current Entry Containes all the objects for this Table. 
	This object is not-accessible, but the user can access all 
	the objects in this table at the next level. "
			INDEX { isdnTnkMgmntId }
			::= {	mfdMgmntTable   1 }

MfdMgmntEntry		::= SEQUENCE {
			isdnTnkMgmntId		INTEGER,
			isdnDurThreshold		INTEGER,
			isdnCntThreshold		INTEGER,
			mfdMgmntCmd		EnableOperation
			}

isdnTnkMgmntId		OBJECT-TYPE
			SYNTAX	INTEGER
			ACCESS	read-only
			STATUS	mandatory
			DESCRIPTION 
	"Isdn Trunk id. "
			::= {	mfdMgmntEntry   1 }

isdnDurThreshold		OBJECT-TYPE
			SYNTAX	INTEGER(1..65535)
			ACCESS	read-write
			STATUS	mandatory
			DESCRIPTION 
	"Bad Call Duration Threshold. 
	A value 0 means disable. 
	If mfd is enabled the normal value for this field would be 3 "
			::= {	mfdMgmntEntry   2 }

isdnCntThreshold		OBJECT-TYPE
			SYNTAX	INTEGER(1..65535)
			ACCESS	read-write
			STATUS	mandatory
			DESCRIPTION 
	"Bad Call Count Threshold 
	A value 0 means disable. 
	If mfd is enabled the normal value for this field would be 3 "
			::= {	mfdMgmntEntry   3 }

mfdMgmntCmd		OBJECT-TYPE
			SYNTAX	EnableOperation
			ACCESS	read-write
			STATUS	mandatory
			DESCRIPTION 
	"Management Command for Enabling/Disabling 'MODEM FAULT DETECTION' feature in MSSC. 
	The possible options are : 
	1) Enable 
	2) Disable [default] "
			::= {	mfdMgmntEntry   4 }

 -- *************************************************     
 -- Isdn Physical Interface Configuration Table
 -- *************************************************     

 -- *************************************************     
 -- Route Config Table
 -- *************************************************     

routeTable		OBJECT-TYPE
			SYNTAX   SEQUENCE OF RouteEntry
			ACCESS	not-accessible
			STATUS	mandatory
			DESCRIPTION 
	"Route Table. Information about the Route(s) in MSSC are 
	provided in this table. The index of this table is routeId (Integer) "
			::= { rt	 1 }

routeEntry		OBJECT-TYPE
			SYNTAX	RouteEntry
			ACCESS	not-accessible
			STATUS	mandatory
			DESCRIPTION 
	"The Current Entry Containes all the objects for this Table. 
	This object is not-accessible, but the user can access all 
	the objects in this table at the next level. "
			INDEX { routeId }
			::= {	routeTable   1 }

RouteEntry		::= SEQUENCE {
			routeId		INTEGER,
			routeAddrType		AddrType,
			routeAdrId		AddrIdentifier,
			routeAddr		AddrString,
			routeNumPlan		NumPlan,
			routeNumOfDigit		INTEGER,
			routeRouteName		NameString,
			routeRouteType		RouteType,
			routeRowStatus		RowStatus,
			routeOpStatus		OpStatus
			}

routeId		OBJECT-TYPE
			SYNTAX	INTEGER(1..65535)
			ACCESS	read-write
			STATUS	mandatory
			DESCRIPTION 
	"Route Group id. Can be any integer 1-65535. "
			::= {	routeEntry   1 }

routeAddrType		OBJECT-TYPE
			SYNTAX	AddrType
			ACCESS	read-write
			STATUS	mandatory
			DESCRIPTION 
	"Call Control routing type 
	The possible option are: 
	1) Call party number 
	2) Transit Network Selection  "
			::= {	routeEntry   2 }

routeAdrId		OBJECT-TYPE
			SYNTAX	AddrIdentifier
			ACCESS	read-write
			STATUS	mandatory
			DESCRIPTION 
	"Call Control route request nature of address. 
	The possible options are: 
	1) National number 
	2) International number 
	3) Unknown  "
			::= {	routeEntry   3 }

routeAddr		OBJECT-TYPE
			SYNTAX	AddrString
			ACCESS	read-write
			STATUS	mandatory
			DESCRIPTION 
	"Call Control routing number "
			::= {	routeEntry   4 }

routeNumPlan		OBJECT-TYPE
			SYNTAX	NumPlan
			ACCESS	read-write
			STATUS	mandatory
			DESCRIPTION 
	"Call control route request numbering plan. 
	The possible options are: 
	1) Number not present(nonumber) 
	2) ISDN numbering Plan(isdnnumplan) 
	3) Telephony numbering plan(telephonynumplan) 
	4) Private Numbering Plan(privatenumplan) "
			::= {	routeEntry   5 }

routeNumOfDigit		OBJECT-TYPE
			SYNTAX	INTEGER(1..65535)
			ACCESS	read-write
			STATUS	mandatory
			DESCRIPTION 
	"Number of Digit in the route. "
			::= {	routeEntry   6 }

routeRouteName		OBJECT-TYPE
			SYNTAX	NameString
			ACCESS	read-write
			STATUS	mandatory
			DESCRIPTION 
	"Route Name. Can be any combination of alphanumeric characters. 
	Spaces are not allowed.  "
			::= {	routeEntry   7 }

routeRouteType		OBJECT-TYPE
			SYNTAX	RouteType
			ACCESS	read-write
			STATUS	mandatory
			DESCRIPTION 
	"Route type: SS7/ISDN "
			::= {	routeEntry   8 }

routeRowStatus		OBJECT-TYPE
			SYNTAX	RowStatus
			ACCESS	read-write
			STATUS	mandatory
			DESCRIPTION 
	"Current Status (configurational Status) of this ROUTE. 
	To Configure this Route, the only option is 'CREATEANDWAIT' 
	To Delete this Route, the only option is 'DESTROY' 
	For the 'GET' Operation, the possible options are 
	1) active 
	2) notinservice 
	3) notr"
			::= {	routeEntry   9 }

routeOpStatus		OBJECT-TYPE
			SYNTAX	OpStatus
			ACCESS	read-only
			STATUS	mandatory
			DESCRIPTION 
	"Current Status (Operational Status) of this Route. 
	'SET' Operation is NOT APPLICABLE. 
	For the 'GET' Operation, the possible options are 
	1) active 
	2) down  "
			::= {	routeEntry   10 }

 -- *************************************************     
 -- CC Route ISDN Configuration Table
 -- *************************************************     

rtEntryIsdnCfgTable		OBJECT-TYPE
			SYNTAX   SEQUENCE OF RtEntryIsdnCfgEntry
			ACCESS	not-accessible
			STATUS	mandatory
			DESCRIPTION 
	"RtEntry Isdn Table. Information about the RtEntry(s) in MSSC are 
	provided in this table.The Table has two indices: 
	rtEntryIsdnGrpId and rtEntryIsdntrunkId (both Integer). "
			::= { rt	 2 }

rtEntryIsdnCfgEntry		OBJECT-TYPE
			SYNTAX	RtEntryIsdnCfgEntry
			ACCESS	not-accessible
			STATUS	mandatory
			DESCRIPTION 
	"The Current Entry Containes all the objects for this Table. 
	This object is not-accessible, but the user can access all 
	the objects in this table at the next level. "
			INDEX { rtEntryIsdnGrpId, rtEntryIsdntrunkId }
			::= {	rtEntryIsdnCfgTable   1 }

RtEntryIsdnCfgEntry		::= SEQUENCE {
			rtEntryIsdnGrpId		INTEGER,
			rtEntryIsdntrunkId		INTEGER,
			rtEntryIsdnRouteName		NameString,
			rtEntryIsdnRowStatus		RowStatus,
			rtEntryIsdnOpStatus		OpStatus
			}

rtEntryIsdnGrpId		OBJECT-TYPE
			SYNTAX	INTEGER(1..65535)
			ACCESS	read-write
			STATUS	mandatory
			DESCRIPTION 
	"Route ISDN group id. Can be any integer 1-65535. "
			::= {	rtEntryIsdnCfgEntry   1 }

rtEntryIsdntrunkId		OBJECT-TYPE
			SYNTAX	INTEGER(1..256)
			ACCESS	read-write
			STATUS	mandatory
			DESCRIPTION 
	"Route ISDN Trunk id. Can be any integer 1-256. "
			::= {	rtEntryIsdnCfgEntry   2 }

rtEntryIsdnRouteName		OBJECT-TYPE
			SYNTAX	NameString
			ACCESS	read-write
			STATUS	mandatory
			DESCRIPTION 
	"Route ISDN group name. Can be any combination of alphanumeric characters. 
	Spaces are not allowed and cannot exceed 15 characters. "
			::= {	rtEntryIsdnCfgEntry   3 }

rtEntryIsdnRowStatus		OBJECT-TYPE
			SYNTAX	RowStatus
			ACCESS	read-write
			STATUS	mandatory
			DESCRIPTION 
	"Current Status (configurational Status) of this ISDN ROUTE Entry. 
	To Configure this Link, the only option is 'CREATEANDWAIT' 
	To Delete this Link, the only option is 'DESTROY' 
	For the 'GET' Operation, the possible options are 
	1) active 
	2) notinservice"
			::= {	rtEntryIsdnCfgEntry   4 }

rtEntryIsdnOpStatus		OBJECT-TYPE
			SYNTAX	OpStatus
			ACCESS	read-only
			STATUS	mandatory
			DESCRIPTION 
	"Current Status (Operational Status) of this ISDN Route. 
	'SET' Operation is NOT APPLICABLE. 
	For the 'GET' Operation, the possible options are 
	1) active 
	2) down  "
			::= {	rtEntryIsdnCfgEntry   5 }

 -- *************************************************     
 -- CC RTEntry SS7 Configuration Table
 -- *************************************************     

rtEntrySs7CfgTable		OBJECT-TYPE
			SYNTAX   SEQUENCE OF RtEntrySs7CfgEntry
			ACCESS	not-accessible
			STATUS	mandatory
			DESCRIPTION 
	"RtEntry SS7 Table. Information about the RtEntry(s) in MSSC are 
	provided in this table.The Table has two indices: 
	rtEntrySs7GrpId and rtEntrySs7CmbLinksetId (both Integer). "
			::= { rt	 3 }

rtEntrySs7CfgEntry		OBJECT-TYPE
			SYNTAX	RtEntrySs7CfgEntry
			ACCESS	not-accessible
			STATUS	mandatory
			DESCRIPTION 
	"The Current Entry Containes all the objects for this Table. 
	This object is not-accessible, but the user can access all 
	the objects in this table at the next level. "
			INDEX { rtEntrySs7GrpId, rtEntrySs7CmbLinksetId }
			::= {	rtEntrySs7CfgTable   1 }

RtEntrySs7CfgEntry		::= SEQUENCE {
			rtEntrySs7GrpId		INTEGER,
			rtEntrySs7CmbLinksetId		INTEGER,
			rtEntrySs7RouteName		NameString,
			rtEntrySs7Dpc		INTEGER,
			rtEntrySs7Mode		Standard,
			rtEntrySs7RowStatus		RowStatus,
			rtEntrySs7OpStatus		OpStatus
			}

rtEntrySs7GrpId		OBJECT-TYPE
			SYNTAX	INTEGER(1..65535)
			ACCESS	read-write
			STATUS	mandatory
			DESCRIPTION 
	"Route SS7 group id. Can be any integer 1-65535. "
			::= {	rtEntrySs7CfgEntry   1 }

rtEntrySs7CmbLinksetId		OBJECT-TYPE
			SYNTAX	INTEGER(1..65535)
			ACCESS	read-write
			STATUS	mandatory
			DESCRIPTION 
	"SS7 Linkset Id which is already configured so far. 
	An incorrect Linkset Id will result a failure at 
	the time of 'CREATION' of the RtEntry ie, addition 
	of the Destination Point Code into the specified 
	Route will fail. "
			::= {	rtEntrySs7CfgEntry   2 }

rtEntrySs7RouteName		OBJECT-TYPE
			SYNTAX	NameString
			ACCESS	read-write
			STATUS	mandatory
			DESCRIPTION 
	"Route SS7 group name. Can be any combination of alphanumeric characters 
	Spaces are not allowed and cannot exceed 15 characters. "
			::= {	rtEntrySs7CfgEntry   3 }

rtEntrySs7Dpc		OBJECT-TYPE
			SYNTAX	INTEGER(1..16777215)
			ACCESS	read-write
			STATUS	mandatory
			DESCRIPTION 
	"Route SS7 Destination Point Code (The Integer Value). 
	The Point Code should be converted into its Integer 
	equivalent. For Example: 
	0-1-1 is converted as 257 (for ANSI) 
	0-1-2 is converted as 10 (for ITU) "
			::= {	rtEntrySs7CfgEntry   4 }

rtEntrySs7Mode		OBJECT-TYPE
			SYNTAX	Standard
			ACCESS	read-write
			STATUS	mandatory
			DESCRIPTION 
	"Route SS7 Type(ANSI/ITU) "
			::= {	rtEntrySs7CfgEntry   5 }

rtEntrySs7RowStatus		OBJECT-TYPE
			SYNTAX	RowStatus
			ACCESS	read-write
			STATUS	mandatory
			DESCRIPTION 
	"Current Status (configurational Status) of this SS7 Route Entry. 
	To Configure this Link, the only option is 'CREATEANDWAIT' 
	To Delete this Link, the only option is 'DESTROY' 
	For the 'GET' Operation, the possible options are 
	1) active 
	2) notinservice "
			::= {	rtEntrySs7CfgEntry   6 }

rtEntrySs7OpStatus		OBJECT-TYPE
			SYNTAX	OpStatus
			ACCESS	read-only
			STATUS	mandatory
			DESCRIPTION 
	"Current Status (Operational Status) of this SS7 Route. 
	'SET' Operation is NOT APPLICABLE. 
	For the 'GET' Operation, the possible options are 
	1) active 
	2) down  "
			::= {	rtEntrySs7CfgEntry   7 }

 -- *************************************************     
 -- Route Management table
 -- *************************************************     

routeMgmntCmdGroup		OBJECT IDENTIFIER   ::=	{ rt	 4 }

 -- *************************************************     
 -- Rout Management Table
 -- *************************************************     

digitStripMgmntTable		OBJECT-TYPE
			SYNTAX   SEQUENCE OF DigitStripMgmntEntry
			ACCESS	not-accessible
			STATUS	mandatory
			DESCRIPTION 
	"Route Management Command Table. Commands for enabling or disabling 
	digit stripping in MSSC's routing feature are applied here. 
	The index for this table is rtName(String). "
			::= { routeMgmntCmdGroup	 1 }

digitStripMgmntEntry		OBJECT-TYPE
			SYNTAX	DigitStripMgmntEntry
			ACCESS	not-accessible
			STATUS	mandatory
			DESCRIPTION 
	"The Current Entry Containes all the objects for this Table. 
	This object is not-accessible, but the user can access all 
	the objects in this table at the next level. "
			INDEX { rtName }
			::= {	digitStripMgmntTable   1 }

DigitStripMgmntEntry		::= SEQUENCE {
			rtName		NameString,
			rtAddrType		AddrIdentifier,
			rtNumOfDigit		INTEGER,
			rtMgmntCmd		EnableOperation
			}

rtName		OBJECT-TYPE
			SYNTAX	NameString
			ACCESS	read-only
			STATUS	mandatory
			DESCRIPTION 
	"Route Name. Can be any combination of alphanumeric characters. 
	Spaces are not allowed.  "
			::= {	digitStripMgmntEntry   1 }

rtAddrType		OBJECT-TYPE
			SYNTAX	AddrIdentifier
			ACCESS	read-write
			STATUS	mandatory
			DESCRIPTION 
	"Call Control route request nature of address. 
	The possible options are: 
	1) National number 
	2) International number 
	3) Unknown  "
			::= {	digitStripMgmntEntry   2 }

rtNumOfDigit		OBJECT-TYPE
			SYNTAX	INTEGER(1..65535)
			ACCESS	read-write
			STATUS	mandatory
			DESCRIPTION 
	"Number of Digit in the route. "
			::= {	digitStripMgmntEntry   3 }

rtMgmntCmd		OBJECT-TYPE
			SYNTAX	EnableOperation
			ACCESS	read-write
			STATUS	mandatory
			DESCRIPTION 
	"Management Command for Enabling/Disabling Digit Strip 
	for MSSC's Routing Feature. 
	The possible options are : 
	1) Enable 
	2) Disable [default] "
			::= {	digitStripMgmntEntry   4 }

 -- *************************************************     
 -- Route Management Table ( ILB)
 -- *************************************************     

isdnLoadBalanceMgmntTable		OBJECT-TYPE
			SYNTAX   SEQUENCE OF IsdnLoadBalanceMgmntEntry
			ACCESS	not-accessible
			STATUS	mandatory
			DESCRIPTION 
	"Isdn Channel Load Balance Command Table. Turning this feature on will 
	result in distributing all the incoming calls evenly in all the trunks 
	for the specified route number. 
	The index for this table is rteName(String). "
			::= { routeMgmntCmdGroup	 2 }

isdnLoadBalanceMgmntEntry		OBJECT-TYPE
			SYNTAX	IsdnLoadBalanceMgmntEntry
			ACCESS	not-accessible
			STATUS	mandatory
			DESCRIPTION 
	"The Current Entry Containes all the objects for this Table. 
	This object is not-accessible, but the user can access all 
	the objects in this table at the next level. "
			INDEX { rteName }
			::= {	isdnLoadBalanceMgmntTable   1 }

IsdnLoadBalanceMgmntEntry		::= SEQUENCE {
			rteName		NameString,
			ilbMgmntCmd		EnableOperation
			}

rteName		OBJECT-TYPE
			SYNTAX	NameString
			ACCESS	read-write
			STATUS	mandatory
			DESCRIPTION 
	"Route Name. Can be any combination of alphanumeric characters. 
	Spaces are not allowed.  "
			::= {	isdnLoadBalanceMgmntEntry   1 }

ilbMgmntCmd		OBJECT-TYPE
			SYNTAX	EnableOperation
			ACCESS	read-write
			STATUS	mandatory
			DESCRIPTION 
	"Management Command for Enabling/Disabling the feature 
	'ISDN Channel LOAD BALANCE'. When this feature is turned on 
	all the incoming calls are distributed evenly in all the 
	trunks for the specified routing numbers. 
	The possible options are : 
	1) Enable "
			::= {	isdnLoadBalanceMgmntEntry   2 }

 -- *************************************************     
 -- Enable Group
 -- *************************************************     

enableSwitch		OBJECT-TYPE
			SYNTAX	EnableStatus
			ACCESS	read-write
			STATUS	mandatory
			DESCRIPTION 
	"This is POST-CONFIGURATION command to 
	ENABLE the switch. The 'GET' operation 
	will result in the default value (no) 
	being returned. The possible options are: 
	1) yes 
	2) no (Default) "
			::= {	enableGroup   1 }

enableSS7Route		OBJECT-TYPE
			SYNTAX	EnableStatus
			ACCESS	read-write
			STATUS	mandatory
			DESCRIPTION 
	"This is POST-CONFIGURATION command to 
	ENABLE the SS7 Route. The 'GET' operation will result in the 
	default value (no) being returned. The possible options are: 
	1) yes 
	2) no (Default) "
			::= {	enableGroup   2 }

enableSS7Ckt		OBJECT-TYPE
			SYNTAX	EnableStatus
			ACCESS	read-write
			STATUS	mandatory
			DESCRIPTION 
	"This is POST-CONFIGURATION command to 
	ENABLE the SS7 Circuit. This Command can only be applied 
	to Enable the SS7 Circuit and COMMIT all the SS7 Circuit Configuration. 
	The 'GET' operation will result in the default value (no) being 
	returned. The possib"
			::= {	enableGroup   3 }

enableIsdntrunk		OBJECT-TYPE
			SYNTAX	EnableStatus
			ACCESS	read-write
			STATUS	mandatory
			DESCRIPTION 
	"This is POST-CONFIGURATION command to 
	ENABLE the ISDN Trunk. This Command can only be applied 
	to Enable the ISDN Trunk. The 'GET' operation will result in the 
	default value (no) being returned. The possible options are: 
	1) yes 
	2) no (Default) "
			::= {	enableGroup   4 }

enableXconnect		OBJECT-TYPE
			SYNTAX	EnableStatus
			ACCESS	read-write
			STATUS	mandatory
			DESCRIPTION 
	"This is POST-CONFIGURATION command to ENABLE the Xconnect. 
	The 'GET' operation will result in the default value (no) being 
	returned. The possible options are: 
	1) yes 
	2) no (Default) "
			::= {	enableGroup   5 }

enableRoute		OBJECT-TYPE
			SYNTAX	EnableStatus
			ACCESS	read-write
			STATUS	mandatory
			DESCRIPTION 
	"This is POST-CONFIGURATION command to 
	ENABLE the ROUTE and COMMIT all the configuration 
	set for MTP2. This Command can only be applied to Enable the XConnect. 
	The 'GET' operation will result in the default value (no) being returned. 
	The possible optio"
			::= {	enableGroup   6 }

 -- *************************************************     
 -- meas file group
 -- *************************************************     

measFileInfo		OBJECT IDENTIFIER   ::=	{ measFile	 1 }

measFileConfig		OBJECT IDENTIFIER   ::=	{ measFile	 2 }

measFileEnableGrp		OBJECT IDENTIFIER   ::=	{ measFile	 3 }

 -- *************************************************     
 -- MeasureMent File Info
 -- *************************************************     

measFileAcknowledge		OBJECT-TYPE
			SYNTAX	DisplayString(SIZE(1..255))
			ACCESS	read-write
			STATUS	mandatory
			DESCRIPTION 
	"Acknowledgement of the receiving of the specified Measurement file  "
			::= {	measFileInfo   1 }

measFileCfgMeasInterval		OBJECT-TYPE
			SYNTAX	INTEGER(0..60)
			ACCESS	read-write
			STATUS	mandatory
			DESCRIPTION 
	"Switch Config Measure Interval. 
	The duration of the collection window (frequency of persisting 
	collected measurements). 
	Default: 15 minutes. 
	Valid Values: 15, 30, 60 minutes. 0 for Disable. "
			::= {	measFileConfig   1 }

measFileCfgUsagescanInterval		OBJECT-TYPE
			SYNTAX	INTEGER(5..300)
			ACCESS	read-write
			STATUS	mandatory
			DESCRIPTION 
	"Switch Config Usage Scan Interval. 
	The interval between scanning the trunk for usage counts. 
	Default: 15 seconds 
	Valid Values: 5 through 300 seconds.  "
			::= {	measFileConfig   2 }

measFileCfgPurgeDay		OBJECT-TYPE
			SYNTAX	INTEGER(0..30)
			ACCESS	read-write
			STATUS	mandatory
			DESCRIPTION 
	"File Config Purge Day. 
	After The specified no of days the file in secondary directory are 
	purged if Measurement File Auto Purge Flag is on. "
			::= {	measFileConfig   3 }

measFileCfgPurgeFlag		OBJECT-TYPE
			SYNTAX	MeasPurgeFlag
			ACCESS	read-write
			STATUS	mandatory
			DESCRIPTION 
	"File Config Flag. 
	This is an auto purge flag. "
			::= {	measFileConfig   4 }

measFileCfgPrimaryDir		OBJECT-TYPE
			SYNTAX	DisplayString
			ACCESS	read-only
			STATUS	mandatory
			DESCRIPTION 
	"Measurement File Primary Dir. 
	Measurement file is written in this directory "
			::= {	measFileConfig   5 }

measFileCfgSecondaryDir		OBJECT-TYPE
			SYNTAX	DisplayString
			ACCESS	read-only
			STATUS	mandatory
			DESCRIPTION 
	"Measurement File Secondary Dir. 
	Measurement file is moved to this directory from Primary Directory 
	after receving the acknowledgement. "
			::= {	measFileConfig   6 }

 -- *************************************************     
 -- Measurement Enabl Group
 -- *************************************************     

measFileEnablePRITraffic		OBJECT-TYPE
			SYNTAX	MeasEnableStatus
			ACCESS	read-write
			STATUS	mandatory
			DESCRIPTION 
	"Measurement File PRI Traffic Enable Group. 
	A mechanism for the user to enable collecting of PRI 
	Traffic measurement data. "
			::= {	measFileEnableGrp   1 }

measFileEnableISUPTraffic		OBJECT-TYPE
			SYNTAX	MeasEnableStatus
			ACCESS	read-write
			STATUS	mandatory
			DESCRIPTION 
	"Measurement File ISUP Traffic Enable Group. 
	A mechanism for the user to enable collecting of ISUP 
	Traffic measurement data. "
			::= {	measFileEnableGrp   2 }

measFileEnablePRIIneffectiveCall		OBJECT-TYPE
			SYNTAX	MeasEnableStatus
			ACCESS	read-write
			STATUS	mandatory
			DESCRIPTION 
	"Measurement File Enable PRI Ineffective Call Group. 
	A mechanism for the user to enable collecting of PRI 
	Ineffective Call Group measurement data. "
			::= {	measFileEnableGrp   3 }

measFileEnableISUPIneffectiveCall		OBJECT-TYPE
			SYNTAX	MeasEnableStatus
			ACCESS	read-write
			STATUS	mandatory
			DESCRIPTION 
	"Measurement File Enable PRI Ineffective Call Group. 
	A mechanism for the user to enable collecting of ISUP 
	Ineffective Call Group Traffic measurement data. "
			::= {	measFileEnableGrp   4 }

measFileEnableTrunkGrp		OBJECT-TYPE
			SYNTAX	MeasEnableStatus
			ACCESS	read-write
			STATUS	mandatory
			DESCRIPTION 
	"Measurement File Enable Trunk Group. 
	A mechanism for the user to enable collecting of Trunk 
	Group Traffic measurement data. "
			::= {	measFileEnableGrp   5 }

measFileEnableSS7LinkTraffic		OBJECT-TYPE
			SYNTAX	MeasEnableStatus
			ACCESS	read-write
			STATUS	mandatory
			DESCRIPTION 
	"Measurement File Enable SS7 Link Traffic Group. 
	A mechanism for the user to enable collecting of SS7 Link 
	Traffic measurement data. "
			::= {	measFileEnableGrp   6 }

 -- *************************************************     
 -- Switch Group of Switch Measurement
 -- *************************************************     

measSwitchIsupGrp		OBJECT IDENTIFIER   ::=	{ measSwitch	 1 }

measSwitchIsupFailCallGrp		OBJECT IDENTIFIER   ::=	{ measSwitch	 2 }

measSwitchPriGrp		OBJECT IDENTIFIER   ::=	{ measSwitch	 3 }

measSwitchPriFailCallGrp		OBJECT IDENTIFIER   ::=	{ measSwitch	 4 }

 -- *************************************************     
 -- Trunk Grp Traffic Table of Switch management
 -- *************************************************     

measTrnkGrpTrafficTable		OBJECT-TYPE
			SYNTAX   SEQUENCE OF MeasTrnkGrpTrafficEntry
			ACCESS	not-accessible
			STATUS	mandatory
			DESCRIPTION 
	"Switch Measurement for Trunk Group traffic Table. Information about Trunk 
	Group traffic measurement are provoded in this table. 
	The index for this table is measTrnkGrpName(String). "
			::= { measTrnkGrp	 1 }

measTrnkGrpTrafficEntry		OBJECT-TYPE
			SYNTAX	MeasTrnkGrpTrafficEntry
			ACCESS	not-accessible
			STATUS	mandatory
			DESCRIPTION 
	"The Current Entry Containes all the objects for this Table. 
	This object is not-accessible, but the user can access all 
	the objects in this table at the next level. "
			INDEX { measTrnkGrpName }
			::= {	measTrnkGrpTrafficTable   1 }

MeasTrnkGrpTrafficEntry		::= SEQUENCE {
			measTrnkGrpName		DisplayString,
			measTrnkGrpDataSuspect		INTEGER,
			measTrnkGrpincomingUsage		INTEGER,
			measTrnkGrpoutgoingUsage		INTEGER,
			measTrnkGrpISCicsChnls		INTEGER,
			measTrnkGrpOOSCicsChnls		INTEGER,
			measTrnkGrptotalUsage		INTEGER,
			measTrnkGrpmaintainanceUsage		INTEGER
			}

measTrnkGrpName		OBJECT-TYPE
			SYNTAX	DisplayString
			ACCESS	read-only
			STATUS	mandatory
			DESCRIPTION 
	"Trunk Group Name. Can be any combination of alphanumeric characters. 
	Spaces are not allowed and cannot exceed 15 characters. "
			::= {	measTrnkGrpTrafficEntry   1 }

measTrnkGrpDataSuspect		OBJECT-TYPE
			SYNTAX	INTEGER
			ACCESS	read-only
			STATUS	mandatory
			DESCRIPTION 
	"Trunk Group Data Suspect. Boolean value indicating if the measurement 
	data set is suspect. Suspect data is that which may or may not be accurate 
	and cannot be verified accurate due to some condition that occurred during 
	the collection interval. "
			::= {	measTrnkGrpTrafficEntry   2 }

measTrnkGrpincomingUsage		OBJECT-TYPE
			SYNTAX	INTEGER
			ACCESS	read-only
			STATUS	mandatory
			DESCRIPTION 
	"Trunk Group Incoming Usage. The sum of the counts of the number of 
	incoming trunks in the use. "
			::= {	measTrnkGrpTrafficEntry   3 }

measTrnkGrpoutgoingUsage		OBJECT-TYPE
			SYNTAX	INTEGER
			ACCESS	read-only
			STATUS	mandatory
			DESCRIPTION 
	"Trunk Group Outgoing Usage. The sum of the counts of the number of 
	outgoing trunks in the use. "
			::= {	measTrnkGrpTrafficEntry   4 }

measTrnkGrpISCicsChnls		OBJECT-TYPE
			SYNTAX	INTEGER
			ACCESS	read-only
			STATUS	mandatory
			DESCRIPTION 
	"Trunk Group Inservice Cic/Channels. The sum of the counts of the 
	number of Inservice circuits in case SS7 TrunkGroup or Inservice 
	Channels in case of ISDN TRunkGroup. "
			::= {	measTrnkGrpTrafficEntry   5 }

measTrnkGrpOOSCicsChnls		OBJECT-TYPE
			SYNTAX	INTEGER
			ACCESS	read-only
			STATUS	mandatory
			DESCRIPTION 
	"Trunk Group OutOfservice Cic/Channels. The sum of the counts of the 
	number of OutOfservice circuits in case SS7 TrunkGroup or OufOfservice 
	Channels in case of ISDN TRunkGroup. "
			::= {	measTrnkGrpTrafficEntry   6 }

measTrnkGrptotalUsage		OBJECT-TYPE
			SYNTAX	INTEGER
			ACCESS	read-only
			STATUS	mandatory
			DESCRIPTION 
	"Trunk Group Total Usage. The sum of number of trunk in use by both 
	incoming and outgoing traffic. "
			::= {	measTrnkGrpTrafficEntry   7 }

measTrnkGrpmaintainanceUsage		OBJECT-TYPE
			SYNTAX	INTEGER
			ACCESS	read-only
			STATUS	mandatory
			DESCRIPTION 
	"Trunk Group Maintenance Usage. The sum of number of trunk in use 
	for any reason other than traffic. "
			::= {	measTrnkGrpTrafficEntry   8 }

 -- *************************************************     
 -- SS7 Link traffic table of Switch measurement
 -- *************************************************     

measLinkTrafficTable		OBJECT-TYPE
			SYNTAX   SEQUENCE OF MeasLinkTrafficEntry
			ACCESS	not-accessible
			STATUS	mandatory
			DESCRIPTION 
	"Switch Measurement per SS7 Link traffic Table. Information about traffic 
	measurement per SS7 Link are provoded in this table. 
	The index for this table is measLinkName(String). "
			::= { measLnk	 1 }

measLinkTrafficEntry		OBJECT-TYPE
			SYNTAX	MeasLinkTrafficEntry
			ACCESS	not-accessible
			STATUS	mandatory
			DESCRIPTION 
	"The Current Entry Containes all the objects for this Table. 
	This object is not-accessible, but the user can access all 
	the objects in this table at the next level. "
			INDEX { measLinkName }
			::= {	measLinkTrafficTable   1 }

MeasLinkTrafficEntry		::= SEQUENCE {
			measLinkName		NameString,
			measLinkDataSuspect		INTEGER,
			measLinkUnavailableDuration		INTEGER,
			measLinkInServiceDuration		INTEGER,
			measLinkMSUsRetransmitted		INTEGER,
			measLinkOctetsReceived		INTEGER,
			measLinkOctectsTransmitted		INTEGER,
			measLinkLostMSUsBufferOverflow		INTEGER,
			measLinkMSUsDiscarded		INTEGER
			}

measLinkName		OBJECT-TYPE
			SYNTAX	NameString
			ACCESS	read-only
			STATUS	mandatory
			DESCRIPTION 
	"SS7 Link name "
			::= {	measLinkTrafficEntry   1 }

measLinkDataSuspect		OBJECT-TYPE
			SYNTAX	INTEGER
			ACCESS	read-only
			STATUS	mandatory
			DESCRIPTION 
	"Link Data Suspect. Boolean value indicating if the measurement data 
	set is suspect. Suspect data is that which may or may not be accurate 
	and cannot be verified accurate due to some condition that occurred 
	during the collection interval. "
			::= {	measLinkTrafficEntry   2 }

measLinkUnavailableDuration		OBJECT-TYPE
			SYNTAX	INTEGER
			ACCESS	read-only
			STATUS	mandatory
			DESCRIPTION 
	"Link Unavailable Duration. The cumulative time (in sconds) that the 
	link was unavailable during the associated time interval (CS) "
			::= {	measLinkTrafficEntry   3 }

measLinkInServiceDuration		OBJECT-TYPE
			SYNTAX	INTEGER
			ACCESS	read-only
			STATUS	mandatory
			DESCRIPTION 
	"Link In Service Duration. The cumulative time (in seconds) during 
	which the link was in the in-service state. A link is said to be in- 
	service when it is capable of transmitting MSUs. This measurement 
	includes periods when no MSUs are available for tra"
			::= {	measLinkTrafficEntry   4 }

measLinkMSUsRetransmitted		OBJECT-TYPE
			SYNTAX	INTEGER
			ACCESS	read-only
			STATUS	mandatory
			DESCRIPTION 
	"Link MSUs Retransmitted. The number of MSUs retransmitted via a 
	particular link during the associated time period (CS) "
			::= {	measLinkTrafficEntry   5 }

measLinkOctetsReceived		OBJECT-TYPE
			SYNTAX	INTEGER
			ACCESS	read-only
			STATUS	mandatory
			DESCRIPTION 
	"Link Octers Received. The number of SIF and SIO octets received 
	on the associate incoming link (CS) "
			::= {	measLinkTrafficEntry   6 }

measLinkOctectsTransmitted		OBJECT-TYPE
			SYNTAX	INTEGER
			ACCESS	read-only
			STATUS	mandatory
			DESCRIPTION 
	"Link Octets Transmitted. The number of SIF and SIO octets 
	transmitted (including those retransmitted) on the associated 
	incoming link (CS) "
			::= {	measLinkTrafficEntry   7 }

measLinkLostMSUsBufferOverflow		OBJECT-TYPE
			SYNTAX	INTEGER
			ACCESS	read-only
			STATUS	mandatory
			DESCRIPTION 
	"Link Lost MSUs Buffer Overflow. The number of MSUs lost because of 
	transmission buffer overflow (CS) "
			::= {	measLinkTrafficEntry   8 }

measLinkMSUsDiscarded		OBJECT-TYPE
			SYNTAX	INTEGER
			ACCESS	read-only
			STATUS	mandatory
			DESCRIPTION 
	"Link MSUs Discarded. This measurement is a count of number of MSUs 
	discarded. "
			::= {	measLinkTrafficEntry   9 }

 -- *************************************************     
 -- Meas Switch ISUP group
 -- *************************************************     

measSwitchIsupDataSuspect		OBJECT-TYPE
			SYNTAX	Counter
			ACCESS	read-only
			STATUS	mandatory
			DESCRIPTION 
	"Switch Isup Data Suspect. 
	Boolean value indicating if the measurement data set is suspect. 
	Suspect data is that which may or may not be accurate and cannot be 
	verified accurate due to a some condition that occurred during the 
	collection interval "
			::= {	measSwitchIsupGrp   1 }

measSwitchIsupIncomingAnsiTrunkCallAttempts		OBJECT-TYPE
			SYNTAX	Counter
			ACCESS	read-only
			STATUS	mandatory
			DESCRIPTION 
	"Switch Isup Incoming Ansi Trunk Call Attempts. 
	The number of incoming ISUP-ANSI trunk call requests. "
			::= {	measSwitchIsupGrp   2 }

measSwitchIsupIncomingAnsiTrunkCallAnswered		OBJECT-TYPE
			SYNTAX	Counter
			ACCESS	read-only
			STATUS	mandatory
			DESCRIPTION 
	"Switch Isup Incoming Ansi Trunk Call Answered. 
	The number of incoming ISUP-ANSI trunk calls answered. "
			::= {	measSwitchIsupGrp   3 }

measSwitchIsupOutgoingAnsiTrunkCallAttempts		OBJECT-TYPE
			SYNTAX	Counter
			ACCESS	read-only
			STATUS	mandatory
			DESCRIPTION 
	"Switch Isup Outgoing Ansi Trunk Call Attempts. 
	The number of outgoing ISUP-ANSi trunk call requests. "
			::= {	measSwitchIsupGrp   4 }

measSwitchIsupOutgoingAnsiTrunkCallAnswered		OBJECT-TYPE
			SYNTAX	Counter
			ACCESS	read-only
			STATUS	mandatory
			DESCRIPTION 
	"Switch Isup Outgoing Ansi Trunk Call Answered. 
	The number of outgoing ISUP-ANSI trunk calls answered. "
			::= {	measSwitchIsupGrp   5 }

measSwitchIsupIncomingItutTrunkCallAttempts		OBJECT-TYPE
			SYNTAX	Counter
			ACCESS	read-only
			STATUS	mandatory
			DESCRIPTION 
	"Switch Isup Incoming Itut Trunk Call Attempts. 
	The number of incoming ISUP-ITUT trunk call requests. "
			::= {	measSwitchIsupGrp   6 }

measSwitchIsupIncomingItutTrunkCallAnswered		OBJECT-TYPE
			SYNTAX	Counter
			ACCESS	read-only
			STATUS	mandatory
			DESCRIPTION 
	"Switch Isup Incoming Itut Trunk Call Answered. 
	The number of incoming ISUP-ITUT trunk calls answered. "
			::= {	measSwitchIsupGrp   7 }

measSwitchIsupOutgoingItutTrunkCallAttempts		OBJECT-TYPE
			SYNTAX	Counter
			ACCESS	read-only
			STATUS	mandatory
			DESCRIPTION 
	"Switch Isup Outgoing Itut Trunk Call Attempts. 
	The number of outgoing ISUP-ITUT trunk call requests. "
			::= {	measSwitchIsupGrp   8 }

measSwitchIsupOutgoingItutTrunkCallAnswered		OBJECT-TYPE
			SYNTAX	Counter
			ACCESS	read-only
			STATUS	mandatory
			DESCRIPTION 
	"Switch Isup Outgoing Itut Trunk Call Answered. 
	The number of outgoing ISUP-ITUT trunk calls answered. "
			::= {	measSwitchIsupGrp   9 }

 -- *************************************************     
 -- Meas Switch ISUP fail Call Group
 -- *************************************************     

measSwitchIsupFailCallDataSuspect		OBJECT-TYPE
			SYNTAX	Counter
			ACCESS	read-only
			STATUS	mandatory
			DESCRIPTION 
	"Switch Isup Fail Call Data Suspect. 
	Boolean value indicating if the measurement data set is suspect. 
	Suspect data is that which may or may not be accurate and cannot 
	be verified accurate due to a some condition that occurred during 
	the collection inte"
			::= {	measSwitchIsupFailCallGrp   1 }

measSwitchIsupFailCallAnsiMatchingLoss		OBJECT-TYPE
			SYNTAX	Counter
			ACCESS	read-only
			STATUS	mandatory
			DESCRIPTION 
	"Switch Isup Fail Call Ansi Matching Loss. 
	The number of calls ISUP-ANSI trunk calls that fail to find a linked 
	cross-connect within XCMs on any stage of the call. "
			::= {	measSwitchIsupFailCallGrp   2 }

measSwitchIsupFailCallAnsiNoCircuit		OBJECT-TYPE
			SYNTAX	Counter
			ACCESS	read-only
			STATUS	mandatory
			DESCRIPTION 
	"Switch Isup Fail Call Ansi No Circuit. 
	The number of ISUP-ANSI calls that cannot forwarded on a trunk because: 
	* No idle PRI trunks available 
	* No cross-connect available between XCMs. "
			::= {	measSwitchIsupFailCallGrp   3 }

measSwitchIsupFailCallAnsiCalledPartyLineBusy		OBJECT-TYPE
			SYNTAX	Counter
			ACCESS	read-only
			STATUS	mandatory
			DESCRIPTION 
	"Switch Isup Fail Call Ansi Called Party Line Busy. 
	The number of ISUP-ANSI calls that result in a called party busy 
	indication returned to the caller. "
			::= {	measSwitchIsupFailCallGrp   4 }

measSwitchIsupFailCallAnsiIneffectiveMachineAttempts		OBJECT-TYPE
			SYNTAX	Counter
			ACCESS	read-only
			STATUS	mandatory
			DESCRIPTION 
	"Switch Isup Fail Call Ansi Ineffective Machine Attempts. 
	The number of ISUP-ANSI call ineffective machine attempts that 
	have not been associated with any of the following: 
	* Matching loss 
	* No circuit 
	* Called party line busy. "
			::= {	measSwitchIsupFailCallGrp   5 }

measSwitchIsupFailCallItutMatchingLoss		OBJECT-TYPE
			SYNTAX	Counter
			ACCESS	read-only
			STATUS	mandatory
			DESCRIPTION 
	"Switch Isup Fail Call Itut Matching Loss. 
	The number of calls ISUP-ITUT trunk calls that fail to find a 
	linked cross-connect within XCMs on any stage of the call. "
			::= {	measSwitchIsupFailCallGrp   6 }

measSwitchIsupFailCallItutNoCircuit		OBJECT-TYPE
			SYNTAX	Counter
			ACCESS	read-only
			STATUS	mandatory
			DESCRIPTION 
	"Switch Isup Fail Call Itut No Circuit. 
	The number of ISUP-ITUT calls that cannot be forwarded on a 
	trunk because: 
	* No idle PRI trunks available 
	* No cross-connect available between XCMs. "
			::= {	measSwitchIsupFailCallGrp   7 }

measSwitchIsupFailCallItutCalledPartyLineBusy		OBJECT-TYPE
			SYNTAX	Counter
			ACCESS	read-only
			STATUS	mandatory
			DESCRIPTION 
	"Switch Isup Fail Call Itut Called Party Line Busy. 
	The number of ISUP-ITUT calls that result in a called 
	party busy indication returned to the caller. "
			::= {	measSwitchIsupFailCallGrp   8 }

measSwitchIsupFailCallItutIneffectiveMachineAttempts		OBJECT-TYPE
			SYNTAX	Counter
			ACCESS	read-only
			STATUS	mandatory
			DESCRIPTION 
	"Switch Isup Fail Call Itut Ineffective Machine Attempts. 
	The number of ISUP-ITUT call ineffective machine attempts that 
	have not been associated with any of the following: 
	* Matching loss 
	* No circuit 
	* Called party line busy. "
			::= {	measSwitchIsupFailCallGrp   9 }

 -- *************************************************     
 -- meas switch ISDN PRI group
 -- *************************************************     

measSwitchPriDataSuspect		OBJECT-TYPE
			SYNTAX	Counter
			ACCESS	read-only
			STATUS	mandatory
			DESCRIPTION 
	"Switch Primary Data Suspect. 
	Boolean value indicating if the measurement data set is suspect. 
	Suspect data is that which may or may not be accurate and cannot 
	be verified accurate due to a some condition that occurred during 
	the collection interval. "
			::= {	measSwitchPriGrp   1 }

measSwitchPriIncomingIsdnPRICallAttempts		OBJECT-TYPE
			SYNTAX	Counter
			ACCESS	read-only
			STATUS	mandatory
			DESCRIPTION 
	"Switch PRI Incoming ISDN PRI Call Attempts. 
	The number of Incoming ISDN trunk call requests. "
			::= {	measSwitchPriGrp   2 }

measSwitchPriIncomingIsdnPRICallAnswered		OBJECT-TYPE
			SYNTAX	Counter
			ACCESS	read-only
			STATUS	mandatory
			DESCRIPTION 
	"Switch PRI Incoming ISDN PRI Call Answered. 
	The number of Incoming ISDN trunk calls answered. "
			::= {	measSwitchPriGrp   3 }

 -- *************************************************     
 -- meas Switch ISDN PRI group
 -- *************************************************     

measSwitchPriFailCallDataSuspect		OBJECT-TYPE
			SYNTAX	Counter
			ACCESS	read-only
			STATUS	mandatory
			DESCRIPTION 
	"Switch ISDN PRI Fail Call Data Suspect. 
	Boolean value indicating if the measurement data set is suspect. 
	Suspect data is that which may or may not be accurate and cannot 
	be verified accurate due to a some condition that occurred during 
	the collection "
			::= {	measSwitchPriFailCallGrp   1 }

measSwitchPriFailCallMatchingLoss		OBJECT-TYPE
			SYNTAX	Counter
			ACCESS	read-only
			STATUS	mandatory
			DESCRIPTION 
	"Switch ISDN PRI Fail Call Matching Loss. 
	The number of calls PRI trunk calls that fail to find a linked 
	cross-connect within XCM on any stage of the call. "
			::= {	measSwitchPriFailCallGrp   2 }

measSwitchPriFailCallNoCircuit		OBJECT-TYPE
			SYNTAX	Counter
			ACCESS	read-only
			STATUS	mandatory
			DESCRIPTION 
	"Switch ISDN PRI Fail Call No Circuit. 
	The number of PRI calls that cannot be forwarded on a trunk because: 
	* No idle PRI trunks available 
	* No cross-connect available between XCMs. "
			::= {	measSwitchPriFailCallGrp   3 }

measSwitchPriFailCallCalledPartyLineBusy		OBJECT-TYPE
			SYNTAX	Counter
			ACCESS	read-only
			STATUS	mandatory
			DESCRIPTION 
	"Switch ISDN PRI Fail Call Called Party Line Busy. 
	The number of PRI calls that result in a called party busy 
	indication returned to the caller. "
			::= {	measSwitchPriFailCallGrp   4 }

measSwitchPriFailCallIneffectiveMachineAttempts		OBJECT-TYPE
			SYNTAX	Counter
			ACCESS	read-only
			STATUS	mandatory
			DESCRIPTION 
	"Switch ISDN PRI Fail Call Ineffective Machine Attempts. 
	The number of PRI call ineffective machine attempts that have 
	not been associated with any of the following: 
	* Matching loss 
	* No circuit 
	* Called party line busy. "
			::= {	measSwitchPriFailCallGrp   5 }

 -- *************************************************     
 -- Xconnect Config Table
 -- *************************************************     

xconnectCfgTable		OBJECT-TYPE
			SYNTAX   SEQUENCE OF XconnectCfgEntry
			ACCESS	not-accessible
			STATUS	mandatory
			DESCRIPTION 
	"XConnext Table. Information about XConnect(s) in MSSC are provided 
	in this table. 
	The index for this table is xconnectId(Integer). "
			::= { xconnect	 1 }

xconnectCfgEntry		OBJECT-TYPE
			SYNTAX	XconnectCfgEntry
			ACCESS	not-accessible
			STATUS	mandatory
			DESCRIPTION 
	"The Current Entry Containes all the objects for this Table. 
	This object is not-accessible, but the user can access all 
	the objects in this table at the next level. "
			INDEX { xconnectId }
			::= {	xconnectCfgTable   1 }

XconnectCfgEntry		::= SEQUENCE {
			xconnectId		INTEGER,
			xconnectName		NameString,
			xconnectIPAddr		IpAddress,
			xconnectTCPPort		INTEGER,
			xconnectRowStatus		RowStatus,
			xconnectOpStatus		OpStatus
			}

xconnectId		OBJECT-TYPE
			SYNTAX	INTEGER(1..65535)
			ACCESS	read-write
			STATUS	mandatory
			DESCRIPTION 
	"Xconnect id. Can be any integer 1-65535. "
			::= {	xconnectCfgEntry   1 }

xconnectName		OBJECT-TYPE
			SYNTAX	NameString
			ACCESS	read-write
			STATUS	mandatory
			DESCRIPTION 
	"Xconnect name. Can be any combination of alphanumeric characters. 
	Spaces are not allowed and cannot exceed 15 characters. "
			::= {	xconnectCfgEntry   2 }

xconnectIPAddr		OBJECT-TYPE
			SYNTAX	IpAddress
			ACCESS	read-write
			STATUS	mandatory
			DESCRIPTION 
	"Xconnect IP address. Submit in xxx.xxx.xxx.xxx format. "
			::= {	xconnectCfgEntry   3 }

xconnectTCPPort		OBJECT-TYPE
			SYNTAX	INTEGER(1..65535)
			ACCESS	read-write
			STATUS	mandatory
			DESCRIPTION 
	"Xconnect TCP port. Can be any integer 1-65535. "
			::= {	xconnectCfgEntry   4 }

xconnectRowStatus		OBJECT-TYPE
			SYNTAX	RowStatus
			ACCESS	read-write
			STATUS	mandatory
			DESCRIPTION 
	"Current Status (configurational Status) of this XConnect. 
	To Configure this Link, the only option is 'CREATEANDWAIT' 
	To Delete this Link, the only option is 'DESTROY' 
	For the 'GET' Operation, the possible options are 
	1) active 
	2) notinservice 
	3) not"
			::= {	xconnectCfgEntry   5 }

xconnectOpStatus		OBJECT-TYPE
			SYNTAX	OpStatus
			ACCESS	read-only
			STATUS	mandatory
			DESCRIPTION 
	"Current Status (Operational Status) of this XConnect. 
	'SET' Operation is NOT APPLICABLE. 
	For the 'GET' Operation, the possible options are 
	1) active 
	2) down  "
			::= {	xconnectCfgEntry   6 }

 -- *************************************************     
 -- Xlink Config Table
 -- *************************************************     

xlinkCfgTable		OBJECT-TYPE
			SYNTAX   SEQUENCE OF XlinkCfgEntry
			ACCESS	not-accessible
			STATUS	mandatory
			DESCRIPTION 
	"XLink Table. Information about XLink(s) in MSSC are provided 
	in this table.This table has six indices: 
	xconnectIdEndA, slotIdEndA, portIdEndA,xconnectIdEndB, 
	xconnectIdEndB,slotIdEndB,portIdEndB (all Integers) "
			::= { xconnect	 2 }

xlinkCfgEntry		OBJECT-TYPE
			SYNTAX	XlinkCfgEntry
			ACCESS	not-accessible
			STATUS	mandatory
			DESCRIPTION 
	"The Current Entry Containes all the objects for this Table. 
	This object is not-accessible, but the user can access all 
	the objects in this table at the next level. "
			INDEX { xconnectIdEndA, slotIdEndA, portIdEndA, xconnectIdEndB, slotIdEndB, portIdEndB }
			::= {	xlinkCfgTable   1 }

XlinkCfgEntry		::= SEQUENCE {
			xconnectIdEndA		INTEGER,
			slotIdEndA		INTEGER,
			portIdEndA		INTEGER,
			xconnectIdEndB		INTEGER,
			slotIdEndB		INTEGER,
			portIdEndB		INTEGER,
			xlinkConnectionType		ConnectionType,
			xlinkRowStatus		RowStatus,
			xlinkOpStatus		OpStatus
			}

xconnectIdEndA		OBJECT-TYPE
			SYNTAX	INTEGER(1..65535)
			ACCESS	read-write
			STATUS	mandatory
			DESCRIPTION 
	"Xconnect id for one end. Can be any integer 1-65535. "
			::= {	xlinkCfgEntry   1 }

slotIdEndA		OBJECT-TYPE
			SYNTAX	INTEGER(1..65535)
			ACCESS	read-write
			STATUS	mandatory
			DESCRIPTION 
	"Slot Id of one end. "
			::= {	xlinkCfgEntry   2 }

portIdEndA		OBJECT-TYPE
			SYNTAX	INTEGER(1..65535)
			ACCESS	read-write
			STATUS	mandatory
			DESCRIPTION 
	"Port id of one end.  "
			::= {	xlinkCfgEntry   3 }

xconnectIdEndB		OBJECT-TYPE
			SYNTAX	INTEGER(1..65535)
			ACCESS	read-write
			STATUS	mandatory
			DESCRIPTION 
	"Xconnect id for the other end. Can be any integer 1-65535. "
			::= {	xlinkCfgEntry   4 }

slotIdEndB		OBJECT-TYPE
			SYNTAX	INTEGER(1..65535)
			ACCESS	read-write
			STATUS	mandatory
			DESCRIPTION 
	"Slot Id of the other end.  "
			::= {	xlinkCfgEntry   5 }

portIdEndB		OBJECT-TYPE
			SYNTAX	INTEGER(1..65535)
			ACCESS	read-write
			STATUS	mandatory
			DESCRIPTION 
	"Port id of the other end.  "
			::= {	xlinkCfgEntry   6 }

xlinkConnectionType		OBJECT-TYPE
			SYNTAX	ConnectionType
			ACCESS	read-write
			STATUS	mandatory
			DESCRIPTION 
	"Connection Type between the Xconnects 
	The possible options are : 
	1) Unchannelised DS3 (ut3) 
	2) Channelised DS3 (t3) "
			::= {	xlinkCfgEntry   7 }

xlinkRowStatus		OBJECT-TYPE
			SYNTAX	RowStatus
			ACCESS	read-write
			STATUS	mandatory
			DESCRIPTION 
	"Current Status (configurational Status) of this XCONNECT Link. 
	To Configure this Link, the only option is 'CREATEANDWAIT' 
	To Delete this Link, the only option is 'DESTROY' 
	For the 'GET' Operation, the possible options are 
	1) active 
	2) notinservice 
	3"
			::= {	xlinkCfgEntry   8 }

xlinkOpStatus		OBJECT-TYPE
			SYNTAX	OpStatus
			ACCESS	read-only
			STATUS	mandatory
			DESCRIPTION 
	"Current Status (Operational Status) of this XConnect Link. 
	'SET' Operation is NOT APPLICABLE. 
	For the 'GET' Operation, the possible options are 
	1) active 
	2) down  "
			::= {	xlinkCfgEntry   9 }

 -- *************************************************     
 -- Xlink Management Table
 -- *************************************************     

xlinkMgmntTable		OBJECT-TYPE
			SYNTAX   SEQUENCE OF XlinkMgmntEntry
			ACCESS	not-accessible
			STATUS	mandatory
			DESCRIPTION 
	"XLink Management Table. 
	This table has six indices: 
	xconnectIdEndA, slotIdEndA, portIdEndA,xconnectIdEndB, 
	xconnectIdEndB,slotIdEndB,portIdEndB (all Integers) "
			::= { xconnect	 3 }

xlinkMgmntEntry		OBJECT-TYPE
			SYNTAX	XlinkMgmntEntry
			ACCESS	not-accessible
			STATUS	mandatory
			DESCRIPTION 
	"The Current Entry Containes all the objects for this Table. 
	This object is not-accessible, but the user can access all 
	the objects in this table at the next level. "
			INDEX { xconnIdEndA, xconnSlotIdEndA, xconnPortIdEndA, xconnIdEndB, xconnSlotIdEndB, xconnPortIdEndB }
			::= {	xlinkMgmntTable   1 }

XlinkMgmntEntry		::= SEQUENCE {
			xconnIdEndA		INTEGER,
			xconnSlotIdEndA		INTEGER,
			xconnPortIdEndA		INTEGER,
			xconnIdEndB		INTEGER,
			xconnSlotIdEndB		INTEGER,
			xconnPortIdEndB		INTEGER,
			xlinkMgmntCmd		EnableOperation
			}

xconnIdEndA		OBJECT-TYPE
			SYNTAX	INTEGER(1..65535)
			ACCESS	read-only
			STATUS	mandatory
			DESCRIPTION 
	"Xconnect id for one end. Can be any integer 1-65535. "
			::= {	xlinkMgmntEntry   1 }

xconnSlotIdEndA		OBJECT-TYPE
			SYNTAX	INTEGER(1..65535)
			ACCESS	read-only
			STATUS	mandatory
			DESCRIPTION 
	"Slot Id of one end. "
			::= {	xlinkMgmntEntry   2 }

xconnPortIdEndA		OBJECT-TYPE
			SYNTAX	INTEGER(1..65535)
			ACCESS	read-only
			STATUS	mandatory
			DESCRIPTION 
	"Port id of one end. "
			::= {	xlinkMgmntEntry   3 }

xconnIdEndB		OBJECT-TYPE
			SYNTAX	INTEGER(1..65535)
			ACCESS	read-only
			STATUS	mandatory
			DESCRIPTION 
	"Xconnect id for the other end. Can be any integer 1-65535. "
			::= {	xlinkMgmntEntry   4 }

xconnSlotIdEndB		OBJECT-TYPE
			SYNTAX	INTEGER(1..65535)
			ACCESS	read-only
			STATUS	mandatory
			DESCRIPTION 
	"Slot Id of the other end.  "
			::= {	xlinkMgmntEntry   5 }

xconnPortIdEndB		OBJECT-TYPE
			SYNTAX	INTEGER
			ACCESS	read-only
			STATUS	mandatory
			DESCRIPTION 
	"Port id of the other end. "
			::= {	xlinkMgmntEntry   6 }

xlinkMgmntCmd		OBJECT-TYPE
			SYNTAX	EnableOperation
			ACCESS	read-write
			STATUS	mandatory
			DESCRIPTION 
	"Management Command for Enabling/Disabling XLink 
	The possible options are : 
	1) Enable 
	2) Disable [default] "
			::= {	xlinkMgmntEntry   7 }

 -- *************************************************     
 -- Cdr Config Group
 -- *************************************************     

cdrConfig		OBJECT IDENTIFIER   ::=	{ switchCdr	 1 }

cdrBafConfig		OBJECT IDENTIFIER   ::=	{ switchCdr	 2 }

cdrFileConfig		OBJECT IDENTIFIER   ::=	{ switchCdr	 3 }

cdrFileInfo		OBJECT IDENTIFIER   ::=	{ switchCdr	 4 }

cdrMgmntCmdGroup		OBJECT IDENTIFIER   ::=	{ switchCdr	 5 }

 -- *************************************************     
 -- CDR Configuaration Group
 -- *************************************************     

cdrLongDurCallGenTime		OBJECT-TYPE
			SYNTAX	INTEGER(0..2359)
			ACCESS	read-write
			STATUS	mandatory
			DESCRIPTION 
	"The Time of the day that the syatem will generate the long 
	duration call. 
	CDR Format ( HHMM ) 
	Valid time of the day from 0000 - 2359  "
			::= {	cdrConfig   1 }

 -- *************************************************     
 -- CDR BAF Config Group
 -- *************************************************     

cdrAppendModule801		OBJECT-TYPE
			SYNTAX	Bool
			ACCESS	read-write
			STATUS	mandatory
			DESCRIPTION 
	"Indicates if the Armillaire Proprietary Module 801 should 
	be appended to those BAF Records. 
	Text Format ( Not Case sensitive ) 
	Valid values : yes, no  "
			::= {	cdrBafConfig   1 }

cdrSensorId		OBJECT-TYPE
			SYNTAX	INTEGER(1..999998)
			ACCESS	read-write
			STATUS	mandatory
			DESCRIPTION 
	"AMA Sensor Id code of the switch. 
	Valid values 000001-999998 for Set. 
	If not configured then Default value is 0.  "
			::= {	cdrBafConfig   2 }

cdrRecordingOfficeId		OBJECT-TYPE
			SYNTAX	INTEGER(1..999998)
			ACCESS	read-write
			STATUS	mandatory
			DESCRIPTION 
	"AMA Record Id code of the switch. 
	Valid values 000001-999998 For Set. 
	If not configured then Default value is 0.  "
			::= {	cdrBafConfig   3 }

 -- *************************************************     
 -- CDR File Config Group
 -- *************************************************     

cdrFileInterval		OBJECT-TYPE
			SYNTAX	INTEGER(1..86400)
			ACCESS	read-write
			STATUS	mandatory
			DESCRIPTION 
	"How often the cdr file being generated. 
	Valid values 1-86400 seconds "
			::= {	cdrFileConfig   1 }

cdrFileRecLimit		OBJECT-TYPE
			SYNTAX	INTEGER(1..86400)
			ACCESS	read-write
			STATUS	mandatory
			DESCRIPTION 
	"Maximum Nubler of BAF records in a CDR File. 
	Valid values 1,677,215 "
			::= {	cdrFileConfig   2 }

cdrFileSourceId		OBJECT-TYPE
			SYNTAX	INTEGER(1..4095)
			ACCESS	read-write
			STATUS	mandatory
			DESCRIPTION 
	"This Source Component id specifies the network element for 
	receiving of cdr files according to AMADNS. This id will be 
	part of first node of CDR filename. 
	Valid values 01-4095 For Set. 
	If not configured then Default value is 0.  "
			::= {	cdrFileConfig   3 }

cdrFileDestinationType		OBJECT-TYPE
			SYNTAX	INTEGER(1..15)
			ACCESS	read-write
			STATUS	mandatory
			DESCRIPTION 
	"This Destination Component type specifies the network 
	element for receiving of cdr files according to AMADNS. 
	This type will be part of second node of CDR filename. 
	Valid values 01-15 For Set. 
	If not configured then Default value is 0.  "
			::= {	cdrFileConfig   4 }

cdrFileDestinationId		OBJECT-TYPE
			SYNTAX	INTEGER(1..4095)
			ACCESS	read-write
			STATUS	mandatory
			DESCRIPTION 
	"This Destination Component Id specifies the network 
	element for receiving of cdr files according to AMADNS. 
	This type will be part of second node of CDR filename. 
	Valid values 01-4095 for Set. 
	If not configured then Default value is 0.  "
			::= {	cdrFileConfig   5 }

 -- *************************************************     
 -- CDR File Info Group
 -- *************************************************     

cdrFileQuery		OBJECT-TYPE
			SYNTAX	INTEGER
			ACCESS	read-write
			STATUS	mandatory
			DESCRIPTION 
	"Number of the desired CDR file. 
	set file number to update the cdr file info. "
			::= {	cdrFileInfo   1 }

cdrFileName		OBJECT-TYPE
			SYNTAX	DisplayString(SIZE(1..24))
			ACCESS	read-only
			STATUS	mandatory
			DESCRIPTION 
	"Name of the desired CDR file. Can be any combination of 
	alphanumeric characters. Spaces are not allowed. Filename cannot 
	exceed 24 characters. "
			::= {	cdrFileInfo   2 }

cdrFileStatus		OBJECT-TYPE
			SYNTAX	INTEGER
			ACCESS	read-only
			STATUS	mandatory
			DESCRIPTION 
	"Status of the desired CDR file "
			::= {	cdrFileInfo   3 }

cdrFileCreateDate		OBJECT-TYPE
			SYNTAX	DisplayString(SIZE(1..32))
			ACCESS	read-only
			STATUS	mandatory
			DESCRIPTION 
	"Creation date of the desired CDR file 
	FORMAT:2000/01/26 "
			::= {	cdrFileInfo   4 }

cdrFileCreateTime		OBJECT-TYPE
			SYNTAX	DisplayString(SIZE(1..32))
			ACCESS	read-only
			STATUS	mandatory
			DESCRIPTION 
	"Creation time of the desired CDR file 
	FORMAT: 20:12:23 "
			::= {	cdrFileInfo   5 }

cdrFileRecordNum		OBJECT-TYPE
			SYNTAX	INTEGER
			ACCESS	read-only
			STATUS	mandatory
			DESCRIPTION 
	"Record number of the desired CDR file "
			::= {	cdrFileInfo   6 }

cdrFileAcknowledge		OBJECT-TYPE
			SYNTAX	DisplayString(SIZE(1..255))
			ACCESS	read-write
			STATUS	mandatory
			DESCRIPTION 
	"Acknowledgement of the CDR file. The input should be the File Name. "
			::= {	cdrFileInfo   7 }

 -- *************************************************     
 -- CDR Gen Management Cmd Group
 -- *************************************************     

cdrGenMgmntCmd		OBJECT-TYPE
			SYNTAX	EnableOperation
			ACCESS	read-write
			STATUS	mandatory
			DESCRIPTION 
	"This command is used to turn on the CDR generation 
	for the entire switch.If switch CDR generation is enabled 
	then CDR generation can be enabled/disabled on Trunk Group. 
	The possible options are : 
	1) Enable 
	2) Disable [default] "
			::= {	cdrMgmntCmdGroup   1 }

 -- *************************************************     
 -- CDR Management Command For Trunk Group
 -- *************************************************     

cdrMngmtTrnkGrpTable		OBJECT-TYPE
			SYNTAX   SEQUENCE OF CdrMngmtTrnkGrpEntry
			ACCESS	not-accessible
			STATUS	mandatory
			DESCRIPTION 
	"CDR Management Command for Trunk group Table. 
	The index for this table is cdrTrnkGrpId (integer) "
			::= { cdrMgmntCmdGroup	 2 }

cdrMngmtTrnkGrpEntry		OBJECT-TYPE
			SYNTAX	CdrMngmtTrnkGrpEntry
			ACCESS	not-accessible
			STATUS	mandatory
			DESCRIPTION 
	"The Current Entry Containes all the objects for this Table. 
	This object is not-accessible, but the user can access all 
	the objects in this table at the next level. "
			INDEX { cdrTrnkGrpId }
			::= {	cdrMngmtTrnkGrpTable   1 }

CdrMngmtTrnkGrpEntry		::= SEQUENCE {
			cdrTrnkGrpId		INTEGER,
			cdrTrnkGrpdirection		CdrFlag,
			cdrTrnkGrpMgmntCmd		EnableOperation
			}

cdrTrnkGrpId		OBJECT-TYPE
			SYNTAX	INTEGER(1..65535)
			ACCESS	read-only
			STATUS	mandatory
			DESCRIPTION 
	"The trunk Group Id.  "
			::= {	cdrMngmtTrnkGrpEntry   1 }

cdrTrnkGrpdirection		OBJECT-TYPE
			SYNTAX	CdrFlag
			ACCESS	read-write
			STATUS	mandatory
			DESCRIPTION 
	"The Direction  "
			::= {	cdrMngmtTrnkGrpEntry   2 }

cdrTrnkGrpMgmntCmd		OBJECT-TYPE
			SYNTAX	EnableOperation
			ACCESS	read-write
			STATUS	mandatory
			DESCRIPTION 
	"This command is used to turn on the CDR generation 
	on the Trunk Group. 
	The possible options are : 
	1) Enable 
	2) Disable [default] "
			::= {	cdrMngmtTrnkGrpEntry   3 }

 -- *************************************************     
 -- ModemFault Detection Table
 -- *************************************************     

modemStatusTable		OBJECT-TYPE
			SYNTAX   SEQUENCE OF ModemStatusEntry
			ACCESS	not-accessible
			STATUS	mandatory
			DESCRIPTION 
	"Faulty Modem Detection Table. This Table provides information 
	about all the potentially faulty modems in MSSC. 
	This table has two indices: 
	faultModemTrnkId and faultModemChnlId (both Integer) "
			::= { modemFaultDetection	 1 }

modemStatusEntry		OBJECT-TYPE
			SYNTAX	ModemStatusEntry
			ACCESS	not-accessible
			STATUS	mandatory
			DESCRIPTION 
	"The Current Entry Containes all the objects for this Table. 
	This object is not-accessible, but the user can access all 
	the objects in this table at the next level. "
			INDEX { faultModemTrnkId, faultModemChnlId }
			::= {	modemStatusTable   1 }

ModemStatusEntry		::= SEQUENCE {
			faultModemTrnkId		INTEGER,
			faultModemChnlId		INTEGER,
			faultModemRepnum		INTEGER,
			faultModemReset		ModemResetStatus
			}

faultModemTrnkId		OBJECT-TYPE
			SYNTAX	INTEGER
			ACCESS	read-only
			STATUS	mandatory
			DESCRIPTION 
	"The terminating Channel trunk Id.  "
			::= {	modemStatusEntry   1 }

faultModemChnlId		OBJECT-TYPE
			SYNTAX	INTEGER
			ACCESS	read-only
			STATUS	mandatory
			DESCRIPTION 
	"The terminating Channel Channel Id.  "
			::= {	modemStatusEntry   2 }

faultModemRepnum		OBJECT-TYPE
			SYNTAX	INTEGER
			ACCESS	read-only
			STATUS	mandatory
			DESCRIPTION 
	"Counter "
			::= {	modemStatusEntry   3 }

faultModemReset		OBJECT-TYPE
			SYNTAX	ModemResetStatus
			ACCESS	read-write
			STATUS	mandatory
			DESCRIPTION 
	"The Option for Reseting the terminating Channel. 
	A 'GET' operation on this object will display the 
	default value [no]. 
	The possible option for 'SET' operation is 
	1) YES  "
			::= {	modemStatusEntry   4 }

 -- *************************************************     
 -- LNP(Local Routing Number)
 -- *************************************************     

lrnTable		OBJECT-TYPE
			SYNTAX   SEQUENCE OF LrnEntry
			ACCESS	not-accessible
			STATUS	mandatory
			DESCRIPTION 
	"Local Routing Number Table. This Table provides information 
	about Local Routing number in MSSC. 
	This table has the index lrnId (Integer) "
			::= { lnp	 1 }

lrnEntry		OBJECT-TYPE
			SYNTAX	LrnEntry
			ACCESS	not-accessible
			STATUS	mandatory
			DESCRIPTION 
	"The Current Entry Containes all the objects for this Table. 
	This object is not-accessible, but the user can access all 
	the objects in this table at the next level. "
			INDEX { lrnNum }
			::= {	lrnTable   1 }

LrnEntry		::= SEQUENCE {
			lrnNum		DisplayString,
			lrnRowStatus		LrnRowStatus
			}

lrnNum		OBJECT-TYPE
			SYNTAX	DisplayString(SIZE(1..10))
			ACCESS	read-write
			STATUS	mandatory
			DESCRIPTION 
	"The Local Routing Number (LRN) Id.  "
			::= {	lrnEntry   1 }

lrnRowStatus		OBJECT-TYPE
			SYNTAX	LrnRowStatus
			ACCESS	read-write
			STATUS	mandatory
			DESCRIPTION 
	"The Local Routing Number (LRN) Number. "
			::= {	lrnEntry   2 }

 -- *************************************************     
 -- Switch DSP Config Table
 -- *************************************************     

switchDSPCfgTable		OBJECT-TYPE
			SYNTAX   SEQUENCE OF SwitchDSPCfgEntry
			ACCESS	not-accessible
			STATUS	mandatory
			DESCRIPTION 
			""
			::= { switchDSP	 1 }

switchDSPCfgEntry		OBJECT-TYPE
			SYNTAX	SwitchDSPCfgEntry
			ACCESS	not-accessible
			STATUS	mandatory
			DESCRIPTION 
	"DSP Configuration Table. This Table provides information 
	about the DSP card(s) in MSSC. 
	This table has two indices: 
	switchDSPXconnId and switchDSPSlotId (both Integer) "
			INDEX { switchDSPXconnId, switchDSPSlotId }
			::= {	switchDSPCfgTable   1 }

SwitchDSPCfgEntry		::= SEQUENCE {
			switchDSPXconnId		INTEGER,
			switchDSPSlotId		INTEGER,
			switchDSPCardType		DSPCardType,
			switchDSPCfgRowStatus		RowStatus,
			switchDSPCfgOpStatus		OpStatus
			}

switchDSPXconnId		OBJECT-TYPE
			SYNTAX	INTEGER(1..65535)
			ACCESS	read-write
			STATUS	mandatory
			DESCRIPTION 
	"Xconnect Id for which DSP card is being configured "
			::= {	switchDSPCfgEntry   1 }

switchDSPSlotId		OBJECT-TYPE
			SYNTAX	INTEGER(1..65535)
			ACCESS	read-write
			STATUS	mandatory
			DESCRIPTION 
	"The Slot id at which the DSP card is being configured. "
			::= {	switchDSPCfgEntry   2 }

switchDSPCardType		OBJECT-TYPE
			SYNTAX	DSPCardType
			ACCESS	read-write
			STATUS	mandatory
			DESCRIPTION 
	"The card Type. The possible options are : 
	1) DSP2B 
	2) DSP2C  "
			::= {	switchDSPCfgEntry   3 }

switchDSPCfgRowStatus		OBJECT-TYPE
			SYNTAX	RowStatus
			ACCESS	read-write
			STATUS	mandatory
			DESCRIPTION 
	"Current Status (configurational Status) of this Switch DSP. 
	To Configure this Link, the only option is 'CREATEANDWAIT' 
	To Delete this Link, the only option is 'DESTROY' 
	For the 'GET' Operation, the possible options are 
	1) active 
	2) notinservice 
	3) n"
			::= {	switchDSPCfgEntry   4 }

switchDSPCfgOpStatus		OBJECT-TYPE
			SYNTAX	OpStatus
			ACCESS	read-only
			STATUS	mandatory
			DESCRIPTION 
	"Current Status (Operational Status) of this Switch DSP. 
	'SET' Operation is NOT APPLICABLE. 
	For the 'GET' Operation, the possible options are 
	1) active 
	2) down  "
			::= {	switchDSPCfgEntry   5 }

 -- *************************************************     
 -- Trunk Group Feature Table
 -- *************************************************     

switchFeatureTGCfgTable		OBJECT-TYPE
			SYNTAX   SEQUENCE OF SwitchFeatureTGCfgEntry
			ACCESS	not-accessible
			STATUS	mandatory
			DESCRIPTION 
	"Trunk Group Feature Table. This Table provides information 
	about the Trunk Group Feature(s) in MSSC. 
	This table has one indices: switchFeatureTGId (Integer) "
			::= { switchTGFeature	 1 }

switchTGGrpCfgEntry		OBJECT-TYPE
			SYNTAX	SwitchFeatureTGCfgEntry
			ACCESS	not-accessible
			STATUS	mandatory
			DESCRIPTION 
	"The Current Entry Containes all the objects for this Table. 
	This object is not-accessible, but the user can access all 
	the objects in this table at the next level. "
			INDEX { switchFeatureTGId }
			::= {	switchFeatureTGCfgTable   1 }

SwitchFeatureTGCfgEntry		::= SEQUENCE {
			switchFeatureTGId		INTEGER,
			switchFeatureTGName		NameString,
			switchFeatureTGType		TrnkGrpType,
			switchFeatureTGFeatureEC		TGFeature,
			switchFeatureTGFeatureCOMPRESS		TGFeature,
			switchFeatureTGFeatureSS		TGFeature,
			switchFeatureTGFeatureCNIS		TGFeature
			}

switchFeatureTGId		OBJECT-TYPE
			SYNTAX	INTEGER
			ACCESS	read-only
			STATUS	mandatory
			DESCRIPTION 
	"Denotes Id for this trunk group. "
			::= {	switchTGGrpCfgEntry   1 }

switchFeatureTGName		OBJECT-TYPE
			SYNTAX	NameString
			ACCESS	read-only
			STATUS	mandatory
			DESCRIPTION 
	"Denotes Name of this trunk group. 
	The Name is a string of length 8. The first two characters 
	of Name have to be an alphabhet. The next 6 characters are 
	numeric. An example of a valid Trunk Group Name is ab123456. 
	NOTE: This format needs to strictly fo"
			::= {	switchTGGrpCfgEntry   2 }

switchFeatureTGType		OBJECT-TYPE
			SYNTAX	TrnkGrpType
			ACCESS	read-only
			STATUS	mandatory
			DESCRIPTION 
	"Denotes Trunk group type. Possible values for Trunk group are: 
	1. ss7 
	2. isdn "
			::= {	switchTGGrpCfgEntry   3 }

switchFeatureTGFeatureEC		OBJECT-TYPE
			SYNTAX	TGFeature
			ACCESS	read-write
			STATUS	mandatory
			DESCRIPTION 
	"Denotes Echo Cancellation feature. Possible Values are: 
	1. Enable 
	2. Disable 
	NOTE: If TrunkGrpType is ISDN, then Enabling Echo Cancellation 
	feature is an INVALID Operation. A 'GET' Operation at 
	this object will ALWAYS result in the default value 
	[di"
			::= {	switchTGGrpCfgEntry   4 }

switchFeatureTGFeatureCOMPRESS		OBJECT-TYPE
			SYNTAX	TGFeature
			ACCESS	read-write
			STATUS	mandatory
			DESCRIPTION 
	"Denotes Compression feature. Possible Values are: 
	1. Enable 
	2. Disable 
	NOTE: if TrunkGrpType is ISDN, then Enabling Compression 
	feature, is an INVALID Operation. A 'GET' Operation at 
	this object will ALWAYS result in the default value 
	[disable] bein"
			::= {	switchTGGrpCfgEntry   5 }

switchFeatureTGFeatureSS		OBJECT-TYPE
			SYNTAX	TGFeature
			ACCESS	read-write
			STATUS	mandatory
			DESCRIPTION 
	"Denotes Silent Supression feature. Possible Values are: 
	1. Enable 
	2. Disable 
	NOTE: If TrunkGrpType is ISDN, the Enabling Silent Supression 
	feature, is an INVALID Operation. A 'GET' Operation at 
	this object will ALWAYS result in the default value 
	[di"
			::= {	switchTGGrpCfgEntry   6 }

switchFeatureTGFeatureCNIS		OBJECT-TYPE
			SYNTAX	TGFeature
			ACCESS	read-write
			STATUS	mandatory
			DESCRIPTION 
	"Denotes Caller Number Identitication Service (CNIS) feature. Possible Values are: 
	1. Enable 
	2. Disable 
	NOTE: If TrunkGrpType is SS7, then Enabling Caller Number 
	Identitication Service, is an INVALID Operation. A 'GET' 
	Operation at this object will AL"
			::= {	switchTGGrpCfgEntry   7 }

 -- *************************************************     
 -- SwitchOver
 -- *************************************************     

switchOver		OBJECT-TYPE
			SYNTAX	FTswitchOver
			ACCESS	read-write
			STATUS	mandatory
			DESCRIPTION 
	"FT Switch Over command. The possible options are 
	1) FT_SIG 
	2) FT_ICC 
	3) FT_ISDN 
	4) FT_SPHR 
	5) FT_LM 
	Select any one and set that option. "
			::= {	ftSwitchOverInfo   1 }

 -- *************************************************     
 -- LOG
 -- *************************************************     

logGenTime		OBJECT-TYPE
			SYNTAX	INTEGER(0..120)
			ACCESS	read-write
			STATUS	mandatory
			DESCRIPTION 
	"Switch Log Generation Time. The Parameter Time-interval 
	determines the period of generating new log files. When 
	the time interval is reached, all the current open log 
	files are closed and new log files are generated for future 
	log. The unit for the ti"
			::= {	logFileInfo   1 }

logPurgeTime		OBJECT-TYPE
			SYNTAX	INTEGER(0..120)
			ACCESS	read-write
			STATUS	mandatory
			DESCRIPTION 
	"Switch Log Deletion Time. The Parameter Time-interval 
	determines the period of purging old log files. When 
	the time interval is reached, all the log files older 
	than this time-interval are deleted. The unit for the 
	time-interval is 'minute'. "
			::= {	logFileInfo   2 }

 -- *************************************************     
 -- Log File Generation Enable
 -- *************************************************     

enablelogGen		OBJECT-TYPE
			SYNTAX	LogFileEnDis
			ACCESS	read-write
			STATUS	mandatory
			DESCRIPTION 
	"This option enables the log file Generation. 
	1) ALARM_LOG 
	2) AUDIT_LOG 
	3) MEAS_LOG 
	4) DIAG_LOG 
	5) SCRTY_LOG 
	6) EVENT_LOG 
	7) BILL_LOG 
	8) EMP_LOG 
	9) LOG_ALL 
	Choose any one from drop down list...  "
			::= {	logFileGenEnable   1 }

disableLogGen		OBJECT-TYPE
			SYNTAX	LogFileEnDis
			ACCESS	read-write
			STATUS	mandatory
			DESCRIPTION 
	"This option disables the log file Generation. 
	1) ALARM_LOG 
	2) AUDIT_LOG 
	3) MEAS_LOG 
	4) DIAG_LOG 
	5) SCRTY_LOG 
	6) EVENT_LOG 
	7) BILL_LOG 
	8) EMP_LOG 
	9) LOG_ALL 
	Choose any one from drop down list..  "
			::= {	logFileGenEnable   2 }

logAttribute		OBJECT-TYPE
			SYNTAX	LogFileAttr
			ACCESS	read-write
			STATUS	mandatory
			DESCRIPTION 
	"Allows the user to inquire about the current LOG file attributes. 
	The possible options are : 
	1) ALARM_LOG 
	2) AUDIT_LOG 
	3) MEAS_LOG 
	4) DIAG_LOG 
	5) SCRTY_LOG 
	6) EVENT_LOG 
	7) BILL_LOG 
	8) EMP_LOG 
	Choose any one from drop down list.. "
			::= {	logFileAttribute   1 }

logFileSize		OBJECT-TYPE
			SYNTAX	INTEGER
			ACCESS	read-only
			STATUS	mandatory
			DESCRIPTION 
			""
			::= {	logFileAttribute   2 }

logFileDuration		OBJECT-TYPE
			SYNTAX	INTEGER
			ACCESS	read-only
			STATUS	mandatory
			DESCRIPTION 
			""
			::= {	logFileAttribute   3 }

logFileStatus		OBJECT-TYPE
			SYNTAX	INTEGER
			ACCESS	read-only
			STATUS	mandatory
			DESCRIPTION 
			""
			::= {	logFileAttribute   4 }

 -- *************************************************     
 -- SS7 Link Trace Information Group
 -- *************************************************     

ss7LnkTraceTable		OBJECT-TYPE
			SYNTAX   SEQUENCE OF Ss7LnkTraceEntry
			ACCESS	not-accessible
			STATUS	mandatory
			DESCRIPTION 
	"This Table is specified for Applying Trace Function for any SS7 Link(s). 
	The index of this table is ss7LnkId (integer) "
			::= { ss7LnkTrace	 1 }

ss7LnkTraceEntry		OBJECT-TYPE
			SYNTAX	Ss7LnkTraceEntry
			ACCESS	not-accessible
			STATUS	mandatory
			DESCRIPTION 
			""
			INDEX { ss7LnkId }
			::= {	ss7LnkTraceTable   1 }

Ss7LnkTraceEntry		::= SEQUENCE {
			ss7LnkId		INTEGER,
			ss7LnkLog		LogType,
			ss7LnkEnable		EnableTrace
			}

ss7LnkId		OBJECT-TYPE
			SYNTAX	INTEGER
			ACCESS	read-only
			STATUS	mandatory
			DESCRIPTION 
	"The SS7 link Id on which the Trace Function is to be applied. "
			::= {	ss7LnkTraceEntry   1 }

ss7LnkLog		OBJECT-TYPE
			SYNTAX	LogType
			ACCESS	read-only
			STATUS	mandatory
			DESCRIPTION 
	"This option displays weather log Function is enabled for 
	the specified SS7 Link. "
			::= {	ss7LnkTraceEntry   2 }

ss7LnkEnable		OBJECT-TYPE
			SYNTAX	EnableTrace
			ACCESS	read-write
			STATUS	mandatory
			DESCRIPTION 
	"This option enables/disables the trace Function for 
	the specified SS7 Link. 
	The possible option are: 
	1) Enable 
	2) Disable [default]  "
			::= {	ss7LnkTraceEntry   3 }

 -- *************************************************     
 -- SS7 Route trace Info Group
 -- *************************************************     

ss7RouteTraceTable		OBJECT-TYPE
			SYNTAX   SEQUENCE OF Ss7RouteTraceEntry
			ACCESS	not-accessible
			STATUS	mandatory
			DESCRIPTION 
	"This Table is specified for Applying Trace Function for any SS7 Route(s). 
	The index of this table is ss7RouteDpc (Integer) "
			::= { ss7RouteTrace	 1 }

ss7RouteTraceEntry		OBJECT-TYPE
			SYNTAX	Ss7RouteTraceEntry
			ACCESS	not-accessible
			STATUS	mandatory
			DESCRIPTION 
	"The Current Entry Containes all the objects for this Table. 
	This object is not-accessible, but the user can access all 
	the objects in this table at the next level. "
			INDEX { ss7RouteDpc }
			::= {	ss7RouteTraceTable   1 }

Ss7RouteTraceEntry		::= SEQUENCE {
			ss7RouteDpc		INTEGER,
			ss7RouteLog		LogType,
			ss7RouteEnable		EnableTrace
			}

ss7RouteDpc		OBJECT-TYPE
			SYNTAX	INTEGER
			ACCESS	read-only
			STATUS	mandatory
			DESCRIPTION 
	"The SS7 Point code. The trace Function is to be applied on this route. "
			::= {	ss7RouteTraceEntry   1 }

ss7RouteLog		OBJECT-TYPE
			SYNTAX	LogType
			ACCESS	read-only
			STATUS	mandatory
			DESCRIPTION 
	"This option displays weather Log Function is enabled for 
	the specified SS7 Route. "
			::= {	ss7RouteTraceEntry   2 }

ss7RouteEnable		OBJECT-TYPE
			SYNTAX	EnableTrace
			ACCESS	read-write
			STATUS	mandatory
			DESCRIPTION 
	"This option enables/disables the trace Functions for 
	the specified SS7 Route. 
	The possible option are: 
	1) Enable 
	2) Disable [default]  "
			::= {	ss7RouteTraceEntry   3 }

 -- *************************************************     
 -- ISDN Trunk Trace Info Group
 -- *************************************************     

isdnTrunkTraceTable		OBJECT-TYPE
			SYNTAX   SEQUENCE OF IsdntrunkTraceEntry
			ACCESS	not-accessible
			STATUS	mandatory
			DESCRIPTION 
	"This Table is specified for Applying Trace Function for any ISDN Trunk(s). 
	The index of this table is isdnTrnkId (Integer) "
			::= { isdnTrnkTrace	 1 }

isdnTrunkTraceEntry		OBJECT-TYPE
			SYNTAX	IsdntrunkTraceEntry
			ACCESS	not-accessible
			STATUS	mandatory
			DESCRIPTION 
	"The Current Entry Containes all the objects for this Table. 
	This object is not-accessible, but the user can access all 
	the objects in this table at the next level. "
			INDEX { isdnTrnkId }
			::= {	isdnTrunkTraceTable   1 }

IsdntrunkTraceEntry		::= SEQUENCE {
			isdnTrnkId		INTEGER,
			isdnTrunkLog		LogType,
			isdnTrunkEnable		EnableTrace
			}

isdnTrnkId		OBJECT-TYPE
			SYNTAX	INTEGER
			ACCESS	read-only
			STATUS	mandatory
			DESCRIPTION 
	"The ISDN Trunk Id for which the Trace Function is to be applied. "
			::= {	isdnTrunkTraceEntry   1 }

isdnTrunkLog		OBJECT-TYPE
			SYNTAX	LogType
			ACCESS	read-only
			STATUS	mandatory
			DESCRIPTION 
	"This option displays weather log Function is enabled for 
	the specified ISDN Trunk.  "
			::= {	isdnTrunkTraceEntry   2 }

isdnTrunkEnable		OBJECT-TYPE
			SYNTAX	EnableTrace
			ACCESS	read-write
			STATUS	mandatory
			DESCRIPTION 
	"This option enables/disables the trace Functions for 
	the specified ISDN Trunk. 
	The possible option are: 
	1) Enable 
	2) Disable [default]  "
			::= {	isdnTrunkTraceEntry   3 }

 -- *************************************************     
 -- Audit ISDN Trunk
 -- *************************************************     

auditISDNTrnkTable		OBJECT-TYPE
			SYNTAX   SEQUENCE OF AuditISDNTrnkCfgEntry
			ACCESS	not-accessible
			STATUS	mandatory
			DESCRIPTION 
	"Audit ISDN Trunk Table. 
	This table has one index: auditTrnkId (Integer) "
			::= { auditInfo	 1 }

auditISDNTrnkCfgEntry		OBJECT-TYPE
			SYNTAX	AuditISDNTrnkCfgEntry
			ACCESS	not-accessible
			STATUS	mandatory
			DESCRIPTION 
	"The Current Entry Containes all the objects for this Table. 
	This object is not-accessible, but the user can access all 
	the objects in this table at the next level. "
			INDEX { auditTrnkId }
			::= {	auditISDNTrnkTable   1 }

AuditISDNTrnkCfgEntry		::= SEQUENCE {
			auditTrnkId		INTEGER,
			auditISDNTrnk		AuditOperation
			}

auditTrnkId		OBJECT-TYPE
			SYNTAX	INTEGER
			ACCESS	read-only
			STATUS	mandatory
			DESCRIPTION 
	"The ISDN Trunk Id on which the audit operation is being applied. "
			::= {	auditISDNTrnkCfgEntry   1 }

auditISDNTrnk		OBJECT-TYPE
			SYNTAX	AuditOperation
			ACCESS	read-write
			STATUS	mandatory
			DESCRIPTION 
	"This Object is set to Apply Audit on this particular ISDN Trunk. 
	The possible option for 'SET' is 
	1) audit 
	A 'GET' Operation on this object would result the default value 
	'no action' being displayed. "
			::= {	auditISDNTrnkCfgEntry   2 }

 -- *************************************************     
 -- Audit Xlink
 -- *************************************************     

auditXLink		OBJECT-TYPE
			SYNTAX	AuditOperation
			ACCESS	read-write
			STATUS	mandatory
			DESCRIPTION 
	"This option audits the All the existing XLinks. "
			::= {	auditInfo   2 }

 -- *************************************************     
 -- Audit DPC
 -- *************************************************     

auditDPCTable		OBJECT-TYPE
			SYNTAX   SEQUENCE OF AuditDPCCfgEntry
			ACCESS	not-accessible
			STATUS	mandatory
			DESCRIPTION 
	"The Current Entry Containes all the objects for this Table. 
	This object is not-accessible, but the user can access all 
	the objects in this table at the next level. "
			::= { auditInfo	 3 }

auditDPCCfgEntry		OBJECT-TYPE
			SYNTAX	AuditDPCCfgEntry
			ACCESS	not-accessible
			STATUS	mandatory
			DESCRIPTION 
			""
			INDEX { auditPointCode }
			::= {	auditDPCTable   1 }

AuditDPCCfgEntry		::= SEQUENCE {
			auditPointCode		INTEGER,
			auditPointCodeType		AuditType,
			auditDPC		AuditOperation
			}

auditPointCode		OBJECT-TYPE
			SYNTAX	INTEGER
			ACCESS	read-only
			STATUS	mandatory
			DESCRIPTION 
	"The Point Code on which the audit operation is being applied. "
			::= {	auditDPCCfgEntry   1 }

auditPointCodeType		OBJECT-TYPE
			SYNTAX	AuditType
			ACCESS	read-only
			STATUS	mandatory
			DESCRIPTION 
	"The Point Code Type. Ansi/Itu. "
			::= {	auditDPCCfgEntry   2 }

auditDPC		OBJECT-TYPE
			SYNTAX	AuditOperation
			ACCESS	read-write
			STATUS	mandatory
			DESCRIPTION 
	"This Object is set to Apply Audit on this particular DPC. 
	The possible option for 'SET' is 
	1) audit 
	A 'GET' Operation on this object would result the default value 
	'no action' being displayed. "
			::= {	auditDPCCfgEntry   3 }

 -- *************************************************     
 -- Audit Period
 -- *************************************************     

auditPeriodGrp		OBJECT IDENTIFIER   ::=	{ auditInfo	 4 }

 -- *************************************************     
 -- Audit Info table
 -- *************************************************     

auditTimePeriod		OBJECT-TYPE
			SYNTAX	INTEGER(1..65535)
			ACCESS	read-write
			STATUS	mandatory
			DESCRIPTION 
	"The Audit Period for which the audit operation is being applied. "
			::= {	auditPeriodGrp   1 }

auditPeriod		OBJECT-TYPE
			SYNTAX	AuditOperation
			ACCESS	read-write
			STATUS	mandatory
			DESCRIPTION 
	"This Object is set to Apply Audit for this particular Period. 
	The possible option for 'SET' is 
	1) audit 
	A 'GET' Operation on this object would result the default value 
	'no action' being displayed. "
			::= {	auditPeriodGrp   2 }

 -- *************************************************     
 -- Process Status
 -- *************************************************     

statusLM1ProcId		OBJECT-TYPE
			SYNTAX	ProcessStatus
			ACCESS	read-only
			STATUS	mandatory
			DESCRIPTION 
	"Indicates the current status of FT_LM: Process Id 512. "
			::= {	processStatusInfo   1 }

statusLM2ProcID		OBJECT-TYPE
			SYNTAX	ProcessStatus
			ACCESS	read-only
			STATUS	mandatory
			DESCRIPTION 
	"Indicates the current status of FT_LM: Process Id 511. "
			::= {	processStatusInfo   2 }

statusICC1ProcId		OBJECT-TYPE
			SYNTAX	ProcessStatus
			ACCESS	read-only
			STATUS	mandatory
			DESCRIPTION 
	"Indicates the current status of FT_ICC : Process Id 480. "
			::= {	processStatusInfo   3 }

statusICC2ProcId		OBJECT-TYPE
			SYNTAX	ProcessStatus
			ACCESS	read-only
			STATUS	mandatory
			DESCRIPTION 
	"Indicates the current status of FT_ICC: Process Id 496. "
			::= {	processStatusInfo   4 }

statusISDN1ProcId		OBJECT-TYPE
			SYNTAX	ProcessStatus
			ACCESS	read-only
			STATUS	mandatory
			DESCRIPTION 
	"Indicates the current status of FT_ISDN: Process Id 476. "
			::= {	processStatusInfo   5 }

statusISDN2ProcId		OBJECT-TYPE
			SYNTAX	ProcessStatus
			ACCESS	read-only
			STATUS	mandatory
			DESCRIPTION 
	"Indicates the current status of FT_ISDN: Process Id 472. "
			::= {	processStatusInfo   6 }

statusSPHR1ProcId		OBJECT-TYPE
			SYNTAX	ProcessStatus
			ACCESS	read-only
			STATUS	mandatory
			DESCRIPTION 
	"Indicates the current status of FT_SPHR: Process Id 448. "
			::= {	processStatusInfo   7 }

statusSPHR2ProcId		OBJECT-TYPE
			SYNTAX	ProcessStatus
			ACCESS	read-only
			STATUS	mandatory
			DESCRIPTION 
	"Indicates the current status of FT_SPHR: Process Id 464. "
			::= {	processStatusInfo   8 }

statusSIG1ProcId		OBJECT-TYPE
			SYNTAX	ProcessStatus
			ACCESS	read-only
			STATUS	mandatory
			DESCRIPTION 
	"Indicates the current status of FT_SIG: Process Id 384. "
			::= {	processStatusInfo   9 }

statusSIG2ProcId		OBJECT-TYPE
			SYNTAX	ProcessStatus
			ACCESS	read-only
			STATUS	mandatory
			DESCRIPTION 
	"Indicates the current status of FT_SIG: Process Id 400. "
			::= {	processStatusInfo   10 }

statusMTP21ProcId		OBJECT-TYPE
			SYNTAX	ProcessStatus
			ACCESS	read-only
			STATUS	mandatory
			DESCRIPTION 
	"Indicates the current status of Mtp2: Process Id 320.  "
			::= {	processStatusInfo   11 }

statusMTP22ProcId		OBJECT-TYPE
			SYNTAX	ProcessStatus
			ACCESS	read-only
			STATUS	mandatory
			DESCRIPTION 
	"Indicates the current status of Mtp2: Process Id 321. "
			::= {	processStatusInfo   12 }

statusMTP23ProcId		OBJECT-TYPE
			SYNTAX	ProcessStatus
			ACCESS	read-only
			STATUS	mandatory
			DESCRIPTION 
	"Indicates the current status of Mtp2 : Process Id 322. "
			::= {	processStatusInfo   13 }

statusMTP24ProcId		OBJECT-TYPE
			SYNTAX	ProcessStatus
			ACCESS	read-only
			STATUS	mandatory
			DESCRIPTION 
	"Indicates the current status of Mtp2: Process Id 323.  "
			::= {	processStatusInfo   14 }

 -- *************************************************     
 -- NMS Status
 -- *************************************************     

ethernetConnStatus		OBJECT-TYPE
			SYNTAX	EthernetConnStatus
			ACCESS	read-only
			STATUS	mandatory
			DESCRIPTION 
	"Current Status of the Ethernet Connection to MSSC. 
	'SET' Operation is NOT APPLICABLE. 
	For the 'GET' Operation, the possible options are 
	1) active 
	2) down  "
			::= {	ethernetConnStatusInfo   1 }

 -- *************************************************     
 -- Trap Objects
 -- *************************************************     

trapOpc		OBJECT-TYPE
			SYNTAX	INTEGER(1..16777215)
			ACCESS	read-only
			STATUS	mandatory
			DESCRIPTION 
	"Indicate the point code of the switch that send trap "
			::= {	trapObjects   1 }

trapXconnectId		OBJECT-TYPE
			SYNTAX	INTEGER
			ACCESS	read-only
			STATUS	mandatory
			DESCRIPTION 
	"Indicate the id of the xconnect that send trap "
			::= {	trapObjects   2 }

trapLinkId		OBJECT-TYPE
			SYNTAX	INTEGER
			ACCESS	read-only
			STATUS	mandatory
			DESCRIPTION 
	"Indicate the id of the link that abnormal situation "
			::= {	trapObjects   3 }

trapSlotId		OBJECT-TYPE
			SYNTAX	INTEGER
			ACCESS	read-only
			STATUS	mandatory
			DESCRIPTION 
	"Indicate the id of the slot that has abnormal situation "
			::= {	trapObjects   4 }

trapPortId		OBJECT-TYPE
			SYNTAX	INTEGER
			ACCESS	read-only
			STATUS	mandatory
			DESCRIPTION 
	"Indicate the id of the port that has abnormal situation "
			::= {	trapObjects   5 }

trapTrunkId		OBJECT-TYPE
			SYNTAX	INTEGER
			ACCESS	read-only
			STATUS	mandatory
			DESCRIPTION 
	"Indicate the id of the trunk that has abnormal situation "
			::= {	trapObjects   6 }

trapInterfaceId		OBJECT-TYPE
			SYNTAX	INTEGER
			ACCESS	read-only
			STATUS	mandatory
			DESCRIPTION 
	"Indicate the id of the interface that has abnormal situation "
			::= {	trapObjects   7 }

trapChnlId		OBJECT-TYPE
			SYNTAX	INTEGER
			ACCESS	read-only
			STATUS	mandatory
			DESCRIPTION 
	"Indicate the id of the channel that has abnormal situation "
			::= {	trapObjects   8 }

trapDbId		OBJECT-TYPE
			SYNTAX	INTEGER
			ACCESS	read-only
			STATUS	mandatory
			DESCRIPTION 
	"Indicate the id of the database that has abnormal situation "
			::= {	trapObjects   9 }

trapLinkName		OBJECT-TYPE
			SYNTAX	NameString
			ACCESS	read-only
			STATUS	mandatory
			DESCRIPTION 
	"Indicate the name of the link that has abnormal situation "
			::= {	trapObjects   10 }

trapSwitchName		OBJECT-TYPE
			SYNTAX	DisplayString
			ACCESS	read-only
			STATUS	mandatory
			DESCRIPTION 
	"Indicate the name "
			::= {	trapObjects   11 }

trapCicvalue		OBJECT-TYPE
			SYNTAX	INTEGER
			ACCESS	read-only
			STATUS	mandatory
			DESCRIPTION 
	"Indicate Circuit Identification Code value. "
			::= {	trapObjects   12 }

trapCicrange		OBJECT-TYPE
			SYNTAX	INTEGER
			ACCESS	read-only
			STATUS	mandatory
			DESCRIPTION 
	"Integer identifying the range ex. no. cics. "
			::= {	trapObjects   13 }

trapCause		OBJECT-TYPE
			SYNTAX	DisplayString(SIZE(1..33))
			ACCESS	read-only
			STATUS	mandatory
			DESCRIPTION 
	"Cause indicates Causes for ISUP related alarms: BLOCKING UNBLOCKING INVALIDRNG GROUPBLOCKING GROUPUNBLOCKACK RESETCIRCUIT RESETRELCOMP GROUPRESETCIRCUIT GROUPRESETACK CIRCUITQUERYRESP VALIDATIONSUCCESS VALIDATIONFAILED VALIDATIONFAILEDWRONGCLLI OTHERS"
			::= {	trapObjects   14 }

trapDpc		OBJECT-TYPE
			SYNTAX	INTEGER(1..16777215)
			ACCESS	read-only
			STATUS	mandatory
			DESCRIPTION 
	"Indicate the point code of the switch "
			::= {	trapObjects   15 }

trapCdrFileSeqNum		OBJECT-TYPE
			SYNTAX	INTEGER
			ACCESS	read-only
			STATUS	mandatory
			DESCRIPTION 
	"Indicate the sequence number of the cdr file that has 
	abnormal situation "
			::= {	trapObjects   16 }

trapCdrFileName		OBJECT-TYPE
			SYNTAX	DisplayString(SIZE(1..255))
			ACCESS	read-only
			STATUS	mandatory
			DESCRIPTION 
	"Indicates the CDR file name or file directory. Can be any combination of 
	alphanumeric characters. Spaces are allowed and cannot 
	exceed 255 characters. "
			::= {	trapObjects   17 }

trapMeasErrCause		OBJECT-TYPE
			SYNTAX	INTEGER
			ACCESS	read-only
			STATUS	mandatory
			DESCRIPTION 
	"Indicates the Measurement Files error operation cause "
			::= {	trapObjects   18 }

trapMeasErrNum		OBJECT-TYPE
			SYNTAX	INTEGER
			ACCESS	read-only
			STATUS	mandatory
			DESCRIPTION 
	"Indicates the Measurement Files error number of the operation "
			::= {	trapObjects   19 }

trapRepeatNum		OBJECT-TYPE
			SYNTAX	INTEGER
			ACCESS	read-only
			STATUS	mandatory
			DESCRIPTION 
	"Indicate the count that trap has occured "
			::= {	trapObjects   20 }

trapSeverity		OBJECT-TYPE
			SYNTAX	DisplayString
			ACCESS	read-only
			STATUS	mandatory
			DESCRIPTION 
	"Indicate the severity of the sent trap "
			::= {	trapObjects   21 }

trapProcessId		OBJECT-TYPE
			SYNTAX	INTEGER
			ACCESS	read-only
			STATUS	mandatory
			DESCRIPTION 
	"Indicate the process id for that trap has occured "
			::= {	trapObjects   22 }

trapBucketSize		OBJECT-TYPE
			SYNTAX	INTEGER
			ACCESS	read-only
			STATUS	mandatory
			DESCRIPTION 
	"Indicate the process Bucket size for the Process for which the trap has occured "
			::= {	trapObjects   23 }

trapNode1Id		OBJECT-TYPE
			SYNTAX	INTEGER
			ACCESS	read-only
			STATUS	mandatory
			DESCRIPTION 
	"Indicates the src Xconnect Id which cause congestion "
			::= {	trapObjects   24 }

trapNode2Id		OBJECT-TYPE
			SYNTAX	INTEGER
			ACCESS	read-only
			STATUS	mandatory
			DESCRIPTION 
	"Indicates the dest Xconnect Id which cause congestion "
			::= {	trapObjects   25 }

trapRoutename		OBJECT-TYPE
			SYNTAX	DisplayString
			ACCESS	read-only
			STATUS	mandatory
			DESCRIPTION 
	"indicate the xoute name that is not found between the xlink "
			::= {	trapObjects   26 }

trapMeasFileName		OBJECT-TYPE
			SYNTAX	DisplayString(SIZE(1..255))
			ACCESS	read-only
			STATUS	mandatory
			DESCRIPTION 
	"indicate the Measurement file name. Can be any combination of 
	alphanumeric characters. Spaces are allowed and cannot 
	exceed 64 characters. "
			::= {	trapObjects   27 }

trapDirectory		OBJECT-TYPE
			SYNTAX	DisplayString
			ACCESS	read-only
			STATUS	mandatory
			DESCRIPTION 
	"indicate the Cdr File Directory "
			::= {	trapObjects   28 }

trapProcessorId		OBJECT-TYPE
			SYNTAX	INTEGER
			ACCESS	read-only
			STATUS	mandatory
			DESCRIPTION 
	"Indicates the Process Id "
			::= {	trapObjects   29 }

trapLogFileName		OBJECT-TYPE
			SYNTAX	DisplayString(SIZE(1..255))
			ACCESS	read-only
			STATUS	mandatory
			DESCRIPTION 
	"Indicate the Log file name. Can be any combination of 
	alphanumeric characters. Spaces are allowed and cannot 
	exceed 64 characters. "
			::= {	trapObjects   30 }

trapLogErrcause		OBJECT-TYPE
			SYNTAX	DisplayString(SIZE(1..64))
			ACCESS	read-only
			STATUS	mandatory
			DESCRIPTION 
	"Indicate the Log error operation cause "
			::= {	trapObjects   31 }

trapLogErrNo		OBJECT-TYPE
			SYNTAX	INTEGER
			ACCESS	read-only
			STATUS	mandatory
			DESCRIPTION 
	"Indicate the log cdr error number of the operation "
			::= {	trapObjects   32 }

trapPsuNo		OBJECT-TYPE
			SYNTAX	INTEGER
			ACCESS	read-only
			STATUS	mandatory
			DESCRIPTION 
	"Indicate the Power supply number "
			::= {	trapObjects   33 }

trapIntId		OBJECT-TYPE
			SYNTAX	INTEGER
			ACCESS	read-only
			STATUS	mandatory
			DESCRIPTION 
	"Indicate the Power supply number "
			::= {	trapObjects   34 }

trapIntfcId		OBJECT-TYPE
			SYNTAX	INTEGER
			ACCESS	read-only
			STATUS	mandatory
			DESCRIPTION 
	"Indicate the Power supply number "
			::= {	trapObjects   35 }

trapLanId		OBJECT-TYPE
			SYNTAX	INTEGER
			ACCESS	read-only
			STATUS	mandatory
			DESCRIPTION 
	"Indicate theLan ID  "
			::= {	trapObjects   36 }

trapnumXlinks		OBJECT-TYPE
			SYNTAX	INTEGER
			ACCESS	read-only
			STATUS	mandatory
			DESCRIPTION 
	"Indicate the no of existing links  "
			::= {	trapObjects   37 }

trapSwitchId1		OBJECT-TYPE
			SYNTAX	INTEGER
			ACCESS	read-only
			STATUS	mandatory
			DESCRIPTION 
	"Indicate the xconnect Id  "
			::= {	trapObjects   38 }

trapSwitchId2		OBJECT-TYPE
			SYNTAX	INTEGER
			ACCESS	read-only
			STATUS	mandatory
			DESCRIPTION 
	"Indicate the xconnect Id  "
			::= {	trapObjects   39 }

trapProcInstNo		OBJECT-TYPE
			SYNTAX	INTEGER
			ACCESS	read-only
			STATUS	mandatory
			DESCRIPTION 
	"Indicate the Process instance number "
			::= {	trapObjects   40 }

trapProcName		OBJECT-TYPE
			SYNTAX	DisplayString(SIZE(1..15))
			ACCESS	read-only
			STATUS	mandatory
			DESCRIPTION 
	"Indicate the Process name that Failed "
			::= {	trapObjects   41 }

trapFanNo		OBJECT-TYPE
			SYNTAX	INTEGER
			ACCESS	read-only
			STATUS	mandatory
			DESCRIPTION 
	"Indicate the Fan Number "
			::= {	trapObjects   42 }

trapUserName		OBJECT-TYPE
			SYNTAX	NameString
			ACCESS	read-only
			STATUS	mandatory
			DESCRIPTION 
	"indicates the user login Name  "
			::= {	trapObjects   43 }

trapBitMapStatus		OBJECT-TYPE
			SYNTAX	DisplayString(SIZE(1..33))
			ACCESS	read-only
			STATUS	mandatory
			DESCRIPTION 
	"Indicates the Bit Map Status of the Cics that are blocked. This Status is only valid for GROUPBLOCKING (I.e range >1)"
			::= {	trapObjects   44 }

 -- *************************************************     
 -- Alarm Group
 -- *************************************************     

alarmTraps		OBJECT IDENTIFIER   ::=	{ alarmGrp	 1 }

 -- *************************************************     
 -- Alarm Traps Group
 -- *************************************************     

genswitchSnmpAgentReadyNotify		TRAP-TYPE
	ENTERPRISE	alarmTraps
	VARIABLES   { trapSeverity, trapOpc, trapSwitchName }
	DESCRIPTION 
	"Info : SNMP Agent is up "
	::=  1

genConsoleLoginNotify		TRAP-TYPE
	ENTERPRISE	alarmTraps
	VARIABLES   { trapSeverity, trapOpc, trapSwitchName, trapUserName }
	DESCRIPTION 
	"Info : A user has successfully logged in from console "
	::=  2

genConsoleLogoutNotify		TRAP-TYPE
	ENTERPRISE	alarmTraps
	VARIABLES   { trapSeverity, trapOpc, trapSwitchName, trapUserName }
	DESCRIPTION 
	"Info : A user has successfully logged out from console "
	::=  3

genProcessBufOverflowNotify		TRAP-TYPE
	ENTERPRISE	alarmTraps
	VARIABLES   { trapSeverity, trapOpc, trapSwitchName, trapProcName, trapProcInstNo, trapBucketSize }
	DESCRIPTION 
	"Info : Process ran out of buffer "
	::=  4

genProcessBufOverflowRecoverNotify		TRAP-TYPE
	ENTERPRISE	alarmTraps
	VARIABLES   { trapSeverity, trapOpc, trapSwitchName, trapProcName, trapProcInstNo, trapBucketSize }
	DESCRIPTION 
	"Info : Process Recovered from Buffer Overflow "
	::=  5

genProcessHeapOverFlowNotify		TRAP-TYPE
	ENTERPRISE	alarmTraps
	VARIABLES   { trapSeverity, trapOpc, trapSwitchName, trapProcName, trapProcInstNo }
	DESCRIPTION 
	"Info : Process Heap OverFlow Detected "
	::=  6

genProcessHeapOverFlowRecoverNotify		TRAP-TYPE
	ENTERPRISE	alarmTraps
	VARIABLES   { trapSeverity, trapOpc, trapSwitchName, trapProcName, trapProcInstNo }
	DESCRIPTION 
	"Info : Recovered from Process Heap Overflow "
	::=  7

xconnectUpNotify		TRAP-TYPE
	ENTERPRISE	alarmTraps
	VARIABLES   { trapSeverity, trapOpc, trapSwitchName, trapXconnectId }
	DESCRIPTION 
	"Info : switch has successfully brought up TCP/IP link between MSCG and AC 120 xconnect "
	::=  8

xconnectDnNotify		TRAP-TYPE
	ENTERPRISE	alarmTraps
	VARIABLES   { trapSeverity, trapOpc, trapSwitchName, trapXconnectId }
	DESCRIPTION 
	"Info : switch has a failure on TCP/IP link between MSCG and AC120 "
	::=  9

xconnectClkClearNotify		TRAP-TYPE
	ENTERPRISE	alarmTraps
	VARIABLES   { trapSeverity, trapOpc, trapSwitchName, trapSlotId, trapPortId, trapXconnectId }
	DESCRIPTION 
	"Info : Stratum Card is available "
	::=  10

xconnectClkFailNotify		TRAP-TYPE
	ENTERPRISE	alarmTraps
	VARIABLES   { trapSeverity, trapOpc, trapSwitchName, trapSlotId, trapPortId, trapXconnectId }
	DESCRIPTION 
	"Info : Stratum Card has either been removed or has failed "
	::=  11

xconnectBkplaneRefClkClearNotify		TRAP-TYPE
	ENTERPRISE	alarmTraps
	VARIABLES   { trapSeverity, trapOpc, trapSwitchName, trapSlotId, trapXconnectId }
	DESCRIPTION 
	"Info : Back Plane reference clock clear "
	::=  12

xconnectBkplaneRefClkFailNotify		TRAP-TYPE
	ENTERPRISE	alarmTraps
	VARIABLES   { trapSeverity, trapOpc, trapSwitchName, trapSlotId, trapPortId, trapXconnectId }
	DESCRIPTION 
	"Info : Back Plane reference clock fail "
	::=  13

xconnectInterfaceInServiceNotify		TRAP-TYPE
	ENTERPRISE	alarmTraps
	VARIABLES   { trapSeverity, trapOpc, trapSwitchName, trapSlotId, trapPortId, trapXconnectId }
	DESCRIPTION 
	"Info : Switch has successfully brought the specified interface to be in service "
	::=  14

xconnectInterfaceOutOfServiceNotify		TRAP-TYPE
	ENTERPRISE	alarmTraps
	VARIABLES   { trapSeverity, trapOpc, trapSwitchName, trapSlotId, trapPortId, trapXconnectId }
	DESCRIPTION 
	"Info : An interface card is out of service "
	::=  15

xconnectCardInsertionNotify		TRAP-TYPE
	ENTERPRISE	alarmTraps
	VARIABLES   { trapSeverity, trapOpc, trapSwitchName, trapSlotId, trapXconnectId }
	DESCRIPTION 
	"Info : A card is inserted in xconnect "
	::=  16

xconnectCardRemovalNotify		TRAP-TYPE
	ENTERPRISE	alarmTraps
	VARIABLES   { trapSeverity, trapOpc, trapSwitchName, trapSlotId, trapXconnectId }
	DESCRIPTION 
	"Info : A card is removed from xconnect "
	::=  17

xconnectIllegalCardTypeNotify		TRAP-TYPE
	ENTERPRISE	alarmTraps
	VARIABLES   { trapSeverity, trapOpc, trapSwitchName, trapSlotId, trapXconnectId }
	DESCRIPTION 
	"Info : Illegal Card Type "
	::=  18

xconnectIntfFarEndLOFNotify		TRAP-TYPE
	ENTERPRISE	alarmTraps
	VARIABLES   { trapSeverity, trapOpc, trapSwitchName, trapSlotId, trapPortId, trapXconnectId }
	DESCRIPTION 
	"Info : Interface Far end LOF "
	::=  19

xconnectIntfFarEndAISNotify		TRAP-TYPE
	ENTERPRISE	alarmTraps
	VARIABLES   { trapSeverity, trapOpc, trapSwitchName, trapSlotId, trapPortId, trapXconnectId }
	DESCRIPTION 
	"Info : Interface Far end AIS "
	::=  20

xconnectIntfNearEndLOFNotify		TRAP-TYPE
	ENTERPRISE	alarmTraps
	VARIABLES   { trapSeverity, trapOpc, trapSwitchName, trapSlotId, trapPortId, trapXconnectId }
	DESCRIPTION 
	"Info : Interface Near end LOF "
	::=  21

xconnectIntfNearEndLOSNotify		TRAP-TYPE
	ENTERPRISE	alarmTraps
	VARIABLES   { trapSeverity, trapOpc, trapSwitchName, trapSlotId, trapPortId, trapXconnectId }
	DESCRIPTION 
	"Info : Interface Near end LOS "
	::=  22

xconnectIntfCreateNotify		TRAP-TYPE
	ENTERPRISE	alarmTraps
	VARIABLES   { trapSeverity, trapOpc, trapSwitchName, trapSlotId, trapPortId, trapXconnectId }
	DESCRIPTION 
	"Info : Interface in AC120 has been created "
	::=  23

xconnectIntfDeleteNotify		TRAP-TYPE
	ENTERPRISE	alarmTraps
	VARIABLES   { trapSeverity, trapOpc, trapSwitchName, trapSlotId, trapPortId, trapXconnectId }
	DESCRIPTION 
	"Info : Interface in AC120 has been deleted "
	::=  24

xconnectXlinkAdjConClrNotify		TRAP-TYPE
	ENTERPRISE	alarmTraps
	VARIABLES   { trapSeverity, trapOpc, trapSwitchName, trapNode1Id, trapNode2Id, trapnumXlinks }
	DESCRIPTION 
	"Info : Xconnect Adjacent Congestion cleared "
	::=  25

xconnectXlinkAdjConNotify		TRAP-TYPE
	ENTERPRISE	alarmTraps
	VARIABLES   { trapSeverity, trapOpc, trapSwitchName, trapNode1Id, trapNode2Id, trapnumXlinks }
	DESCRIPTION 
	"Info : Xconnect Adjacent Congestion Notified "
	::=  26

xconnectXlinkRouteFailNotify		TRAP-TYPE
	ENTERPRISE	alarmTraps
	VARIABLES   { trapSeverity, trapOpc, trapSwitchName, trapNode1Id, trapNode2Id }
	DESCRIPTION 
	"Info : Xpath not found between the Xlink "
	::=  27

xconnectPortUpNotify		TRAP-TYPE
	ENTERPRISE	alarmTraps
	VARIABLES   { trapSeverity, trapOpc, trapSwitchName, trapSlotId, trapPortId, trapXconnectId }
	DESCRIPTION 
	"Info : Port is Up "
	::=  28

xconnectCPUSwitchOverNotify		TRAP-TYPE
	ENTERPRISE	alarmTraps
	VARIABLES   { trapSeverity, trapOpc, trapSwitchName, trapXconnectId }
	DESCRIPTION 
	"Info : XConnect CPU SwitchOver "
	::=  29

atmRAINotify		TRAP-TYPE
	ENTERPRISE	alarmTraps
	VARIABLES   { trapSeverity, trapOpc, trapSwitchName, trapSlotId, trapPortId, trapXconnectId }
	DESCRIPTION 
	"Info : ATM Remote Alarm Indication "
	::=  30

atmAISNotify		TRAP-TYPE
	ENTERPRISE	alarmTraps
	VARIABLES   { trapSeverity, trapOpc, trapSwitchName, trapSlotId, trapPortId, trapXconnectId }
	DESCRIPTION 
	"Info : ATM AIS "
	::=  31

atmLOFNotify		TRAP-TYPE
	ENTERPRISE	alarmTraps
	VARIABLES   { trapSeverity, trapOpc, trapSwitchName, trapSlotId, trapPortId, trapXconnectId }
	DESCRIPTION 
	"Info : ATM LOF "
	::=  32

atmLOSNotify		TRAP-TYPE
	ENTERPRISE	alarmTraps
	VARIABLES   { trapSeverity, trapOpc, trapSwitchName, trapSlotId, trapPortId, trapXconnectId }
	DESCRIPTION 
	"Info : ATM LOS "
	::=  33

mfdClearNotify		TRAP-TYPE
	ENTERPRISE	alarmTraps
	VARIABLES   { trapSeverity, trapOpc, trapSwitchName, trapTrunkId, trapChnlId }
	DESCRIPTION 
	"Info : A potential fault modem is cleared "
	::=  34

mfdDetectionNotify		TRAP-TYPE
	ENTERPRISE	alarmTraps
	VARIABLES   { trapSeverity, trapOpc, trapSwitchName, trapRepeatNum, trapTrunkId, trapChnlId }
	DESCRIPTION 
	"Info : Faulty Modem: A Potential Faulty Modem has been Detected "
	::=  35

measFileReadyNotify		TRAP-TYPE
	ENTERPRISE	alarmTraps
	VARIABLES   { trapSeverity, trapOpc, trapSwitchName, trapMeasFileName }
	DESCRIPTION 
	"Info : Measurement file is ready for FTP  "
	::=  36

measDiskOverCrtclThresholdNotify		TRAP-TYPE
	ENTERPRISE	alarmTraps
	VARIABLES   { trapSeverity, trapOpc, trapSwitchName, trapMeasErrCause, trapMeasErrNum }
	DESCRIPTION 
	"Info : The partition that the measurement file resides on is over critical threshold. "
	::=  37

measFileMoveNotify		TRAP-TYPE
	ENTERPRISE	alarmTraps
	VARIABLES   { trapSeverity, trapOpc, trapSwitchName, trapMeasFileName }
	DESCRIPTION 
	"Info : Measurement file moved to secondary directory "
	::=  38

measFileMoveErrNotify		TRAP-TYPE
	ENTERPRISE	alarmTraps
	VARIABLES   { trapSeverity, trapOpc, trapSwitchName, trapMeasFileName }
	DESCRIPTION 
	"Info : Error in moving Measurement file to secondary directory "
	::=  39

measFileOpenErrNotify		TRAP-TYPE
	ENTERPRISE	alarmTraps
	VARIABLES   { trapSeverity, trapOpc, trapSwitchName, trapMeasFileName }
	DESCRIPTION 
	"Info : Measurement open file error  "
	::=  40

measFileDeleteNotify		TRAP-TYPE
	ENTERPRISE	alarmTraps
	VARIABLES   { trapSeverity, trapOpc, trapSwitchName, trapMeasFileName }
	DESCRIPTION 
	"Info : Measurement file deleted "
	::=  41

measFileDeleteErrNotify		TRAP-TYPE
	ENTERPRISE	alarmTraps
	VARIABLES   { trapSeverity, trapOpc, trapSwitchName, trapMeasFileName }
	DESCRIPTION 
	"Info : Measurement delete file error "
	::=  42

cdrFileReadyNotify		TRAP-TYPE
	ENTERPRISE	alarmTraps
	VARIABLES   { trapSeverity, trapOpc, trapSwitchName, trapCdrFileName }
	DESCRIPTION 
	"Info :Cdr file is ready for Polling "
	::=  43

cdrDiskFullNotify		TRAP-TYPE
	ENTERPRISE	alarmTraps
	VARIABLES   { trapSeverity, trapOpc, trapSwitchName, trapDirectory }
	DESCRIPTION 
	"Info :CDR file disk usage reach critical threshold  "
	::=  44

cdrFileOpenErrNotify		TRAP-TYPE
	ENTERPRISE	alarmTraps
	VARIABLES   { trapSeverity, trapOpc, trapSwitchName, trapCdrFileName }
	DESCRIPTION 
	"Info :CDR open file error  "
	::=  45

cdrFileMoveErrNotify		TRAP-TYPE
	ENTERPRISE	alarmTraps
	VARIABLES   { trapSeverity, trapOpc, trapSwitchName, trapCdrFileName }
	DESCRIPTION 
	"Info : Error in moving CDR file from temp location to target CDR file location "
	::=  46

cdrDeleteErrNotify		TRAP-TYPE
	ENTERPRISE	alarmTraps
	VARIABLES   { trapSeverity, trapOpc, trapSwitchName, trapCdrFileName }
	DESCRIPTION 
	"Info : CDR file cannot be deleted  "
	::=  47

cdrWriteHeaderErrNotify		TRAP-TYPE
	ENTERPRISE	alarmTraps
	VARIABLES   { trapSeverity, trapOpc, trapSwitchName, trapCdrFileName }
	DESCRIPTION 
	"Info :Error in writing CDR file header "
	::=  48

cdrWriteRecErrNotify		TRAP-TYPE
	ENTERPRISE	alarmTraps
	VARIABLES   { trapSeverity, trapOpc, trapSwitchName, trapCdrFileName }
	DESCRIPTION 
	"Info :Error in writing CDR record "
	::=  49

cdrErrFileLocErrNotify		TRAP-TYPE
	ENTERPRISE	alarmTraps
	VARIABLES   { trapSeverity, trapOpc, trapSwitchName, trapCdrFileName }
	DESCRIPTION 
	"Info: Invalid Cdr Directory "
	::=  50

cdrErrTempFileLocErrNotify		TRAP-TYPE
	ENTERPRISE	alarmTraps
	VARIABLES   { trapSeverity, trapOpc, trapSwitchName, trapCdrFileName }
	DESCRIPTION 
	"Info: Invalid Cdr Directory "
	::=  51

cdrFileSysErrNotify		TRAP-TYPE
	ENTERPRISE	alarmTraps
	VARIABLES   { trapSeverity, trapOpc, trapSwitchName, trapCdrFileName }
	DESCRIPTION 
	"Info: Cdr File System Operation error. "
	::=  52

cdrFileCloseErrNotify		TRAP-TYPE
	ENTERPRISE	alarmTraps
	VARIABLES   { trapSeverity, trapOpc, trapSwitchName, trapCdrFileName }
	DESCRIPTION 
	"Info: Error in closing CDR file "
	::=  53

cdrFileDelete5DaysNotify		TRAP-TYPE
	ENTERPRISE	alarmTraps
	VARIABLES   { trapSeverity, trapOpc, trapSwitchName, trapCdrFileName }
	DESCRIPTION 
	"Info: cdr files created within past 5 days are deleted "
	::=  54

ss7LinkUpNotify		TRAP-TYPE
	ENTERPRISE	alarmTraps
	VARIABLES   { trapSeverity, trapOpc, trapSwitchName, trapLinkId }
	DESCRIPTION 
	"Info : switch has successfully brought up ss7 mtp3 link "
	::=  55

ss7LinkDnNotify		TRAP-TYPE
	ENTERPRISE	alarmTraps
	VARIABLES   { trapSeverity, trapOpc, trapSwitchName, trapLinkId }
	DESCRIPTION 
	"Info : switch has a failure  on ss7 mtp3 link "
	::=  56

ss7Mtp2LinkUpNotify		TRAP-TYPE
	ENTERPRISE	alarmTraps
	VARIABLES   { trapSeverity, trapOpc, trapSwitchName, trapLinkId }
	DESCRIPTION 
	"Info : switch has successfully brought up ss7 mtp2 link "
	::=  57

ss7Mtp2LinkDnNotify		TRAP-TYPE
	ENTERPRISE	alarmTraps
	VARIABLES   { trapSeverity, trapOpc, trapSwitchName, trapLinkId }
	DESCRIPTION 
	"Info : switch has a failure on ss7 mtp2 link "
	::=  58

ss7LinkEnterCongestionNotify		TRAP-TYPE
	ENTERPRISE	alarmTraps
	VARIABLES   { trapSeverity, trapOpc, trapSwitchName, trapLinkId }
	DESCRIPTION 
	"Info : the specified link has entered a congestion situation "
	::=  59

ss7LinkExitCongestionNotify		TRAP-TYPE
	ENTERPRISE	alarmTraps
	VARIABLES   { trapSeverity, trapOpc, trapSwitchName, trapLinkId }
	DESCRIPTION 
	"Info : the ss7 link has exited the congestion situation "
	::=  60

ss7InvalidSLCNotify		TRAP-TYPE
	ENTERPRISE	alarmTraps
	VARIABLES   { trapSeverity, trapOpc, trapSwitchName, trapDpc }
	DESCRIPTION 
	"Info : Mtp3 invalid SLC configured. "
	::=  61

ss7ConcernedDpcPauseNotify		TRAP-TYPE
	ENTERPRISE	alarmTraps
	VARIABLES   { trapSeverity, trapOpc, trapSwitchName, trapDpc }
	DESCRIPTION 
	"Info : Concerned DPC pause "
	::=  62

ss7ConcernedDpcResumeNotify		TRAP-TYPE
	ENTERPRISE	alarmTraps
	VARIABLES   { trapSeverity, trapOpc, trapSwitchName, trapDpc }
	DESCRIPTION 
	"Info : Concerned DPC resume "
	::=  63

ss7ConcernedDpcRemUnAvailNotify		TRAP-TYPE
	ENTERPRISE	alarmTraps
	VARIABLES   { trapSeverity, trapOpc, trapSwitchName, trapDpc }
	DESCRIPTION 
	"Info : Concerned DPC remote user unavailable "
	::=  64

ss7LinkRemInhNotify		TRAP-TYPE
	ENTERPRISE	alarmTraps
	VARIABLES   { trapSeverity, trapOpc, trapSwitchName, trapLinkId }
	DESCRIPTION 
	"Info : Link Inhibited Remotely "
	::=  65

ss7LinkRemUnInhNotify		TRAP-TYPE
	ENTERPRISE	alarmTraps
	VARIABLES   { trapSeverity, trapOpc, trapSwitchName, trapLinkId }
	DESCRIPTION 
	"Info : Link UnInhibited Remotely "
	::=  66

ss7LinkLocInhNotify		TRAP-TYPE
	ENTERPRISE	alarmTraps
	VARIABLES   { trapSeverity, trapOpc, trapSwitchName, trapLinkId }
	DESCRIPTION 
	"Info : Link Inhibited Locally "
	::=  67

ss7LinkLocUnInhNotify		TRAP-TYPE
	ENTERPRISE	alarmTraps
	VARIABLES   { trapSeverity, trapOpc, trapSwitchName, trapLinkId }
	DESCRIPTION 
	"Info : Link UnInhibited Locally "
	::=  68

ss7LinkLOPBlkNotify		TRAP-TYPE
	ENTERPRISE	alarmTraps
	VARIABLES   { trapSeverity, trapOpc, trapSwitchName, trapLinkId }
	DESCRIPTION 
	"Info : Local Processor Recovered causing link unblocked "
	::=  69

ss7LinkLPRNotify		TRAP-TYPE
	ENTERPRISE	alarmTraps
	VARIABLES   { trapSeverity, trapOpc, trapSwitchName, trapLinkId }
	DESCRIPTION 
	"Info : Local Processor Recovered causing link unblocked "
	::=  70

ss7LinkRPONotify		TRAP-TYPE
	ENTERPRISE	alarmTraps
	VARIABLES   { trapSeverity, trapOpc, trapSwitchName, trapLinkId }
	DESCRIPTION 
	"Info :LSSU/SIPO Received "
	::=  71

ss7LinkRPRNotify		TRAP-TYPE
	ENTERPRISE	alarmTraps
	VARIABLES   { trapSeverity, trapOpc, trapSwitchName, trapLinkId }
	DESCRIPTION 
	"Info :LSSU/SIPO stopped and FISU/MSU recived "
	::=  72

ss7IsupCicLocNotify		TRAP-TYPE
	ENTERPRISE	alarmTraps
	VARIABLES   { trapSeverity, trapOpc, trapSwitchName, trapDpc, trapCicvalue, trapCicrange, trapCause }
	DESCRIPTION 
	"Info : ISUP Circuits are blocked/unblocked locally "
	::=  73

ss7IsupCicRemNotify		TRAP-TYPE
	ENTERPRISE	alarmTraps
	VARIABLES   { trapSeverity, trapOpc, trapSwitchName, trapDpc, trapCicvalue, trapCicrange, trapCause }
	DESCRIPTION 
	"Info : ISUP Circuits are blocked/unblocked remotely "
	::=  74

ss7IsupCongLvl1Notify		TRAP-TYPE
	ENTERPRISE	alarmTraps
	VARIABLES   { trapSeverity, trapOpc, trapSwitchName, trapDpc }
	DESCRIPTION 
	"Info : Route to DPC is encountering Level 1 Congestion "
	::=  75

ss7IsupCongLvl2Notify		TRAP-TYPE
	ENTERPRISE	alarmTraps
	VARIABLES   { trapSeverity, trapOpc, trapSwitchName, trapDpc }
	DESCRIPTION 
	"Info : Route to DPC is encountering Level 2 Congestion "
	::=  76

isdnDChnlUpNotify		TRAP-TYPE
	ENTERPRISE	alarmTraps
	VARIABLES   { trapSeverity, trapOpc, trapSwitchName, trapXconnectId, trapSlotId, trapPortId }
	DESCRIPTION 
	"Info : An ISDN D-channel is Up "
	::=  77

isdnDChnlDnNotify		TRAP-TYPE
	ENTERPRISE	alarmTraps
	VARIABLES   { trapSeverity, trapOpc, trapSwitchName, trapXconnectId, trapSlotId, trapPortId }
	DESCRIPTION 
	"Info : An ISDN D-channel is down "
	::=  78

logFileReadyNotify		TRAP-TYPE
	ENTERPRISE	alarmTraps
	VARIABLES   { trapSeverity, trapOpc, trapSwitchName, trapLogFileName }
	DESCRIPTION 
	"Info : Logger file is ready "
	::=  79

logDiskFull60PercentNotify		TRAP-TYPE
	ENTERPRISE	alarmTraps
	VARIABLES   { trapSeverity, trapOpc, trapSwitchName, trapLogErrcause, trapLogErrNo }
	DESCRIPTION 
	"Info : Log Files occupy 60% of disk quota "
	::=  80

logDiskFull70PercentNotify		TRAP-TYPE
	ENTERPRISE	alarmTraps
	VARIABLES   { trapSeverity, trapOpc, trapSwitchName, trapLogErrcause, trapLogErrNo }
	DESCRIPTION 
	"Info : Log Files occupy 70% of disk quota "
	::=  81

logDiskFull80PercentNotify		TRAP-TYPE
	ENTERPRISE	alarmTraps
	VARIABLES   { trapSeverity, trapOpc, trapSwitchName, trapLogErrcause, trapLogErrNo }
	DESCRIPTION 
	"Info : Log Files occupy 80% of disk quota "
	::=  82

logErrFileOpenNotify		TRAP-TYPE
	ENTERPRISE	alarmTraps
	VARIABLES   { trapSeverity, trapOpc, trapSwitchName, trapLogFileName }
	DESCRIPTION 
	"Info : Log file open error "
	::=  83

logErrFileCloseNotify		TRAP-TYPE
	ENTERPRISE	alarmTraps
	VARIABLES   { trapSeverity, trapOpc, trapSwitchName, trapLogFileName }
	DESCRIPTION 
	"Info : Log file close error "
	::=  84

logErrFileDeleteNotify		TRAP-TYPE
	ENTERPRISE	alarmTraps
	VARIABLES   { trapSeverity, trapOpc, trapSwitchName, trapLogFileName }
	DESCRIPTION 
	"Info : Log file cannot be deleted "
	::=  85

logErrFileWriteNotify		TRAP-TYPE
	ENTERPRISE	alarmTraps
	VARIABLES   { trapSeverity, trapOpc, trapSwitchName, trapLogFileName }
	DESCRIPTION 
	"Info : Log manager cannot write to log file "
	::=  86

msscPriDedicatedLinkUpNotify		TRAP-TYPE
	ENTERPRISE	alarmTraps
	VARIABLES   { trapSeverity, trapOpc, trapSwitchName, trapLinkId }
	DESCRIPTION 
	"Info : Dedicated link between the 2 Netra machine is UP "
	::=  87

msscPriDedicatedLinkDownNotify		TRAP-TYPE
	ENTERPRISE	alarmTraps
	VARIABLES   { trapSeverity, trapOpc, trapSwitchName, trapLinkId }
	DESCRIPTION 
	"Info : Dedicated link between the 2 Netra machine is down "
	::=  88

msscSecDedicatedLinkUpNotify		TRAP-TYPE
	ENTERPRISE	alarmTraps
	VARIABLES   { trapSeverity, trapOpc, trapSwitchName, trapLinkId }
	DESCRIPTION 
	"Info : Dedicated link between the 2 Netra machine is UP "
	::=  89

msscSecDedicatedLinkDownNotify		TRAP-TYPE
	ENTERPRISE	alarmTraps
	VARIABLES   { trapSeverity, trapOpc, trapSwitchName, trapLinkId }
	DESCRIPTION 
	"Info :Dedicated link between the 2 Netra machine is down  "
	::=  90

msscPriPsuUpNotify		TRAP-TYPE
	ENTERPRISE	alarmTraps
	VARIABLES   { trapSeverity, trapOpc, trapSwitchName, trapPsuNo }
	DESCRIPTION 
	"Info : Primary hosts power supply up "
	::=  91

msscPriPsuDownNotify		TRAP-TYPE
	ENTERPRISE	alarmTraps
	VARIABLES   { trapSeverity, trapOpc, trapSwitchName, trapPsuNo }
	DESCRIPTION 
	"Info : Primary hosts power supply down "
	::=  92

msscBakPsuUpNotify		TRAP-TYPE
	ENTERPRISE	alarmTraps
	VARIABLES   { trapSeverity, trapOpc, trapSwitchName, trapPsuNo }
	DESCRIPTION 
	"Info : Backup hosts power supply up "
	::=  93

msscBakPsuDownNotify		TRAP-TYPE
	ENTERPRISE	alarmTraps
	VARIABLES   { trapSeverity, trapOpc, trapSwitchName, trapPsuNo }
	DESCRIPTION 
	"Info : Backup hosts power supply down "
	::=  94

msscPriLanPhyIntfUpNotify		TRAP-TYPE
	ENTERPRISE	alarmTraps
	VARIABLES   { trapSeverity, trapOpc, trapSwitchName, trapLanId }
	DESCRIPTION 
	"Info : Primary Physical LAN Interface Up "
	::=  95

msscPriLanPhyIntfDownNotify		TRAP-TYPE
	ENTERPRISE	alarmTraps
	VARIABLES   { trapSeverity, trapOpc, trapSwitchName, trapLanId }
	DESCRIPTION 
	"Info : Primary Physical LAN Interface Down "
	::=  96

msscSecLanPhyIntfUpNotify		TRAP-TYPE
	ENTERPRISE	alarmTraps
	VARIABLES   { trapSeverity, trapOpc, trapSwitchName, trapLanId }
	DESCRIPTION 
	"Info : Secondary physical LAN Interface Up "
	::=  97

msscSecLanPhyIntfDownNotify		TRAP-TYPE
	ENTERPRISE	alarmTraps
	VARIABLES   { trapSeverity, trapOpc, trapSwitchName, trapLanId }
	DESCRIPTION 
	"Info : Secondary Physical LAN Interface Down "
	::=  98

msscPriHostFanUpNotify		TRAP-TYPE
	ENTERPRISE	alarmTraps
	VARIABLES   { trapSeverity, trapOpc, trapSwitchName, trapFanNo }
	DESCRIPTION 
	"Info : Primary Fan Up "
	::=  99

msscPriHostFanDownNotify		TRAP-TYPE
	ENTERPRISE	alarmTraps
	VARIABLES   { trapSeverity, trapOpc, trapSwitchName, trapFanNo }
	DESCRIPTION 
	"Info : Primary Fan Down "
	::=  100

msscBckHostFanUpNotify		TRAP-TYPE
	ENTERPRISE	alarmTraps
	VARIABLES   { trapSeverity, trapOpc, trapSwitchName, trapFanNo }
	DESCRIPTION 
	"Info : Backup Fan Up "
	::=  101

msscBckHostFanDownNotify		TRAP-TYPE
	ENTERPRISE	alarmTraps
	VARIABLES   { trapSeverity, trapOpc, trapSwitchName, trapFanNo }
	DESCRIPTION 
	"Info : Backup Fan Down "
	::=  102

hubPriIntfUpNotify		TRAP-TYPE
	ENTERPRISE	alarmTraps
	VARIABLES   { trapSeverity, trapOpc, trapSwitchName, trapLanId }
	DESCRIPTION 
	"Info : Primary Interface Up "
	::=  103

hubPriIntfDownNotify		TRAP-TYPE
	ENTERPRISE	alarmTraps
	VARIABLES   { trapSeverity, trapOpc, trapSwitchName, trapLanId }
	DESCRIPTION 
	"Info : Primary Interface down "
	::=  104

hubSecIntfUpNotify		TRAP-TYPE
	ENTERPRISE	alarmTraps
	VARIABLES   { trapSeverity, trapOpc, trapSwitchName, trapLanId }
	DESCRIPTION 
	"Info : Secondary Interface Up "
	::=  105

hubSecIntfDownNotify		TRAP-TYPE
	ENTERPRISE	alarmTraps
	VARIABLES   { trapSeverity, trapOpc, trapSwitchName, trapLanId }
	DESCRIPTION 
	"Info : Secondary Interface Down  "
	::=  106

ftProcessAbnormalTerminationNotify		TRAP-TYPE
	ENTERPRISE	alarmTraps
	VARIABLES   { trapSeverity, trapOpc, trapSwitchName, trapProcName, trapProcInstNo }
	DESCRIPTION 
	"Info : Process abnormal termination "
	::=  107

ftProcessRestartConfigSucceededNotify		TRAP-TYPE
	ENTERPRISE	alarmTraps
	VARIABLES   { trapSeverity, trapOpc, trapSwitchName, trapProcName, trapProcInstNo }
	DESCRIPTION 
	"Info : Process abnormal termination "
	::=  108

ftProcessRestartConfigFailedNotify		TRAP-TYPE
	ENTERPRISE	alarmTraps
	VARIABLES   { trapSeverity, trapOpc, trapSwitchName, trapProcName, trapProcInstNo }
	DESCRIPTION 
	"Info : Process abnormal termination "
	::=  109

ftMsscFtmupNotify		TRAP-TYPE
	ENTERPRISE	alarmTraps
	VARIABLES   { trapSeverity, trapOpc, trapSwitchName }
	DESCRIPTION 
	"Info : Process abnormal termination "
	::=  110

ftControlSwitchOverSucceededNotify		TRAP-TYPE
	ENTERPRISE	alarmTraps
	VARIABLES   { trapSeverity, trapOpc, trapSwitchName, trapProcName }
	DESCRIPTION 
	"Info : Control SwitchOver Successful "
	::=  111

ftControlSwitchOverFailedNotify		TRAP-TYPE
	ENTERPRISE	alarmTraps
	VARIABLES   { trapSeverity, trapOpc, trapSwitchName, trapProcName }
	DESCRIPTION 
	"Info : Control SwitchOver Failure "
	::=  112

ftForcedSwitchOverSucceededNotify		TRAP-TYPE
	ENTERPRISE	alarmTraps
	VARIABLES   { trapSeverity, trapOpc, trapSwitchName, trapProcName }
	DESCRIPTION 
	"Info : Forced SwitchOver Successful "
	::=  113

ftForcedSwitchOverFailedNotify		TRAP-TYPE
	ENTERPRISE	alarmTraps
	VARIABLES   { trapSeverity, trapOpc, trapSwitchName, trapProcName }
	DESCRIPTION 
	"Info : Forced SwitchOver Failure "
	::=  114

ftProcessRestartDisableNotify		TRAP-TYPE
	ENTERPRISE	alarmTraps
	VARIABLES   { trapSeverity, trapOpc, trapSwitchName, trapProcName, trapProcInstNo }
	DESCRIPTION 
	""
	::=  115

updateDBAuditOpStatNotify		TRAP-TYPE
	ENTERPRISE	alarmTraps
	VARIABLES   { trapSeverity, trapOpc, trapSwitchName }
	DESCRIPTION 
	"Info : Updated the Database for Audited Related Operational Status "
	::=  116

isupIccAuditNotify		TRAP-TYPE
	ENTERPRISE	alarmTraps
	VARIABLES   { trapSeverity, trapOpc, trapSwitchName }
	DESCRIPTION 
	"ISUP ICC Audit Notify"
	::=  117

cdrDiskFullMinorNotify		TRAP-TYPE
	ENTERPRISE	alarmTraps
	VARIABLES   { trapSeverity, trapOpc, trapSwitchName, trapDirectory }
	DESCRIPTION 
	"CDR Disk Usage reached Minor Threshold"
	::=  118

cdrDiskFullMajorNotify		TRAP-TYPE
	ENTERPRISE	alarmTraps
	VARIABLES   { trapSeverity, trapOpc, trapSwitchName, trapDirectory }
	DESCRIPTION 
	"CDR Disk Usage reached Major Threshold"
	::=  119

cdrErrMoveCdrNackNotify		TRAP-TYPE
	ENTERPRISE	alarmTraps
	VARIABLES   { trapSeverity, trapOpc, trapSwitchName, trapCdrFileName }
	DESCRIPTION 
	"Invalid CDR file Non-Ack Directory"
	::=  120

cdrFileMoveCdrNackNotify		TRAP-TYPE
	ENTERPRISE	alarmTraps
	VARIABLES   { trapSeverity, trapOpc, trapSwitchName, trapCdrFileName }
	DESCRIPTION 
	"CDR file moved to Non-Ack Directory"
	::=  121

ss7CktValidationNotify		TRAP-TYPE
	ENTERPRISE	alarmTraps
	VARIABLES   { trapSeverity, trapOpc, trapSwitchName, trapDpc, trapCicvalue, trapCause }
	DESCRIPTION 
	"Validation of Circuits"
	::=  122

 -- *************************************************     
 -- Active Alarm List
 -- *************************************************     

switchActiveAlarmTable		OBJECT-TYPE
			SYNTAX   SEQUENCE OF SwitchActiveAlarmEntry
			ACCESS	not-accessible
			STATUS	mandatory
			DESCRIPTION 
			""
			::= { alarmGrp	 2 }

switchActiveAlarmEntry		OBJECT-TYPE
			SYNTAX	SwitchActiveAlarmEntry
			ACCESS	not-accessible
			STATUS	mandatory
			DESCRIPTION 
			""
			INDEX { switchAlarmMsgId, switchAlarmInstNo }
			::= {	switchActiveAlarmTable   1 }

SwitchActiveAlarmEntry		::= SEQUENCE {
			switchAlarmMsgId		INTEGER,
			switchAlarmInstNo		INTEGER,
			switchAlarmTime		DisplayString,
			switchAlarmType		EventType,
			switchAlarmMainEvent		AlarmEvent,
			switchAlarmSubEvent		AlarmSubEvent,
			switchAlarmId		INTEGER,
			switchAlarmSeverity		AlarmSeverity,
			switchAlarmDesc		DisplayString,
			switchAlarmAck		ActiveAlarmAckStatus,
			switchAlarmRepeatTime		INTEGER
			}

switchAlarmMsgId		OBJECT-TYPE
			SYNTAX	INTEGER(1..65535)
			ACCESS	read-only
			STATUS	mandatory
			DESCRIPTION 
	"Alarm Message Id. Can be any integer from 1-65535. "
			::= {	switchActiveAlarmEntry   1 }

switchAlarmInstNo		OBJECT-TYPE
			SYNTAX	INTEGER(1..65535)
			ACCESS	read-only
			STATUS	mandatory
			DESCRIPTION 
	"Instance number related to alarm. Can be any integer from 1-65535. "
			::= {	switchActiveAlarmEntry   2 }

switchAlarmTime		OBJECT-TYPE
			SYNTAX	DisplayString
			ACCESS	read-only
			STATUS	mandatory
			DESCRIPTION 
	"Date and time when the alarma was generated "
			::= {	switchActiveAlarmEntry   3 }

switchAlarmType		OBJECT-TYPE
			SYNTAX	EventType
			ACCESS	read-only
			STATUS	mandatory
			DESCRIPTION 
	"This specifies the event group is alarm. Default :ALARM "
			::= {	switchActiveAlarmEntry   4 }

switchAlarmMainEvent		OBJECT-TYPE
			SYNTAX	AlarmEvent
			ACCESS	read-only
			STATUS	mandatory
			DESCRIPTION 
	"This specifies the main event event group of alarm "
			::= {	switchActiveAlarmEntry   5 }

switchAlarmSubEvent		OBJECT-TYPE
			SYNTAX	AlarmSubEvent
			ACCESS	read-only
			STATUS	mandatory
			DESCRIPTION 
	"This specifies the main event event group of alarm "
			::= {	switchActiveAlarmEntry   6 }

switchAlarmId		OBJECT-TYPE
			SYNTAX	INTEGER
			ACCESS	read-only
			STATUS	mandatory
			DESCRIPTION 
	"This specifies the alarm that was sent "
			::= {	switchActiveAlarmEntry   7 }

switchAlarmSeverity		OBJECT-TYPE
			SYNTAX	AlarmSeverity
			ACCESS	read-only
			STATUS	mandatory
			DESCRIPTION 
	"This field defines the severity of alarms of alarm. 
	Alarms can od : Major,Minor,Critical and Informational "
			::= {	switchActiveAlarmEntry   8 }

switchAlarmDesc		OBJECT-TYPE
			SYNTAX	DisplayString
			ACCESS	read-only
			STATUS	mandatory
			DESCRIPTION 
	"This description related to Generated alarm "
			::= {	switchActiveAlarmEntry   9 }

switchAlarmAck		OBJECT-TYPE
			SYNTAX	ActiveAlarmAckStatus
			ACCESS	read-write
			STATUS	mandatory
			DESCRIPTION 
	"This field is to acknowelge the alarms manually "
			::= {	switchActiveAlarmEntry   10 }

switchAlarmRepeatTime		OBJECT-TYPE
			SYNTAX	INTEGER(0..60)
			ACCESS	read-write
			STATUS	mandatory
			DESCRIPTION 
	"Alarm Repeat Time in minutes: After the set time all alarms 
	in the active alarm table will be displayed to the user again "
			::= {	switchActiveAlarmEntry   11 }

 -- *************************************************     
 -- This MIB was Automatically Generated 
 -- *************************************************     

END
