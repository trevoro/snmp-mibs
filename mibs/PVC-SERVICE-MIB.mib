-- PairGain DSLAM PVC SERVICE MIB Release 1.1
-- Revision 06/17/99

-- Copyright 1998 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.
--
-- Revision History
--------------------------------------------------------------
-- Date     Ver     Programmer  Description
--------------------------------------------------------------
-- 03/03/98 1.0     Abbas       Initial Release
-- 06/10/99 1.01    Vinh Ngo    Indexing modifications
-- 06/23/99 1.1     R. Wada     Add object for next VCI and index on slot

PVC-SERVICE-MIB DEFINITIONS ::= BEGIN

IMPORTS
	MODULE-IDENTITY,
	OBJECT-TYPE,
	Counter32,
	Gauge32,
	IpAddress,
    NOTIFICATION-TYPE,
	Integer32
		FROM SNMPv2-SMI
	DisplayString,
	PhysAddress,
    MacAddress,
	RowStatus,
	TruthValue
		FROM SNMPv2-TC
	ifIndex
		FROM RFC1213-MIB
	frCircuitIfIndex, frCircuitDlci
		FROM FRAME-RELAY-DTE-MIB
	pgainDSLAM
		FROM PAIRGAIN-COMMON-HD-MIB;

pgService MODULE-IDENTITY
    LAST-UPDATED    "9803030000Z"
	ORGANIZATION	"PairGain Technology"
    CONTACT-INFO    ""
    DESCRIPTION     "The module defines the MIB for PVC Service configuration."
    ::= {pgainDSLAM 6}


pgServiceObjects OBJECT IDENTIFIER ::= {pgService 1}

--
-- PVC Service Type enumeration
--
PgPvcServiceType ::=
	INTEGER {
                other (1),                 -- None of the following
                ipoa  (2),                 -- IPOA
                lant  (3),                 -- LANT
                ppp   (4),                 -- PPP
                frame-relay   (5),         -- Frame Relay
                null  (6),				   -- NULL encapsulation
				ramp1483 (7)		   	   -- WebRamp 1483 encapsulation
	}

--
-- xDSL Port Framie type
--
PgXdslFrameType ::=
	INTEGER {
                other (1),                 -- None of the following
                mac  (2)                   -- MAC
	}

--
-- SECTION 1:
-- DSLAM Subagent  ... xDSL Subscriber Service table
--
--		pgXdslServiceIfIndex			INTEGER,
--pgXdslServiceIfIndex OBJECT-TYPE
--  SYNTAX          INTEGER (0..16384)
--	MAX-ACCESS     	read-only
--  STATUS          current
--	DESCRIPTION     "The Interface Index for the channel (xDSL) port for which the Network route
--			is being defined."
--	::= {pgXdslServiceEntry 1}


pgXdslServiceTable  OBJECT-TYPE
    SYNTAX          SEQUENCE OF PgXdslPortEntry
    MAX-ACCESS      not-accessible
    STATUS          current
    DESCRIPTION     "A table of xDSL port entries that defines the Service
                    Application and other port/interface related parameters needed
                    to use the xDSL port for that service."
    ::= {pgServiceObjects 1}

pgXdslServiceEntry OBJECT-TYPE
    SYNTAX          PgXdslPortEntry
    MAX-ACCESS      not-accessible
    STATUS          current
    DESCRIPTION     "An entry in the pgXdslServiceTable."
    INDEX           {ifIndex}
    ::= {pgXdslServiceTable 1}

PgXdslPortEntry ::=
	SEQUENCE {
                pgXdslServiceSubscriberName     DisplayString,
                pgXdslServiceType               PgPvcServiceType,
                pgXdslServiceMacAddress			MacAddress,
                pgXdslServiceIpAddress          IpAddress,
                pgXdslServiceSubnetMask         IpAddress,
                pgXdslServiceRowStatus			RowStatus
	}

pgXdslServiceSubscriberName   OBJECT-TYPE
    SYNTAX          DisplayString(SIZE(1..32))
    MAX-ACCESS      read-write
    STATUS          current
    DESCRIPTION     "The Subscriber name."
    ::= {pgXdslServiceEntry 1}

pgXdslServiceType   OBJECT-TYPE
    SYNTAX          PgPvcServiceType
    MAX-ACCESS      read-write
    STATUS          current
    DESCRIPTION     "The Service name as defined by PgPvcServiceType."
    ::= {pgXdslServiceEntry 2}

pgXdslServiceMacAddress   OBJECT-TYPE
    SYNTAX          MacAddress
    MAX-ACCESS      read-write
    STATUS          current
    DESCRIPTION     "The Physical(MAC) address of the xDSL port."
    ::= {pgXdslServiceEntry 3}

pgXdslServiceIpAddress   OBJECT-TYPE
    SYNTAX          IpAddress
    MAX-ACCESS      read-write
    STATUS          current
    DESCRIPTION     "The IP address of the xDSL port."
    ::= {pgXdslServiceEntry 4}

pgXdslServiceSubnetMask   OBJECT-TYPE
    SYNTAX          IpAddress
    MAX-ACCESS      read-write
    STATUS          current
    DESCRIPTION     "The Subnet mask for the Interface."
    ::= {pgXdslServiceEntry 5}

pgXdslServiceRowStatus OBJECT-TYPE
    SYNTAX          RowStatus
    MAX-ACCESS      read-create
    STATUS          current
	DESCRIPTION	"This object allows entries to be created and deleted
                in this table. The RowStatus should be out of
                the ACTIVE state for other columns to be modified."
    ::= {pgXdslServiceEntry 6}

--
-- SECTION 2:
-- DSLAM Subagent  ... Pvc Service Mapping Table
--
--                pgPvcServiceSarIfIndex             INTEGER,
-- pgPvcServiceSarIfIndex OBJECT-TYPE
--  SYNTAX          INTEGER (0..16384)
--  MAX-ACCESS      read-write
--  STATUS          current
--	DESCRIPTION     "The SAR IfIndex."
--	::= {pgPvcServiceEntry 1}

PgPvcServiceEncapType ::=
        INTEGER {
                other (1),              -- None of the following
                vc-mux-iso (2),         -- Null Encapsulation.
                vc-mux-ip (3),          -- Null Encapsulation.
                vc-mux-8023 (4),        -- VC_MUX encapsulaton for 802.3
                llc-iso (5),            -- LLC/SNAP encapsulation for ISO
                llc-ip (6),             -- LLC/SNAP encapsulation for IP
                llc-8023-crc (7),       -- LLC/SNAP encapsulation for 802.3 w/ CRC
                llc-8023 (8),           -- LLC/SNAP encapsulation for 802.3 w/o CRC
	        	vc-mux-ppp (9),			-- VC_MUX encapsulation for PPP
				llc-ppp (10),			-- LLC/SNAP encapsulation for PPP
				vc-mux-ramp1483 (11)    -- WebRamp 1483 encapsulation
        }


pgPvcServiceTable OBJECT-TYPE
    SYNTAX          SEQUENCE OF PgPvcServiceEntry
    MAX-ACCESS      not-accessible
    STATUS          current
    DESCRIPTION     "A table of PVC entries (as described by pgPvcServiceSarIfIndex and
                    pgPvcServiceSarIfIndex/Vpi/Vci ) that defines the Service Application
                    name such as LANT/PPP etc., and maps the PVC to the xDSL port."
    ::= {pgServiceObjects 2}

pgPvcServiceEntry OBJECT-TYPE
    SYNTAX          PgPvcServiceEntry
    MAX-ACCESS      not-accessible
    STATUS          current
    DESCRIPTION     "The Route information that maps Network numbers to the
                    ifIndex of the xDSL port."
    INDEX   {   pgPvcServiceSarVpi,
                pgPvcServiceSarVci,
                ifIndex}
    ::= {pgPvcServiceTable 1}

PgPvcServiceEntry ::=
	SEQUENCE {
                pgPvcServiceSarVpi              INTEGER,
                pgPvcServiceSarVci              INTEGER,
                pgPvcServiceIpAddress           IpAddress,
                pgPvcServiceSubnetMask          IpAddress,
                pgPvcServiceEncapType           PgPvcServiceEncapType,
                pgPvcServiceRowStatus           RowStatus
	}

pgPvcServiceSarVpi OBJECT-TYPE
    SYNTAX          INTEGER (0..255)
    MAX-ACCESS      read-write
    STATUS          current
    DESCRIPTION     "The SAR VPI."
    ::= {pgPvcServiceEntry 1}

pgPvcServiceSarVci OBJECT-TYPE
    SYNTAX          INTEGER (0..65535)
    MAX-ACCESS      read-write
    STATUS          current
    DESCRIPTION     "The SAR VCI."
    ::= {pgPvcServiceEntry 2}

pgPvcServiceIpAddress   OBJECT-TYPE
    SYNTAX          IpAddress
    MAX-ACCESS      read-write
    STATUS          deprecated
    DESCRIPTION     "The IP address."
    ::= {pgPvcServiceEntry 3}

pgPvcServiceSubnetMask  OBJECT-TYPE
    SYNTAX          IpAddress
    MAX-ACCESS      read-write
    STATUS          deprecated
    DESCRIPTION     "The Subnet mask for the Interface."
    ::= {pgPvcServiceEntry 4}

pgPvcServiceEncapType   OBJECT-TYPE
    SYNTAX          PgPvcServiceEncapType
    MAX-ACCESS      read-write
    STATUS          deprecated
    DESCRIPTION     "The encapsulation mode used by the PVC."
    ::= {pgPvcServiceEntry 5}

pgPvcServiceRowStatus OBJECT-TYPE
    SYNTAX          RowStatus
    MAX-ACCESS      read-create
    STATUS          current
    DESCRIPTION     "This object allows entries to be created and deleted
                    in this table. The RowStatus should be out of
                    the ACTIVE state for other columns to be modified."
    ::= {pgPvcServiceEntry 6}


--
-- SECTION 3:
-- DSLAM Subagent  ... Next Available VCI
--
pgNextSarVciTable OBJECT-TYPE
    SYNTAX          SEQUENCE OF PgNextSarVciEntry
    MAX-ACCESS      not-accessible
    STATUS          current
    DESCRIPTION     "This object is referenced by the slot since each
                    SDSL card has a certain number of VCI entries.
                    The value returned can be used for the next VCI value."
    ::= {pgServiceObjects 3}

pgNextSarVciEntry   OBJECT-TYPE
    SYNTAX          PgNextSarVciEntry
    MAX-ACCESS      not-accessible
    STATUS          current
    DESCRIPTION     "The slot dependent table that gives the next available VCI
                    for a particular card."
    INDEX           {ifIndex}
    ::= {pgNextSarVciTable 1}

PgNextSarVciEntry ::=
    SEQUENCE
    {
                pgNextSarSlotVci    INTEGER
    }

pgNextSarSlotVci    OBJECT-TYPE
    SYNTAX          INTEGER (1024..4095)
    MAX-ACCESS      read-only
    STATUS          current
    DESCRIPTION     "contains an appropriate value to
                    be used for pgPvcServiceSarVci when creating
                    entries in the pgPvcServiceTable.  The value
                    0 indicates that no unassigned entries are
                    available. To obtain the pgPvcServiceSarVci
                    value for a new entry, the manager issues a
                    management protocol retrieval operation to obtain
                    the current value of this object.  This value is
                    updated whenever a VCL is set up."

    ::= {pgNextSarVciEntry 1}

--
-- SECTION 4:
-- DSLAM Subagent  ... Pvc/Frame Relay Mapping Table
--

pgPvcFrServiceTable OBJECT-TYPE
    SYNTAX          SEQUENCE OF PgPvcFrServiceEntry
    MAX-ACCESS      not-accessible
    STATUS          current
    DESCRIPTION     "A table of PVC entries (as described by pgPvcServiceSarIfIndex and
                    pgPvcServiceSarIfIndex/Vpi/Vci ) that defines the Service Application
                     as other, and maps the PVC to the xDSL port."
    ::= {pgServiceObjects 4}

pgPvcFrServiceEntry OBJECT-TYPE
    SYNTAX          PgPvcFrServiceEntry
    MAX-ACCESS      not-accessible
    STATUS          current
    DESCRIPTION     "The Route information that maps Network numbers to the
                    ifIndex of xDSL port."
    INDEX   {   frCircuitIfIndex,
				frCircuitDlci,
				pgPvcServiceSarVpi,
                pgPvcServiceSarVci
    } ::= {pgPvcFrServiceTable 1}

PgPvcFrServiceEntry ::=
	SEQUENCE {
                pgPvcFrServiceRowStatus			RowStatus,
				pgPvcFrSubSystemType			INTEGER
	}

pgPvcFrServiceRowStatus OBJECT-TYPE
    SYNTAX          RowStatus
    MAX-ACCESS      read-create
    STATUS          current
    DESCRIPTION     "This object allows entries to be created and deleted
                    in this table. The RowStatus should be out of
                    the ACTIVE state for other columns to be modified."
    ::= {pgPvcFrServiceEntry 1}

pgPvcFrSubSystemType OBJECT-TYPE
    SYNTAX          INTEGER {
		frf5(5),
		frf8(8)
	}
    MAX-ACCESS      read-create
    STATUS          current
    DESCRIPTION     "This object allows entries to be created and deleted
                    in this table. The RowStatus should be out of
                    the ACTIVE state for other columns to be modified."
    ::= {pgPvcFrServiceEntry 2}

END
