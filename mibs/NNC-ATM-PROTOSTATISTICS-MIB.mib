-------------------------------------------------------------------------------
-- file: AtmProtoStatistics.mib 
--
-- description:
--   This file contains the SNMP definitions for the ATM interface protocol 
--   statistics area.
--
-- %%history-start%%
-- 98.01.28 tsellars 31A1155: Merge from FRAPS.3.1 tributary 
-- 98.02.01 tsellars 31A1155: FRAPS.3.1 tributary merge 
-- 98.02.19 jwei P.227165: Changed the nncExtensions to 54 
-- 98.05.08 dkruse P.242089: Added the nncAtmProtoRaw type objects. 
-- %%history-end%%
--
-- Copyright 1997 Newbridge Networks Corporation.  All Rights Reserved
-------------------------------------------------------------------------------
NNC-ATM-PROTOSTATISTICS-MIB DEFINITIONS ::= BEGIN

  IMPORTS
    MODULE-IDENTITY, OBJECT-TYPE, Counter32
      FROM SNMPv2-SMI
    TEXTUAL-CONVENTION
      FROM SNMPv2-TC
    MODULE-COMPLIANCE, OBJECT-GROUP
      FROM SNMPv2-CONF
    ifIndex
      FROM IF-MIB
    nncExtensions, NncExtCounter64
      FROM NNCGNI0001-SMI;
                  
  nncAtmProtoStatistics MODULE-IDENTITY        
    LAST-UPDATED    "9604240330Z"
    ORGANIZATION    "Newbridge Networks Corporation"
    CONTACT-INFO
		    "Newbridge Networks Corporation
		    Postal: 600 March Road
		    Kanata, Ontario
		    Canada K2K 2E6

		    Phone:  +1 613 591 3600
		    Fax:    +1 613 591 3680"
                
    DESCRIPTION "
      This module contains definitions for performance monitoring of the
      ATM cell layers.

      This MIB module contains the following tables:

      	ATM Cell Layer 15 Minute Current Table (per interface)
      	ATM Cell Layer 15 Minute History Table (per interface)
        ATM Cell Layer 24 Hour Table (per interface)
        ATM Cell Layer Raw Table (per interface; unintervalized)
       
      Intervals:
	      Statistics per interface are collected over a historical stratum of
        up to a maximum of M intervals. The value of M is a function of a
        product's storage capability. For example, on the 36170 product, 
        M = 96.  

        The intervals are 15 minutes aligned to the quarter of an 
        hour.  The current interval spans back to the last 15 minute tick on
        the wall clock. Continuing along the timeline from that point is the
        most recently completed interval and has an index of 1. The previous
      	interval has an index of 2 and so on. Note that the oldest interval
	      may be incomplete since the statistic collection may have been
	      enabled offset to the quarter or one hour tick.

  		     t
	  	     0          -15min    -30min      -45min
	     ==========|===========|===========|===========|===========
	      current      N = 1       N = 2       N = 3       N = 4    ... N = M
	      interval
    "
      
  ::= { nncExtensions 54 }

  nncAtmProtoObjects OBJECT IDENTIFIER ::= { nncAtmProtoStatistics 1 }
  nncAtmProtoGroups OBJECT IDENTIFIER ::= { nncAtmProtoStatistics 2 }
  nncAtmProtoCompliances OBJECT IDENTIFIER ::= { nncAtmProtoStatistics 3 }

  -- ATM Cell Protocol Monitoring Current Data (per interface)

  nncAtmProtoCurrTable       OBJECT-TYPE 
        SYNTAX               SEQUENCE OF NncAtmProtoCurrEntry 
        MAX-ACCESS           not-accessible
        STATUS               current
        DESCRIPTION          "The ATM Cell Protocol Monitoring Current Data 
                              table.This table maintains per-interface 
                              statistics for the fifteen-minute interval
                              currently being collected."
  ::= { nncAtmProtoObjects 1 }


   nncAtmProtoCurrEntry      OBJECT-TYPE 
        SYNTAX               NncAtmProtoCurrEntry 
        MAX-ACCESS           not-accessible
        STATUS               current
        DESCRIPTION          "An entry in the ATM Cell Protocol Monitoring
                              Current Data table.
                              Each ATM interface (UNI, BICI, BISSI)
                              automatically has an entry in this table
                              associated with it."
        INDEX                { ifIndex }
  ::= { nncAtmProtoCurrTable 1 }

  NncAtmProtoCurrEntry ::=
    SEQUENCE {
      nncAtmProtoCurrValidInCells           NncExtCounter64,
      nncAtmProtoCurrCorrHeaderInCells      NncExtCounter64,
      nncAtmProtoCurrDisHECInCells          NncExtCounter64,
      nncAtmProtoCurrDisInvalidVPIVCIInCells NncExtCounter64,
      nncAtmProtoCurrOutCells               NncExtCounter64
    }
  

   nncAtmProtoCurrValidInCells      OBJECT-TYPE
        SYNTAX               NncExtCounter64
        MAX-ACCESS           read-only
        STATUS               current
        DESCRIPTION          "Number of cells received with correct or
                              corrected headers, and valid VPI/VCI on this
                              interface, since the start of this interval"
  ::= { nncAtmProtoCurrEntry 1 }

  nncAtmProtoCurrCorrHeaderInCells      OBJECT-TYPE
       SYNTAX               NncExtCounter64
       MAX-ACCESS           read-only
       STATUS               current
       DESCRIPTION          "Number of cells received with corrected header
                             errors on this interface, since the start of 
                             this interval."
  ::= { nncAtmProtoCurrEntry 2 }

  nncAtmProtoCurrDisHECInCells     OBJECT-TYPE
        SYNTAX               NncExtCounter64
        MAX-ACCESS           read-only
        STATUS               current
        DESCRIPTION          "Number of received cells discarded due to 
                              uncorrectable header (HEC) errors on this
                              interface, since the start of this interval."
  ::= { nncAtmProtoCurrEntry 3 }

  nncAtmProtoCurrDisInvalidVPIVCIInCells OBJECT-TYPE
       SYNTAX               NncExtCounter64
       MAX-ACCESS           read-only
       STATUS               current
       DESCRIPTION          "Number of received cells discarded due to invalid
                            VPI/VCI on this interface, since the start of 
                            this interval."
  ::= { nncAtmProtoCurrEntry 4 }

  nncAtmProtoCurrOutCells OBJECT-TYPE
       SYNTAX               NncExtCounter64
       MAX-ACCESS           read-only
       STATUS               current
       DESCRIPTION          "Number of cells transmitted on this interface,
                             since the start of this interval."
  ::= { nncAtmProtoCurrEntry 5 }


  -- ATM Cell Protocol Monitoring History Data (per interface and time
  -- interval)

  nncAtmProtoHistTable       OBJECT-TYPE 
        SYNTAX               SEQUENCE OF NncAtmProtoHistEntry 
        MAX-ACCESS           not-accessible
        STATUS               current
        DESCRIPTION          "The ATM Cell Protocol Monitoring Current Data 
                              table.This table maintains per-interface 
                              statistics for the fifteen-minute interval
                              currently being collected."
  ::= { nncAtmProtoObjects 2 }


   nncAtmProtoHistEntry      OBJECT-TYPE 
        SYNTAX               NncAtmProtoHistEntry 
        MAX-ACCESS           not-accessible
        STATUS               current
        DESCRIPTION          "An entry in the ATM Cell Protocol Monitoring
                              History Data table."
        INDEX                { ifIndex, nncAtmProtoHistIndex }
  ::= { nncAtmProtoHistTable 1 }

  NncAtmProtoHistEntry ::=
    SEQUENCE {
      nncAtmProtoHistIndex                  INTEGER,
      nncAtmProtoHistValidInCells           NncExtCounter64,
      nncAtmProtoHistCorrHeaderInCells      NncExtCounter64,
      nncAtmProtoHistDisHECInCells          NncExtCounter64,
      nncAtmProtoHistDisInvalidVPIVCIInCells NncExtCounter64,
      nncAtmProtoHistOutCells               NncExtCounter64
    }
  
  nncAtmProtoHistIndex     OBJECT-TYPE
        SYNTAX               INTEGER (1..96)
        MAX-ACCESS           not-accessible
        STATUS               current
        DESCRIPTION          "A number between 1 and 96, which identifies the
                              interval for which the set of statistics in this
                              entry was collected.  The interval identified by
                              1 is the most recently completed 15 minute
                              interval, and the interval identified by N is
                              the interval immediately preceding the one 
                              identified by N-1."
  ::= { nncAtmProtoHistEntry 1 }

   nncAtmProtoHistValidInCells      OBJECT-TYPE
        SYNTAX               NncExtCounter64
        MAX-ACCESS           read-only
        STATUS               current
        DESCRIPTION          "Number of cells received with correct or
                              corrected headers, and valid VPI/VCI on this
                              interface for this 15-min interval."
  ::= { nncAtmProtoHistEntry 2 }

  nncAtmProtoHistCorrHeaderInCells      OBJECT-TYPE
        SYNTAX               NncExtCounter64
        MAX-ACCESS           read-only
        STATUS               current
        DESCRIPTION          "Number of cells received with corrected header
                              errors on this interface."
  ::= { nncAtmProtoHistEntry 3 }

  nncAtmProtoHistDisHECInCells     OBJECT-TYPE
        SYNTAX               NncExtCounter64
        MAX-ACCESS           read-only
        STATUS               current
        DESCRIPTION          "Number of received cells discarded due to 
                              uncorrectable header (HEC) errors on this
                              interface for this 15-min interval."
  ::= { nncAtmProtoHistEntry 4 }

  nncAtmProtoHistDisInvalidVPIVCIInCells OBJECT-TYPE
        SYNTAX               NncExtCounter64
        MAX-ACCESS           read-only
        STATUS               current
        DESCRIPTION          "Number of received cells discarded due to invalid
                              VPI/VCI on this interface for this 15-min 
                              interval."
  ::= { nncAtmProtoHistEntry 5 }

  nncAtmProtoHistOutCells OBJECT-TYPE
        SYNTAX               NncExtCounter64
        MAX-ACCESS           read-only
        STATUS               current
        DESCRIPTION          "Number of cells transmitted on this interface,
                              for this 15-min interval."
  ::= { nncAtmProtoHistEntry 6 }


  -- ATM Cell Protocol Monitoring Total Data (per interface)

  nncAtmProtoTotalTable       OBJECT-TYPE 
        SYNTAX               SEQUENCE OF NncAtmProtoTotalEntry 
        MAX-ACCESS           not-accessible
        STATUS               current
        DESCRIPTION          "The ATM Cell Protocol Monitoring Total 24 Hour
                              Data table.  This table maintains the cumulative
                              sum of statistics per interface for the 24 hour
                              period preceding the current interval."
  ::= { nncAtmProtoObjects 3 }


   nncAtmProtoTotalEntry      OBJECT-TYPE 
        SYNTAX               NncAtmProtoTotalEntry 
        MAX-ACCESS           not-accessible
        STATUS               current
        DESCRIPTION          "An entry in the ATM Cell Protocol Monitoring
                              Total 24 Hour Data table."
        INDEX                { ifIndex }
  ::= { nncAtmProtoTotalTable 1 }

  NncAtmProtoTotalEntry ::=
    SEQUENCE {
      nncAtmProtoTotalValidIntervals         INTEGER,
      nncAtmProtoTotalValidInCells           NncExtCounter64,
      nncAtmProtoTotalCorrHeaderInCells      NncExtCounter64,
      nncAtmProtoTotalDisHECInCells          NncExtCounter64,
      nncAtmProtoTotalDisInvalidVPIVCIInCells NncExtCounter64,
      nncAtmProtoTotalOutCells               NncExtCounter64
    }
  
   nncAtmProtoTotalValidIntervals    OBJECT-TYPE
        SYNTAX               INTEGER (1..96)
        MAX-ACCESS           read-only
        STATUS               current
        DESCRIPTION          "Number of valid intervals in the previous 24 hour"
   ::= { nncAtmProtoTotalEntry 1 }
   nncAtmProtoTotalValidInCells      OBJECT-TYPE
        SYNTAX               NncExtCounter64
        MAX-ACCESS           read-only
        STATUS               current
        DESCRIPTION          "Number of cells received with correct or
                              corrected headers, and valid VPI/VCI on this
                              interface, in the previous 24 hour interval."
  ::= { nncAtmProtoTotalEntry 2 }

  nncAtmProtoTotalCorrHeaderInCells      OBJECT-TYPE
        SYNTAX               NncExtCounter64
        MAX-ACCESS           read-only
        STATUS               current
        DESCRIPTION          "Number of cells received with corrected header
                              errors on this interface, in the previous 24
                              hour interval."
  ::= { nncAtmProtoTotalEntry 3 }

  nncAtmProtoTotalDisHECInCells     OBJECT-TYPE
        SYNTAX               NncExtCounter64
        MAX-ACCESS           read-only
        STATUS               current
        DESCRIPTION          "Number of received cells discarded due to 
                              uncorrectable header (HEC) errors on this
                              interface, in the previous 24 hour interval."
  ::= { nncAtmProtoTotalEntry 4 }

  nncAtmProtoTotalDisInvalidVPIVCIInCells OBJECT-TYPE
        SYNTAX               NncExtCounter64
        MAX-ACCESS           read-only
        STATUS               current
        DESCRIPTION          "Number of received cells discarded due to invalid
                              VPI/VCI on this interface, in the previous 24
                              hour interval." 
  ::= { nncAtmProtoTotalEntry 5 }

  nncAtmProtoTotalOutCells OBJECT-TYPE
        SYNTAX               NncExtCounter64
        MAX-ACCESS           read-only
        STATUS               current
        DESCRIPTION          "Number of cells transmitted on this interface, in
                              the previous 24 hour interval."
  ::= { nncAtmProtoTotalEntry 6 }


  -- ATM Cell Protocol Monitoring Raw Data (per interface; these are 
  -- unintervalized counters which roll over when maximum value is reached).

  nncAtmProtoRawTable       OBJECT-TYPE 
        SYNTAX               SEQUENCE OF NncAtmProtoRawEntry 
        MAX-ACCESS           not-accessible
        STATUS               current
        DESCRIPTION          "The ATM Cell Protocol Monitoring Raw Data 
                              table. This table maintains per-interface 
                              raw statistics."
  ::= { nncAtmProtoObjects 4 }


   nncAtmProtoRawEntry      OBJECT-TYPE 
        SYNTAX               NncAtmProtoRawEntry 
        MAX-ACCESS           not-accessible
        STATUS               current
        DESCRIPTION          "An entry in the ATM Cell Protocol Monitoring
                              Raw Data table.
                              Each ATM interface (UNI, BICI, BISSI)
                              automatically has an entry in this table
                              associated with it."
        INDEX                { ifIndex }
  ::= { nncAtmProtoRawTable 1 }

  NncAtmProtoRawEntry ::=
    SEQUENCE {
      nncAtmProtoRawValidInCells           Counter32,
      nncAtmProtoRawCorrHeaderInCells      Counter32,
      nncAtmProtoRawDisHECInCells          Counter32,
      nncAtmProtoRawDisInvalidVPIVCIInCells Counter32,
      nncAtmProtoRawOutCells               Counter32
    }
  

   nncAtmProtoRawValidInCells      OBJECT-TYPE
        SYNTAX               Counter32
        MAX-ACCESS           read-only
        STATUS               current
        DESCRIPTION          "The number of cells received with 
                              correct or corrected headers, and valid 
                              VPI/VCI on this interface, since startup."
  ::= { nncAtmProtoRawEntry 1 }

  nncAtmProtoRawCorrHeaderInCells      OBJECT-TYPE
       SYNTAX               Counter32
       MAX-ACCESS           read-only
       STATUS               current
       DESCRIPTION          "The number of cells received with 
                             corrected header errors on this interface, 
                             since startup."
  ::= { nncAtmProtoRawEntry 2 }

  nncAtmProtoRawDisHECInCells     OBJECT-TYPE
        SYNTAX               Counter32
        MAX-ACCESS           read-only
        STATUS               current
        DESCRIPTION          "The number of received cells discarded 
                              due to uncorrectable header (HEC) errors on this
                              interface, since startup."
  ::= { nncAtmProtoRawEntry 3 }

  nncAtmProtoRawDisInvalidVPIVCIInCells OBJECT-TYPE
       SYNTAX               Counter32
       MAX-ACCESS           read-only
       STATUS               current
       DESCRIPTION          "The number of received cells discarded due
                             to invalid VPI/VCI on this interface, since 
                             startup."
  ::= { nncAtmProtoRawEntry 4 }

  nncAtmProtoRawOutCells OBJECT-TYPE
       SYNTAX               Counter32
       MAX-ACCESS           read-only
       STATUS               current
       DESCRIPTION          "The number of cells transmitted on this 
                             interface, since startup."
  ::= { nncAtmProtoRawEntry 5 }


-------------------------------------------------------------------------------
-- Conformance Group Definitions
-------------------------------------------------------------------------------
  nncAtmProtoCurrGroup         OBJECT-GROUP 
    OBJECTS {
      nncAtmProtoCurrValidInCells,
      nncAtmProtoCurrCorrHeaderInCells,
      nncAtmProtoCurrDisHECInCells,
      nncAtmProtoCurrDisInvalidVPIVCIInCells,
      nncAtmProtoCurrOutCells
    }
    STATUS          current
    DESCRIPTION     "A collection of objects providing 15 Min current 
                     monitoring data for a ATM interface."
    ::= { nncAtmProtoGroups 1 }

  nncAtmProtoHistGroup         OBJECT-GROUP 
    OBJECTS {
      nncAtmProtoHistIndex,
      nncAtmProtoHistValidInCells,
      nncAtmProtoHistCorrHeaderInCells,
      nncAtmProtoHistDisHECInCells,
      nncAtmProtoHistDisInvalidVPIVCIInCells,
      nncAtmProtoHistOutCells
    }
    STATUS          current
    DESCRIPTION     "A collection of objects providing 15 Min history 
                     monitoring data for a ATM interface."
    ::= { nncAtmProtoGroups 2 }

  nncAtmProtoTotalGroup         OBJECT-GROUP 
    OBJECTS {
      nncAtmProtoTotalValidIntervals,
      nncAtmProtoTotalValidInCells,
      nncAtmProtoTotalCorrHeaderInCells,
      nncAtmProtoTotalDisHECInCells,
      nncAtmProtoTotalDisInvalidVPIVCIInCells,
      nncAtmProtoTotalOutCells
    }
    STATUS          current
    DESCRIPTION     "A collection of objects providing previous 24 hour 
                     monitoring data for a ATM interface."
    ::= { nncAtmProtoGroups 3 }

  nncAtmProtoRawGroup         OBJECT-GROUP 
    OBJECTS {
      nncAtmProtoRawValidInCells,
      nncAtmProtoRawCorrHeaderInCells,
      nncAtmProtoRawDisHECInCells,
      nncAtmProtoRawDisInvalidVPIVCIInCells,
      nncAtmProtoRawOutCells
    }
    STATUS          current
    DESCRIPTION     "A collection of objects providing raw monitoring data 
                     for a ATM interface."
    ::= { nncAtmProtoGroups 4 }


-------------------------------------------------------------------------------
-- Compliance Statements (mandatory)
-------------------------------------------------------------------------------
  nncAtmProtoCompliance      MODULE-COMPLIANCE
    STATUS          current
    DESCRIPTION     "The complicance statement for Newbridge SNMP entities 
                     which have ATM protocol monitoring data."
    MODULE
      MANDATORY-GROUPS {
      nncAtmProtoCurrGroup,
      nncAtmProtoHistGroup,
      nncAtmProtoTotalGroup,
      nncAtmProtoRawGroup
      }
    ::= { nncAtmProtoCompliances 1 } 


-------------------------------------------------------------------------------
--      Review Minutes 
-------------------------------------------------------------------------------
--      MINUTES-BEGIN
--              REVIEW-DATE  "1998.04.30"
--              BODY  "
--
--      
--      TO:     Det Kruse*, Randy Jones*, Mark Weedmark*
--      FROM:   Det Kruse
--
--	A meeting was held on 1998.04.30 to review ATMProtoStatistics.mib.
--      To review the new nncAtmProtoRaw objects that were added.
--	Attendees are marked with * in the TO list above.
--
--      Outcome
--
--      It was the consensus of the review team that this file is 
--      acceptable with the indicated modifications.
--
--      Comments:
--
--      Actions:
--      A1 -    Update the file with a few extra comments.
--		Response:	Status: CLOSED
--
--      A2 -    Did not add original file creation minutes since they
--              could not be located.
--		Response:	Status: CLOSED
--
--      Decisions:
--      D1 -    Add a few extra comments.
--
--      D2 -    Add missing minutes from original creation of
--              ATMProtoStatistics.mib.
--      "
--
--      END-MINUTES
--
END -- DEFINITION OF NNCATMPROTOSTATISTICS-MIB
