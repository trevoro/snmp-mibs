CXBRI-MIB DEFINITIONS ::= BEGIN

IMPORTS
   OBJECT-TYPE     FROM RFC-1212
   cxBri           FROM CXProduct-SMI;


--  ISDN Basic Rate Interface Built-In Self Test Configuration Table

--  The table describing:
-- statistics available for monitoring test results of an ISDN U or 
-- S/T-Interface daughter card

briTable OBJECT-TYPE
   SYNTAX  SEQUENCE OF BriEntry
   ACCESS  not-accessible
   STATUS  mandatory
   DESCRIPTION
"A table containing test results of an ISDN U or S/T-Interface daughter card."
   ::= { cxBri 10 }


briEntry OBJECT-TYPE
      SYNTAX  BriEntry
      ACCESS  not-accessible
      STATUS  mandatory
      DESCRIPTION
"The parameters for a specific ISDN U or S/T-Interface daughter card."
      INDEX { briSlotNumberIndex }
      ::= { briTable 1 }


BriEntry ::=
      SEQUENCE {
-- Parameters
         briSlotNumberIndex               INTEGER,
-- Control
-- Status
         briIoRegTest                     INTEGER,
         briIoLedsTest                    INTEGER,
         briImpRegTest                    INTEGER,
         briImpComTestPollResult          INTEGER,        
         briTxcvrRegTest                  INTEGER,
         briTxcvrComTestPollResult        INTEGER
-- Statistics           
         }

briSlotNumberIndex OBJECT-TYPE
      SYNTAX  INTEGER (1..8)
      ACCESS  read-only
      STATUS  mandatory
      DESCRIPTION
"Indicates the row containing objects for monitoring an I/O card in the 
CX900 or CX950.

Range of Values: 1-6 for CX900 (slot)
                 1-8 for CX950 (slot)

Default Value: none"
      ::= { briEntry 1 }
   

briIoRegTest OBJECT-TYPE
      SYNTAX  INTEGER {
              failed    (1),
              passed    (2)
            }
      ACCESS  read-only
      STATUS  mandatory
      DESCRIPTION
"Indicates the result of the ISDN U or S/T-interface I/O register test.

Options:
failed (1): register test failed

passed (2): register test passed

Default Value: passed (2)"
      ::= { briEntry 20 }


briIoLedsTest OBJECT-TYPE
      SYNTAX  INTEGER {
              initializationFailed    (1),
              initializationPassed    (2)
            }
      ACCESS  read-only
      STATUS  mandatory
      DESCRIPTION
"Indicates the result of the ISDN U or S/T-interface Integrated Multiprotocol 
Processor (IMP) LEDs test.

Options:
initializationFailed (1): IMP initialization failed

initializationPassed (2): IMP initialization passed

Default Value: initializationPassed"
      ::= { briEntry 21 }


briImpRegTest OBJECT-TYPE
      SYNTAX  INTEGER {
              initializationFailed            (1),
              failed                          (2),
              passed                          (3)
            }
      ACCESS  read-only
      STATUS  mandatory
      DESCRIPTION
"Indicates the result of the ISDN U or S/T-interface Integrated Multiprotocol 
Processor (IMP) register test.

Options:
initializationFailed (1): IMP initialization failed

failed (2): IMP register test failed

passed (3): IMP register test passed

Default Value: passed (3)"
      ::= { briEntry 22 }


briImpComTestPollResult OBJECT-TYPE
      SYNTAX  INTEGER {
              initializationFailed            (1),
              failed                          (2),
              passed                          (3)
            }
      ACCESS  read-only
      STATUS  mandatory
      DESCRIPTION
"Indicates the result of the ISDN U or S/T-interface IMP internal communication 
test while in polling mode.

Options:
initializationFailed (1): IMP initialization failed

failed (2): IMP communication test failed in polling mode

passed (3): IMP communication test passed in polling mode

Default Value: passed (3)"
      ::= { briEntry 23 }


briTxcvrRegTest OBJECT-TYPE
      SYNTAX  INTEGER {
              initializationFailed            (1),
              failed                          (2),
              passed                          (3)
            }
      ACCESS  read-only
      STATUS  mandatory
      DESCRIPTION
"Indicates the result of the ISDN U or S/T-interface transceiver register test.

Options:
initializationFailed (1): IMP initialization test failed

failed (2): transceiver register test failed

passed (3): transceiver register test passed

Default Value: passed (3)"
      ::= { briEntry 24 }


briTxcvrComTestPollResult OBJECT-TYPE
      SYNTAX  INTEGER {
              initializationFailed            (1),
              failed                          (2),
              passed                          (3)
            }
      ACCESS  read-only
      STATUS  mandatory
      DESCRIPTION
"Indicates the result of the ISDN U or S/T-interface transceiver internal 
communication test while in polling mode.

Options:
initializationFailed (1): IMP initialization failed

failed (2): transceiver communication test failed in polling mode

passed (3): transceiver communication test passed in polling mode

Default Value: passed (3)"
      ::= { briEntry 25 }

END
