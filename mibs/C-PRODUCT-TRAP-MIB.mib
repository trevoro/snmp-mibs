--            Trap Management Information Base for C-PRODUCT
-- 
-- This module contains C-PRODUCT enterprise-specific traps.  In order
-- for a NMS to receive SNMP traps from C-PRODUCT, the trap client
-- table (sysIpConfigTrapClientTable) in C-PRODUCT base MIB must be
-- properly configured (by telnet, vt-100 terminal, or SNMP-Set requests).
--

C-PRODUCT-TRAP-MIB DEFINITIONS ::= BEGIN

IMPORTS
        DisplayString          FROM RFC1213-MIB
        TRAP-TYPE              FROM RFC-1215
        OBJECT-TYPE            FROM RFC-1212
        c-product, fault       FROM C-PRODUCT-GROUP-MIB
        TimeAndDate, CardType  FROM C-PRODUCT-BASE-MIB;


-- alarm group

alarm OBJECT IDENTIFIER ::= { fault 5 }

alarmSeverity OBJECT-TYPE
    SYNTAX  INTEGER { info  (1),  -- a fault whose status cannot be cleared
                      minor (2),
                      major (3) }
    ACCESS  not-accessible
    STATUS  mandatory
    DESCRIPTION
            "Severity of an alarm."
    ::= { alarm 1 }

alarmCardType OBJECT-TYPE
    SYNTAX  CardType 
    ACCESS  not-accessible
    STATUS  mandatory
    DESCRIPTION
            "Card type of the card which caused an alarm."
    ::= { alarm 2 }

alarmCardNumber OBJECT-TYPE
    SYNTAX  INTEGER (1..6)
    ACCESS  not-accessible
    STATUS  mandatory
    DESCRIPTION
            "Slot number of the card which caused an alarm."
    ::= { alarm 3 }

alarmPortNumber OBJECT-TYPE
    SYNTAX  INTEGER (1..8)
    ACCESS  not-accessible
    STATUS  mandatory
    DESCRIPTION
            "Port number of the card which caused an alarm."
    ::= { alarm 4 }

alarmSetTime OBJECT-TYPE
    SYNTAX  TimeAndDate
    ACCESS  not-accessible
    STATUS  mandatory
    DESCRIPTION
            "The time when an alarm was generated."
    ::= { alarm 5 }

alarmClearTime OBJECT-TYPE
    SYNTAX  TimeAndDate
    ACCESS  not-accessible
    STATUS  mandatory
    DESCRIPTION
            "The time when an alarm was cleared.  For active alarms,
             the value of this object contains all zero's.  
             For cleared alarms, this object contains the time when 
             the alarms were cleared."
    ::= { alarm 6 }

alarmDescription OBJECT-TYPE
    SYNTAX  DisplayString
    ACCESS  not-accessible
    STATUS  mandatory
    DESCRIPTION
            "A readable string which describes an alarm."
    ::= { alarm 7 }

-- trap types

alarmLossOfSignal TRAP-TYPE
    ENTERPRISE c-product
    VARIABLES  { alarmSeverity,
                 alarmCardType,
                 alarmCardNumber,
                 alarmPortNumber,
                 alarmSetTime,
                 alarmClearTime,
                 alarmDescription }
    DESCRIPTION
            "Loss of signal alarm."
    ::= 1

alarmOutOfFrame TRAP-TYPE
    ENTERPRISE c-product
    VARIABLES  { alarmSeverity,
                 alarmCardType,
                 alarmCardNumber,
                 alarmPortNumber,
                 alarmSetTime,
                 alarmClearTime,
                 alarmDescription }
    DESCRIPTION
            "Out of frame alarm."
    ::= 2

alarmAlarmIndicationSignal TRAP-TYPE
    ENTERPRISE c-product
    VARIABLES  { alarmSeverity,
                 alarmCardType,
                 alarmCardNumber,
                 alarmPortNumber,
                 alarmSetTime,
                 alarmClearTime,
                 alarmDescription }
    DESCRIPTION
            "AIS alarm."
    ::= 3

alarmIdleSignal TRAP-TYPE
    ENTERPRISE c-product
    VARIABLES  { alarmSeverity,
                 alarmCardType,
                 alarmCardNumber,
                 alarmPortNumber,
                 alarmSetTime,
                 alarmClearTime,
                 alarmDescription }
    DESCRIPTION
            "Idle signal alarm."
    ::= 4

alarmFarEndRcvFailure TRAP-TYPE
    ENTERPRISE c-product
    VARIABLES  { alarmSeverity,
                 alarmCardType,
                 alarmCardNumber,
                 alarmPortNumber,
                 alarmSetTime,
                 alarmClearTime,
                 alarmDescription }
    DESCRIPTION
            "Far end receive failure alarm."
    ::= 5

alarmLossOfCellDelineation TRAP-TYPE
    ENTERPRISE c-product
    VARIABLES  { alarmSeverity,
                 alarmCardType,
                 alarmCardNumber,
                 alarmPortNumber,
                 alarmSetTime,
                 alarmClearTime,
                 alarmDescription }
    DESCRIPTION
            "Loss of cell delineation alarm."
    ::= 6

alarmVirtualPathAis TRAP-TYPE
    ENTERPRISE c-product
    VARIABLES  { alarmSeverity,
                 alarmCardType,
                 alarmCardNumber,
                 alarmPortNumber,
                 alarmSetTime,
                 alarmClearTime,
                 alarmDescription }
    DESCRIPTION
            "Virtual Path AIS."
    ::= 7

alarmVirtualChannelAis TRAP-TYPE
    ENTERPRISE c-product
    VARIABLES  { alarmSeverity,
                 alarmCardType,
                 alarmCardNumber,
                 alarmPortNumber,
                 alarmSetTime,
                 alarmClearTime,
                 alarmDescription }
    DESCRIPTION
            "Virtual Channel AIS."
    ::= 8

alarmMissingUploadImage TRAP-TYPE
    ENTERPRISE c-product
    VARIABLES  { alarmSeverity,
                 alarmCardType,
                 alarmCardNumber,
                 alarmPortNumber,
                 alarmSetTime,
                 alarmClearTime,
                 alarmDescription }
    DESCRIPTION
            "Cannot find card image to upload."
    ::= 9

alarmCardReconfigOk TRAP-TYPE
    ENTERPRISE c-product
    VARIABLES  { alarmSeverity,
                 alarmCardType,
                 alarmCardNumber,
                 alarmPortNumber,
                 alarmSetTime,
                 alarmClearTime,
                 alarmDescription }
    DESCRIPTION
            "Configuration data of a card is reloaded."
    ::= 10

alarmUnknownDbCardType TRAP-TYPE
    ENTERPRISE c-product
    VARIABLES  { alarmSeverity,
                 alarmCardType,
                 alarmCardNumber,
                 alarmPortNumber,
                 alarmSetTime,
                 alarmClearTime,
                 alarmDescription }
    DESCRIPTION
            "An unknown card type is found in database."
    ::= 11

alarmCardReconfigFailure TRAP-TYPE
    ENTERPRISE c-product
    VARIABLES  { alarmSeverity,
                 alarmCardType,
                 alarmCardNumber,
                 alarmPortNumber,
                 alarmSetTime,
                 alarmClearTime,
                 alarmDescription }
    DESCRIPTION
            "Cannot reload configuration data to a card."
    ::= 12

alarmCardTypeMismatch TRAP-TYPE
    ENTERPRISE c-product
    VARIABLES  { alarmSeverity,
                 alarmCardType,
                 alarmCardNumber,
                 alarmPortNumber,
                 alarmSetTime,
                 alarmClearTime,
                 alarmDescription }
    DESCRIPTION
            "The card type of a card slot in database does not match
             the card type of the same card slot in the shelf."
    ::= 13

alarmNewCardConfigOk TRAP-TYPE
    ENTERPRISE c-product
    VARIABLES  { alarmSeverity,
                 alarmCardType,
                 alarmCardNumber,
                 alarmPortNumber,
                 alarmSetTime,
                 alarmClearTime,
                 alarmDescription }
    DESCRIPTION
            "Configuration data for a new card is uploaded."
    ::= 14

alarmCardConfigFailure TRAP-TYPE
    ENTERPRISE c-product
    VARIABLES  { alarmSeverity,
                 alarmCardType,
                 alarmCardNumber,
                 alarmPortNumber,
                 alarmSetTime,
                 alarmClearTime,
                 alarmDescription }
    DESCRIPTION
            "Cannot upload configuration data to a card."
    ::= 15

alarmUnknownCardType TRAP-TYPE
    ENTERPRISE c-product
    VARIABLES  { alarmSeverity,
                 alarmCardType,
                 alarmCardNumber,
                 alarmPortNumber,
                 alarmSetTime,
                 alarmClearTime,
                 alarmDescription }
    DESCRIPTION
            "An unknown card type is detected in a card slot."
    ::= 16

alarmCardRemoval TRAP-TYPE
    ENTERPRISE c-product
    VARIABLES  { alarmSeverity,
                 alarmCardType,
                 alarmCardNumber,
                 alarmPortNumber,
                 alarmSetTime,
                 alarmClearTime,
                 alarmDescription }
    DESCRIPTION
            "A card is removed from a card slot."
    ::= 17

alarmCardDownloadFailure TRAP-TYPE
    ENTERPRISE c-product
    VARIABLES  { alarmSeverity,
                 alarmCardType,
                 alarmCardNumber,
                 alarmPortNumber,
                 alarmSetTime,
                 alarmClearTime,
                 alarmDescription }
    DESCRIPTION
            "Cannot download card image to a card."
    ::= 18

alarmMissingLeftPowerSupply TRAP-TYPE
    ENTERPRISE c-product
    VARIABLES  { alarmSeverity,
                 alarmCardType,
                 alarmCardNumber,
                 alarmPortNumber,
                 alarmSetTime,
                 alarmClearTime,
                 alarmDescription }
    DESCRIPTION
            "Power Supply 1 absent."
    ::= 19

alarmMissingRightPowerSupply TRAP-TYPE
    ENTERPRISE c-product
    VARIABLES  { alarmSeverity,
                 alarmCardType,
                 alarmCardNumber,
                 alarmPortNumber,
                 alarmSetTime,
                 alarmClearTime,
                 alarmDescription }
    DESCRIPTION
            "Power Supply 2 absent."
    ::= 20

alarmLeftPowerSupplyFailure TRAP-TYPE
    ENTERPRISE c-product
    VARIABLES  { alarmSeverity,
                 alarmCardType,
                 alarmCardNumber,
                 alarmPortNumber,
                 alarmSetTime,
                 alarmClearTime,
                 alarmDescription }
    DESCRIPTION
            "Left power supply failed."
    ::= 21

alarmRightPowerSupplyFailure TRAP-TYPE
    ENTERPRISE c-product
    VARIABLES  { alarmSeverity,
                 alarmCardType,
                 alarmCardNumber,
                 alarmPortNumber,
                 alarmSetTime,
                 alarmClearTime,
                 alarmDescription }
    DESCRIPTION
            "Right power supply failed."
    ::= 22

alarmRelayPowerFuseFailure TRAP-TYPE
    ENTERPRISE c-product
    VARIABLES  { alarmSeverity,
                 alarmCardType,
                 alarmCardNumber,
                 alarmPortNumber,
                 alarmSetTime,
                 alarmClearTime,
                 alarmDescription }
    DESCRIPTION
            "Relay power fuse failed."
    ::= 23

alarmCommunicationFailure TRAP-TYPE
    ENTERPRISE c-product
    VARIABLES  { alarmSeverity,
                 alarmCardType,
                 alarmCardNumber,
                 alarmPortNumber,
                 alarmSetTime,
                 alarmClearTime,
                 alarmDescription }
    DESCRIPTION
            "Communication through DPRAM failed."
    ::= 24

alarmFan1Failure TRAP-TYPE
    ENTERPRISE c-product
    VARIABLES  { alarmSeverity,
                 alarmCardType,
                 alarmCardNumber,
                 alarmPortNumber,
                 alarmSetTime,
                 alarmClearTime,
                 alarmDescription }
    DESCRIPTION
            "Fan #1 failed."
    ::= 25

alarmFan2Failure TRAP-TYPE
    ENTERPRISE c-product
    VARIABLES  { alarmSeverity,
                 alarmCardType,
                 alarmCardNumber,
                 alarmPortNumber,
                 alarmSetTime,
                 alarmClearTime,
                 alarmDescription }
    DESCRIPTION
            "Fan #2 failed."
    ::= 26

alarmFan3Failure TRAP-TYPE
    ENTERPRISE c-product
    VARIABLES  { alarmSeverity,
                 alarmCardType,
                 alarmCardNumber,
                 alarmPortNumber,
                 alarmSetTime,
                 alarmClearTime,
                 alarmDescription }
    DESCRIPTION
            "Fan #3 failed."
    ::= 27

alarmFan4Failure TRAP-TYPE
    ENTERPRISE c-product
    VARIABLES  { alarmSeverity,
                 alarmCardType,
                 alarmCardNumber,
                 alarmPortNumber,
                 alarmSetTime,
                 alarmClearTime,
                 alarmDescription }
    DESCRIPTION
            "Fan #4 failed."
    ::= 28

alarmFeacLoopback TRAP-TYPE
    ENTERPRISE c-product
    VARIABLES  { alarmSeverity,
                 alarmCardType,
                 alarmCardNumber,
                 alarmPortNumber,
                 alarmSetTime,
                 alarmClearTime,
                 alarmDescription }
    DESCRIPTION
            "FEAC loopback alarm."
    ::= 29

alarmNetworkLineLoopback TRAP-TYPE
    ENTERPRISE c-product
    VARIABLES  { alarmSeverity,
                 alarmCardType,
                 alarmCardNumber,
                 alarmPortNumber,
                 alarmSetTime,
                 alarmClearTime,
                 alarmDescription }
    DESCRIPTION
            "Network line loopback alarm."
    ::= 30

alarmLocalCardLoopback TRAP-TYPE
    ENTERPRISE c-product
    VARIABLES  { alarmSeverity,
                 alarmCardType,
                 alarmCardNumber,
                 alarmPortNumber,
                 alarmSetTime,
                 alarmClearTime,
                 alarmDescription }
    DESCRIPTION
            "Local card loopback alarm."
    ::= 31

alarmNetworkCardLoopback TRAP-TYPE
    ENTERPRISE c-product
    VARIABLES  { alarmSeverity,
                 alarmCardType,
                 alarmCardNumber,
                 alarmPortNumber,
                 alarmSetTime,
                 alarmClearTime,
                 alarmDescription }
    DESCRIPTION
            "Network card loopback alarm."
    ::= 32

alarmCardNotInstalled TRAP-TYPE
    ENTERPRISE c-product
    VARIABLES  { alarmSeverity,
                 alarmCardType,
                 alarmCardNumber,
                 alarmPortNumber,
                 alarmSetTime,
                 alarmClearTime,
                 alarmDescription }
    DESCRIPTION
            "Card not installed."
    ::= 33

alarmCardInitialized TRAP-TYPE
    ENTERPRISE c-product
    VARIABLES  { alarmSeverity,
                 alarmCardType,
                 alarmCardNumber,
                 alarmPortNumber,
                 alarmSetTime,
                 alarmClearTime,
                 alarmDescription }
    DESCRIPTION
            "Card initialized."
    ::= 34

alarmCellbusParity TRAP-TYPE
    ENTERPRISE c-product
    VARIABLES  { alarmSeverity,
                 alarmCardType,
                 alarmCardNumber,
                 alarmPortNumber,
                 alarmSetTime,
                 alarmClearTime,
                 alarmDescription }
    DESCRIPTION
            "Cellbus parity alarm."
    ::= 35

alarmReceiveFifoOverflow TRAP-TYPE
    ENTERPRISE c-product
    VARIABLES  { alarmSeverity,
                 alarmCardType,
                 alarmCardNumber,
                 alarmPortNumber,
                 alarmSetTime,
                 alarmClearTime,
                 alarmDescription }
    DESCRIPTION
            "Receive FIFO overflow alarm."
    ::= 36

alarmTransmitFifoOverflow TRAP-TYPE
    ENTERPRISE c-product
    VARIABLES  { alarmSeverity,
                 alarmCardType,
                 alarmCardNumber,
                 alarmPortNumber,
                 alarmSetTime,
                 alarmClearTime,
                 alarmDescription }
    DESCRIPTION
            "Transmit FIFO overflow alarm."
    ::= 37

alarmLpCellbusCongestion TRAP-TYPE
    ENTERPRISE c-product
    VARIABLES  { alarmSeverity,
                 alarmCardType,
                 alarmCardNumber,
                 alarmPortNumber,
                 alarmSetTime,
                 alarmClearTime,
                 alarmDescription }
    DESCRIPTION
            "LP cellbus congested alarm."
    ::= 38

alarmMpCellbusCongestion TRAP-TYPE
    ENTERPRISE c-product
    VARIABLES  { alarmSeverity,
                 alarmCardType,
                 alarmCardNumber,
                 alarmPortNumber,
                 alarmSetTime,
                 alarmClearTime,
                 alarmDescription }
    DESCRIPTION
            "MP cellbus congested alarm."
    ::= 39

alarmHpCellbusCongestion TRAP-TYPE
    ENTERPRISE c-product
    VARIABLES  { alarmSeverity,
                 alarmCardType,
                 alarmCardNumber,
                 alarmPortNumber,
                 alarmSetTime,
                 alarmClearTime,
                 alarmDescription }
    DESCRIPTION
            "HP cellbus congested alarm."
    ::= 40

alarmLoginFailure TRAP-TYPE
    ENTERPRISE c-product
    VARIABLES  { alarmSeverity,
                 alarmCardType,
                 alarmCardNumber,
                 alarmPortNumber,
                 alarmSetTime,
                 alarmClearTime,
                 alarmDescription }
    DESCRIPTION
            "Terminal login attempts failed for three times."
    ::= 42

alarmPromChecksumError TRAP-TYPE
    ENTERPRISE c-product
    VARIABLES  { alarmSeverity,
                 alarmCardType,
                 alarmCardNumber,
                 alarmPortNumber,
                 alarmSetTime,
                 alarmClearTime,
                 alarmDescription }
    DESCRIPTION
            "PROM checksum error alarm."
    ::= 43

alarmBank0SramFailure TRAP-TYPE
    ENTERPRISE c-product
    VARIABLES  { alarmSeverity,
                 alarmCardType,
                 alarmCardNumber,
                 alarmPortNumber,
                 alarmSetTime,
                 alarmClearTime,
                 alarmDescription }
    DESCRIPTION
            "Bank 0 SRAM failure alarm."
    ::= 44

alarmBank1SramFailure TRAP-TYPE
    ENTERPRISE c-product
    VARIABLES  { alarmSeverity,
                 alarmCardType,
                 alarmCardNumber,
                 alarmPortNumber,
                 alarmSetTime,
                 alarmClearTime,
                 alarmDescription }
    DESCRIPTION
            "Bank 1 SRAM failure alarm."
    ::= 45

alarmSarSramFailure TRAP-TYPE
    ENTERPRISE c-product
    VARIABLES  { alarmSeverity,
                 alarmCardType,
                 alarmCardNumber,
                 alarmPortNumber,
                 alarmSetTime,
                 alarmClearTime,
                 alarmDescription }
    DESCRIPTION
            "SAR SRAM failure alarm."
    ::= 46

alarmHdlcSramFailure TRAP-TYPE
    ENTERPRISE c-product
    VARIABLES  { alarmSeverity,
                 alarmCardType,
                 alarmCardNumber,
                 alarmPortNumber,
                 alarmSetTime,
                 alarmClearTime,
                 alarmDescription }
    DESCRIPTION
            "HDLC SRAM failure alarm."
    ::= 47

alarmMailboxSramFailure TRAP-TYPE
    ENTERPRISE c-product
    VARIABLES  { alarmSeverity,
                 alarmCardType,
                 alarmCardNumber,
                 alarmPortNumber,
                 alarmSetTime,
                 alarmClearTime,
                 alarmDescription }
    DESCRIPTION
            "Mailbox SRAM failure alarm."
    ::= 48

alarmCellbusXlnkPrgFailure TRAP-TYPE
    ENTERPRISE c-product
    VARIABLES  { alarmSeverity,
                 alarmCardType,
                 alarmCardNumber,
                 alarmPortNumber,
                 alarmSetTime,
                 alarmClearTime,
                 alarmDescription }
    DESCRIPTION
            "Cellbus Xilinx programming failure alarm."
    ::= 49

alarmPort01XlnkPrgFailure TRAP-TYPE
    ENTERPRISE c-product
    VARIABLES  { alarmSeverity,
                 alarmCardType,
                 alarmCardNumber,
                 alarmPortNumber,
                 alarmSetTime,
                 alarmClearTime,
                 alarmDescription }
    DESCRIPTION
            "Port 01 Xilinx programming failure alarm."
    ::= 50

alarmPort23XlnkPrgFailure TRAP-TYPE
    ENTERPRISE c-product
    VARIABLES  { alarmSeverity,
                 alarmCardType,
                 alarmCardNumber,
                 alarmPortNumber,
                 alarmSetTime,
                 alarmClearTime,
                 alarmDescription }
    DESCRIPTION
            "Port 23 Xilinx programming failure alarm."
    ::= 51

alarmPort45XlnkPrgFailure TRAP-TYPE
    ENTERPRISE c-product
    VARIABLES  { alarmSeverity,
                 alarmCardType,
                 alarmCardNumber,
                 alarmPortNumber,
                 alarmSetTime,
                 alarmClearTime,
                 alarmDescription }
    DESCRIPTION
            "Port 45 Xilinx programming failure alarm."
    ::= 52

alarmPort67XlnkPrgFailure TRAP-TYPE
    ENTERPRISE c-product
    VARIABLES  { alarmSeverity,
                 alarmCardType,
                 alarmCardNumber,
                 alarmPortNumber,
                 alarmSetTime,
                 alarmClearTime,
                 alarmDescription }
    DESCRIPTION
            "Port 67 Xilinx programming failure alarm."
    ::= 53

alarmSarXlnkPrgFailure TRAP-TYPE
    ENTERPRISE c-product
    VARIABLES  { alarmSeverity,
                 alarmCardType,
                 alarmCardNumber,
                 alarmPortNumber,
                 alarmSetTime,
                 alarmClearTime,
                 alarmDescription }
    DESCRIPTION
            "SAR Xilinx programming failure alarm."
    ::= 54

alarmPortInBandLpbkFailure TRAP-TYPE
    ENTERPRISE c-product
    VARIABLES  { alarmSeverity,
                 alarmCardType,
                 alarmCardNumber,
                 alarmPortNumber,
                 alarmSetTime,
                 alarmClearTime,
                 alarmDescription }
    DESCRIPTION
            "Port in-band loopback failure alarm."
    ::= 55

alarmE1Channel16Ais TRAP-TYPE
    ENTERPRISE c-product
    VARIABLES  { alarmSeverity,
                 alarmCardType,
                 alarmCardNumber,
                 alarmPortNumber,
                 alarmSetTime,
                 alarmClearTime,
                 alarmDescription }
    DESCRIPTION
            "E1 channel 16 AIS alarm."
    ::= 56

alarmE1LossOfMultiframeCas TRAP-TYPE
    ENTERPRISE c-product
    VARIABLES  { alarmSeverity,
                 alarmCardType,
                 alarmCardNumber,
                 alarmPortNumber,
                 alarmSetTime,
                 alarmClearTime,
                 alarmDescription }
    DESCRIPTION
            "E1 loss of multiframe CAS alarm."
    ::= 57

alarmE1FarEndLossOfCas TRAP-TYPE
    ENTERPRISE c-product
    VARIABLES  { alarmSeverity,
                 alarmCardType,
                 alarmCardNumber,
                 alarmPortNumber,
                 alarmSetTime,
                 alarmClearTime,
                 alarmDescription }
    DESCRIPTION
            "E1 far end loss of CAS alarm."
    ::= 58

alarmPortYellow TRAP-TYPE
    ENTERPRISE c-product
    VARIABLES  { alarmSeverity,
                 alarmCardType,
                 alarmCardNumber,
                 alarmPortNumber,
                 alarmSetTime,
                 alarmClearTime,
                 alarmDescription }
    DESCRIPTION
            "Port Yellow alarm."
    ::= 61

alarmVcRdiReceived TRAP-TYPE
    ENTERPRISE c-product
    VARIABLES  { alarmSeverity,
                 alarmCardType,
                 alarmCardNumber,
                 alarmPortNumber,
                 alarmSetTime,
                 alarmClearTime,
                 alarmDescription }
    DESCRIPTION
            "VC RDI Received."
    ::= 64

alarmInternalRefClkFailure TRAP-TYPE
    ENTERPRISE c-product
    VARIABLES  { alarmSeverity,
                 alarmCardType,
                 alarmCardNumber,
                 alarmPortNumber,
                 alarmSetTime,
                 alarmClearTime,
                 alarmDescription }
    DESCRIPTION
            "Internal reference clock failure alarm."
    ::= 66

alarmBitsRefClkFailure TRAP-TYPE
    ENTERPRISE c-product
    VARIABLES  { alarmSeverity,
                 alarmCardType,
                 alarmCardNumber,
                 alarmPortNumber,
                 alarmSetTime,
                 alarmClearTime,
                 alarmDescription }
    DESCRIPTION
            "BITS reference clock failure alarm."
    ::= 67

alarmCbrRefClkFailure TRAP-TYPE
    ENTERPRISE c-product
    VARIABLES  { alarmSeverity,
                 alarmCardType,
                 alarmCardNumber,
                 alarmPortNumber,
                 alarmSetTime,
                 alarmClearTime,
                 alarmDescription }
    DESCRIPTION
            "CBR reference clock failure alarm."
    ::= 68

alarmDs3RefClkFailure TRAP-TYPE
    ENTERPRISE c-product
    VARIABLES  { alarmSeverity,
                 alarmCardType,
                 alarmCardNumber,
                 alarmPortNumber,
                 alarmSetTime,
                 alarmClearTime,
                 alarmDescription }
    DESCRIPTION
            "DS3 reference clock failure alarm."
    ::= 69

alarmLossOfClock TRAP-TYPE
    ENTERPRISE c-product
    VARIABLES  { alarmSeverity,
                 alarmCardType,
                 alarmCardNumber,
                 alarmPortNumber,
                 alarmSetTime,
                 alarmClearTime,
                 alarmDescription }
    DESCRIPTION
            "Loss of clock alarm."
    ::= 70

alarmRemoteLoopback TRAP-TYPE
    ENTERPRISE c-product
    VARIABLES  { alarmSeverity,
                 alarmCardType,
                 alarmCardNumber,
                 alarmPortNumber,
                 alarmSetTime,
                 alarmClearTime,
                 alarmDescription }
    DESCRIPTION
            "Remote loopback alarm."
    ::= 71

alarmOc3RefClkFailure TRAP-TYPE
    ENTERPRISE c-product
    VARIABLES  { alarmSeverity,
                 alarmCardType,
                 alarmCardNumber,
                 alarmPortNumber,
                 alarmSetTime,
                 alarmClearTime,
                 alarmDescription }
    DESCRIPTION
            "OC3 reference clock failure alarm."
    ::= 73

alarmE3RefClkFailure TRAP-TYPE
    ENTERPRISE c-product
    VARIABLES  { alarmSeverity,
                 alarmCardType,
                 alarmCardNumber,
                 alarmPortNumber,
                 alarmSetTime,
                 alarmClearTime,
                 alarmDescription }
    DESCRIPTION
            "E3 reference clock failure alarm."
    ::= 74

alarmSystemPowerUp TRAP-TYPE
    ENTERPRISE c-product
    VARIABLES  { alarmSeverity,
                 alarmCardType,
                 alarmCardNumber,
                 alarmPortNumber,
                 alarmSetTime,
                 alarmClearTime,
                 alarmDescription }
    DESCRIPTION
            "System power up."
    ::= 75

alarmLossCellDelin TRAP-TYPE
    ENTERPRISE c-product
    VARIABLES  { alarmSeverity,
                 alarmCardType,
                 alarmCardNumber,
                 alarmPortNumber,
                 alarmSetTime,
                 alarmClearTime,
                 alarmDescription }
    DESCRIPTION
            "Loss of cell delineation."
    ::= 77

alarmLossImaFrame TRAP-TYPE
    ENTERPRISE c-product
    VARIABLES  { alarmSeverity,
                 alarmCardType,
                 alarmCardNumber,
                 alarmPortNumber,
                 alarmSetTime,
                 alarmClearTime,
                 alarmDescription }
    DESCRIPTION
            "Loss of IMA frame."
    ::= 78

alarmLossDiffSync TRAP-TYPE
    ENTERPRISE c-product
    VARIABLES  { alarmSeverity,
                 alarmCardType,
                 alarmCardNumber,
                 alarmPortNumber,
                 alarmSetTime,
                 alarmClearTime,
                 alarmDescription }
    DESCRIPTION
            "Loss of differential synchronization."
    ::= 79

alarmDupImaId TRAP-TYPE
    ENTERPRISE c-product
    VARIABLES  { alarmSeverity,
                 alarmCardType,
                 alarmCardNumber,
                 alarmPortNumber,
                 alarmSetTime,
                 alarmClearTime,
                 alarmDescription }
    DESCRIPTION
            "Duplicate IMA ID."
    ::= 80

alarmBadImaId TRAP-TYPE
    ENTERPRISE c-product
    VARIABLES  { alarmSeverity,
                 alarmCardType,
                 alarmCardNumber,
                 alarmPortNumber,
                 alarmSetTime,
                 alarmClearTime,
                 alarmDescription }
    DESCRIPTION
            "Bad IMA ID."
    ::= 81

alarmBadM TRAP-TYPE
    ENTERPRISE c-product
    VARIABLES  { alarmSeverity,
                 alarmCardType,
                 alarmCardNumber,
                 alarmPortNumber,
                 alarmSetTime,
                 alarmClearTime,
                 alarmDescription }
    DESCRIPTION
            "Bad IMA M value."
    ::= 82

alarmDupLinkId TRAP-TYPE
    ENTERPRISE c-product
    VARIABLES  { alarmSeverity,
                 alarmCardType,
                 alarmCardNumber,
                 alarmPortNumber,
                 alarmSetTime,
                 alarmClearTime,
                 alarmDescription }
    DESCRIPTION
            "Duplicate link ID."
    ::= 83

alarmDupOff TRAP-TYPE
    ENTERPRISE c-product
    VARIABLES  { alarmSeverity,
                 alarmCardType,
                 alarmCardNumber,
                 alarmPortNumber,
                 alarmSetTime,
                 alarmClearTime,
                 alarmDescription }
    DESCRIPTION
            "Duplicate IMA offset."
    ::= 84

alarmTestPatFailed TRAP-TYPE
    ENTERPRISE c-product
    VARIABLES  { alarmSeverity,
                 alarmCardType,
                 alarmCardNumber,
                 alarmPortNumber,
                 alarmSetTime,
                 alarmClearTime,
                 alarmDescription }
    DESCRIPTION
            "Test pattern failed."
    ::= 85

alarmBadLinkId TRAP-TYPE
    ENTERPRISE c-product
    VARIABLES  { alarmSeverity,
                 alarmCardType,
                 alarmCardNumber,
                 alarmPortNumber,
                 alarmSetTime,
                 alarmClearTime,
                 alarmDescription }
    DESCRIPTION
            "Bad IMA Link ID."
    ::= 86

alarmBadOffset TRAP-TYPE
    ENTERPRISE c-product
    VARIABLES  { alarmSeverity,
                 alarmCardType,
                 alarmCardNumber,
                 alarmPortNumber,
                 alarmSetTime,
                 alarmClearTime,
                 alarmDescription }
    DESCRIPTION
            "Bad IMA offset."
    ::= 87

alarmBadScci TRAP-TYPE
    ENTERPRISE c-product
    VARIABLES  { alarmSeverity,
                 alarmCardType,
                 alarmCardNumber,
                 alarmPortNumber,
                 alarmSetTime,
                 alarmClearTime,
                 alarmDescription }
    DESCRIPTION
            "Bad SCCI."
    ::= 88

alarmFeBadM TRAP-TYPE
    ENTERPRISE c-product
    VARIABLES  { alarmSeverity,
                 alarmCardType,
                 alarmCardNumber,
                 alarmPortNumber,
                 alarmSetTime,
                 alarmClearTime,
                 alarmDescription }
    DESCRIPTION
            "Far end config abort due to bad M value."
    ::= 89

alarmBadSymmetry TRAP-TYPE
    ENTERPRISE c-product
    VARIABLES  { alarmSeverity,
                 alarmCardType,
                 alarmCardNumber,
                 alarmPortNumber,
                 alarmSetTime,
                 alarmClearTime,
                 alarmDescription }
    DESCRIPTION
            "Far end symmetry has changed."
    ::= 90

alarmTxMscon TRAP-TYPE
    ENTERPRISE c-product
    VARIABLES  { alarmSeverity,
                 alarmCardType,
                 alarmCardNumber,
                 alarmPortNumber,
                 alarmSetTime,
                 alarmClearTime,
                 alarmDescription }
    DESCRIPTION
            "Near end and far end transmit link misconnect."
    ::= 91

alarmImaFault TRAP-TYPE
    ENTERPRISE c-product
    VARIABLES  { alarmSeverity,
                 alarmCardType,
                 alarmCardNumber,
                 alarmPortNumber,
                 alarmSetTime,
                 alarmClearTime,
                 alarmDescription }
    DESCRIPTION
            "Near end IMA fault."
    ::= 92

alarmFeTxUnusable TRAP-TYPE
    ENTERPRISE c-product
    VARIABLES  { alarmSeverity,
                 alarmCardType,
                 alarmCardNumber,
                 alarmPortNumber,
                 alarmSetTime,
                 alarmClearTime,
                 alarmDescription }
    DESCRIPTION
            "Transmit IMA is unusable due to far end."
    ::= 93

alarmFeRxUnusable TRAP-TYPE
    ENTERPRISE c-product
    VARIABLES  { alarmSeverity,
                 alarmCardType,
                 alarmCardNumber,
                 alarmPortNumber,
                 alarmSetTime,
                 alarmClearTime,
                 alarmDescription }
    DESCRIPTION
            "Receive IMA is unusable due to far end."
    ::= 94

alarmImaRFI TRAP-TYPE
    ENTERPRISE c-product
    VARIABLES  { alarmSeverity,
                 alarmCardType,
                 alarmCardNumber,
                 alarmPortNumber,
                 alarmSetTime,
                 alarmClearTime,
                 alarmDescription }
    DESCRIPTION
            "Remote failure indication."
    ::= 95

alarmGroupNoLink TRAP-TYPE
    ENTERPRISE c-product
    VARIABLES  { alarmSeverity,
                 alarmCardType,
                 alarmCardNumber,
                 alarmPortNumber,
                 alarmSetTime,
                 alarmClearTime,
                 alarmDescription }
    DESCRIPTION
            "IMA group total link loss."
    ::= 96

alarmGrMultiImaID TRAP-TYPE
    ENTERPRISE c-product
    VARIABLES  { alarmSeverity,
                 alarmCardType,
                 alarmCardNumber,
                 alarmPortNumber,
                 alarmSetTime,
                 alarmClearTime,
                 alarmDescription }
    DESCRIPTION
	    "Group has multiple IMA ID values on links of same group."

    ::= 97

alarmGrMultiM TRAP-TYPE
    ENTERPRISE c-product
    VARIABLES  { alarmSeverity,
                 alarmCardType,
                 alarmCardNumber,
                 alarmPortNumber,
                 alarmSetTime,
                 alarmClearTime,
                 alarmDescription }
    DESCRIPTION
            "IMA frame length mismatch on links of same group."
    ::= 98

alarmGrMultiSymm TRAP-TYPE
    ENTERPRISE c-product
    VARIABLES  { alarmSeverity,
                 alarmCardType,
                 alarmCardNumber,
                 alarmPortNumber,
                 alarmSetTime,
                 alarmClearTime,
                 alarmDescription }
    DESCRIPTION
            "Symmetry mismatch on links of same group."
    ::= 99


alarmIMARefClkFailure TRAP-TYPE
    ENTERPRISE c-product
    VARIABLES  { alarmSeverity,
                 alarmCardType,
                 alarmCardNumber,
                 alarmPortNumber,
                 alarmSetTime,
                 alarmClearTime,
                 alarmDescription }
    DESCRIPTION
            "DS1 UNI reference clock failure alarm."
    ::= 100
                                                   
alarmFAMRefClkFailure TRAP-TYPE
    ENTERPRISE c-product
    VARIABLES  { alarmSeverity,
                 alarmCardType,
                 alarmCardNumber,
                 alarmPortNumber,
                 alarmSetTime,
                 alarmClearTime,
                 alarmDescription }
    DESCRIPTION
            "FAM reference clock failure alarm."
    ::= 101
                                                   
alarmAlarmsCleared TRAP-TYPE
    ENTERPRISE c-product
    VARIABLES  { alarmSeverity,
                 alarmCardType,
                 alarmCardNumber,
                 alarmPortNumber,
                 alarmSetTime,
                 alarmClearTime,
                 alarmDescription }
    DESCRIPTION
            "Current alarms have been cleared by user."
    ::= 102

alarmAlarmHistoryOverflow TRAP-TYPE
    ENTERPRISE c-product
    VARIABLES  { alarmSeverity,
                 alarmCardType,
                 alarmCardNumber,
                 alarmPortNumber,
                 alarmSetTime,
                 alarmClearTime,
                 alarmDescription }
    DESCRIPTION
            "History alarm information is being lost."
    ::= 103

alarmAfaLinkRemoval TRAP-TYPE
    ENTERPRISE c-product
    VARIABLES  { alarmSeverity,
                 alarmCardType,
                 alarmCardNumber,
                 alarmPortNumber,
                 alarmSetTime,
                 alarmClearTime,
                 alarmDescription }
    DESCRIPTION
            "Link removed because of AFA conditions."
    ::= 104

alarmLmiLinkDown TRAP-TYPE
    ENTERPRISE c-product
    VARIABLES  { alarmSeverity,
                 alarmCardType,
                 alarmCardNumber,
                 alarmPortNumber,
                 alarmSetTime,
                 alarmClearTime,
                 alarmDescription }
    DESCRIPTION
            "LMI has brought down link."
    ::= 105

alarmExcessLinkDelay TRAP-TYPE
    ENTERPRISE c-product
    VARIABLES  { alarmSeverity,
                 alarmCardType,
                 alarmCardNumber,
                 alarmPortNumber,
                 alarmSetTime,
                 alarmClearTime,
                 alarmDescription }
    DESCRIPTION
            "Excessive link delay."
    ::= 106

alarmGrDupImaID TRAP-TYPE
    ENTERPRISE c-product
    VARIABLES  { alarmSeverity,
                 alarmCardType,
                 alarmCardNumber,
                 alarmPortNumber,
                 alarmSetTime,
                 alarmClearTime,
                 alarmDescription }
    DESCRIPTION
            "Group has duplicate IMA ID."
    ::= 107

alarmGroupDegradedSer TRAP-TYPE
    ENTERPRISE c-product
    VARIABLES  { alarmSeverity,
                 alarmCardType,
                 alarmCardNumber,
                 alarmPortNumber,
                 alarmSetTime,
                 alarmClearTime,
                 alarmDescription }
    DESCRIPTION
            "Group is running with degraded service."
    ::= 108

alarmGroupNlessP TRAP-TYPE
    ENTERPRISE c-product
    VARIABLES  { alarmSeverity,
                 alarmCardType,
                 alarmCardNumber,
                 alarmPortNumber,
                 alarmSetTime,
                 alarmClearTime,
                 alarmDescription }
    DESCRIPTION
            "Group failed because there are not enough links."
    ::= 109

alarmSarInitFailure TRAP-TYPE
    ENTERPRISE c-product
    VARIABLES  { alarmSeverity,
                 alarmCardType,
                 alarmCardNumber,
                 alarmPortNumber,
                 alarmSetTime,
                 alarmClearTime,
                 alarmDescription }
    DESCRIPTION
            "SAR failed during initialization."
    ::= 110

alarmInBandLpbk TRAP-TYPE
    ENTERPRISE c-product
    VARIABLES  { alarmSeverity,
                 alarmCardType,
                 alarmCardNumber,
                 alarmPortNumber,
                 alarmSetTime,
                 alarmClearTime,
                 alarmDescription }
    DESCRIPTION
            "In-band loopback active."
    ::= 111

alarmWrongSlotForCard TRAP-TYPE
    ENTERPRISE c-product
    VARIABLES  { alarmSeverity,
                 alarmCardType,
                 alarmCardNumber,
                 alarmPortNumber,
                 alarmSetTime,
                 alarmClearTime,
                 alarmDescription }
    DESCRIPTION
            "Wrong slot for card."
    ::= 112

alarmCellBfSDRamFail TRAP-TYPE
    ENTERPRISE c-product
    VARIABLES  { alarmSeverity,
                 alarmCardType,
                 alarmCardNumber,
                 alarmPortNumber,
                 alarmSetTime,
                 alarmClearTime,
                 alarmDescription }
    DESCRIPTION
            "Cell Buffer SDRAM Failure."
    ::= 113

alarmXilinxProgramFail TRAP-TYPE
    ENTERPRISE c-product
    VARIABLES  { alarmSeverity,
                 alarmCardType,
                 alarmCardNumber,
                 alarmPortNumber,
                 alarmSetTime,
                 alarmClearTime,
                 alarmDescription }
    DESCRIPTION
            "Xilinx Program Failure."
    ::= 114

alarmHeartBeatFail TRAP-TYPE
    ENTERPRISE c-product
    VARIABLES  { alarmSeverity,
                 alarmCardType,
                 alarmCardNumber,
                 alarmPortNumber,
                 alarmSetTime,
                 alarmClearTime,
                 alarmDescription }
    DESCRIPTION
            "Heart Beat Failure."
    ::= 115

alarmQcontrollerSRAMFail TRAP-TYPE
    ENTERPRISE c-product
    VARIABLES  { alarmSeverity,
                 alarmCardType,
                 alarmCardNumber,
                 alarmPortNumber,
                 alarmSetTime,
                 alarmClearTime,
                 alarmDescription }
    DESCRIPTION
            "Q Controller SRAM Failure."
    ::= 116

alarmShaperSRAMFail TRAP-TYPE
    ENTERPRISE c-product
    VARIABLES  { alarmSeverity,
                 alarmCardType,
                 alarmCardNumber,
                 alarmPortNumber,
                 alarmSetTime,
                 alarmClearTime,
                 alarmDescription }
    DESCRIPTION
            "Shaper SRAM Failure."
    ::= 117

alarmMulticastSRAMFail TRAP-TYPE
    ENTERPRISE c-product
    VARIABLES  { alarmSeverity,
                 alarmCardType,
                 alarmCardNumber,
                 alarmPortNumber,
                 alarmSetTime,
                 alarmClearTime,
                 alarmDescription }
    DESCRIPTION
            "Multicast SRAM Failure."
    ::= 118

alarmBusAParityError TRAP-TYPE
    ENTERPRISE c-product
    VARIABLES  { alarmSeverity,
                 alarmCardType,
                 alarmCardNumber,
                 alarmPortNumber,
                 alarmSetTime,
                 alarmClearTime,
                 alarmDescription }
    DESCRIPTION
            "Bus A Parity Error."
    ::= 119

alarmBusBParityError TRAP-TYPE
    ENTERPRISE c-product
    VARIABLES  { alarmSeverity,
                 alarmCardType,
                 alarmCardNumber,
                 alarmPortNumber,
                 alarmSetTime,
                 alarmClearTime,
                 alarmDescription }
    DESCRIPTION
            "Bus B Parity Error."
    ::= 120

alarmBusCParityError TRAP-TYPE
    ENTERPRISE c-product
    VARIABLES  { alarmSeverity,
                 alarmCardType,
                 alarmCardNumber,
                 alarmPortNumber,
                 alarmSetTime,
                 alarmClearTime,
                 alarmDescription }
    DESCRIPTION
            "Bus C Parity Error."
    ::= 121

alarmBusDParityError TRAP-TYPE
    ENTERPRISE c-product
    VARIABLES  { alarmSeverity,
                 alarmCardType,
                 alarmCardNumber,
                 alarmPortNumber,
                 alarmSetTime,
                 alarmClearTime,
                 alarmDescription }
    DESCRIPTION
            "Bus D Parity Error."
    ::= 122

alarmBusEParityError TRAP-TYPE
    ENTERPRISE c-product
    VARIABLES  { alarmSeverity,
                 alarmCardType,
                 alarmCardNumber,
                 alarmPortNumber,
                 alarmSetTime,
                 alarmClearTime,
                 alarmDescription }
    DESCRIPTION
            "Bus E Parity Error."
    ::= 123

alarmBusFParityError TRAP-TYPE
    ENTERPRISE c-product
    VARIABLES  { alarmSeverity,
                 alarmCardType,
                 alarmCardNumber,
                 alarmPortNumber,
                 alarmSetTime,
                 alarmClearTime,
                 alarmDescription }
    DESCRIPTION
            "Bus F Parity Error."
    ::= 124

alarmLoss25MHzATMClock TRAP-TYPE
    ENTERPRISE c-product
    VARIABLES  { alarmSeverity,
                 alarmCardType,
                 alarmCardNumber,
                 alarmPortNumber,
                 alarmSetTime,
                 alarmClearTime,
                 alarmDescription }
    DESCRIPTION
            "Loss 25MHz ATM Clock."
    ::= 125

alarmLoss8KHzRefClock TRAP-TYPE
    ENTERPRISE c-product
    VARIABLES  { alarmSeverity,
                 alarmCardType,
                 alarmCardNumber,
                 alarmPortNumber,
                 alarmSetTime,
                 alarmClearTime,
                 alarmDescription }
    DESCRIPTION
            "Loss 8KHz Ref Clock."
    ::= 126

alarmLossBITSInputSignal TRAP-TYPE
    ENTERPRISE c-product
    VARIABLES  { alarmSeverity,
                 alarmCardType,
                 alarmCardNumber,
                 alarmPortNumber,
                 alarmSetTime,
                 alarmClearTime,
                 alarmDescription }
    DESCRIPTION
            "Loss BITS Input Signal."
    ::= 127

alarmALMExtSSRAMFail TRAP-TYPE
    ENTERPRISE c-product
    VARIABLES  { alarmSeverity,
                 alarmCardType,
                 alarmCardNumber,
                 alarmPortNumber,
                 alarmSetTime,
                 alarmClearTime,
                 alarmDescription }
    DESCRIPTION
            "ALM Ext SSRAM Failure."
    ::= 129

alarmALMIngrFIFOOverflow TRAP-TYPE
    ENTERPRISE c-product
    VARIABLES  { alarmSeverity,
                 alarmCardType,
                 alarmCardNumber,
                 alarmPortNumber,
                 alarmSetTime,
                 alarmClearTime,
                 alarmDescription }
    DESCRIPTION
            "ALM Ingress FIFO Overflow."
    ::= 130

alarmALMDestSlotOverrun TRAP-TYPE
    ENTERPRISE c-product
    VARIABLES  { alarmSeverity,
                 alarmCardType,
                 alarmCardNumber,
                 alarmPortNumber,
                 alarmSetTime,
                 alarmClearTime,
                 alarmDescription }
    DESCRIPTION
            "ALM Dest Slot Overrun."
    ::= 131

alarmALMIngrVPIOver255 TRAP-TYPE
    ENTERPRISE c-product
    VARIABLES  { alarmSeverity,
                 alarmCardType,
                 alarmCardNumber,
                 alarmPortNumber,
                 alarmSetTime,
                 alarmClearTime,
                 alarmDescription }
    DESCRIPTION
            "ALM Ingress VPI Over 255."
    ::= 132

alarmALMIngrVCIOutRange TRAP-TYPE
    ENTERPRISE c-product
    VARIABLES  { alarmSeverity,
                 alarmCardType,
                 alarmCardNumber,
                 alarmPortNumber,
                 alarmSetTime,
                 alarmClearTime,
                 alarmDescription }
    DESCRIPTION
            "ALM Ingress VCI Out of Range."
    ::= 133

alarmALMIngrSyncError TRAP-TYPE
    ENTERPRISE c-product
    VARIABLES  { alarmSeverity,
                 alarmCardType,
                 alarmCardNumber,
                 alarmPortNumber,
                 alarmSetTime,
                 alarmClearTime,
                 alarmDescription }
    DESCRIPTION
            "ALM Ingress Sync Error."
    ::= 134

alarmALMParityErrEgrQCX TRAP-TYPE
    ENTERPRISE c-product
    VARIABLES  { alarmSeverity,
                 alarmCardType,
                 alarmCardNumber,
                 alarmPortNumber,
                 alarmSetTime,
                 alarmClearTime,
                 alarmDescription }
    DESCRIPTION
            "ALM Parity Error Egress/QController."
    ::= 135

alarmALMParityErrIgrCB TRAP-TYPE
    ENTERPRISE c-product
    VARIABLES  { alarmSeverity,
                 alarmCardType,
                 alarmCardNumber,
                 alarmPortNumber,
                 alarmSetTime,
                 alarmClearTime,
                 alarmDescription }
    DESCRIPTION
            "ALM Parity Error Ingress/CB."
    ::= 136

alarmALMExtSRAMParityEr TRAP-TYPE
    ENTERPRISE c-product
    VARIABLES  { alarmSeverity,
                 alarmCardType,
                 alarmCardNumber,
                 alarmPortNumber,
                 alarmSetTime,
                 alarmClearTime,
                 alarmDescription }
    DESCRIPTION
            "ALM Ext SRAM Parity Error."
    ::= 137

alarmALMInsertFIFOError TRAP-TYPE
    ENTERPRISE c-product
    VARIABLES  { alarmSeverity,
                 alarmCardType,
                 alarmCardNumber,
                 alarmPortNumber,
                 alarmSetTime,
                 alarmClearTime,
                 alarmDescription }
    DESCRIPTION
            "ALM Insert FIFO Error."
    ::= 138

alarmALMIgrCapFIFOError TRAP-TYPE
    ENTERPRISE c-product
    VARIABLES  { alarmSeverity,
                 alarmCardType,
                 alarmCardNumber,
                 alarmPortNumber,
                 alarmSetTime,
                 alarmClearTime,
                 alarmDescription }
    DESCRIPTION
            "ALM Ingress Cap FIFO Error."
    ::= 139

alarmALMEgrCapFIFOError TRAP-TYPE
    ENTERPRISE c-product
    VARIABLES  { alarmSeverity,
                 alarmCardType,
                 alarmCardNumber,
                 alarmPortNumber,
                 alarmSetTime,
                 alarmClearTime,
                 alarmDescription }
    DESCRIPTION
            "ALM Egress Cap FIFO Error."
    ::= 140

alarmCBRQOverThreshold TRAP-TYPE
    ENTERPRISE c-product
    VARIABLES  { alarmSeverity,
                 alarmCardType,
                 alarmCardNumber,
                 alarmPortNumber,
                 alarmSetTime,
                 alarmClearTime,
                 alarmDescription }
    DESCRIPTION
            "Queue 0 Over Threshold."
    ::= 141

alarmVBRQOverThreshold TRAP-TYPE
    ENTERPRISE c-product
    VARIABLES  { alarmSeverity,
                 alarmCardType,
                 alarmCardNumber,
                 alarmPortNumber,
                 alarmSetTime,
                 alarmClearTime,
                 alarmDescription }
    DESCRIPTION
            "Queue 1 Over Threshold."
    ::= 142

alarmABRQOverThreshold TRAP-TYPE
    ENTERPRISE c-product
    VARIABLES  { alarmSeverity,
                 alarmCardType,
                 alarmCardNumber,
                 alarmPortNumber,
                 alarmSetTime,
                 alarmClearTime,
                 alarmDescription }
    DESCRIPTION
            "Queue 2 Over Threshold."
    ::= 143

alarmUBRQOverThreshold TRAP-TYPE
    ENTERPRISE c-product
    VARIABLES  { alarmSeverity,
                 alarmCardType,
                 alarmCardNumber,
                 alarmPortNumber,
                 alarmSetTime,
                 alarmClearTime,
                 alarmDescription }
    DESCRIPTION
            "Queue 3 Over Threshold."
    ::= 144

alarmPerConnectionVcAIS TRAP-TYPE
    ENTERPRISE c-product
    VARIABLES  { alarmSeverity,
                 alarmCardType,
                 alarmCardNumber,
                 alarmPortNumber,
                 alarmSetTime,
                 alarmClearTime,
                 alarmDescription }
    DESCRIPTION
            "Per-Connection VC AIS."
    ::= 145

alarmPerConnectionVcRDI TRAP-TYPE
    ENTERPRISE c-product
    VARIABLES  { alarmSeverity,
                 alarmCardType,
                 alarmCardNumber,
                 alarmPortNumber,
                 alarmSetTime,
                 alarmClearTime,
                 alarmDescription }
    DESCRIPTION
            "Per-Connection VC RDI."
    ::= 146

-- only used for testing
-- alarmFlashDBUpdate TRAP-TYPE
--    ENTERPRISE c-product
--    VARIABLES  { alarmSeverity,
--                 alarmCardType,
--                 alarmCardNumber,
--                 alarmPortNumber,
--                 alarmSetTime,
--                 alarmClearTime,
--                 alarmDescription }
--    DESCRIPTION
--            "Flash DB Update."
--    ::= 147

alarmGrMultiTest TRAP-TYPE
    ENTERPRISE c-product
    VARIABLES  { alarmSeverity,
                 alarmCardType,
                 alarmCardNumber,
                 alarmPortNumber,
                 alarmSetTime,
                 alarmClearTime,
                 alarmDescription }
    DESCRIPTION
            "Multiple test procedure requests from different links of same group."
    ::= 148

alarmGrConfigAbort TRAP-TYPE
    ENTERPRISE c-product
    VARIABLES  { alarmSeverity,
                 alarmCardType,
                 alarmCardNumber,
                 alarmPortNumber,
                 alarmSetTime,
                 alarmClearTime,
                 alarmDescription }
    DESCRIPTION
            "Group Near end config abort."
    ::= 149

alarmGrInsufLink TRAP-TYPE
    ENTERPRISE c-product
    VARIABLES  { alarmSeverity,
                 alarmCardType,
                 alarmCardNumber,
                 alarmPortNumber,
                 alarmSetTime,
                 alarmClearTime,
                 alarmDescription }
    DESCRIPTION
            "Group Near end insufficient links."
    ::= 150

alarmFeAbortSymm TRAP-TYPE
    ENTERPRISE c-product
    VARIABLES  { alarmSeverity,
                 alarmCardType,
                 alarmCardNumber,
                 alarmPortNumber,
                 alarmSetTime,
                 alarmClearTime,
                 alarmDescription }
    DESCRIPTION
            "Far end config abort due to bad symmetry."
    ::= 151

alarmFeStartup TRAP-TYPE
    ENTERPRISE c-product
    VARIABLES  { alarmSeverity,
                 alarmCardType,
                 alarmCardNumber,
                 alarmPortNumber,
                 alarmSetTime,
                 alarmClearTime,
                 alarmDescription }
    DESCRIPTION
            "Far end start up."
    ::= 152

alarmFeConfigAbort TRAP-TYPE
    ENTERPRISE c-product
    VARIABLES  { alarmSeverity,
                 alarmCardType,
                 alarmCardNumber,
                 alarmPortNumber,
                 alarmSetTime,
                 alarmClearTime,
                 alarmDescription }
    DESCRIPTION
            "Far end config abort due to bad M."
    ::= 153

alarmFeInsufLink TRAP-TYPE
    ENTERPRISE c-product
    VARIABLES  { alarmSeverity,
                 alarmCardType,
                 alarmCardNumber,
                 alarmPortNumber,
                 alarmSetTime,
                 alarmClearTime,
                 alarmDescription }
    DESCRIPTION
            "Far end insufficient links."
    ::= 154

alarmFeBlock TRAP-TYPE
    ENTERPRISE c-product
    VARIABLES  { alarmSeverity,
                 alarmCardType,
                 alarmCardNumber,
                 alarmPortNumber,
                 alarmSetTime,
                 alarmClearTime,
                 alarmDescription }
    DESCRIPTION
            "Far end blocked."
    ::= 155

alarmGrTimeSynch TRAP-TYPE
    ENTERPRISE c-product
    VARIABLES  { alarmSeverity,
                 alarmCardType,
                 alarmCardNumber,
                 alarmPortNumber,
                 alarmSetTime,
                 alarmClearTime,
                 alarmDescription }
    DESCRIPTION
            "Group timing synchronization failed."
    ::= 156

alarmGrLackLink TRAP-TYPE
    ENTERPRISE c-product
    VARIABLES  { alarmSeverity,
                 alarmCardType,
                 alarmCardNumber,
                 alarmPortNumber,
                 alarmSetTime,
                 alarmClearTime,
                 alarmDescription }
    DESCRIPTION
            "Group does not have enough links."
    ::= 157

alarmImaPrtclMismtch TRAP-TYPE
    ENTERPRISE c-product
    VARIABLES  { alarmSeverity,
                 alarmCardType,
                 alarmCardNumber,
                 alarmPortNumber,
                 alarmSetTime,
                 alarmClearTime,
                 alarmDescription }
    DESCRIPTION
	    "IMA protocol mismatch. Far end IMA group is not running compatible protocol."

    ::= 158

alarmRemoteLpbk TRAP-TYPE
    ENTERPRISE c-product
    VARIABLES  { alarmSeverity,
                 alarmCardType,
                 alarmCardNumber,
                 alarmPortNumber,
                 alarmSetTime,
                 alarmClearTime,
                 alarmDescription }
    DESCRIPTION
            "IMA remote loopback."
    ::= 159

alarmGroupAbortSymm TRAP-TYPE
    ENTERPRISE c-product
    VARIABLES  { alarmSeverity,
                 alarmCardType,
                 alarmCardNumber,
                 alarmPortNumber,
                 alarmSetTime,
                 alarmClearTime,
                 alarmDescription }
    DESCRIPTION
            "IMA group abort symmetry."
    ::= 160

alarmMissIcpCells TRAP-TYPE
    ENTERPRISE c-product
    VARIABLES  { alarmSeverity,
                 alarmCardType,
                 alarmCardNumber,
                 alarmPortNumber,
                 alarmSetTime,
                 alarmClearTime,
                 alarmDescription }
    DESCRIPTION
            "Port Missing ICP Cells."
    ::= 161

alarmSystemClkRevert TRAP-TYPE
    ENTERPRISE c-product
    VARIABLES  { alarmSeverity,
                 alarmCardType,
                 alarmCardNumber,
                 alarmPortNumber,
                 alarmSetTime,
                 alarmClearTime,
                 alarmDescription }
    DESCRIPTION
            "System Clock Reverted."
    ::= 162

alarmTakeOverBySU TRAP-TYPE
    ENTERPRISE c-product
    VARIABLES  { alarmSeverity,
                 alarmCardType,
                 alarmCardNumber,
                 alarmPortNumber,
                 alarmSetTime,
                 alarmClearTime,
                 alarmDescription }
    DESCRIPTION
            "Write Session is taken by Super User."
    ::= 163

alarmLinkUp TRAP-TYPE
    ENTERPRISE c-product
    VARIABLES  { alarmSeverity,
                 alarmCardType,
                 alarmCardNumber,
                 alarmPortNumber,
                 alarmSetTime,
                 alarmClearTime,
                 alarmDescription }
    DESCRIPTION
            "Link Up."
    ::= 164

alarmLinkDown TRAP-TYPE
    ENTERPRISE c-product
    VARIABLES  { alarmSeverity,
                 alarmCardType,
                 alarmCardNumber,
                 alarmPortNumber,
                 alarmSetTime,
                 alarmClearTime,
                 alarmDescription }
    DESCRIPTION
            "Link Down."
    ::= 165

alarmGrLinkUp TRAP-TYPE
    ENTERPRISE c-product
    VARIABLES  { alarmSeverity,
                 alarmCardType,
                 alarmCardNumber,
                 alarmPortNumber,
                 alarmSetTime,
                 alarmClearTime,
                 alarmDescription }
    DESCRIPTION
            "Group Link Up."
    ::= 166

alarmGrLinkDown TRAP-TYPE
    ENTERPRISE c-product
    VARIABLES  { alarmSeverity,
                 alarmCardType,
                 alarmCardNumber,
                 alarmPortNumber,
                 alarmSetTime,
                 alarmClearTime,
                 alarmDescription }
    DESCRIPTION
            "Group Link Down."
    ::= 167

alarmFwVerMismatch TRAP-TYPE
    ENTERPRISE c-product
    VARIABLES  { alarmSeverity,
                 alarmCardType,
                 alarmCardNumber,
                 alarmPortNumber,
                 alarmSetTime,
                 alarmClearTime,
                 alarmDescription }
    DESCRIPTION
            "Firmware Versions Mismatch."
    ::= 168

alarmIdPromChkError TRAP-TYPE
    ENTERPRISE c-product
    VARIABLES  { alarmSeverity,
                 alarmCardType,
                 alarmCardNumber,
                 alarmPortNumber,
                 alarmSetTime,
                 alarmClearTime,
                 alarmDescription }
    DESCRIPTION
            "ID Prom Checksum Error."
    ::= 169

alarmPwrSupply3Absent TRAP-TYPE
    ENTERPRISE c-product
    VARIABLES  { alarmSeverity,
                 alarmCardType,
                 alarmCardNumber,
                 alarmPortNumber,
                 alarmSetTime,
                 alarmClearTime,
                 alarmDescription }
    DESCRIPTION
            "Power Supply 3 absent."
    ::= 170

alarmPwrSupply4Absent TRAP-TYPE
    ENTERPRISE c-product
    VARIABLES  { alarmSeverity,
                 alarmCardType,
                 alarmCardNumber,
                 alarmPortNumber,
                 alarmSetTime,
                 alarmClearTime,
                 alarmDescription }
    DESCRIPTION
            "Power Supply 4 absent."
    ::= 171

alarmPwrSupply5Absent TRAP-TYPE
    ENTERPRISE c-product
    VARIABLES  { alarmSeverity,
                 alarmCardType,
                 alarmCardNumber,
                 alarmPortNumber,
                 alarmSetTime,
                 alarmClearTime,
                 alarmDescription }
    DESCRIPTION
            "Power Supply 5 absent."
    ::= 172

alarmPwrSupply6Absent TRAP-TYPE
    ENTERPRISE c-product
    VARIABLES  { alarmSeverity,
                 alarmCardType,
                 alarmCardNumber,
                 alarmPortNumber,
                 alarmSetTime,
                 alarmClearTime,
                 alarmDescription }
    DESCRIPTION
            "Power Supply 6 absent."
    ::= 173

alarmRcvdExtAlm1 TRAP-TYPE
    ENTERPRISE c-product
    VARIABLES  { alarmSeverity,
                 alarmCardType,
                 alarmCardNumber,
                 alarmPortNumber,
                 alarmSetTime,
                 alarmClearTime,
                 alarmDescription }
    DESCRIPTION
            "Received External Alarm 1."
    ::= 174


alarmRcvdExtAlm2 TRAP-TYPE
    ENTERPRISE c-product
    VARIABLES  { alarmSeverity,
                 alarmCardType,
                 alarmCardNumber,
                 alarmPortNumber,
                 alarmSetTime,
                 alarmClearTime,
                 alarmDescription }
    DESCRIPTION
            "Received External Alarm 2."
    ::= 175


alarmRcvdExtAlm3 TRAP-TYPE
    ENTERPRISE c-product
    VARIABLES  { alarmSeverity,
                 alarmCardType,
                 alarmCardNumber,
                 alarmPortNumber,
                 alarmSetTime,
                 alarmClearTime,
                 alarmDescription }
    DESCRIPTION
            "Received External Alarm 3."
    ::= 176

alarmVCMRefClkFailur TRAP-TYPE
    ENTERPRISE c-product
    VARIABLES  { alarmSeverity,
                 alarmCardType,
                 alarmCardNumber,
                 alarmPortNumber,
                 alarmSetTime,
                 alarmClearTime,
                 alarmDescription }
    DESCRIPTION
            "VCM reference clock failure alarm."
    ::= 177

alarmOC3LossOfPtr TRAP-TYPE
    ENTERPRISE c-product
    VARIABLES  { alarmSeverity,
                 alarmCardType,
                 alarmCardNumber,
                 alarmPortNumber,
                 alarmSetTime,
                 alarmClearTime,
                 alarmDescription }
    DESCRIPTION
            "OC3 Loss of Pointer."
    ::= 178

alarmImaGrp1Reass TRAP-TYPE
    ENTERPRISE c-product
    VARIABLES  { alarmSeverity,
                 alarmCardType,
                 alarmCardNumber,
                 alarmPortNumber,
                 alarmSetTime,
                 alarmClearTime,
                 alarmDescription }
    DESCRIPTION
            "IMA Group 1 Reassigned to DS3."
    ::= 179


alarmChnlPcmLpbk TRAP-TYPE
    ENTERPRISE c-product
    VARIABLES  { alarmSeverity,
                 alarmCardType,
                 alarmCardNumber,
                 alarmPortNumber,
                 alarmSetTime,
                 alarmClearTime,
                 alarmDescription }
    DESCRIPTION
            "Channel PCM Loopback."
    ::= 180


alarmChnlPcmPktLpbk TRAP-TYPE
    ENTERPRISE c-product
    VARIABLES  { alarmSeverity,
                 alarmCardType,
                 alarmCardNumber,
                 alarmPortNumber,
                 alarmSetTime,
                 alarmClearTime,
                 alarmDescription }
    DESCRIPTION
            "Channel PCM Packet Loopback."
    ::= 181


alarmChnlNtwkPktLpbk TRAP-TYPE
    ENTERPRISE c-product
    VARIABLES  { alarmSeverity,
                 alarmCardType,
                 alarmCardNumber,
                 alarmPortNumber,
                 alarmSetTime,
                 alarmClearTime,
                 alarmDescription }
    DESCRIPTION
            "Channel Network Packet Loopback."
    ::= 182

END
