--
-- CDD-564.my
-- MIB generated by MG-SOFT Visual MIB Builder Version 2.1 Build 199
-- Tuesday, January 17, 2006 at 13:37:32
--

	CDD-564 DEFINITIONS ::= BEGIN

		IMPORTS 
			comtechEFData			
				FROM ComtechEFData			
			OBJECT-GROUP, MODULE-COMPLIANCE, NOTIFICATION-GROUP			
				FROM SNMPv2-CONF			
			IpAddress, Counter32, OBJECT-TYPE, MODULE-IDENTITY, NOTIFICATION-TYPE			
				FROM SNMPv2-SMI			
			DisplayString			
				FROM SNMPv2-TC;
	
	
		cdd564 MODULE-IDENTITY
			LAST-UPDATED "200409231700Z"
			ORGANIZATION
				"Comtech EF Data Corp."
			CONTACT-INFO
				"Comtech EF Data Crop.
				2114 W. 7th Street
				Tempe, AZ  85281 USA
				
				Tel: 480-333-2200
				Fax: 480-333-2540
				Web: http://www.comtechefdata.com
				"
			DESCRIPTION
				"Module for CDD-564 Satellite Demod"
			REVISION "200512061018Z"
			DESCRIPTION
				"1.5.3 Maintenance Release."
			::= { comtechEFData 25 }
		
	
	
--
-- Node definitions
--
	
		cdd564Objects OBJECT IDENTIFIER ::= { cdd564 1 }
		
		cdd564Administration OBJECT IDENTIFIER ::= { cdd564Objects 1 }
		
		cdd564AccessLists OBJECT IDENTIFIER ::= { cdd564Administration 1 }
		
		cdd564AccessListTable OBJECT-TYPE
			SYNTAX SEQUENCE OF Cdd564AccessListEntry
			MAX-ACCESS not-accessible
			STATUS current
			DESCRIPTION
				"The table for the access list."
			::= { cdd564AccessLists 1 }
		
		cdd564AccessListEntry OBJECT-TYPE
			SYNTAX Cdd564AccessListEntry
			MAX-ACCESS not-accessible
			STATUS current
			DESCRIPTION
				"The entry for the access list table."
			INDEX { cdd564AccessListIndex }
			::= { cdd564AccessListTable 1 }
		
		Cdd564AccessListEntry ::=
			SEQUENCE { 
				cdd564AccessListIndex
					INTEGER,
				cdd564AccessIPAddress
					IpAddress,
				cdd564AccessSubnetMaskLength
					INTEGER
			 }

		cdd564AccessListIndex OBJECT-TYPE
			SYNTAX INTEGER (1..4)
			MAX-ACCESS read-only
			STATUS current
			DESCRIPTION
				"The index for the access list from 1..4."
			::= { cdd564AccessListEntry 1 }
		
		cdd564AccessIPAddress OBJECT-TYPE
			SYNTAX IpAddress
			MAX-ACCESS read-write
			STATUS current
			DESCRIPTION
				"The IP addresses that can access the unit.
				The value of 0.0.0.0 means not defined."
			::= { cdd564AccessListEntry 2 }
		
		cdd564AccessSubnetMaskLength OBJECT-TYPE
			SYNTAX INTEGER (0 | 8..32)
			MAX-ACCESS read-write
			STATUS current
			DESCRIPTION
				"The subnet mask length of the IP address 
				for the access list.  Subnet mask can be 
				from 8..32. The value of 0 means not defined."
			::= { cdd564AccessListEntry 3 }
		
		cdd564AccessListEnforcement OBJECT-TYPE
			SYNTAX INTEGER
				{
				disabled(0),
				enabled(1)
				}
			MAX-ACCESS read-write
			STATUS current
			DESCRIPTION
				"Enable or disable enforcement of the the access 
				list.
				
				Note: Be sure that you have added the SNMP 
				browser's/manager's IP Address to the access 
				list before enabling access list filtering.
				Otherwise, the SNMP browser/manager will no 
				longer be able to gain access to the unit."
			::= { cdd564AccessLists 2 }
		
		cdd564Features OBJECT IDENTIFIER ::= { cdd564Administration 2 }
		
		cdd564PingReply OBJECT-TYPE
			SYNTAX INTEGER
				{
				disabled(0),
				enabled(1)
				}
			MAX-ACCESS read-write
			STATUS current
			DESCRIPTION
				"Enable or disable ping reply from unit."
			::= { cdd564Features 1 }
		
		cdd564Telnet OBJECT-TYPE
			SYNTAX INTEGER
				{
				disabled(0),
				enabled(1)
				}
			MAX-ACCESS read-write
			STATUS current
			DESCRIPTION
				"Enable or disable telnet access to unit."
			::= { cdd564Features 2 }
		
		cdd564IGMP OBJECT-TYPE
			SYNTAX INTEGER
				{
				disabled(0),
				enabled(1)
				}
			MAX-ACCESS read-write
			STATUS current
			DESCRIPTION
				"Enable or disable the Internet Group Management 
				Protocol (IGMP)."
			::= { cdd564Features 3 }
		
		cdd564ForwardMulticasts OBJECT-TYPE
			SYNTAX INTEGER
				{
				disabled(0),
				enabled(1)
				}
			MAX-ACCESS read-write
			STATUS current
			DESCRIPTION
				"Enable or disable forwarding all multicasts 
				received from the Satellite interface 
				to the Ethernet interface."
			::= { cdd564Features 4 }
		
		cdd564FeaturesTable OBJECT-TYPE
			SYNTAX SEQUENCE OF Cdd564FeaturesEntry
			MAX-ACCESS not-accessible
			STATUS current
			DESCRIPTION
				"The table (per demodulator) of FAST Features."
			::= { cdd564Features 5 }
		
		cdd564FeaturesEntry OBJECT-TYPE
			SYNTAX Cdd564FeaturesEntry
			MAX-ACCESS not-accessible
			STATUS current
			DESCRIPTION
				"The entry for the FAST Feature (per demod) table."
			INDEX { cdd564FeatureIndex }
			::= { cdd564FeaturesTable 1 }
		
		Cdd564FeaturesEntry ::=
			SEQUENCE { 
				cdd564FeatureIndex
					INTEGER,
				cdd564HeaderCompression
					INTEGER
			 }

		cdd564FeatureIndex OBJECT-TYPE
			SYNTAX INTEGER (1..4)
			MAX-ACCESS read-only
			STATUS current
			DESCRIPTION
				"The index for the FAST Feature (per demod) table."
			::= { cdd564FeaturesEntry 1 }
		
		cdd564HeaderCompression OBJECT-TYPE
			SYNTAX INTEGER
				{
				unavailable(0),
				enabled(1),
				disabled(2)
				}
			MAX-ACCESS read-write
			STATUS current
			DESCRIPTION
				"Availability of header compression is based on 
				FAST features
				
				Note: To use header compression, it must be 
				FAST available and enabled on both the 
				transmit and receive sides."
			::= { cdd564FeaturesEntry 2 }
		
		cdd564WorkingMode OBJECT-TYPE
			SYNTAX INTEGER
				{
				routerSmallNetworkMode(1),
				routerLargeNetworkMode(2),
				routerPointToPointMode(3),
				routerVipersatMode(4)
				}
			MAX-ACCESS read-write
			STATUS current
			DESCRIPTION
				"Configure the system's working mode. 
				
				The CDM-IP can operate in any of these modes.
				
				  1. Router - Small Network Mode - The system functions as router and 
				     uses the route table to determine how to forward packets in a 
				     small network HDLC address mode. The HDLC packet uses a 1 byte 
				     HDLC address.  The valid values are from 1 to 254 (0x1 - 0xFE).
				  
				  2. Router - Small Network Mode - The system functions as router and 
				     uses the route table to determine how to forward packets in a 
				     large network HDLC address mode. The HDLC packet uses a 2- byte 
				     HDLC address.  The valid values are from 1 to 32766 (0x1 - 0x7FFE).
				
				  3. Router - Point To Point Mode - The system functions as router but 
				     does not use HDLC addresses.
				
				  4. Router - Vipersat Mode - The system functions as router and is
				     configured to work in a Vipersat network.
				
				***  IMPORTANT NOTE ***
				Changing Working mode requires the system to reboot.
				System configuration is saved before rebooting.
				
				Please make sure you are setting the correct value.
				"
			::= { cdd564Features 6 }
		
		cdd5643xDESEncryption OBJECT IDENTIFIER ::= { cdd564Administration 3 }
		
		cdd5643xDESRxKeyTable OBJECT-TYPE
			SYNTAX SEQUENCE OF Cdd5643xDESRxKeyEntry
			MAX-ACCESS not-accessible
			STATUS current
			DESCRIPTION
				"The table (one row per demod) for triple DES 
				(3xDES) receive decrypt keys."
			::= { cdd5643xDESEncryption 1 }
		
		cdd5643xDESRxKeyEntry OBJECT-TYPE
			SYNTAX Cdd5643xDESRxKeyEntry
			MAX-ACCESS not-accessible
			STATUS current
			DESCRIPTION
				"The entry (per demod) of the 3xDES receive 
				decrypt key table."
			INDEX { cdd5643xDESRxKeyIndex }
			::= { cdd5643xDESRxKeyTable 1 }
		
		Cdd5643xDESRxKeyEntry ::=
			SEQUENCE { 
				cdd5643xDESRxKeyIndex
					INTEGER,
				cdd5643xDESRxKey1
					DisplayString,
				cdd5643xDESRxKey2
					DisplayString,
				cdd5643xDESRxKey3
					DisplayString,
				cdd5643xDESRxKey4
					DisplayString,
				cdd5643xDESRxKey5
					DisplayString,
				cdd5643xDESRxKey6
					DisplayString,
				cdd5643xDESRxKey7
					DisplayString,
				cdd5643xDESRxKey8
					DisplayString
			 }

		cdd5643xDESRxKeyIndex OBJECT-TYPE
			SYNTAX INTEGER (1..4)
			MAX-ACCESS read-only
			STATUS current
			DESCRIPTION
				"The index (per demod) of the 3xDES receive 
				decrypt key table."
			::= { cdd5643xDESRxKeyEntry 1 }
		
		cdd5643xDESRxKey1 OBJECT-TYPE
			SYNTAX DisplayString (SIZE (48))
			MAX-ACCESS read-write
			STATUS current
			DESCRIPTION
				"The 3xDES receive decrypt key.
				The key length is 192 bits 
				(24 bytes or 48 characters)."
			::= { cdd5643xDESRxKeyEntry 2 }
		
		cdd5643xDESRxKey2 OBJECT-TYPE
			SYNTAX DisplayString (SIZE (48))
			MAX-ACCESS read-write
			STATUS current
			DESCRIPTION
				"The 3xDES receive decrypt key.
				The key length is 192 bits 
				(24 bytes or 48 characters)."
			::= { cdd5643xDESRxKeyEntry 3 }
		
		cdd5643xDESRxKey3 OBJECT-TYPE
			SYNTAX DisplayString (SIZE (48))
			MAX-ACCESS read-write
			STATUS current
			DESCRIPTION
				"The 3xDES receive decrypt key.
				The key length is 192 bits 
				(24 bytes or 48 characters)."
			::= { cdd5643xDESRxKeyEntry 4 }
		
		cdd5643xDESRxKey4 OBJECT-TYPE
			SYNTAX DisplayString (SIZE (48))
			MAX-ACCESS read-write
			STATUS current
			DESCRIPTION
				"The 3xDES receive decrypt key.
				The key length is 192 bits 
				(24 bytes or 48 characters)."
			::= { cdd5643xDESRxKeyEntry 5 }
		
		cdd5643xDESRxKey5 OBJECT-TYPE
			SYNTAX DisplayString (SIZE (48))
			MAX-ACCESS read-write
			STATUS current
			DESCRIPTION
				"The 3xDES receive decrypt key.
				The key length is 192 bits 
				(24 bytes or 48 characters)."
			::= { cdd5643xDESRxKeyEntry 6 }
		
		cdd5643xDESRxKey6 OBJECT-TYPE
			SYNTAX DisplayString (SIZE (48))
			MAX-ACCESS read-write
			STATUS current
			DESCRIPTION
				"The 3xDES receive decrypt key.
				The key length is 192 bits 
				(24 bytes or 48 characters)."
			::= { cdd5643xDESRxKeyEntry 7 }
		
		cdd5643xDESRxKey7 OBJECT-TYPE
			SYNTAX DisplayString (SIZE (48))
			MAX-ACCESS read-write
			STATUS current
			DESCRIPTION
				"The 3xDES receive decrypt key.
				The key length is 192 bits 
				(24 bytes or 48 characters)."
			::= { cdd5643xDESRxKeyEntry 8 }
		
		cdd5643xDESRxKey8 OBJECT-TYPE
			SYNTAX DisplayString (SIZE (48))
			MAX-ACCESS read-write
			STATUS current
			DESCRIPTION
				"The 3xDES receive decrypt key.
				The key length is 192 bits 
				(24 bytes or 48 characters)."
			::= { cdd5643xDESRxKeyEntry 9 }
		
		cdd564SMTP OBJECT IDENTIFIER ::= { cdd564Administration 4 }
		
		cdd564SMTPServerIPAddress OBJECT-TYPE
			SYNTAX IpAddress
			MAX-ACCESS read-write
			STATUS current
			DESCRIPTION
				"The IP address of the SMTP server for sending 
				problem reports.  This IP adderess should 
				correspond to a local Mail server."
			::= { cdd564SMTP 1 }
		
		cdd564SMTPDomain OBJECT-TYPE
			SYNTAX DisplayString
			MAX-ACCESS read-write
			STATUS current
			DESCRIPTION
				"The SMTP Domain for sending problem reports.
				This value should be comtechefdata.com."
			::= { cdd564SMTP 2 }
		
		cdd564SMTPUserName OBJECT-TYPE
			SYNTAX DisplayString
			MAX-ACCESS read-write
			STATUS current
			DESCRIPTION
				"The user name for sending problem reports.
				This value should be cdmipsupport."
			::= { cdd564SMTP 3 }
		
		cdd564SNMP OBJECT IDENTIFIER ::= { cdd564Administration 5 }
		
		cdd564SNMPTrapDestinationIPAddress OBJECT-TYPE
			SYNTAX IpAddress
			MAX-ACCESS read-write
			STATUS current
			DESCRIPTION
				"The IP address were SNMP notifications (traps)
				are to be sent.  This IP address should 
				correspond to a SNMP manager or browser."
			::= { cdd564SNMP 1 }
		
		cdd564SNMPTrapCommunity OBJECT-TYPE
			SYNTAX DisplayString
			MAX-ACCESS read-write
			STATUS current
			DESCRIPTION
				"The community that will be included in SNMP 
				notifications (traps) that are sent from unit."
			::= { cdd564SNMP 2 }
		
		cdd564SNMPTrapVersion OBJECT-TYPE
			SYNTAX INTEGER
				{
				snmpV1(1),
				snmpV2(2)
				}
			MAX-ACCESS read-write
			STATUS current
			DESCRIPTION
				"The SNMP version that will be used when sending 
				traps from the unit.  SNMPv1 will send V1 traps.
				SNMPv2 will send V2 notifications."
			::= { cdd564SNMP 3 }
		
		cdd564SNMPAuthenticationFailureCommunity OBJECT-TYPE
			SYNTAX DisplayString
			MAX-ACCESS accessible-for-notify
			STATUS current
			DESCRIPTION
				"The community that did not match valid SNMP 
				Read or Write community.
				Note:  This is ONLY used in the Authentication 
				Failure trap."
			::= { cdd564SNMP 4 }
		
		cdd564SNMPAuthenticationFailureIPAddress OBJECT-TYPE
			SYNTAX IpAddress
			MAX-ACCESS accessible-for-notify
			STATUS current
			DESCRIPTION
				"The IP address that did not send a valid SNMP 
				Read or Write community.
				Note:  This is ONLY used in the Authentication 
				Failure trap."
			::= { cdd564SNMP 5 }
		
		cdd564SNMPTrapDestinationIPAddress2 OBJECT-TYPE
			SYNTAX IpAddress
			MAX-ACCESS read-write
			STATUS current
			DESCRIPTION
				"The secondary IP address were SNMP notifications (traps)
				are to be sent.  This IP address should correspond 
				to a secondary SNMP manager or browser."
			::= { cdd564SNMP 6 }
		
		cdd564Interfaces OBJECT IDENTIFIER ::= { cdd564Objects 2 }
		
		cdd564EthernetInterface OBJECT IDENTIFIER ::= { cdd564Interfaces 1 }
		
		cdd564MACAddress OBJECT-TYPE
			SYNTAX DisplayString
			MAX-ACCESS read-only
			STATUS current
			DESCRIPTION
				"The MAC address assigned to the Ethernet 
				interface."
			::= { cdd564EthernetInterface 1 }
		
		cdd564EthernetSpeed OBJECT-TYPE
			SYNTAX INTEGER
				{
				auto(1),
				halfDuplex10M(2),
				halfDuplex100M(3),
				fullDuplex10M(4),
				fullDuplex100M(5)
				}
			MAX-ACCESS read-write
			STATUS current
			DESCRIPTION
				"The speed of the Ethernet interface."
			::= { cdd564EthernetInterface 2 }
		
		cdd564IPAddress OBJECT-TYPE
			SYNTAX IpAddress
			MAX-ACCESS read-write
			STATUS current
			DESCRIPTION
				"The IP address assigned to the Ethernet 
				interface."
			::= { cdd564EthernetInterface 3 }
		
		cdd564SubnetMaskLen OBJECT-TYPE
			SYNTAX INTEGER (8..30)
			MAX-ACCESS read-write
			STATUS current
			DESCRIPTION
				"The subnet mask length of the IP address."
			::= { cdd564EthernetInterface 4 }
		
		cdd564DemodulatorInterfaces OBJECT IDENTIFIER ::= { cdd564Interfaces 2 }
		
		cdd564HDLCAddressMode OBJECT-TYPE
			SYNTAX INTEGER
				{
				smallNetworkMode(1),
				largeNetworkMode(2),
				pointToPointMode(3)
				}
			MAX-ACCESS read-only
			STATUS current
			DESCRIPTION
				"The size of HDLC address used for sending 
				packets over satellite interface can range 
				from 0 - 2 bytes. 
				
				The satellite interface will operate in one of 
				the following modes:
				                                
				 1.Small Network mode - The packet uses a 
				    1 byte HDLC address.  The valid 
				    values are from 1 to 254 (0x1 - 0xFE).
				
				 2.Large Network mode - The packet uses a 2 
				    byte HDLC address.  The valid values are 
				    from 1 to 32766 (0x1 - 0x7FFE).
				
				 3. Point To Point mode - The packet does not use 
				     a HDLC address.
				                                
				An HDLC address cannot have 0x00 or 0xFF in 
				least Significant Byte. i.e., 0x400 or 0x6ff 
				or 0x11ff are NOT valid HDLC addresses.
				"
			::= { cdd564DemodulatorInterfaces 2 }
		
		cdd564HDLCAddressTable OBJECT-TYPE
			SYNTAX SEQUENCE OF Cdd564HDLCAddressEntry
			MAX-ACCESS not-accessible
			STATUS current
			DESCRIPTION
				"The table for the Demodulator HDLC Addresses."
			::= { cdd564DemodulatorInterfaces 3 }
		
		cdd564HDLCAddressEntry OBJECT-TYPE
			SYNTAX Cdd564HDLCAddressEntry
			MAX-ACCESS not-accessible
			STATUS current
			DESCRIPTION
				"The entry of the HDLC Address table."
			INDEX { cdd564HDLCAddressIndex }
			::= { cdd564HDLCAddressTable 1 }
		
		Cdd564HDLCAddressEntry ::=
			SEQUENCE { 
				cdd564HDLCAddressIndex
					INTEGER,
				cdd564HDLCAddress1
					INTEGER,
				cdd564HDLCAddress2
					INTEGER,
				cdd564HDLCAddress3
					INTEGER,
				cdd564HDLCAddress4
					INTEGER
			 }

		cdd564HDLCAddressIndex OBJECT-TYPE
			SYNTAX INTEGER (1..4)
			MAX-ACCESS read-only
			STATUS current
			DESCRIPTION
				"The Demod number corresponding to 1 of 4 
				demodulators."
			::= { cdd564HDLCAddressEntry 1 }
		
		cdd564HDLCAddress1 OBJECT-TYPE
			SYNTAX INTEGER (0 | 1..32766)
			MAX-ACCESS read-write
			STATUS current
			DESCRIPTION
				"The HDLC address #1 for the satellite 
				interface.
				                                
				The valid values are: 
				 1. Small network, 1 to 254   (0x1 - 0xFE).
				 2. Large network, 1 to 32766 (0x1 - 0x0x7FFE).
				 3. Point to point, not used.
				 4. EasyConnect, not used.
				
				HDLC address can not have 0x00 or 0xFF 
				in least significant byte, i.e., 0x400 or 
				0x6ff or 0x11ff are NOT valid HDLC addresses.
				
				Deletion:
				To delete the HDLC address, set it to zero.                             
				
				"
			::= { cdd564HDLCAddressEntry 3 }
		
		cdd564HDLCAddress2 OBJECT-TYPE
			SYNTAX INTEGER (0 | 1..32766)
			MAX-ACCESS read-write
			STATUS current
			DESCRIPTION
				"The HDLC address #2 for the satellite 
				interface.
				                                
				The valid values are: 
				 1. Small network, 1 to 254   (0x1 - 0xFE).
				 2. Large network, 1 to 32766 (0x1 - 0x0x7FFE).
				 3. Point to point, not used.
				 4. EasyConnect, not used.
				
				HDLC address can not have 0x00 or 0xFF 
				in least significant byte, i.e., 0x400 or 
				0x6ff or 0x11ff are NOT valid HDLC addresses.
				
				Deletion:
				To delete the HDLC address, set it to zero."
			::= { cdd564HDLCAddressEntry 4 }
		
		cdd564HDLCAddress3 OBJECT-TYPE
			SYNTAX INTEGER (0 | 1..32766)
			MAX-ACCESS read-write
			STATUS current
			DESCRIPTION
				"The HDLC address #3 for the satellite 
				interface.
				                                
				The valid values are: 
				 1. Small network, 1 to 254   (0x1 - 0xFE).
				 2. Large network, 1 to 32766 (0x1 - 0x0x7FFE).
				 3. Point to point, not used.
				 4. EasyConnect, not used.
				
				HDLC address can not have 0x00 or 0xFF 
				in least significant byte, i.e., 0x400 or 
				0x6ff or 0x11ff are NOT valid HDLC addresses.
				
				Deletion:
				To delete the HDLC address, set it to zero."
			::= { cdd564HDLCAddressEntry 5 }
		
		cdd564HDLCAddress4 OBJECT-TYPE
			SYNTAX INTEGER (0 | 1..32766)
			MAX-ACCESS read-write
			STATUS current
			DESCRIPTION
				"The HDLC address #4 for the satellite 
				interface.
				                                
				The valid values are: 
				 1. Small network, 1 to 254   (0x1 - 0xFE).
				 2. Large network, 1 to 32766 (0x1 - 0x0x7FFE).
				 3. Point to point, not used.
				 4. EasyConnect, not used.
				
				HDLC address can not have 0x00 or 0xFF 
				in least significant byte, i.e., 0x400 or 
				0x6ff or 0x11ff are NOT valid HDLC addresses.
				
				Deletion:
				To delete the HDLC address, set it to zero."
			::= { cdd564HDLCAddressEntry 6 }
		
		cdd564Routes OBJECT IDENTIFIER ::= { cdd564Objects 3 }
		
		cdd564RouteTable OBJECT-TYPE
			SYNTAX SEQUENCE OF Cdd564RouteEntry
			MAX-ACCESS not-accessible
			STATUS current
			DESCRIPTION
				"The route table used in Router mode."
			::= { cdd564Routes 1 }
		
		cdd564RouteEntry OBJECT-TYPE
			SYNTAX Cdd564RouteEntry
			MAX-ACCESS not-accessible
			STATUS current
			DESCRIPTION
				"The entry for the the route table."
			INDEX { cdd564RouteIndex }
			::= { cdd564RouteTable 1 }
		
		Cdd564RouteEntry ::=
			SEQUENCE { 
				cdd564RouteIndex
					INTEGER,
				cdd564RouteName
					DisplayString,
				cdd564RouteDestAddress
					IpAddress,
				cdd564RouteDestMaskLen
					INTEGER,
				cdd564RouteNextHopAddress
					IpAddress,
				cdd564RouteMulticast
					INTEGER,
				cdd564RouteInterface
					INTEGER,
				cdd564RouteRowStatus
					INTEGER
			 }

		cdd564RouteIndex OBJECT-TYPE
			SYNTAX INTEGER (1..1024)
			MAX-ACCESS read-write
			STATUS current
			DESCRIPTION
				"The index for the route table."
			::= { cdd564RouteEntry 1 }
		
		cdd564RouteName OBJECT-TYPE
			SYNTAX DisplayString
			MAX-ACCESS read-write
			STATUS current
			DESCRIPTION
				"The name of the route.  All routes must be 
				named."
			::= { cdd564RouteEntry 2 }
		
		cdd564RouteDestAddress OBJECT-TYPE
			SYNTAX IpAddress
			MAX-ACCESS read-write
			STATUS current
			DESCRIPTION
				"The destination IP address for the route."
			::= { cdd564RouteEntry 3 }
		
		cdd564RouteDestMaskLen OBJECT-TYPE
			SYNTAX INTEGER (0..32)
			MAX-ACCESS read-write
			STATUS current
			DESCRIPTION
				"The subnet mask lenght for the destination IP 
				address."
			::= { cdd564RouteEntry 4 }
		
		cdd564RouteNextHopAddress OBJECT-TYPE
			SYNTAX IpAddress
			MAX-ACCESS read-write
			STATUS current
			DESCRIPTION
				"The next hop IP address for the route."
			::= { cdd564RouteEntry 5 }
		
		cdd564RouteMulticast OBJECT-TYPE
			SYNTAX INTEGER
				{
				notApplicable(0),
				forward(1),
				filtered(2)
				}
			MAX-ACCESS read-write
			STATUS current
			DESCRIPTION
				"If the route is a multicast, packets can be:
				
				1. forwarded
				2. filtered
				
				If the route is unicast, the field is not applicable."
			::= { cdd564RouteEntry 6 }
		
		cdd564RouteInterface OBJECT-TYPE
			SYNTAX INTEGER { toEthernet(2) }
			MAX-ACCESS read-write
			STATUS current
			DESCRIPTION
				"Routes are destined to the Ethernet interface."
			::= { cdd564RouteEntry 7 }
		
		cdd564RouteRowStatus OBJECT-TYPE
			SYNTAX INTEGER
				{
				active(1),
				notInService(2),
				notReady(3),
				createAndGo(4),
				createAndWait(5),
				destroy(6)
				}
			MAX-ACCESS read-write
			STATUS current
			DESCRIPTION
				"This value is used for status of route:
				active(1) - The route is active.
				
				These values are used to create or delete route:
				createAndGo(4) - The route is to be created.
				destroy(6) - The route to be deleted."
			::= { cdd564RouteEntry 8 }
		
		cdd564Protocols OBJECT IDENTIFIER ::= { cdd564Objects 4 }
		
		cdd564IGMPConfig OBJECT IDENTIFIER ::= { cdd564Protocols 1 }
		
		cdd564IGMPServer OBJECT IDENTIFIER ::= { cdd564IGMPConfig 1 }
		
		cdd564IGMPQueryPeriod OBJECT-TYPE
			SYNTAX INTEGER (1..600)
			MAX-ACCESS read-write
			STATUS current
			DESCRIPTION
				"The IGMP query period, in seconds."
			::= { cdd564IGMPServer 1 }
		
		cdd564IGMPMaxResponseTime OBJECT-TYPE
			SYNTAX INTEGER (1..600)
			MAX-ACCESS read-write
			STATUS current
			DESCRIPTION
				"The IGMP maximum response time, in seconds."
			::= { cdd564IGMPServer 2 }
		
		cdd564IGMPMaxMissBeforeLeavingGroup OBJECT-TYPE
			SYNTAX INTEGER (1..30)
			MAX-ACCESS read-write
			STATUS current
			DESCRIPTION
				"The maximum number of missed responses before 
				leaving the IGMP group."
			::= { cdd564IGMPServer 3 }
		
		cdd564IGMPTable OBJECT-TYPE
			SYNTAX SEQUENCE OF Cdd564IGMPEntry
			MAX-ACCESS not-accessible
			STATUS current
			DESCRIPTION
				"The table for IGMP groups."
			::= { cdd564IGMPConfig 3 }
		
		cdd564IGMPEntry OBJECT-TYPE
			SYNTAX Cdd564IGMPEntry
			MAX-ACCESS not-accessible
			STATUS current
			DESCRIPTION
				"The entry for the IGMP group table."
			INDEX { cdd564IGMPIndex }
			::= { cdd564IGMPTable 1 }
		
		Cdd564IGMPEntry ::=
			SEQUENCE { 
				cdd564IGMPIndex
					INTEGER,
				cdd564IGMPTTL
					INTEGER,
				cdd564IGMPClientState
					INTEGER,
				cdd564IGMPSrc
					INTEGER,
				cdd564IGMPGroupIPAddress
					IpAddress
			 }

		cdd564IGMPIndex OBJECT-TYPE
			SYNTAX INTEGER (1..256)
			MAX-ACCESS read-only
			STATUS current
			DESCRIPTION
				"The index for the IGMP group table."
			::= { cdd564IGMPEntry 1 }
		
		cdd564IGMPTTL OBJECT-TYPE
			SYNTAX INTEGER (0..255)
			MAX-ACCESS read-only
			STATUS current
			DESCRIPTION
				"The TTL for the multicast group."
			::= { cdd564IGMPEntry 2 }
		
		cdd564IGMPClientState OBJECT-TYPE
			SYNTAX INTEGER
				{
				idle(1),
				active(2),
				closing(3)
				}
			MAX-ACCESS read-only
			STATUS current
			DESCRIPTION
				"The state for the multicast group."
			::= { cdd564IGMPEntry 3 }
		
		cdd564IGMPSrc OBJECT-TYPE
			SYNTAX INTEGER
				{
				ethernet(1),
				satellite(2)
				}
			MAX-ACCESS read-only
			STATUS current
			DESCRIPTION
				"The interface from which the multicast group
				was received."
			::= { cdd564IGMPEntry 4 }
		
		cdd564IGMPGroupIPAddress OBJECT-TYPE
			SYNTAX IpAddress
			MAX-ACCESS read-only
			STATUS current
			DESCRIPTION
				"The multicast group address."
			::= { cdd564IGMPEntry 5 }
		
		cdd564Maint OBJECT IDENTIFIER ::= { cdd564Objects 5 }
		
		cdd564UnitInformation OBJECT IDENTIFIER ::= { cdd564Maint 1 }
		
		cdd564BootInfo OBJECT-TYPE
			SYNTAX DisplayString
			MAX-ACCESS read-only
			STATUS current
			DESCRIPTION
				"The version and revision information for the 
				boot application."
			::= { cdd564UnitInformation 1 }
		
		cdd564Bulk1Info OBJECT-TYPE
			SYNTAX DisplayString
			MAX-ACCESS read-only
			STATUS current
			DESCRIPTION
				"The version and revision information for the 
				bulk application in image 1."
			::= { cdd564UnitInformation 2 }
		
		cdd564Bulk2Info OBJECT-TYPE
			SYNTAX DisplayString
			MAX-ACCESS read-only
			STATUS current
			DESCRIPTION
				"The version and revision information for the 
				bulk application in image 2."
			::= { cdd564UnitInformation 3 }
		
		cdd564FPGARx1Info OBJECT-TYPE
			SYNTAX DisplayString
			MAX-ACCESS read-only
			STATUS current
			DESCRIPTION
				"The version and revision information for the 
				Rx FPGA in image 1."
			::= { cdd564UnitInformation 4 }
		
		cdd564FPGARx2Info OBJECT-TYPE
			SYNTAX DisplayString
			MAX-ACCESS read-only
			STATUS current
			DESCRIPTION
				"The version and revision information for the 
				Rx FPGA in image 2."
			::= { cdd564UnitInformation 5 }
		
		cdd564BulkDatabase OBJECT IDENTIFIER ::= { cdd564Maint 2 }
		
		cdd564BootImage OBJECT-TYPE
			SYNTAX INTEGER
				{
				latest(0),
				image1(1),
				image2(2)
				}
			MAX-ACCESS read-write
			STATUS current
			DESCRIPTION
				"Specifies which image will be booted:
				
				latest - boots the latest image determined by 
				           the most recent build date
				image 1 - boots image from bulk #1
				image 2 - boots image from bulk #2"
			::= { cdd564BulkDatabase 1 }
		
		cdd564UpgradeImage OBJECT-TYPE
			SYNTAX INTEGER
				{
				oldest(0),
				image1(1),
				image2(2)
				}
			MAX-ACCESS read-write
			STATUS current
			DESCRIPTION
				"Specifies which image will be overwritten 
				during an upgrade:
				
				 oldest - overwrites the oldest image 
				           determined by build date.
				 image 1 - overwrites image 1 
				 image 2 - overwrites image 2
				
				NOTE: Set this value before performing an 
				      upgrade."
			::= { cdd564BulkDatabase 2 }
		
		cdd564ParamDatabase OBJECT IDENTIFIER ::= { cdd564Maint 3 }
		
		cdd564ParamImage OBJECT-TYPE
			SYNTAX INTEGER
				{
				paramFile(1),
				factoryDefaults(2)
				}
			MAX-ACCESS read-write
			STATUS current
			DESCRIPTION
				"Specifies if configuration should be read from:
				
				paramFile - parameter file stored in flash
				factoryDefaults - the factory defaults"
			::= { cdd564ParamDatabase 1 }
		
		cdd564SaveParamToFlash OBJECT-TYPE
			SYNTAX INTEGER { save(1) }
			MAX-ACCESS read-write
			STATUS current
			DESCRIPTION
				"This is a SET command to save the 
				configuration to the parameter file 
				in flash."
			::= { cdd564ParamDatabase 2 }
		
		cdd564ReloadParamFromFlash OBJECT-TYPE
			SYNTAX INTEGER { reload(1) }
			MAX-ACCESS read-write
			STATUS current
			DESCRIPTION
				"This is a SET command to reload the 
				configuration from the parameter 
				file in flash."
			::= { cdd564ParamDatabase 3 }
		
		cdd564RestoreFactoryDefaults OBJECT-TYPE
			SYNTAX INTEGER { restore(1) }
			MAX-ACCESS read-write
			STATUS current
			DESCRIPTION
				"This is a SET command that restore the 
				configuration to the factory defaults.
				
				*** Imporant ***
				Setting this command ERASES the parameter 
				file in flash."
			::= { cdd564ParamDatabase 4 }
		
		cdd564RebootUnit OBJECT IDENTIFIER ::= { cdd564Maint 4 }
		
		cdd564Reboot OBJECT-TYPE
			SYNTAX INTEGER { reboot(1) }
			MAX-ACCESS read-write
			STATUS current
			DESCRIPTION
				"The is a SET command that will reboot the unit.
				
				*** Important ***
				The command will reboot the unit without 
				saving the configuration to the parameter file
				in flash."
			::= { cdd564RebootUnit 1 }
		
		cdd564Statistics OBJECT IDENTIFIER ::= { cdd564Objects 6 }
		
		cdd564IPRoutingStatistics OBJECT IDENTIFIER ::= { cdd564Statistics 1 }
		
		cdd564IPRoutingEthernet OBJECT IDENTIFIER ::= { cdd564IPRoutingStatistics 1 }
		
		cdd564TotalPacketsToEthernet OBJECT-TYPE
			SYNTAX Counter32
			MAX-ACCESS read-only
			STATUS current
			DESCRIPTION
				"The total number of IP packets routed to 
				the Ethernet interface."
			::= { cdd564IPRoutingEthernet 1 }
		
		cdd564TotalUnicastsToEthernet OBJECT-TYPE
			SYNTAX Counter32
			MAX-ACCESS read-only
			STATUS current
			DESCRIPTION
				"The total number of Unicast packets routed to 
				the Ethernet interface."
			::= { cdd564IPRoutingEthernet 2 }
		
		cdd564TotalMulticastsToEthernet OBJECT-TYPE
			SYNTAX Counter32
			MAX-ACCESS read-only
			STATUS current
			DESCRIPTION
				"The total number of Multicast packets routed to 
				the Ethernet interface."
			::= { cdd564IPRoutingEthernet 3 }
		
		cdd564TotalBroadcastsToEthernet OBJECT-TYPE
			SYNTAX Counter32
			MAX-ACCESS read-only
			STATUS current
			DESCRIPTION
				"The total number of Broadcast packets routed to 
				the Ethernet interface."
			::= { cdd564IPRoutingEthernet 4 }
		
		cdd564TotalPacketsFromEthernet OBJECT-TYPE
			SYNTAX Counter32
			MAX-ACCESS read-only
			STATUS current
			DESCRIPTION
				"The total number of IP packets received from 
				the Ethernet interface."
			::= { cdd564IPRoutingEthernet 5 }
		
		cdd564IPRoutingSatellite OBJECT IDENTIFIER ::= { cdd564IPRoutingStatistics 2 }
		
		cdd564TotalPacketsFromSatellite OBJECT-TYPE
			SYNTAX Counter32
			MAX-ACCESS read-only
			STATUS current
			DESCRIPTION
				"The total number of IP packets received 
				from the satellite interfaces."
			::= { cdd564IPRoutingSatellite 1 }
		
		cdd564IPRoutingEndstation OBJECT IDENTIFIER ::= { cdd564IPRoutingStatistics 3 }
		
		cdd564TotalPacketsFromEndstation OBJECT-TYPE
			SYNTAX Counter32
			MAX-ACCESS read-only
			STATUS current
			DESCRIPTION
				"The total number of packets received from the 
				Endstation to be sent out one of the 
				interfaces."
			::= { cdd564IPRoutingEndstation 1 }
		
		cdd564TotalPacketsToEndstation OBJECT-TYPE
			SYNTAX Counter32
			MAX-ACCESS read-only
			STATUS current
			DESCRIPTION
				"The total number of packets sent to the 
				Endstation from one of the interfaces."
			::= { cdd564IPRoutingEndstation 2 }
		
		cdd564IPRoutingMisc OBJECT IDENTIFIER ::= { cdd564IPRoutingStatistics 4 }
		
		cdd564IGMPPacketsReceived OBJECT-TYPE
			SYNTAX Counter32
			MAX-ACCESS read-only
			STATUS current
			DESCRIPTION
				"The total number of IGMP packets received by 
				the endstation."
			::= { cdd564IPRoutingMisc 1 }
		
		cdd564IPOptionPacketsReceived OBJECT-TYPE
			SYNTAX Counter32
			MAX-ACCESS read-only
			STATUS current
			DESCRIPTION
				"The total number of packets received with IP 
				Options in the IP header."
			::= { cdd564IPRoutingMisc 2 }
		
		cdd564IPRoutingDropped OBJECT IDENTIFIER ::= { cdd564IPRoutingStatistics 5 }
		
		cdd564TotalDroppedPackets OBJECT-TYPE
			SYNTAX Counter32
			MAX-ACCESS read-only
			STATUS current
			DESCRIPTION
				"The total number of packets dropped by 
				the router."
			::= { cdd564IPRoutingDropped 1 }
		
		cdd564DroppedPacketsBadIPHeader OBJECT-TYPE
			SYNTAX Counter32
			MAX-ACCESS read-only
			STATUS current
			DESCRIPTION
				"The total number of packets dropped by 
				the router because of a bad checksum in 
				the IP header."
			::= { cdd564IPRoutingDropped 2 }
		
		cdd564DroppedPacketsBadBufferLength OBJECT-TYPE
			SYNTAX Counter32
			MAX-ACCESS read-only
			STATUS current
			DESCRIPTION
				"The total number of packets dropped by 
				the router because of a bad packet 
				buffer length."
			::= { cdd564IPRoutingDropped 3 }
		
		cdd564DroppedPacketsBadIPVersion OBJECT-TYPE
			SYNTAX Counter32
			MAX-ACCESS read-only
			STATUS current
			DESCRIPTION
				"The total number of packets dropped by 
				the router because of the packet is 
				not IPv4.
				
				Note: IPv6 packets are not support by 
				the router."
			::= { cdd564IPRoutingDropped 4 }
		
		cdd564DroppedPacketsTTLExpired OBJECT-TYPE
			SYNTAX Counter32
			MAX-ACCESS read-only
			STATUS current
			DESCRIPTION
				"The total number of packets dropped by 
				the router because the TTL (time to live) 
				in the IP header had expired 
				(i.e. reached zero)."
			::= { cdd564IPRoutingDropped 5 }
		
		cdd564DroppedPacketsNoRoute OBJECT-TYPE
			SYNTAX Counter32
			MAX-ACCESS read-only
			STATUS current
			DESCRIPTION
				"The total number of packets dropped by 
				the router because the packet did not 
				match any route in the route table 
				and could not be forwarded."
			::= { cdd564IPRoutingDropped 6 }
		
		cdd564DroppedPacketsNoARPEntry OBJECT-TYPE
			SYNTAX Counter32
			MAX-ACCESS read-only
			STATUS current
			DESCRIPTION
				"The total number of packets dropped by 
				the router because the ARP table did 
				not have an ARP entry for the packet's 
				next hop."
			::= { cdd564IPRoutingDropped 7 }
		
		cdd564DroppedPacketsFilteredMulticast OBJECT-TYPE
			SYNTAX Counter32
			MAX-ACCESS read-only
			STATUS current
			DESCRIPTION
				"The total number of multicast packets dropped 
				by the router because the multicast address 
				is not being forwarded."
			::= { cdd564IPRoutingDropped 8 }
		
		cdd564DroppedPacketsMulticastDisableGroup OBJECT-TYPE
			SYNTAX Counter32
			MAX-ACCESS read-only
			STATUS current
			DESCRIPTION
				"The total number of multicast packets dropped 
				by the router because the multicast group is 
				not being forwarded."
			::= { cdd564IPRoutingDropped 9 }
		
		cdd564DroppedPacketsFiltered OBJECT-TYPE
			SYNTAX Counter32
			MAX-ACCESS read-only
			STATUS current
			DESCRIPTION
				"The total number of packets dropped by the 
				router for the following reasons:
				1. Boot
				2. Flow Descriptor
				3. Unknown Reason Code
				4. Flow Correlator
				5. Management Path
				6. Ping
				7. Access Control
				8. Vipersat Multicommand
				9. Vipersat Unicommand
				10. Codeload
				11. Multicast
				12. Bad Packet
				13. Route
				14. Bad Header Len
				15. Bad Data Ptr    
				16. MAC Split Err
				17. L3Type Err
				18. Local Destination
				19. ICMP Filter
				20. Port Err
				21. Per port route rule"
			::= { cdd564IPRoutingDropped 10 }
		
		cdd564DroppedPacketsRouterQueueFull OBJECT-TYPE
			SYNTAX Counter32
			MAX-ACCESS read-only
			STATUS current
			DESCRIPTION
				"The total number of packets dropped by 
				the router because the router queue is 
				full."
			::= { cdd564IPRoutingDropped 11 }
		
		cdd564IPRoutingClearCounters OBJECT-TYPE
			SYNTAX INTEGER { clear(1) }
			MAX-ACCESS read-write
			STATUS current
			DESCRIPTION
				"This is a SET command to clear the IP routing 
				counters."
			::= { cdd564IPRoutingStatistics 6 }
		
		cdd564EthernetStatistics OBJECT IDENTIFIER ::= { cdd564Statistics 2 }
		
		cdd564EthernetTxStats OBJECT IDENTIFIER ::= { cdd564EthernetStatistics 1 }
		
		cdd564EtherTxGoodFrames OBJECT-TYPE
			SYNTAX Counter32
			MAX-ACCESS read-only
			STATUS current
			DESCRIPTION
				"The number of transmitted good frames from 
				the Ethernet interface."
			::= { cdd564EthernetTxStats 1 }
		
		cdd564EtherTxMaxCollisions OBJECT-TYPE
			SYNTAX Counter32
			MAX-ACCESS read-only
			STATUS current
			DESCRIPTION
				"The number of frames that were NOT transmitted 
				because they encountered the maximum configured 
				collisions. This counter should only increment 
				when network is heavily saturated with traffic."
			::= { cdd564EthernetTxStats 2 }
		
		cdd564EtherTxLateCollisions OBJECT-TYPE
			SYNTAX Counter32
			MAX-ACCESS read-only
			STATUS current
			DESCRIPTION
				"The number of frames that were NOT transmitted 
				because they encountered collision outside 
				the normal collision window."
			::= { cdd564EthernetTxStats 3 }
		
		cdd564EtherTxDMAUnderrun OBJECT-TYPE
			SYNTAX Counter32
			MAX-ACCESS read-only
			STATUS current
			DESCRIPTION
				"The number of frames that were either NOT 
				transmitted or retransmitted due to Transmit 
				DMA underrun. Underruns occur due to lack of 
				PCI bandwidth resulting in the internal 
				transmit FIFO running dry during the 
				transmission of a frame."
			::= { cdd564EthernetTxStats 4 }
		
		cdd564EtherTxLostCarrierSense OBJECT-TYPE
			SYNTAX Counter32
			MAX-ACCESS read-only
			STATUS current
			DESCRIPTION
				"The number of frames transmitted by the device 
				despite the fact that it detected the 
				de-assertion of Transmit Lost Carrier Sense 
				(CRS) during the transmission.
				"
			::= { cdd564EthernetTxStats 5 }
		
		cdd564EtherTxDeferred OBJECT-TYPE
			SYNTAX Counter32
			MAX-ACCESS read-only
			STATUS current
			DESCRIPTION
				"The number of frames deferred before 
				transmission due to activity on the link."
			::= { cdd564EthernetTxStats 6 }
		
		cdd564EtherTxSingleCollisions OBJECT-TYPE
			SYNTAX Counter32
			MAX-ACCESS read-only
			STATUS current
			DESCRIPTION
				"The number of transmitted frames that 
				encountered only 1 collision."
			::= { cdd564EthernetTxStats 7 }
		
		cdd564EtherTxMultipleCollisions OBJECT-TYPE
			SYNTAX Counter32
			MAX-ACCESS read-only
			STATUS current
			DESCRIPTION
				"The number of transmitted frames that 
				encountered more than 1 collision."
			::= { cdd564EthernetTxStats 8 }
		
		cdd564EtherTxTotalCollisions OBJECT-TYPE
			SYNTAX Counter32
			MAX-ACCESS read-only
			STATUS current
			DESCRIPTION
				"The total number of collisions that were 
				encountered while attempting to transmit. This 
				count includes late collisions and collisions 
				from frames that encountered maximum 
				collisions."
			::= { cdd564EthernetTxStats 9 }
		
		cdd564EtherTxFlowControlPauseFrames OBJECT-TYPE
			SYNTAX Counter32
			MAX-ACCESS read-only
			STATUS current
			DESCRIPTION
				"The number of flow control frames transmitted 
				by the device. This count includes both the 
				XOFF and XON frames transmitted by the device."
			::= { cdd564EthernetTxStats 10 }
		
		cdd564EthernetRxStats OBJECT IDENTIFIER ::= { cdd564EthernetStatistics 2 }
		
		cdd564EtherRxGoodFrames OBJECT-TYPE
			SYNTAX Counter32
			MAX-ACCESS read-only
			STATUS current
			DESCRIPTION
				"The number of frames properly received from the 
				link. It is updated only after actual reception 
				from the link is completed and all data bytes 
				are stored in memory."
			::= { cdd564EthernetRxStats 1 }
		
		cdd564EtherRxCRCErrorFrames OBJECT-TYPE
			SYNTAX Counter32
			MAX-ACCESS read-only
			STATUS current
			DESCRIPTION
				"The number of aligned frames discarded due to 
				CRC Errors."
			::= { cdd564EthernetRxStats 2 }
		
		cdd564EtherRxAllignmentErrors OBJECT-TYPE
			SYNTAX Counter32
			MAX-ACCESS read-only
			STATUS current
			DESCRIPTION
				"The number of frames that are both misaligned 
				[in other words, CRS de-asserts on a non-octet
				boundary] and contain a CRC error."
			::= { cdd564EthernetRxStats 3 }
		
		cdd564EtherRxResourceErrors OBJECT-TYPE
			SYNTAX Counter32
			MAX-ACCESS read-only
			STATUS current
			DESCRIPTION
				"The number of good frames discarded due to 
				unavailable resources."
			::= { cdd564EthernetRxStats 4 }
		
		cdd564EtherRxFIFOOverrunErrors OBJECT-TYPE
			SYNTAX Counter32
			MAX-ACCESS read-only
			STATUS current
			DESCRIPTION
				"The number of frames known to be lost because 
				the internal receive FIFO overflowed [also 
				known as receive overrun]. This can occur if 
				the device is unable to get necessary PCI 
				bandwidth. If the overflow condition persists 
				for more than one frame, the frames that 
				follow the first can also be lost.
				
				A frame that was counted as an overrun will 
				not be counted in other error counters like 
				(short frames, misaligned, CRC error)."
			::= { cdd564EthernetRxStats 5 }
		
		cdd564EtherRxCollisionDetectErrors OBJECT-TYPE
			SYNTAX Counter32
			MAX-ACCESS read-only
			STATUS current
			DESCRIPTION
				"The number of frames that encountered collision 
				during reception. This is always zero."
			::= { cdd564EthernetRxStats 6 }
		
		cdd564EtherRxShortFrames OBJECT-TYPE
			SYNTAX Counter32
			MAX-ACCESS read-only
			STATUS current
			DESCRIPTION
				"The number of received frames that are shorter 
				than the minimum frame length."
			::= { cdd564EthernetRxStats 7 }
		
		cdd564EtherRxFlowControlPauseFrames OBJECT-TYPE
			SYNTAX Counter32
			MAX-ACCESS read-only
			STATUS current
			DESCRIPTION
				"The number of flow control frames received by 
				the device. This count includes both XOFF and 
				XON frames received."
			::= { cdd564EthernetRxStats 8 }
		
		cdd564EthernetClearCounters OBJECT-TYPE
			SYNTAX INTEGER { clear(1) }
			MAX-ACCESS read-write
			STATUS current
			DESCRIPTION
				"Reset all ethernet transmit & receive counters."
			::= { cdd564EthernetStatistics 3 }
		
		cdd564SatelliteStatistics OBJECT IDENTIFIER ::= { cdd564Statistics 3 }
		
		cdd564SatelliteRxStatsTable OBJECT-TYPE
			SYNTAX SEQUENCE OF Cdd564SatelliteRxStatsEntry
			MAX-ACCESS not-accessible
			STATUS current
			DESCRIPTION
				"The table for Satellite interface statistics."
			::= { cdd564SatelliteStatistics 1 }
		
		cdd564SatelliteRxStatsEntry OBJECT-TYPE
			SYNTAX Cdd564SatelliteRxStatsEntry
			MAX-ACCESS not-accessible
			STATUS current
			DESCRIPTION
				"The entry for the Satellite interface 
				statistics table."
			INDEX { cdd564RxStatsIndex }
			::= { cdd564SatelliteRxStatsTable 1 }
		
		Cdd564SatelliteRxStatsEntry ::=
			SEQUENCE { 
				cdd564RxStatsIndex
					INTEGER,
				cdd564RxGoodFrames
					Counter32,
				cdd564RxHeaderBytes
					Counter32,
				cdd564RxPayloadBytes
					Counter32,
				cdd564RxBadHDLCAddressErrors
					Counter32,
				cdd564RxPktProcCRCErrors
					Counter32,
				cdd564RxAbortOctetErrors
					Counter32,
				cdd564RxOverrunErrors
					Counter32,
				cdd564RxHDLCCRCErrors
					Counter32,
				cdd564RxInvalidFlowIDErrors
					Counter32,
				cdd564RxSARReassembleErrors
					Counter32,
				cdd564RxHeaderDecompressionErrors
					Counter32,
				cdd564RxMemoryAlignmentErrors
					Counter32,
				cdd564RxCRCErrors
					Counter32
			 }

		cdd564RxStatsIndex OBJECT-TYPE
			SYNTAX INTEGER (1..4)
			MAX-ACCESS read-only
			STATUS current
			DESCRIPTION
				"The Rx index for the satellite interface,
				where index can be from 1 to 4."
			::= { cdd564SatelliteRxStatsEntry 1 }
		
		cdd564RxGoodFrames OBJECT-TYPE
			SYNTAX Counter32
			MAX-ACCESS read-only
			STATUS current
			DESCRIPTION
				"The total number of good frames received over 
				satellite interface."
			::= { cdd564SatelliteRxStatsEntry 2 }
		
		cdd564RxHeaderBytes OBJECT-TYPE
			SYNTAX Counter32
			MAX-ACCESS read-only
			STATUS current
			DESCRIPTION
				"The count of HDLC header bytes received over
				the satellite interface.
				
				HDLC header = Control + 
				              HDLC address + 
				              Flow ID + 
				              CRC"
			::= { cdd564SatelliteRxStatsEntry 3 }
		
		cdd564RxPayloadBytes OBJECT-TYPE
			SYNTAX Counter32
			MAX-ACCESS read-only
			STATUS current
			DESCRIPTION
				"The count of payload bytes that were received 
				over satellite interface, excluding any frame 
				overhead."
			::= { cdd564SatelliteRxStatsEntry 4 }
		
		cdd564RxBadHDLCAddressErrors OBJECT-TYPE
			SYNTAX Counter32
			MAX-ACCESS read-only
			STATUS current
			DESCRIPTION
				"The count of received frames that did not match 
				any of the Rx HDLC addresses."
			::= { cdd564SatelliteRxStatsEntry 5 }
		
		cdd564RxPktProcCRCErrors OBJECT-TYPE
			SYNTAX Counter32
			MAX-ACCESS read-only
			STATUS current
			DESCRIPTION
				"The Packet Processor CRC check is the second 
				CRC check performed after the HDLC CRC check.  
				It is the checksum calculated after Decryption 
				and Payload Decompression.  Failures due to 
				3xDES and Payload Comp are detected at 
				this level.  
				"
			::= { cdd564SatelliteRxStatsEntry 6 }
		
		cdd564RxAbortOctetErrors OBJECT-TYPE
			SYNTAX Counter32
			MAX-ACCESS read-only
			STATUS current
			DESCRIPTION
				"The count of aborted frames and octet error 
				frames.
				
				Aborted frame:
				A frame is aborted when the frame is not 
				complete and is terminated prematurely with 
				the Abort signal, which is 8 consecutive '1's.  
				                                
				Octet error:
				A frames that was not on a byte boudary or on 
				a multiple of 8-bit boundary."
			::= { cdd564SatelliteRxStatsEntry 7 }
		
		cdd564RxOverrunErrors OBJECT-TYPE
			SYNTAX Counter32
			MAX-ACCESS read-only
			STATUS current
			DESCRIPTION
				"The count of received frames that exceeded the 
				maximum frame length of 2K bytes or overflowed 
				the buffer which stores complete HDLC frames."
			::= { cdd564SatelliteRxStatsEntry 8 }
		
		cdd564RxHDLCCRCErrors OBJECT-TYPE
			SYNTAX Counter32
			MAX-ACCESS read-only
			STATUS current
			DESCRIPTION
				"The HDLC CRC is the first stage of the CRC 
				check, before 3xDES and paylod Decompression.
				It indicates any errors due to the satellite 
				link only."
			::= { cdd564SatelliteRxStatsEntry 9 }
		
		cdd564RxInvalidFlowIDErrors OBJECT-TYPE
			SYNTAX Counter32
			MAX-ACCESS read-only
			STATUS current
			DESCRIPTION
				"The number of frames received where the flow 
				ID did not match to a valid flow descriptor."
			::= { cdd564SatelliteRxStatsEntry 10 }
		
		cdd564RxSARReassembleErrors OBJECT-TYPE
			SYNTAX Counter32
			MAX-ACCESS read-only
			STATUS current
			DESCRIPTION
				"The number of frames corresponding to a packet 
				which had undergone segmentation and 
				encountered an error in reassembly."
			::= { cdd564SatelliteRxStatsEntry 11 }
		
		cdd564RxHeaderDecompressionErrors OBJECT-TYPE
			SYNTAX Counter32
			MAX-ACCESS read-only
			STATUS current
			DESCRIPTION
				"The number of frames with a compressed IP 
				header that encountered an error in 
				decompressing (rebuilding) the full IP header."
			::= { cdd564SatelliteRxStatsEntry 12 }
		
		cdd564RxMemoryAlignmentErrors OBJECT-TYPE
			SYNTAX Counter32
			MAX-ACCESS read-only
			STATUS current
			DESCRIPTION
				"The number of frames which were incorrectly 
				transferred (frame too small) from the Rx FPGA."
			::= { cdd564SatelliteRxStatsEntry 13 }
		
		cdd564RxCRCErrors OBJECT-TYPE
			SYNTAX Counter32
			MAX-ACCESS read-only
			STATUS current
			DESCRIPTION
				"The number of frames with a CRC error detected
				by the Rx FPGA."
			::= { cdd564SatelliteRxStatsEntry 14 }
		
		cdd564SatelliteClearCounters OBJECT-TYPE
			SYNTAX INTEGER { clear(1) }
			MAX-ACCESS read-write
			STATUS current
			DESCRIPTION
				"This is a SET command for clearing all the 
				Satellite statistic counters."
			::= { cdd564SatelliteStatistics 2 }
		
		cdd564Config OBJECT IDENTIFIER ::= { cdd564Objects 7 }
		
		cdd564Rx OBJECT IDENTIFIER ::= { cdd564Config 1 }
		
		cdd564RxTable OBJECT-TYPE
			SYNTAX SEQUENCE OF Cdd564RxEntry
			MAX-ACCESS not-accessible
			STATUS current
			DESCRIPTION
				"The table of Demodulators."
			::= { cdd564Rx 1 }
		
		cdd564RxEntry OBJECT-TYPE
			SYNTAX Cdd564RxEntry
			MAX-ACCESS not-accessible
			STATUS current
			DESCRIPTION
				"The entry for the Demodulator table."
			INDEX { cdd564RxTableIndex }
			::= { cdd564RxTable 1 }
		
		Cdd564RxEntry ::=
			SEQUENCE { 
				cdd564RxTableIndex
					INTEGER,
				cdd564RxFEC
					INTEGER,
				cdd564RxDemodulation
					INTEGER,
				cdd564RxCodeRate
					INTEGER,
				cdd564RxDataRate
					INTEGER,
				cdd564RxFrequency
					INTEGER,
				cdd564RxAcquisitionSweepWidth
					INTEGER,
				cdd564RxDescrambling
					INTEGER,
				cdd564RxBufferSize
					INTEGER,
				cdd546RxSpectrumInversion
					INTEGER,
				cdd564RxDataInversion
					INTEGER,
				cdd564RxEbNoAlarmPoint
					INTEGER,
				cdd564RxRecenterBuffer
					INTEGER,
				cdd564RxSymbolRate
					INTEGER
			 }

		cdd564RxTableIndex OBJECT-TYPE
			SYNTAX INTEGER (1..4)
			MAX-ACCESS read-only
			STATUS current
			DESCRIPTION
				"The index for the Rx table,
				where index can be from 1 to 4."
			::= { cdd564RxEntry 1 }
		
		cdd564RxFEC OBJECT-TYPE
			SYNTAX INTEGER
				{
				uncoded(0),
				turbo(6)
				}
			MAX-ACCESS read-write
			STATUS current
			DESCRIPTION
				"Rx FEC type where:
				0 = Uncoded
				6 = Turbo"
			::= { cdd564RxEntry 2 }
		
		cdd564RxDemodulation OBJECT-TYPE
			SYNTAX INTEGER
				{
				demodQPSK(1),
				demod8PSK(3),
				demod16QAM(4)
				}
			MAX-ACCESS read-write
			STATUS current
			DESCRIPTION
				"Rx demodulation type, where:
				1 = QPSK
				3 = 8-PSK
				4 = 16-QAM"
			::= { cdd564RxEntry 3 }
		
		cdd564RxCodeRate OBJECT-TYPE
			SYNTAX INTEGER
				{
				rate3over4(4),
				rate7over8(5),
				rate095(6),
				uncoded(7)
				}
			MAX-ACCESS read-write
			STATUS current
			DESCRIPTION
				"Rx code rate, where
				4 = Rate 3/4
				5 = Rate 7/8
				6 = Rate 0.95
				7 = Rate 1/1 (Uncoded)"
			::= { cdd564RxEntry 4 }
		
		cdd564RxDataRate OBJECT-TYPE
			SYNTAX INTEGER (16000..9980000)
			UNITS "bps"
			MAX-ACCESS read-write
			STATUS current
			DESCRIPTION
				"Rx data rate in bps (Varies based on chart below.)
				Units = bps
				Resolution = 1 bps
				
				FEC Type   Modulation    Code Rate           Data Rate        High Rate
				--------   -----------   ----------   ---------------------   ---------
				Turbo      QPSK          Rate 3/4     16.0 Kbps to 4.5 Mbps   N/A
				Turbo      QPSK          Rate 7/8     16.0 Kbps to 5.0 Mbps   5.25  Mbps
				Turbo      QPSK          Rate 0.95    16.0 Kbps to 5.0 Mbps   5.667 Mbps
				Turbo      8-PSK         Rate 3/4     16.0 Kbps to 5.0 Mbps   6.75  Mbps
				Turbo      8-PSK         Rate 7/8     16.0 Kbps to 5.0 Mbps   7.875 Mbps
				Turbo      8-PSK         Rate 0.95    16.0 Kbps to 5.0 Mbps   8.5   Mbps
				Turbo      16-QAM        Rate 3/4     16.0 Kbps to 5.0 Mbps   9.0   Mbps
				Turbo      16-QAM        Rate 7/8     16.8 Kbps to 5.0 Mbps   9.98  Mbps"
			::= { cdd564RxEntry 5 }
		
		cdd564RxFrequency OBJECT-TYPE
			SYNTAX INTEGER (50000000..90000000 | 100000000..180000000 | 950000000..1950000000)
			UNITS "Hz"
			MAX-ACCESS read-write
			STATUS current
			DESCRIPTION
				"Rx frequency for L-Band and IF-Band modes.
				L-Band is 950 MHz to 1950 MHz.
				IF-Band is 50 MHz to 90 MHz and 100 MHz to 180 MHz.
				Units = Hz.
				Resolution = 100 Hz."
			::= { cdd564RxEntry 6 }
		
		cdd564RxAcquisitionSweepWidth OBJECT-TYPE
			SYNTAX INTEGER (1..200)
			UNITS "KHz"
			MAX-ACCESS read-write
			STATUS current
			DESCRIPTION
				"Rx +/- acquisition sweep range of demodulator, 
				in KHz, ranging from:
				+/- 1 to +/- 32 KHz (rates < 625 ksym/second)
				or +/- 1 to 200 KHz (rates >= 625 ksym/second)"
			::= { cdd564RxEntry 7 }
		
		cdd564RxDescrambling OBJECT-TYPE
			SYNTAX INTEGER
				{
				off(0),
				onDefault(1),
				onIESS315(2)
				}
			MAX-ACCESS read-write
			STATUS current
			DESCRIPTION
				"Rx descrambler state, where:
				0 = Off
				1 = On (default descrambler type)
				2 = On - IESS-315 (Turbo only)"
			::= { cdd564RxEntry 8 }
		
		cdd564RxBufferSize OBJECT-TYPE
			SYNTAX INTEGER { disabled(0) }
			MAX-ACCESS read-write
			STATUS current
			DESCRIPTION
				"Rx buffer size, where:
				0 = Buffer disabled (Clock mode = Rx satellite)"
			::= { cdd564RxEntry 9 }
		
		cdd546RxSpectrumInversion OBJECT-TYPE
			SYNTAX INTEGER
				{
				normal(0),
				inverted(1)
				}
			MAX-ACCESS read-write
			STATUS current
			DESCRIPTION
				"Rx spectrum inversion, where:
				0 = Normal
				1 = Rx spectrum inverted"
			::= { cdd564RxEntry 10 }
		
		cdd564RxDataInversion OBJECT-TYPE
			SYNTAX INTEGER
				{
				normal(0),
				inverted(1)
				}
			MAX-ACCESS read-write
			STATUS current
			DESCRIPTION
				"Invert receive data, where:
				0 = Normal
				1 = Inverted"
			::= { cdd564RxEntry 11 }
		
		cdd564RxEbNoAlarmPoint OBJECT-TYPE
			SYNTAX INTEGER (1..160)
			UNITS "0.1dB"
			MAX-ACCESS read-write
			STATUS current
			DESCRIPTION
				"Rx Eb/No alarm point in 0.1 dB, with a range 
				between 0.1 dB and 16 dB.
				Units = 0.1 dB
				Resolution = 0.1 dB"
			::= { cdd564RxEntry 12 }
		
		cdd564RxRecenterBuffer OBJECT-TYPE
			SYNTAX INTEGER { recenter(1) }
			MAX-ACCESS read-write
			STATUS current
			DESCRIPTION
				"This is a SET command that recenters the 
				receive Plesiochronous/Doppler buffer."
			::= { cdd564RxEntry 13 }
		
		cdd564RxSymbolRate OBJECT-TYPE
			SYNTAX INTEGER (5000..3000000)
			UNITS "sym"
			MAX-ACCESS read-only
			STATUS current
			DESCRIPTION
				"Rx symbol rate in symbols per second (sym)
				Units = sym
				Resolution = 1 sym"
			::= { cdd564RxEntry 14 }
		
		cdd564AlarmMask OBJECT IDENTIFIER ::= { cdd564Config 2 }
		
		cdd564AlarmMaskTable OBJECT-TYPE
			SYNTAX SEQUENCE OF Cdd564AlarmMaskEntry
			MAX-ACCESS not-accessible
			STATUS current
			DESCRIPTION
				"Description."
			::= { cdd564AlarmMask 1 }
		
		cdd564AlarmMaskEntry OBJECT-TYPE
			SYNTAX Cdd564AlarmMaskEntry
			MAX-ACCESS not-accessible
			STATUS current
			DESCRIPTION
				"Description."
			INDEX { cdd564AlarmMaskIndex }
			::= { cdd564AlarmMaskTable 1 }
		
		Cdd564AlarmMaskEntry ::=
			SEQUENCE { 
				cdd564AlarmMaskIndex
					INTEGER,
				cdd564AGCAlarmMask
					INTEGER,
				cdd564EbNoAlarmMask
					INTEGER,
				cdd564LNBAlarmMask
					INTEGER
			 }

		cdd564AlarmMaskIndex OBJECT-TYPE
			SYNTAX INTEGER (1..4)
			MAX-ACCESS read-only
			STATUS current
			DESCRIPTION
				"The index for the Demodulator."
			::= { cdd564AlarmMaskEntry 1 }
		
		cdd564AGCAlarmMask OBJECT-TYPE
			SYNTAX INTEGER
				{
				active(0),
				masked(1)
				}
			MAX-ACCESS read-write
			STATUS current
			DESCRIPTION
				"Rx AGC alarm mask, where:
				0 = Unmasked
				1 = Masked"
			::= { cdd564AlarmMaskEntry 2 }
		
		cdd564EbNoAlarmMask OBJECT-TYPE
			SYNTAX INTEGER
				{
				active(0),
				masked(1)
				}
			MAX-ACCESS read-write
			STATUS current
			DESCRIPTION
				"Eb/No alarm mask, where:
				0 = Unmasked
				1 = Masked"
			::= { cdd564AlarmMaskEntry 3 }
		
		cdd564LNBAlarmMask OBJECT-TYPE
			SYNTAX INTEGER
				{
				active(0),
				masked(1)
				}
			MAX-ACCESS read-write
			STATUS current
			DESCRIPTION
				"LNB alarm mask, where:
				0 = Unmasked
				1 = Masked"
			::= { cdd564AlarmMaskEntry 5 }
		
		cdd564Reference OBJECT IDENTIFIER ::= { cdd564Config 3 }
		
		cdd564ReferenceFrequency OBJECT-TYPE
			SYNTAX INTEGER { int10MHz(0) }
			MAX-ACCESS read-write
			STATUS current
			DESCRIPTION
				"External reference frequency, where:
				0 = Internal 10 MHz"
			::= { cdd564Reference 1 }
		
		cdd564InternalReferenceAdjust OBJECT-TYPE
			SYNTAX INTEGER (-999..999)
			UNITS "KHz"
			MAX-ACCESS read-write
			STATUS current
			DESCRIPTION
				"Internal Reference Adjust, from -999 to +999.
				Units = KHz"
			::= { cdd564Reference 2 }
		
		cdd564LNB OBJECT IDENTIFIER ::= { cdd564Config 4 }
		
		cdd564LNBTable OBJECT-TYPE
			SYNTAX SEQUENCE OF Cdd564LNBEntry
			MAX-ACCESS not-accessible
			STATUS current
			DESCRIPTION
				"The table for LNBs."
			::= { cdd564LNB 1 }
		
		cdd564LNBEntry OBJECT-TYPE
			SYNTAX Cdd564LNBEntry
			MAX-ACCESS not-accessible
			STATUS current
			DESCRIPTION
				"The entry for the LNBs table."
			INDEX { cdd564LNBIndex }
			::= { cdd564LNBTable 1 }
		
		Cdd564LNBEntry ::=
			SEQUENCE { 
				cdd564LNBIndex
					INTEGER,
				cdd564LNBDCPower
					INTEGER,
				cdd564LNB10MHzReference
					INTEGER,
				cdm564LLNBLowCurrentLimit
					INTEGER,
				cdd564LNBHighCurrentLimit
					INTEGER,
				cdd564LNBLOFrequency
					INTEGER,
				cdd564LNBLOMix
					INTEGER
			 }

		cdd564LNBIndex OBJECT-TYPE
			SYNTAX INTEGER (1..4)
			MAX-ACCESS read-only
			STATUS current
			DESCRIPTION
				"The index for the LNB.."
			::= { cdd564LNBEntry 1 }
		
		cdd564LNBDCPower OBJECT-TYPE
			SYNTAX INTEGER
				{
				off(0),
				on13volts(1),
				on18volts(2),
				on24volts(3)
				}
			MAX-ACCESS read-write
			STATUS current
			DESCRIPTION
				"LNB power control, where:
				0 = Off
				1 = On, 13V LNB voltage
				2 = On, 18V LNB voltage
				3 = On, 24V LNB voltage"
			::= { cdd564LNBEntry 2 }
		
		cdd564LNB10MHzReference OBJECT-TYPE
			SYNTAX INTEGER
				{
				disable(0),
				enable(1)
				}
			MAX-ACCESS read-write
			STATUS current
			DESCRIPTION
				"LNB 10MHz frequency reference, where:
				0 = Disable LNB 10MHz reference
				1 = Enable LNB 10MHz reference"
			::= { cdd564LNBEntry 3 }
		
		cdm564LLNBLowCurrentLimit OBJECT-TYPE
			SYNTAX INTEGER (10..400)
			MAX-ACCESS read-write
			STATUS current
			DESCRIPTION
				"LNB lower alarm limit for current, between 
				10 and 400 mA."
			::= { cdd564LNBEntry 4 }
		
		cdd564LNBHighCurrentLimit OBJECT-TYPE
			SYNTAX INTEGER (50..600)
			UNITS "mA"
			MAX-ACCESS read-write
			STATUS current
			DESCRIPTION
				"LNB upper alarm limit for current, between 
				50 and 600 mA."
			::= { cdd564LNBEntry 5 }
		
		cdd564LNBLOFrequency OBJECT-TYPE
			SYNTAX INTEGER (0 | 3000..65000)
			UNITS "MHz"
			MAX-ACCESS read-write
			STATUS current
			DESCRIPTION
				"LNB receieve LO frequency, in the range of 
				3000 to 65000 MHz.
				Setting a 0 disables the feature.
				                
				Terminal Frequency = LNB_LO +/- Rx_Frequency 
				(depending on High/Low Mix)"
			::= { cdd564LNBEntry 6 }
		
		cdd564LNBLOMix OBJECT-TYPE
			SYNTAX INTEGER
				{
				lowSideMix(0),
				highSideMix(1)
				}
			MAX-ACCESS read-write
			STATUS current
			DESCRIPTION
				"LO frequency mix, where:
				0 = Low-side mix
				1 = High-side mix"
			::= { cdd564LNBEntry 7 }
		
		cdd564Monitor OBJECT IDENTIFIER ::= { cdd564Objects 8 }
		
		cdd564UnitMonitor OBJECT IDENTIFIER ::= { cdd564Monitor 1 }
		
		cdd564SerialNumber OBJECT-TYPE
			SYNTAX DisplayString
			MAX-ACCESS read-only
			STATUS current
			DESCRIPTION
				"Unit's 9-digit serial number."
			::= { cdd564UnitMonitor 1 }
		
		cdd564SoftwareRevision OBJECT-TYPE
			SYNTAX DisplayString
			MAX-ACCESS read-only
			STATUS current
			DESCRIPTION
				"Unit returns the value of the internal 
				software revision installed in the unit, 
				in the form of x.x.x."
			::= { cdd564UnitMonitor 2 }
		
		cdd564ModelNumber OBJECT-TYPE
			SYNTAX INTEGER (0..999)
			MAX-ACCESS read-only
			STATUS current
			DESCRIPTION
				"Unit's model number."
			::= { cdd564UnitMonitor 3 }
		
		cdd564UnitAlarm OBJECT-TYPE
			SYNTAX INTEGER
				{
				noFaults(0),
				powerSupply5volts(1),
				powerSupply12volts(2),
				powerSupplyNeg5volts(3),
				powerSupply23volts(4),
				powerSupplyNeg12volts(5),
				rx1stLOSynthesizerLock(6),
				rx2ndLOSynthesizerLock(7),
				refPLLLock(8),
				checksumErrorEEPROM(9)
				}
			MAX-ACCESS read-only
			STATUS current
			DESCRIPTION
				"Modem Unit Faults:
				
				Value    Description of unit fault
				
				  0      No faults
				  1      +5 Volt power supply 
				  2      +12 Volt power supply 
				  3      -5 Volt power supply 
				  4      +23 Volt power supply 
				  5      -12 Volt power supply 
				  6      Rx 1st LO synthesize lock
				  7      Rx 2nd LO synthesize lock
				  8      Ref PLL lock
				  9      EEPROM checksum error
				"
			::= { cdd564UnitMonitor 4 }
		
		cdd564Temperature OBJECT-TYPE
			SYNTAX INTEGER (-99..99)
			MAX-ACCESS read-only
			STATUS current
			DESCRIPTION
				"Unit returns the value of the internal 
				temperature, in degrees Celsius."
			::= { cdd564UnitMonitor 5 }
		
		cdd564RxMonitor OBJECT IDENTIFIER ::= { cdd564Monitor 2 }
		
		cdd564RxMonitorTable OBJECT-TYPE
			SYNTAX SEQUENCE OF Cdd564RxMonitorEntry
			MAX-ACCESS not-accessible
			STATUS current
			DESCRIPTION
				"The table for monitoring demodulators."
			::= { cdd564RxMonitor 1 }
		
		cdd564RxMonitorEntry OBJECT-TYPE
			SYNTAX Cdd564RxMonitorEntry
			MAX-ACCESS not-accessible
			STATUS current
			DESCRIPTION
				"The entry for the demoduator monitor table."
			INDEX { cdd564RxMonitorIndex }
			::= { cdd564RxMonitorTable 1 }
		
		Cdd564RxMonitorEntry ::=
			SEQUENCE { 
				cdd564RxMonitorIndex
					INTEGER,
				cdd564RxAlarm
					INTEGER,
				cdd564RxEbNo
					INTEGER,
				cdd564RxSignalLevel
					INTEGER,
				cdd564RxFreqOffset
					INTEGER,
				cddRxBERMultiplier
					INTEGER
			 }

		cdd564RxMonitorIndex OBJECT-TYPE
			SYNTAX INTEGER (1..4)
			MAX-ACCESS read-only
			STATUS current
			DESCRIPTION
				"The index for the demodulator monitor table."
			::= { cdd564RxMonitorEntry 1 }
		
		cdd564RxAlarm OBJECT-TYPE
			SYNTAX INTEGER
				{
				rxTrafficOK(0),
				demodulatorUnlocked(1),
				agcAlarmSignalOutOfRange(3),
				bufferUnderflow(10),
				bufferOverflow(11),
				ebNoAlarm(13),
				aisDetectedOnIncomingData(15)
				}
			MAX-ACCESS read-only
			STATUS current
			DESCRIPTION
				"Modem RX Traffic Faults
				
				Value   Description of status parameter
				
				 0      Rx Traffic OK
				 1      Demodulator unlocked 
				 3      AGC Alarm - signal out of range
				 10     Buffer underflow
				 11     Buffer overflow
				 13     Eb/No alarm
				 15     AIS detected on incoming data"
			::= { cdd564RxMonitorEntry 2 }
		
		cdd564RxEbNo OBJECT-TYPE
			SYNTAX INTEGER (0..160 | 999)
			MAX-ACCESS read-only
			STATUS current
			DESCRIPTION
				"Unit returns the value of Eb/No, between 
				0 and 16 db.
				Units = 0.1 dB
				Resolution 0.1 dB
				
				Returns 999 if demod is unlocked.
				
				For values greater than 16 dB, the reply 
				will be 160."
			::= { cdd564RxMonitorEntry 3 }
		
		cdd564RxSignalLevel OBJECT-TYPE
			SYNTAX INTEGER (-100 | -99..-20 | -19)
			MAX-ACCESS read-only
			STATUS current
			DESCRIPTION
				"Unit returns the value of the Rx signal level, 
				in dBm, between -20 and -99 dBm, 
				Returns -100 if signal is less than -99dBm.
				Returns  -19 if signal is greater than -20dBm."
			::= { cdd564RxMonitorEntry 4 }
		
		cdd564RxFreqOffset OBJECT-TYPE
			SYNTAX INTEGER (-200000..200000 | 999900)
			MAX-ACCESS read-only
			STATUS current
			DESCRIPTION
				"Unit returns the value of the measured 
				frequency offset of the carrier being 
				demodulated in Hz.
				Units = Hz.
				Resolution 100 Hz.
				Range = -200,000 Hz to 0 Hz and 
				        0 Hz to 200,000 Hz.
				"
			::= { cdd564RxMonitorEntry 5 }
		
		cddRxBERMultiplier OBJECT-TYPE
			SYNTAX INTEGER (0..999999999 | 2147483647)
			MAX-ACCESS read-only
			STATUS current
			DESCRIPTION
				"Estimated corrected BER.  The BER is calculated 
				by multiplying the Multiplier by 10E-10.
				                                
				Calculuation:
				RxBER = (Multiplier) * 0.0000000001
				                                
				Returns 2147483647 (max int) if demod is 
				unlocked.
				"
			::= { cdd564RxMonitorEntry 7 }
		
		cdd564LNBMonitor OBJECT IDENTIFIER ::= { cdd564Monitor 3 }
		
		cdd564LNBMonitorTable OBJECT-TYPE
			SYNTAX SEQUENCE OF Cdd564LNBMonitorEntry
			MAX-ACCESS not-accessible
			STATUS current
			DESCRIPTION
				"The table for monitoring LNBs."
			::= { cdd564LNBMonitor 1 }
		
		cdd564LNBMonitorEntry OBJECT-TYPE
			SYNTAX Cdd564LNBMonitorEntry
			MAX-ACCESS not-accessible
			STATUS current
			DESCRIPTION
				"The entry for the LNBs monitoring table."
			INDEX { cdd564LNBMonitorIndex }
			::= { cdd564LNBMonitorTable 1 }
		
		Cdd564LNBMonitorEntry ::=
			SEQUENCE { 
				cdd564LNBMonitorIndex
					INTEGER,
				cdd564LNBAlarm
					INTEGER,
				cdd564LNBCurrent
					INTEGER,
				cdd564LNBVoltage
					INTEGER,
				cdd564LNBTerminalRxFreq
					INTEGER
			 }

		cdd564LNBMonitorIndex OBJECT-TYPE
			SYNTAX INTEGER (1..4)
			MAX-ACCESS read-only
			STATUS current
			DESCRIPTION
				"The index for the LNBs monitoring table."
			::= { cdd564LNBMonitorEntry 1 }
		
		cdd564LNBAlarm OBJECT-TYPE
			SYNTAX INTEGER
				{
				noLNBfaults(0),
				lnbCurrent(7),
				lnbVoltage(9)
				}
			MAX-ACCESS read-only
			STATUS current
			DESCRIPTION
				"LNB alarms
				
				Value   Description of status parameter
				
				   0     No LNB faults
				   7     LNB current
				   9     LNB voltage"
			::= { cdd564LNBMonitorEntry 2 }
		
		cdd564LNBCurrent OBJECT-TYPE
			SYNTAX INTEGER (0..999)
			MAX-ACCESS read-only
			STATUS current
			DESCRIPTION
				"Indicates the value of the LNB current, 
				between 0 and 999 mA."
			::= { cdd564LNBMonitorEntry 3 }
		
		cdd564LNBVoltage OBJECT-TYPE
			SYNTAX INTEGER (0..300)
			MAX-ACCESS read-only
			STATUS current
			DESCRIPTION
				"Indicates the value of the LNB voltage, 
				between 0 and 30 volts.
				Units = 0.1 volts
				
				If not available, response is 0."
			::= { cdd564LNBMonitorEntry 4 }
		
		cdd564LNBTerminalRxFreq OBJECT-TYPE
			SYNTAX INTEGER (0..999999999)
			MAX-ACCESS read-only
			STATUS current
			DESCRIPTION
				"Terminal Rx frequency = LNB LO +/- Rx_Frequency
				(depending on LO mix)
				Units = 100 Hz
				Resolution = 100 Hz
				
				Returns 0 if LNB_LO is zero."
			::= { cdd564LNBMonitorEntry 5 }
		
		cdd564StoredEvents OBJECT IDENTIFIER ::= { cdd564Monitor 4 }
		
		cdd564StoredEventsTable OBJECT-TYPE
			SYNTAX SEQUENCE OF Cdd564StoredEventsEntry
			MAX-ACCESS not-accessible
			STATUS current
			DESCRIPTION
				"The table of stored events for all four demods."
			::= { cdd564StoredEvents 1 }
		
		cdd564StoredEventsEntry OBJECT-TYPE
			SYNTAX Cdd564StoredEventsEntry
			MAX-ACCESS not-accessible
			STATUS current
			DESCRIPTION
				"The entry for stored events table for all 4 demods."
			INDEX { cdd564EventIndex, cdd564EventDemod }
			::= { cdd564StoredEventsTable 1 }
		
		Cdd564StoredEventsEntry ::=
			SEQUENCE { 
				cdd564EventDemod
					INTEGER,
				cdd564EventIndex
					INTEGER,
				cdd564EventDescription
					DisplayString
			 }

		cdd564EventDemod OBJECT-TYPE
			SYNTAX INTEGER (1..4)
			MAX-ACCESS read-only
			STATUS current
			DESCRIPTION
				"The demodulator index for which event log is 
				being returned."
			::= { cdd564StoredEventsEntry 1 }
		
		cdd564EventIndex OBJECT-TYPE
			SYNTAX INTEGER (1..255)
			MAX-ACCESS read-only
			STATUS current
			DESCRIPTION
				"The index for a demod's stored events table."
			::= { cdd564StoredEventsEntry 2 }
		
		cdd564EventDescription OBJECT-TYPE
			SYNTAX DisplayString
			MAX-ACCESS read-only
			STATUS current
			DESCRIPTION
				"Event description string with the following format
				seprated by commas:
				
				1. Date 
				   in form dd/mm/yy, where:
				      dd = day of the month (01 to 31)
				      mm = month (01 to 12)
				      yy = year (00 to 99)
				
				2. Time
				   in form hh:mm:ss, where: 
				     hh = hours (00 to 23)
				     mm = minutes (00 to 59)
				     ss = seconds (00 to 59)
				
				3. Event Type
				   in form xxxxx, where xxxxx is
				      Clear = fault cleared
				      Fault = fault occurred
				      Info  = information
				
				4. Texual Description of Event"
			::= { cdd564StoredEventsEntry 3 }
		
		cdd564ClearAllStoredEvents OBJECT-TYPE
			SYNTAX INTEGER (1..4)
			MAX-ACCESS read-write
			STATUS current
			DESCRIPTION
				"This is a SET command to clear the event log for 
				one of the four demods (1 - 4)."
			::= { cdd564StoredEvents 2 }
		
		cdd564StoredStatistics OBJECT IDENTIFIER ::= { cdd564Monitor 5 }
		
		cdd564StoredStatisticsTable OBJECT-TYPE
			SYNTAX SEQUENCE OF Cdd564StoredStatisticsEntry
			MAX-ACCESS not-accessible
			STATUS current
			DESCRIPTION
				"The table of stored statistics for all four
				demods."
			::= { cdd564StoredStatistics 1 }
		
		cdd564StoredStatisticsEntry OBJECT-TYPE
			SYNTAX Cdd564StoredStatisticsEntry
			MAX-ACCESS not-accessible
			STATUS current
			DESCRIPTION
				"The entry for stored statistics table for all
				four demods."
			INDEX { cdd564StatisticDemod, cdd564StatisticIndex }
			::= { cdd564StoredStatisticsTable 1 }
		
		Cdd564StoredStatisticsEntry ::=
			SEQUENCE { 
				cdd564StatisticDemod
					INTEGER,
				cdd564StatisticIndex
					INTEGER,
				cdd564StatisticDate
					DisplayString,
				cdd564StatisticTime
					DisplayString,
				cdd564StatisticAvgEbNo
					INTEGER,
				cdd564StatisticMinEbNo
					INTEGER
			 }

		cdd564StatisticDemod OBJECT-TYPE
			SYNTAX INTEGER (1..4)
			MAX-ACCESS read-only
			STATUS current
			DESCRIPTION
				"The demod index for which statistics table
				is being returned."
			::= { cdd564StoredStatisticsEntry 1 }
		
		cdd564StatisticIndex OBJECT-TYPE
			SYNTAX INTEGER (1..255)
			MAX-ACCESS read-only
			STATUS current
			DESCRIPTION
				"The index in one of the four demod's stored 
				statistics table."
			::= { cdd564StoredStatisticsEntry 2 }
		
		cdd564StatisticDate OBJECT-TYPE
			SYNTAX DisplayString
			MAX-ACCESS read-only
			STATUS current
			DESCRIPTION
				"The date of the statistic in the 
				form dd/mm/yy, where:
				dd = day of the month (01 to 31)
				mm = month (01 to 12)
				yy = year (00 to 99)"
			::= { cdd564StoredStatisticsEntry 3 }
		
		cdd564StatisticTime OBJECT-TYPE
			SYNTAX DisplayString
			MAX-ACCESS read-only
			STATUS current
			DESCRIPTION
				"The time of the statistic in the form hh:mm:ss, 
				indicating the time from midnight, where:
				hh = hours (00 to 23)
				mm = minutes (00 to 59)
				ss = seconds (00 to 59)"
			::= { cdd564StoredStatisticsEntry 4 }
		
		cdd564StatisticAvgEbNo OBJECT-TYPE
			SYNTAX INTEGER (0..160 | 999)
			MAX-ACCESS read-only
			STATUS current
			DESCRIPTION
				"Minimum Eb/No during sample period.
				Units = 0.1 dB.
				Returns 999 if demod was unlocked 
				during sample period."
			::= { cdd564StoredStatisticsEntry 5 }
		
		cdd564StatisticMinEbNo OBJECT-TYPE
			SYNTAX INTEGER (0..160 | 999)
			MAX-ACCESS read-only
			STATUS current
			DESCRIPTION
				"Minimum Eb/No during sample period.
				Units = 0.1 dB.
				Returns 999 if demod was unlocked 
				during sample period."
			::= { cdd564StoredStatisticsEntry 6 }
		
		cdd564StoredStatisticsConfigTable OBJECT-TYPE
			SYNTAX SEQUENCE OF Cdd564StoredStatisticsConfigEntry
			MAX-ACCESS not-accessible
			STATUS current
			DESCRIPTION
				"The configuration for the stored statistics (per Demod)."
			::= { cdd564StoredStatistics 2 }
		
		cdd564StoredStatisticsConfigEntry OBJECT-TYPE
			SYNTAX Cdd564StoredStatisticsConfigEntry
			MAX-ACCESS not-accessible
			STATUS current
			DESCRIPTION
				"The entry for the stored statistics configuration table."
			INDEX { cdd564StoredStatisticsConfigIndex }
			::= { cdd564StoredStatisticsConfigTable 1 }
		
		Cdd564StoredStatisticsConfigEntry ::=
			SEQUENCE { 
				cdd564StoredStatisticsConfigIndex
					INTEGER,
				cdd564StatisticsSampleInterval
					INTEGER
			 }

		cdd564StoredStatisticsConfigIndex OBJECT-TYPE
			SYNTAX INTEGER (1..4)
			MAX-ACCESS read-only
			STATUS current
			DESCRIPTION
				"The index for the Demodulator."
			::= { cdd564StoredStatisticsConfigEntry 1 }
		
		cdd564StatisticsSampleInterval OBJECT-TYPE
			SYNTAX INTEGER
				{
				disabled(0),
				mins10(1),
				mins20(2),
				mins30(3),
				mins40(4),
				mins50(5),
				mins60(6),
				mins70(7),
				mins80(8),
				mins90(9)
				}
			MAX-ACCESS read-write
			STATUS current
			DESCRIPTION
				"Used to set the sample interval for the 
				statistics logging function, where the 
				enumerated lists goes from 0 to 9 in 
				10 minute steps.
				                                
				Setting 0 disables the statistics logging 
				function.
				"
			::= { cdd564StoredStatisticsConfigEntry 2 }
		
		cdd564ClearAllStoredStatistics OBJECT-TYPE
			SYNTAX INTEGER (1..4)
			MAX-ACCESS read-write
			STATUS current
			DESCRIPTION
				"This is a SET command to clear the statistics 
				log for one of the four demods (1 - 4)."
			::= { cdd564StoredStatistics 3 }
		
		cdd564Util OBJECT IDENTIFIER ::= { cdd564Objects 9 }
		
		cdd564RTCDate OBJECT-TYPE
			SYNTAX DisplayString
			MAX-ACCESS read-write
			STATUS current
			DESCRIPTION
				"A date in the form dd/mm/yy, where
				dd = day of the month (01 to 31)
				mm = month (01 to 12)
				yy = year (00 to 99)"
			::= { cdd564Util 4 }
		
		cdd564RTCTime OBJECT-TYPE
			SYNTAX DisplayString
			MAX-ACCESS read-write
			STATUS current
			DESCRIPTION
				"A time in the form hh:mm:ss, indicating the 
				time from midnight, where:
				hh = hours (00 to 23)
				mm = minutes (00 to 59)
				ss = seconds (00 to 59)"
			::= { cdd564Util 5 }
		
		cdd564CircuitIDTable OBJECT-TYPE
			SYNTAX SEQUENCE OF Cdd564CircuitIDEntry
			MAX-ACCESS not-accessible
			STATUS current
			DESCRIPTION
				"The table for Circuit IDs (Per Demod)."
			::= { cdd564Util 6 }
		
		cdd564CircuitIDEntry OBJECT-TYPE
			SYNTAX Cdd564CircuitIDEntry
			MAX-ACCESS not-accessible
			STATUS current
			DESCRIPTION
				"The entry for the circuit ID table."
			INDEX { cdd564CircuitIDIndex }
			::= { cdd564CircuitIDTable 1 }
		
		Cdd564CircuitIDEntry ::=
			SEQUENCE { 
				cdd564CircuitIDIndex
					INTEGER,
				cdd564CircuitID
					DisplayString
			 }

		cdd564CircuitIDIndex OBJECT-TYPE
			SYNTAX INTEGER (1..4)
			MAX-ACCESS read-only
			STATUS current
			DESCRIPTION
				"The index for the Demodulator."
			::= { cdd564CircuitIDEntry 1 }
		
		cdd564CircuitID OBJECT-TYPE
			SYNTAX DisplayString
			MAX-ACCESS read-write
			STATUS current
			DESCRIPTION
				"Sets or queries the user-defined Circuit 
				ID string, which is a fixed length of 
				24 characters.
				
				Valid characters include: 
				Space ( ) * + - , . / 0 thru 9 and A thru Z."
			::= { cdd564CircuitIDEntry 2 }
		
		cdd564Notifications OBJECT IDENTIFIER ::= { cdd564 2 }
		
		cdd564NotificationsPrefix OBJECT IDENTIFIER ::= { cdd564Notifications 0 }
		
		cdd564UnitAlarmNotification NOTIFICATION-TYPE
			OBJECTS { cdd564UnitAlarm }
			STATUS current
			DESCRIPTION
				"Trap for Unit alarms."
			::= { cdd564NotificationsPrefix 1 }
		
		cdd564RxAlarmNotification NOTIFICATION-TYPE
			OBJECTS { cdd564RxMonitorIndex, cdd564RxAlarm }
			STATUS current
			DESCRIPTION
				"Trap for Rx alarms."
			::= { cdd564NotificationsPrefix 2 }
		
		cdd564LNBAlarmNotification NOTIFICATION-TYPE
			OBJECTS { cdd564LNBMonitorIndex, cdd564LNBAlarm }
			STATUS current
			DESCRIPTION
				"Trap for LNB alarms."
			::= { cdd564NotificationsPrefix 3 }
		
		cdd564Conformance OBJECT IDENTIFIER ::= { cdd564 3 }
		
		cdd564Groups OBJECT IDENTIFIER ::= { cdd564Conformance 1 }
		
		cdd564ObjectsGroup OBJECT-GROUP
			OBJECTS { cdd564AccessListIndex, cdd564AccessIPAddress, cdd564AccessSubnetMaskLength, cdd564AccessListEnforcement, cdd564PingReply, 
				cdd564Telnet, cdd564IGMP, cdd564ForwardMulticasts, cdd564FeatureIndex, cdd564HeaderCompression, 
				cdd564WorkingMode, cdd5643xDESRxKeyIndex, cdd5643xDESRxKey1, cdd5643xDESRxKey2, cdd5643xDESRxKey3, 
				cdd5643xDESRxKey4, cdd5643xDESRxKey5, cdd5643xDESRxKey6, cdd5643xDESRxKey7, cdd5643xDESRxKey8, 
				cdd564SMTPServerIPAddress, cdd564SMTPDomain, cdd564SMTPUserName, cdd564SNMPTrapDestinationIPAddress, cdd564SNMPTrapCommunity, 
				cdd564SNMPTrapVersion, cdd564SNMPAuthenticationFailureCommunity, cdd564SNMPAuthenticationFailureIPAddress, cdd564SNMPTrapDestinationIPAddress2, cdd564MACAddress, 
				cdd564EthernetSpeed, cdd564IPAddress, cdd564SubnetMaskLen, cdd564HDLCAddressMode, cdd564HDLCAddressIndex, 
				cdd564HDLCAddress1, cdd564HDLCAddress2, cdd564HDLCAddress3, cdd564HDLCAddress4, cdd564RouteIndex, 
				cdd564RouteName, cdd564RouteDestAddress, cdd564RouteDestMaskLen, cdd564RouteNextHopAddress, cdd564RouteMulticast, 
				cdd564RouteInterface, cdd564RouteRowStatus, cdd564IGMPQueryPeriod, cdd564IGMPMaxResponseTime, cdd564IGMPMaxMissBeforeLeavingGroup, 
				cdd564IGMPIndex, cdd564IGMPTTL, cdd564IGMPClientState, cdd564IGMPSrc, cdd564IGMPGroupIPAddress, 
				cdd564BootInfo, cdd564Bulk1Info, cdd564Bulk2Info, cdd564FPGARx1Info, cdd564FPGARx2Info, 
				cdd564BootImage, cdd564UpgradeImage, cdd564ParamImage, cdd564SaveParamToFlash, cdd564ReloadParamFromFlash, 
				cdd564RestoreFactoryDefaults, cdd564Reboot, cdd564TotalPacketsToEthernet, cdd564TotalUnicastsToEthernet, cdd564TotalMulticastsToEthernet, 
				cdd564TotalBroadcastsToEthernet, cdd564TotalPacketsFromEthernet, cdd564TotalPacketsFromSatellite, cdd564TotalPacketsFromEndstation, cdd564TotalPacketsToEndstation, 
				cdd564IGMPPacketsReceived, cdd564IPOptionPacketsReceived, cdd564TotalDroppedPackets, cdd564DroppedPacketsBadIPHeader, cdd564DroppedPacketsBadBufferLength, 
				cdd564DroppedPacketsBadIPVersion, cdd564DroppedPacketsTTLExpired, cdd564DroppedPacketsNoRoute, cdd564DroppedPacketsNoARPEntry, cdd564DroppedPacketsFilteredMulticast, 
				cdd564DroppedPacketsMulticastDisableGroup, cdd564DroppedPacketsFiltered, cdd564DroppedPacketsRouterQueueFull, cdd564IPRoutingClearCounters, cdd564EtherTxGoodFrames, 
				cdd564EtherTxMaxCollisions, cdd564EtherTxLateCollisions, cdd564EtherTxDMAUnderrun, cdd564EtherTxLostCarrierSense, cdd564EtherTxDeferred, 
				cdd564EtherTxSingleCollisions, cdd564EtherTxMultipleCollisions, cdd564EtherTxTotalCollisions, cdd564EtherTxFlowControlPauseFrames, cdd564EtherRxGoodFrames, 
				cdd564EtherRxCRCErrorFrames, cdd564EtherRxAllignmentErrors, cdd564EtherRxResourceErrors, cdd564EtherRxFIFOOverrunErrors, cdd564EtherRxCollisionDetectErrors, 
				cdd564EtherRxShortFrames, cdd564EtherRxFlowControlPauseFrames, cdd564EthernetClearCounters, cdd564RxStatsIndex, cdd564RxGoodFrames, 
				cdd564RxHeaderBytes, cdd564RxPayloadBytes, cdd564RxBadHDLCAddressErrors, cdd564RxPktProcCRCErrors, cdd564RxAbortOctetErrors, 
				cdd564RxOverrunErrors, cdd564RxHDLCCRCErrors, cdd564RxInvalidFlowIDErrors, cdd564RxSARReassembleErrors, cdd564RxHeaderDecompressionErrors, 
				cdd564RxMemoryAlignmentErrors, cdd564RxCRCErrors, cdd564SatelliteClearCounters, cdd564RxTableIndex, cdd564RxFEC, 
				cdd564RxDemodulation, cdd564RxCodeRate, cdd564RxDataRate, cdd564RxFrequency, cdd564RxAcquisitionSweepWidth, 
				cdd564RxDescrambling, cdd564RxBufferSize, cdd546RxSpectrumInversion, cdd564RxDataInversion, cdd564RxEbNoAlarmPoint, 
				cdd564RxRecenterBuffer, cdd564RxSymbolRate, cdd564AlarmMaskIndex, cdd564AGCAlarmMask, cdd564EbNoAlarmMask, 
				cdd564LNBAlarmMask, cdd564ReferenceFrequency, cdd564InternalReferenceAdjust, cdd564LNBIndex, cdd564LNBDCPower, 
				cdd564LNB10MHzReference, cdd564LNBHighCurrentLimit, cdd564LNBLOFrequency, cdd564LNBLOMix, cdd564SerialNumber, 
				cdd564SoftwareRevision, cdd564ModelNumber, cdd564UnitAlarm, cdd564Temperature, cdd564RxMonitorIndex, 
				cdd564RxAlarm, cdd564RxEbNo, cdd564RxSignalLevel, cdd564RxFreqOffset, cddRxBERMultiplier, 
				cdd564LNBMonitorIndex, cdd564LNBAlarm, cdd564LNBCurrent, cdd564LNBVoltage, cdd564LNBTerminalRxFreq, 
				cdd564EventDemod, cdd564EventIndex, cdd564EventDescription, cdd564ClearAllStoredEvents, cdd564StatisticDemod, 
				cdd564StatisticIndex, cdd564StatisticDate, cdd564StatisticTime, cdd564StatisticAvgEbNo, cdd564StatisticMinEbNo, 
				cdd564StoredStatisticsConfigIndex, cdd564StatisticsSampleInterval, cdd564ClearAllStoredStatistics, cdd564RTCDate, cdd564RTCTime, 
				cdd564CircuitIDIndex, cdd564CircuitID, cdm564LLNBLowCurrentLimit }
			STATUS current
			DESCRIPTION
				"CDD-564 Objects Group."
			::= { cdd564Groups 1 }
		
		cdd564NotificationsGroup NOTIFICATION-GROUP
			NOTIFICATIONS { cdd564UnitAlarmNotification, cdd564RxAlarmNotification, cdd564LNBAlarmNotification }
			STATUS current
			DESCRIPTION
				"CDD-564 Trap Group."
			::= { cdd564Groups 2 }
		
		cdd564Compliances OBJECT IDENTIFIER ::= { cdd564Conformance 2 }
		
		cdd564Compliance MODULE-COMPLIANCE
			STATUS current
			DESCRIPTION
				"CDD-564 Compliance."
			MODULE -- this module
				MANDATORY-GROUPS { cdd564ObjectsGroup, cdd564NotificationsGroup }
			::= { cdd564Compliances 1 }
		
	
	END

--
-- CDD-564.my
--
