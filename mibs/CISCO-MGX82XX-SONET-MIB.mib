-- LAST-UPDATED "200206260000Z"
CISCO-MGX82XX-SONET-MIB DEFINITIONS ::= BEGIN

 IMPORTS
 Counter,Gauge             FROM RFC1155-SMI
 cwsonetObjects            FROM BASIS-MIB 
 OBJECT-TYPE	         FROM RFC-1212
 DisplayString	         FROM RFC1213-MIB;
-- --------------------------------------------------------------
--
-- Group "SONET"
-- This group standard within the scope of the BASIS system
--
-- --------------------------------------------------------------

-- SONET Line definition
-- sonet object is imported from BASIS-MIB its
-- OBJECT IDENTIFIER is { basisLines 4 }

-- groups in SONET lines
-- This group consists of 7 tables:
-- 	sonetConfig
-- 	sonetAlarmConfig
-- 	sonetAlarm
-- 	sonetCounters 
-- sonet                 OBJECT IDENTIFIER ::= { basisLines 6 }

sonetConfig           	OBJECT IDENTIFIER ::= { cwsonetObjects 1 }
cwsonetMedium             OBJECT IDENTIFIER ::= { cwsonetObjects 2 }
cwsonetSection            OBJECT IDENTIFIER ::= { cwsonetObjects 3 }
cwsonetLine               OBJECT IDENTIFIER ::= { cwsonetObjects 4 }
cwsonetPath               OBJECT IDENTIFIER ::= { cwsonetObjects 5 }


-- todo sonetFarEndLine	OBJECT IDENTIFIER ::= { cwsonetObjects 5 }
-- todo sonetPath		OBJECT IDENTIFIER ::= { cwsonetObjects 6 }
-- todo sonetFarEndPath	OBJECT IDENTIFIER ::= { cwsonetObjects 7 }

-- sonetAlarmConfig      OBJECT IDENTIFIER ::= { cwsonetObjects 2 }
-- sonetAlarm            OBJECT IDENTIFIER ::= { cwsonetObjects 3 }
-- sonetCounter          OBJECT IDENTIFIER ::= { cwsonetObjects 4 }
-- --------------------------------------------------------------
-- 
-- sonetConfig group
-- This group contains sonet line configuration table
-- 
-- --------------------------------------------------------------
	sonetConfigTable OBJECT-TYPE
		SYNTAX	SEQUENCE OF SonetConfigEntry
		ACCESS	not-accessible
		STATUS	mandatory
		DESCRIPTION
		"The SONET Configuration table. There is one row for each
		 SONET port in the BASIS system. The table size (number of 
		 rows) is given by the value of sonetLineNumOfValidEntries."
		::= { sonetConfig 1 }

	sonetConfigEntry OBJECT-TYPE
		SYNTAX	SonetConfigEntry
		ACCESS	not-accessible
		STATUS	mandatory
		DESCRIPTION
			"An entry in the SONET Configuration table."
		INDEX	{ sonetLineNum }
		::= { sonetConfigTable 1 }

	SonetConfigEntry ::=
		SEQUENCE {
			sonetLineNum               INTEGER,
			sonetLineType              INTEGER,
			sonetLineLoopbackCommand   INTEGER,
			sonetHCSmasking            INTEGER,
			sonetPayloadScrambling     INTEGER,
			sonetFrameScrambling       INTEGER,
            sonetLineEnable            INTEGER,

-- added for POP1SRME
			sonetLineXmtClkSrc         INTEGER,
			sonetRDIVType              INTEGER,
			sonetRDIPType              INTEGER,
			sonetTributaryType         INTEGER,
			sonetTributaryMappingType  INTEGER,
			sonetTributaryFramingFormat INTEGER,
			sonetSignallingTransportMode    INTEGER,
			sonetTributaryGroupingType   INTEGER
-- end of added for POP1SRME
         		}

	sonetLineNum OBJECT-TYPE
		SYNTAX	INTEGER (1..4)
		ACCESS	read-only
		STATUS	mandatory
		DESCRIPTION
			"This object is the identifier of a SONET
			 Interface on a managed device.
             For MGX8850(For example PXM1 Module): 
                OC-3 : sonetLineNum in a range 1..4
                OC-12: sonetLineNum = 1 is the ONLY valid number
             For Other: sonetLineNum = 1 is the ONLY valid number"
		::= { sonetConfigEntry 1 }

	sonetLineType OBJECT-TYPE
		SYNTAX  INTEGER {
				sonetSts3c(1),
				sonetStm1(2),
				sonetSts12c(3),
				sonetStm4(4),
				sonetSts48c(5),
				sonetStm16(6),
				sonetSts192c(7),
				sonetStm64(8),
				sonetSts3(9)
				}
		ACCESS  read-write
		STATUS  mandatory
		DESCRIPTION
			"This variable indicates the cell framing.
			Defaults to Sts-3c
			"
		::= { sonetConfigEntry 2 }

	sonetLineLoopbackCommand OBJECT-TYPE
		SYNTAX  INTEGER {
				sonetNoLoop(1),
				sonetRemoteLineLoop(2),
				sonetLocalLineLoop(3)
			}
                 ACCESS  read-write
                 STATUS  mandatory
                 DESCRIPTION
			"This variable represents the loopback configuration
			 of the SONET interface.

			 The values mean:

			 sonetNoLoop
				Not in the loopback state.  A device that is
				not capable of performing a loopback on
				the interface shall always return this as
				it's value.

			 sonetRemoteLineLoop
            Near End loops back Remote data

			 sonetLocalLineLoop
            Near End loops back Local data."

		::= { sonetConfigEntry 3 }

	sonetHCSmasking OBJECT-TYPE
		SYNTAX  INTEGER {
				disable(1),
				enable(2)
				}
		ACCESS  read-write
		STATUS  mandatory
		DESCRIPTION
			"HCS masking. Defaults to enable.
			"
		::= { sonetConfigEntry 4 }

	sonetPayloadScrambling OBJECT-TYPE
		SYNTAX  INTEGER {
				disable(1),
				enable(2)
				}
		ACCESS  read-write
		STATUS  mandatory
		DESCRIPTION
			"STS3c or STM-1 payload scrambling. Defaults to enable.
			"
		::= { sonetConfigEntry 5 }

	sonetFrameScrambling OBJECT-TYPE
		SYNTAX  INTEGER {
				disable(1),
				enable(2)
				}
		ACCESS  read-write
		STATUS  mandatory
		DESCRIPTION
			"STS3c or STM-1 frame scrambling. Defaults to enable.
			"
		::= { sonetConfigEntry 6 }

	sonetLineEnable OBJECT-TYPE
		SYNTAX  INTEGER {
				enable(1),
				disable(2)
				}
		ACCESS  read-write
		STATUS  mandatory
		DESCRIPTION
			"This variable indicates if the line is enabled or not
             defaults to disable
			"
		::= { sonetConfigEntry 7 }

-- Added for POP1SRME
        sonetLineXmtClkSrc OBJECT-TYPE
		SYNTAX  INTEGER {
                                backplaneClk(1),
                                recoverClk(2),
                                localClk(3)
                                }
		ACCESS  read-write
		STATUS  mandatory
		DESCRIPTION
                      "This represents the type of transmit clock source.
                         backplaneClk: clock source is from the controller card, 
			     transmitted via the backplane to the service module.
			 recoverClk: clock is recovered from the received signal. 
			 localClk: clock is from a local oscillator on the card.
					 Default is backplaneClk."
         
		::= { sonetConfigEntry 8 }

        sonetRDIVType OBJECT-TYPE
		SYNTAX  INTEGER {
                                onebit(1),
                                threebit(3)
				}
		ACCESS  read-write
		STATUS  mandatory
		DESCRIPTION
			"This variable represents the type of RDI-V
                         sent by this NE to remote NE.

			onebit: use 1 bit RDI-V. Compatible with older equipment.
			threebit: use 3 bit, enhanced RDI-V.

             Defaults to onebit.
			"
		::= { sonetConfigEntry 9 }

        sonetRDIPType OBJECT-TYPE
		SYNTAX  INTEGER {
                                onebit(1),
                                threebit(3)
				}
		ACCESS  read-write
		STATUS  mandatory
		DESCRIPTION
			"This variable represents the type of RDI-P
                         sent by this NE to remote NE.

			onebit: use 1 bit RDI-P. Compatible with older equipment.
			threebit: use 3 bit, enhanced RDI-P.

             Defaults to onebit.
			"
		::= { sonetConfigEntry 10 }

        sonetTributaryType OBJECT-TYPE
		SYNTAX  INTEGER {
                                vt15vc11(1),
				vt2vc12(2)
				}
		ACCESS  read-write
		STATUS  mandatory
		DESCRIPTION
			"Type of tributary carried within the
			 Sonet/Sdh signal.

			vt15vc11: carries T1 signals (VT15 or VC11)
			vt2vc12:  carries E1 signals (VT2 or VC12)

			Default is vt15vc11 for Sonet interfaces and
                       vt2vc12  for SDH   interfaces.
			"
		::= { sonetConfigEntry 11 }

        sonetTributaryMappingType OBJECT-TYPE
		SYNTAX  INTEGER {
				asynchronous(1),
                                byteSynchronous(2)
				}
		ACCESS  read-write
		STATUS  mandatory
		DESCRIPTION
			"Type of VT/VC mapping.

			asynchronous: In this mode, the channel structure 
			of the DS1/E1 is neither visible nor preserved.

			byteSynchronous: In this mode, the DS0 channels inside
			the VC/VT can be found and extracted.

			Default is asynchronous.
			"
		::= { sonetConfigEntry 12 }

        sonetTributaryFramingFormat OBJECT-TYPE
		SYNTAX  INTEGER {
                                notApplicable(1),
                                sf(2),
                                esf(3)
                                }
		ACCESS  read-write
		STATUS  mandatory
		DESCRIPTION
                        "Type of vt framing format. Is applicable
			only in byte-sync mapping mode for T1 tributaries.

                        notApplicable: if VT mapping is not byte-sync.
			sf: superframe format.
			esf: extended superframe format.

            Default is esf if sonetTributaryMappingType is set to
            byteSynchronous, else the default is notApplicable.
			"
		::= { sonetConfigEntry 13 }

        sonetSignallingTransportMode OBJECT-TYPE
		SYNTAX  INTEGER {
                                notApplicable(1),
				signallingTransferMode(2),
				clearMode(3)
				}
		ACCESS  read-write
		STATUS  mandatory
		DESCRIPTION
			"The mode used to transport DS0 signalling
                         information for T1 byte-sync mapping.

                        notApplicable: if byte-sync mapping is not used.

                        signallingTransferMode: the robbed bit signalling
                          is transferred into the S bits of the VT header
			  and framing bit is discarded.

			clearMode: only the framing bit is transferred to
				VT header. The signalling bits are left intact
				in the VT payload.

			Default is signallingTransferMode if sonetTributaryMappingType
            is set to byteSynchronous, else the default is notApplicable.
			"
		::= { sonetConfigEntry 14 }

        sonetTributaryGroupingType OBJECT-TYPE
		SYNTAX  INTEGER {
                                notApplicable(1),
				au3Grouping(2),
				au4Grouping(3)
				}
		ACCESS  read-write
		STATUS  mandatory
		DESCRIPTION
			"This variable indicates the method used to group 
             VCs into an STM-1 signal. Applicable only to SDH.

            notApplicable: for sonet interfaces.
			au3Grouping: STM-1 <- AU-3 <- TUG-2 <- TU-12 <- VC12 or 
			             STM-1 <- AU-3 <- TUG-2 <- TU-11 <- VC11.  
			au4Grouping: STM-1 <- AU-4 <- TUG-3 <- TUG-2 <- TU-12 <- VC12 or  
			             STM-1 <- AU-4 <- TUG-3 <- TUG-2 <- TU-11 <- VC11.

            Defaults to au3Grouping for SDH interfaces and notApplicable for
            Sonet interfaces.
			"
		::= { sonetConfigEntry 15 }

-- End of added for POP1SRME 

	sonetConfigNumOfValidEntries OBJECT-TYPE
		SYNTAX	INTEGER
		ACCESS	read-only
		STATUS	mandatory
		DESCRIPTION
		"The number of SONET configuration entries (regardless
		 of their current configuration) in the sonetConfigTable."
		::= { sonetConfig 2 }
 
          -- the SONET/SDH Medium group

          -- SONET/SDH interfaces for some applications may be
          -- electrical interfaces and not optical interfaces.
          -- This group handles the configuration information for
          -- both optical SONET/SDH interfaces and electrical
          -- SONET/SDH interfaces.

          cwSonetMediumTable OBJECT-TYPE
              SYNTAX  SEQUENCE OF CwSonetMediumEntry
              ACCESS  not-accessible
              STATUS  mandatory
              DESCRIPTION
		" Sonet medium table parameters" 
              ::= { cwsonetMedium 1 }

          cwSonetMediumEntry OBJECT-TYPE
              SYNTAX  CwSonetMediumEntry
              ACCESS  not-accessible
              STATUS  mandatory
              DESCRIPTION
                 "An entry in the SONET/SDH Medium table."
              INDEX	{ sonetLineNum }
               ::= { cwSonetMediumTable 1 }

          CwSonetMediumEntry ::=
              SEQUENCE {
                   cwSonetMediumType               INTEGER,
                   cwSonetMediumTimeElapsed        INTEGER,
                   cwSonetMediumValidIntervals     INTEGER,
                   cwSonetMediumLineCoding         INTEGER,
                   cwSonetMediumLineType           INTEGER,
                   cwSonetMediumCircuitIdentifier  DisplayString
              }


          cwSonetMediumType OBJECT-TYPE
              SYNTAX  INTEGER  {
                         sonet(1),
                         sdh(2)
                      }
              ACCESS  read-only
              STATUS  mandatory
              DESCRIPTION
                 "This variable identifies whether a SONET
                 or a SDH signal is used across this interface."
              ::= { cwSonetMediumEntry 1 }

          cwSonetMediumTimeElapsed OBJECT-TYPE
              SYNTAX  INTEGER (1..900)
              ACCESS  read-only
              STATUS  mandatory
              DESCRIPTION
                 "The number of seconds, including partial
                 seconds, that have elapsed since the beginning of
                 the mandatory error-measurement period."
              ::= { cwSonetMediumEntry 2 }

          cwSonetMediumValidIntervals OBJECT-TYPE
              SYNTAX  INTEGER (0..96)
              ACCESS  read-only
              STATUS  mandatory
              DESCRIPTION
                 "The number of previous intervals for which valid
                 data has been stored.  A SONET device must support
                 at least n intervals.
                 The minimum value of n is 4.
                 The default of n is 32.
                 The maximum value of n is 96.
                 The value of this object will be n unless
                 the device was brought online within the last
                 (nx15) minutes, in which case the value will be the
                 number of complete 15 minute intervals the device has
                 been online."
              ::= { cwSonetMediumEntry 3 }

          cwSonetMediumLineCoding OBJECT-TYPE
              SYNTAX  INTEGER {
                          sonetMediumOther(1),
                          sonetMediumB3ZS(2),
                          sonetMediumCMI(3),
                          sonetMediumNRZ(4),
                          sonetMediumRZ(5)
                      }
              ACCESS  read-only
              STATUS  mandatory
              DESCRIPTION
                 "This variable describes the line coding for
                 this interface. The B3ZS and CMI are used for
                 electrical SONET/SDH signals (STS-1 and STS-3).
                 The Non-Return to Zero (NRZ) and the Return
                 to Zero are used for optical SONET/SDH signals."
              ::= { cwSonetMediumEntry 4 }

          cwSonetMediumLineType OBJECT-TYPE
              SYNTAX  INTEGER {
                          sonetOther(1),
                          sonetShortSingleMode(2),
                          sonetLongSingleMode(3),
                          sonetMultiMode(4),
                          sonetCoax(5),
                          sonetUTP(6)
                      }
              ACCESS  read-only
              STATUS  mandatory
              DESCRIPTION
                 "This variable describes the line type for
                 this interface. The line types are
                 Short and Long Range
                 Single Mode fiber or Multi-Mode fiber interfaces,
                 and coax and UTP for electrical interfaces.  The
                 value sonetOther should be used when the Line Type is
                 not one of the listed values."
              ::= { cwSonetMediumEntry 5 }

          cwSonetMediumCircuitIdentifier OBJECT-TYPE
              SYNTAX  DisplayString (SIZE (0..255))
              ACCESS  read-only
              STATUS  mandatory
              DESCRIPTION
                 "This variable contains the transmission
                 vendor's circuit identifier, for the
                 purpose of facilitating troubleshooting."
              ::= { cwSonetMediumEntry 6 }


          -- the SONET/SDH Section group

          -- this group consists of 5 tables:
          -- - the SONET/SDH Section Current Table
	  -- - the SONET/SDH Section Current Day Table
          -- - the SONET/SDH Section Interval Table
          -- - the SONET/SDH Section Alarm Config Table
	  -- - the SONET/SDH Section Counter Table 	

          -- the SONET/SDH Section Current Table

          -- The SONET/SDH Section
          -- current table contains various statistics
          -- being collected for the current 15 minute interval.

          cwSonetSectionCurrentTable OBJECT-TYPE
              SYNTAX  SEQUENCE OF CwSonetSectionCurrentEntry
              ACCESS  not-accessible
              STATUS  mandatory
              DESCRIPTION
                 "The SONET/SDH Section Current table."
               ::= { cwsonetSection 1 }

          cwSonetSectionCurrentEntry OBJECT-TYPE
              SYNTAX  CwSonetSectionCurrentEntry
              ACCESS  not-accessible
              STATUS  mandatory
              DESCRIPTION
                 "An entry in the SONET/SDH Section Current table."
             INDEX	{ cwSonetSectionCurrentLineNum }
               ::= { cwSonetSectionCurrentTable 1 }

          CwSonetSectionCurrentEntry ::=
              SEQUENCE {
                  cwSonetSectionCurrentLineNum	  	INTEGER,
                  cwSonetSectionCurrentStatus   INTEGER,
                  cwSonetSectionCurrentValidFlag  	INTEGER,
                  cwSonetSectionCurrent15minTimeElapsed  	INTEGER,
                  cwSonetSectionCurrentESs      Counter,
                  cwSonetSectionCurrentSESs     Counter,
                  cwSonetSectionCurrentSEFSs    Counter,
                  cwSonetSectionCurrentCVs      Counter,
                  cwSonetSectionCurrentClrButton   	INTEGER
              }

         cwSonetSectionCurrentLineNum OBJECT-TYPE
                  SYNTAX INTEGER (1..1)
                  ACCESS read-only
                  STATUS mandatory
                  DESCRIPTION
                        " line number.
                          There are Max 1 line Num
                        "
                  ::= {cwSonetSectionCurrentEntry 1}

          cwSonetSectionCurrentStatus OBJECT-TYPE
              SYNTAX  INTEGER(1..6)
              ACCESS  read-only
              STATUS  mandatory
              DESCRIPTION
                 "This variable indicates the status of the sonet section layer.
                 The cwSonetSectionCurrentStatus is a bit map represented
                 as a sum, therefore, it can represent multiple defects
                 simultaneously.
                 The sonetSectionNoDefect should be set if and only if
                 no other flag is set.

                 The various bit positions are:
                    bit 1 = sonetSectionNoDefect
                    bit 2 = sonetSectionLOS
                    bit 3 = sonetSectionLOF
                 "
               ::= { cwSonetSectionCurrentEntry 2 }

         cwSonetSectionCurrentValidFlag OBJECT-TYPE
              SYNTAX  INTEGER  {
			  notValid(1),
			  valid(2)
			}
              ACCESS  read-only
              STATUS  mandatory
              DESCRIPTION
                 "Indicates if the current 15min bucket is valid or not.
 		 "
               ::= { cwSonetSectionCurrentEntry 3 }
 
         cwSonetSectionCurrent15minTimeElapsed OBJECT-TYPE 
              SYNTAX  INTEGER  (1..900)
              ACCESS  read-only 
              STATUS  mandatory  
              DESCRIPTION 
                 "The number of seconds, including partial seconds,
		  that have elapsed since the beginning of the 15min 
		  error-measurement period.
                 " 
               ::= { cwSonetSectionCurrentEntry 4 } 

          cwSonetSectionCurrentESs OBJECT-TYPE
              SYNTAX  Counter
              ACCESS  read-only
              STATUS  mandatory
              DESCRIPTION
                 "The counter associated with the number of Errored
                 Seconds encountered by a SONET/SDH
                 Section in the current 15 minute interval."
               ::= { cwSonetSectionCurrentEntry 5 }

          cwSonetSectionCurrentSESs OBJECT-TYPE
              SYNTAX  Counter
              ACCESS  read-only
              STATUS  mandatory
              DESCRIPTION
                 "The counter associated with the number of
                 Severely Errored Seconds
                 encountered by a SONET/SDH Section in the current 15
                 minute interval."
               ::= { cwSonetSectionCurrentEntry 6 }

          cwSonetSectionCurrentSEFSs OBJECT-TYPE
              SYNTAX  Counter
              ACCESS  read-only
              STATUS  mandatory
              DESCRIPTION
                 "The counter associated with the number of
                 Severely Errored Framing Seconds
                 encountered by a SONET/SDH Section in the current
                 15 minute interval."
              ::= { cwSonetSectionCurrentEntry 7 }

          cwSonetSectionCurrentCVs OBJECT-TYPE
              SYNTAX  Counter
              ACCESS  read-only
              STATUS  mandatory
              DESCRIPTION
                 "The counter associated with the number of Coding
                 Violations encountered by a
                 SONET/SDH Section in the current 15 minute interval."
               ::= { cwSonetSectionCurrentEntry 8 }

         cwSonetSectionCurrentClrButton OBJECT-TYPE
              SYNTAX  INTEGER {
				noAction(1),
				clear(2)
			}
              ACCESS  read-write
              STATUS  mandatory
              DESCRIPTION
                 "Clears all the Section's Current15min counters.
		 "
               ::= { cwSonetSectionCurrentEntry 9 }

          -- being collected for the CurrentDay day interval.

          sonetSectionCurrentDayTable OBJECT-TYPE
              SYNTAX  SEQUENCE OF SonetSectionCurrentDayEntry
              ACCESS  not-accessible
              STATUS  mandatory
              DESCRIPTION
                 "The SONET/SDH Section CurrentDay table."
               ::= { cwsonetSection 2 }

          sonetSectionCurrentDayEntry OBJECT-TYPE
              SYNTAX  SonetSectionCurrentDayEntry
              ACCESS  not-accessible
              STATUS  mandatory
              DESCRIPTION
                 "An entry in the SONET/SDH Section CurrentDay table."
               INDEX	{ sonetSectionCurrentDayLineNum }               
		::= { sonetSectionCurrentDayTable 1 }

          SonetSectionCurrentDayEntry ::=
              SEQUENCE {
		  sonetSectionCurrentDayLineNum INTEGER,
                  sonetSectionCurrentDayValidFlag  	INTEGER,
                  sonetSectionCurrentDayESs      Counter,
                  sonetSectionCurrentDaySESs     Counter,
                  sonetSectionCurrentDaySEFSs    Counter,
                  sonetSectionCurrentDayCVs      Counter,
                  sonetSectionCurrentDayClrButton     INTEGER
              }

         sonetSectionCurrentDayLineNum OBJECT-TYPE
                  SYNTAX INTEGER (1..1)
                  ACCESS read-only
                  STATUS mandatory
                  DESCRIPTION
                        " line number.
                          BNM has one line
                        "
                  ::= {sonetSectionCurrentDayEntry 1}

         sonetSectionCurrentDayValidFlag OBJECT-TYPE
              SYNTAX  INTEGER  {
                          notValid(1),
                          valid(2)
                        }
              ACCESS  read-only
              STATUS  mandatory
              DESCRIPTION
                 "Indicates if the current day bucket is valid or not.
                 "
               ::= { sonetSectionCurrentDayEntry 2 }

          sonetSectionCurrentDayESs OBJECT-TYPE
              SYNTAX  Counter
              ACCESS  read-only
              STATUS  mandatory
              DESCRIPTION
                 "The counter associated with the number of Errored
                 Seconds encountered by a SONET/SDH
                 Section in the CurrentDay one day interval."
               ::= { sonetSectionCurrentDayEntry 3 }

          sonetSectionCurrentDaySESs OBJECT-TYPE
              SYNTAX  Counter
              ACCESS  read-only
              STATUS  mandatory
              DESCRIPTION
                 "The counter associated with the number of
                 Severely Errored Seconds
                 encountered by a SONET/SDH Section in the CurrentDay 
                 minute interval."
               ::= { sonetSectionCurrentDayEntry 4 }

          sonetSectionCurrentDaySEFSs OBJECT-TYPE
              SYNTAX  Counter
              ACCESS  read-only
              STATUS  mandatory
              DESCRIPTION
                 "The counter associated with the number of
                 Severely Errored Framing Seconds
                 encountered by a SONET/SDH Section in the CurrentDay
                 one day interval."
              ::= { sonetSectionCurrentDayEntry 5 }

          sonetSectionCurrentDayCVs OBJECT-TYPE
              SYNTAX  Counter
              ACCESS  read-only
              STATUS  mandatory
              DESCRIPTION
                 "The counter associated with the number of Coding
                 Violations encountered by a
                 SONET/SDH Section in the CurrentDay one day interval."
               ::= { sonetSectionCurrentDayEntry 6 }


         sonetSectionCurrentDayClrButton OBJECT-TYPE
              SYNTAX  INTEGER {
                                noAction(1),
                                clear(2)
                        }
              ACCESS  read-write
              STATUS  mandatory
              DESCRIPTION
                 "Clears all the Section's Current Day counters.
                 "
               ::= { sonetSectionCurrentDayEntry 7 }

          -- the SONET/SDH Section Interval Table

          -- The SONET/SDH Section Interval Table
          -- contains various statistics
          -- collected by each system over a maximum
          -- of the previous 24 hours of
          -- operation.  The past 24 hours may be broken into 96
          -- completed 15 minute intervals.
          -- A system is required to store at
          -- least 4 completed 15 minute interval.
          -- The default value is 32 intervals.

          cwSonetSectionIntervalTable OBJECT-TYPE
              SYNTAX  SEQUENCE OF CwSonetSectionIntervalEntry
              ACCESS  not-accessible
              STATUS  mandatory
              DESCRIPTION
                 "The SONET/SDH Section Interval table."
               ::= { cwsonetSection 3 }

          cwSonetSectionIntervalEntry OBJECT-TYPE
              SYNTAX  CwSonetSectionIntervalEntry
              ACCESS  not-accessible
              STATUS  mandatory
              DESCRIPTION
                 "An entry in the SONET/SDH Section Interval table."
               INDEX	{ cwSonetSectionIntervalLineNum,
                        cwSonetSectionIntervalNumber }
               ::= { cwSonetSectionIntervalTable 1 }

          CwSonetSectionIntervalEntry ::=
              SEQUENCE {
		   cwSonetSectionIntervalLineNum INTEGER,
                   cwSonetSectionIntervalNumber  INTEGER,
                   cwSonetSectionIntervalValidFlag  	INTEGER,
                   cwSonetSectionIntervalESs     Counter,
                   cwSonetSectionIntervalSESs    Counter,
                   cwSonetSectionIntervalSEFss   Counter,
                   cwSonetSectionIntervalCVs     Counter
              }

          cwSonetSectionIntervalLineNum OBJECT-TYPE
                  SYNTAX INTEGER (1..1)
                  ACCESS read-only
                  STATUS mandatory
                  DESCRIPTION
                        " line number.
                          BNM has one line
                        "
                  ::= {cwSonetSectionIntervalEntry 1}

          cwSonetSectionIntervalNumber OBJECT-TYPE
              SYNTAX  INTEGER(1..96)
              ACCESS  read-only
              STATUS  mandatory
              DESCRIPTION
                "A number between 1 and 96, which identifies the
                interval for which the set of statistics is available.
                The interval identified by 1 is the most recently
                completed 15 minute interval,
                and the interval identified
                by N is the interval immediately preceding the
                one identified
                by N-1."
               ::= { cwSonetSectionIntervalEntry 2 }

          cwSonetSectionIntervalValidFlag OBJECT-TYPE
              SYNTAX  INTEGER  {
                          notValid(1),
                          valid(2)
                        }
              ACCESS  read-only
              STATUS  mandatory
              DESCRIPTION
                 "Indicates if the bucket specified by the interval 
		  is valid or not.
                 "
               ::= { cwSonetSectionIntervalEntry 3 }

          cwSonetSectionIntervalESs OBJECT-TYPE
              SYNTAX  Counter
              ACCESS  read-only
              STATUS  mandatory
              DESCRIPTION
                 "The counter associated with the number of
                 Errored Seconds encountered
                 by a SONET/SDH Section in a
                 particular 15-minute interval
                 in the past 24 hours."
               ::= { cwSonetSectionIntervalEntry 4 }

          cwSonetSectionIntervalSESs OBJECT-TYPE
              SYNTAX  Counter
              ACCESS  read-only
              STATUS  mandatory
              DESCRIPTION
                 "The counter associated with the number of
                 Severely Errored Seconds
                 encountered by a SONET/SDH Section in a
                 particular 15-minute interval
                 in the past 24 hours."
              ::= { cwSonetSectionIntervalEntry 5 }

          cwSonetSectionIntervalSEFss OBJECT-TYPE
              SYNTAX  Counter
              ACCESS  read-only
              STATUS  mandatory
              DESCRIPTION
                 "The counter associated with the number of
                 Severely Errored Framing Seconds
                 encountered by a SONET/SDH Section in a
                 particular 15-minute interval
                 in the past 24 hours."
              ::= { cwSonetSectionIntervalEntry 6 }

          cwSonetSectionIntervalCVs OBJECT-TYPE
              SYNTAX  Counter
              ACCESS  read-only
              STATUS  mandatory
              DESCRIPTION
                 "The counter associated with the number of Coding
                 Violations encountered by a
                 SONET/SDH Section in a particular 15-minute interval
                 in the past 24 hours."
              ::= { cwSonetSectionIntervalEntry 7 }

 
-- ------------------------------------------------------------
--
-- Section Alarm Group
--
-- ------------------------------------------------------------
	-- SONET/SDH Section Alarm Group


          sonetSectionAlarmTable OBJECT-TYPE
              SYNTAX  SEQUENCE OF SonetSectionAlarmEntry
              ACCESS  not-accessible
              STATUS  mandatory
              DESCRIPTION
                "The SONET/SDH Section Alarm table."
              ::= { cwsonetSection 4 }

          sonetSectionAlarmEntry OBJECT-TYPE
              SYNTAX  SonetSectionAlarmEntry
              ACCESS  not-accessible
              STATUS  mandatory
              DESCRIPTION
                "An entry in the SONET/SDH Section Alarm table."
              INDEX   { sectionAlarmLineNum }
              ::= { sonetSectionAlarmTable 1 }


          SonetSectionAlarmEntry ::=
              SEQUENCE {
                  sectionAlarmLineNum             		INTEGER,
                  sonetSectionStatisticalAlarmSeverity  	INTEGER,
                  sonetSectionCurrent15minESsThreshold 		INTEGER,
                  sonetSectionCurrentDayESsThreshold 		INTEGER,
                  sonetSectionCurrent15minSESsThreshold 	INTEGER,
                  sonetSectionCurrentDaySESsThreshold 		INTEGER,
                  sonetSectionCurrent15minSEFSsThreshold 	INTEGER,
                  sonetSectionCurrentDaySEFSsThreshold 		INTEGER,
                  sonetSectionCurrent15minCVsThreshold	 	INTEGER,
                  sonetSectionCurrentDayCVsThreshold 		INTEGER,
                  sonetSectionTraceSelection                    INTEGER,
                  sonetSectionTraceToTransmit                   OCTET STRING,
                  sonetSectionTraceToExpect                     OCTET STRING,
                  sonetSectionTraceReceived                     OCTET STRING,
                  sonetSectionStatAlarmStatus               	INTEGER
              }  

          sectionAlarmLineNum OBJECT-TYPE
                  SYNTAX INTEGER (1..1)
                  ACCESS read-only
                  STATUS mandatory
                  DESCRIPTION
                        " line number.
                          BNM has 1 line
                        "
                  ::= {sonetSectionAlarmEntry 1}

          sonetSectionStatisticalAlarmSeverity OBJECT-TYPE 
              SYNTAX  INTEGER {
				minor(1),
				major(2)
			}
              ACCESS  read-write  
              STATUS  mandatory     
              DESCRIPTION 
                 "When any statistical threshold is exceeded.
                 " 
               ::= { sonetSectionAlarmEntry 2 }
  
          sonetSectionCurrent15minESsThreshold OBJECT-TYPE 
              SYNTAX  INTEGER (0..2147483647)  
              ACCESS  read-write  
              STATUS  mandatory     
              DESCRIPTION 
                 "The default is set to 20.
                 " 
               ::= { sonetSectionAlarmEntry 3 }
  
          sonetSectionCurrentDayESsThreshold OBJECT-TYPE  
              SYNTAX  INTEGER (0..2147483647)  
              ACCESS  read-write   
              STATUS  mandatory      
              DESCRIPTION  
                 "The default is set to 200.
                 " 
               ::= { sonetSectionAlarmEntry 4 }
                  
          sonetSectionCurrent15minSESsThreshold OBJECT-TYPE  
              SYNTAX  INTEGER (0..2147483647)  
              ACCESS  read-write   
              STATUS  mandatory      
              DESCRIPTION  
                 "The default is set to 3.
                 " 
               ::= { sonetSectionAlarmEntry 5 }
                  
                  
          sonetSectionCurrentDaySESsThreshold OBJECT-TYPE   
              SYNTAX  INTEGER (0..2147483647)  
              ACCESS  read-write   
              STATUS  mandatory       
              DESCRIPTION      
                 "The default is set to 7.
                 " 
               ::= { sonetSectionAlarmEntry 6 }
                  
          sonetSectionCurrent15minSEFSsThreshold OBJECT-TYPE   
              SYNTAX  INTEGER (0..2147483647)  
              ACCESS  read-write    
              STATUS  mandatory       
              DESCRIPTION   
                 "The default is set to 3. 
                 "  
               ::= { sonetSectionAlarmEntry 7 } 

          sonetSectionCurrentDaySEFSsThreshold OBJECT-TYPE    
              SYNTAX  INTEGER (0..2147483647)   
              ACCESS  read-write    
              STATUS  mandatory        
              DESCRIPTION       
                 "The default is set to 7.
                 "  
               ::= { sonetSectionAlarmEntry 8 } 

          sonetSectionCurrent15minCVsThreshold OBJECT-TYPE    
              SYNTAX  INTEGER (0..2147483647)   
              ACCESS  read-write    
              STATUS  mandatory       
              DESCRIPTION   
                 "The default is set to 25. 
                 "  
               ::= { sonetSectionAlarmEntry 9 } 

          sonetSectionCurrentDayCVsThreshold OBJECT-TYPE     
              SYNTAX  INTEGER (0..2147483647)   
              ACCESS  read-write    
              STATUS  mandatory        
              DESCRIPTION         
                 "The default is set to 250. 
                 "   
               ::= { sonetSectionAlarmEntry 10 }  

          sonetSectionTraceSelection OBJECT-TYPE
              SYNTAX  INTEGER {
                          none(1),
                          sixtyFourBytes(2),
                          sixtyFourBytesCrlf(3),
                          sixteenBytes(4),
                          sixteenBytesCrc7(5),
                          sixteenBytesMsb1(6)
                        }
              ACCESS  read-write
              STATUS  mandatory
              DESCRIPTION
                 "Sonet Section Trace Selection.
                 "
               ::= { sonetSectionAlarmEntry 11 }

          sonetSectionTraceToTransmit OBJECT-TYPE
              SYNTAX  OCTET STRING (SIZE(0..64))
              ACCESS  read-write
              STATUS  mandatory
              DESCRIPTION
                 "Sonet Section Trace To Transmit. 16-64 bytes String.
                  If 16 byte trace is selected, FW will only
                  use bytes 0-15 of the string.
                 "
               ::= { sonetSectionAlarmEntry 12 }

          sonetSectionTraceToExpect OBJECT-TYPE
              SYNTAX  OCTET STRING (SIZE(0..64))
              ACCESS  read-write    
              STATUS  mandatory
              DESCRIPTION
                 "Sonet Section Trace To Expect. 16-64 bytes String.
                  If 16 byte trace is selected, FW will only
                  use bytes 0-15 of the string.   
                 "
               ::= { sonetSectionAlarmEntry 13 } 

          sonetSectionTraceReceived OBJECT-TYPE
              SYNTAX  OCTET STRING (SIZE(0..64))
              ACCESS  read-write    
              STATUS  mandatory    
              DESCRIPTION
                 "Sonet Section Trace Received. 16-64 bytes String.
                  The write option is for debugging only.
                 "
               ::= { sonetSectionAlarmEntry 14 }
 
          sonetSectionStatAlarmStatus OBJECT-TYPE
              SYNTAX  INTEGER (1..'1FF'h)
              ACCESS  read-write
              STATUS  mandatory
              DESCRIPTION
                 "This variable indicates the
                 status of the interface.
                 The sonetSectionStatAlarmStatus
                 is a bit map represented
                 as a sum, therefore,
                 it can represent multiple defects
                 simultaneously.
                 The sonetLineStatAlarmNoDefect should be
                 set if and only if
                 no other flag is set.

                 The various bit positions are:
                  1     sonetSectionStatAlarmNoDefect
                  2     sonetSectionCurrent15minESs
                  3     sonetSectionCurrent15minSESs
                  4     sonetSectionCurrent15minSEFSs
                  5     sonetSectionCurrent15minCVs
                  6     sonetSectionCurrentDayESs
                  7     sonetSectionCurrentDaySESs
                  8     sonetSectionCurrentDaySEFSs
                  9     sonetSectionCurrentDayCVs
                  "
               ::= { sonetSectionAlarmEntry 15 }
             


-- ----------------------------------------------------------------
--
-- Section Counter Group
--
-- ----------------------------------------------------------------

         sonetSectionCounterTable OBJECT-TYPE
              SYNTAX  SEQUENCE OF SonetSectionCounterEntry
              ACCESS  not-accessible
              STATUS  mandatory
              DESCRIPTION
                "The SONET/SDH Section Counter table."
              ::= { cwsonetSection 5 }

          sonetSectionCounterEntry OBJECT-TYPE
              SYNTAX  SonetSectionCounterEntry
              ACCESS  not-accessible
              STATUS  mandatory
              DESCRIPTION
                "An entry in the SONET/SDH Section  table."
              INDEX   { sectionCounterLineNum }
              ::= { sonetSectionCounterTable 1 }


          SonetSectionCounterEntry ::=
              SEQUENCE {
                  sectionCounterLineNum	           INTEGER,
                  sonetSectionCounterLOSs          Gauge,
                  sonetSectionCounterLOFs          Gauge,
                  sonetSectionCounterClrButton     INTEGER
              }  

          sectionCounterLineNum OBJECT-TYPE
                  SYNTAX INTEGER (1..1)
                  ACCESS read-only
                  STATUS mandatory
                  DESCRIPTION
                        " line number.
                          There are Max 1 line on the BNM
                        "
                  ::= {sonetSectionCounterEntry 1}

          sonetSectionCounterLOSs OBJECT-TYPE
              SYNTAX  Gauge
              ACCESS  read-only
              STATUS  mandatory
              DESCRIPTION
                 "The counter associated with the number of LOSs
                  encountered by a SONET/SDH.
                "
               ::= { sonetSectionCounterEntry 2 }


          sonetSectionCounterLOFs OBJECT-TYPE
              SYNTAX  Gauge
              ACCESS  read-only
              STATUS  mandatory
              DESCRIPTION
                 "The counter associated with the number of
                 LOFs encountered by a SONET/SDH Section.
                "
               ::= { sonetSectionCounterEntry 3 }


          sonetSectionCounterClrButton OBJECT-TYPE
              SYNTAX  INTEGER {
                                noAction(1),
                                clear(2)
                        }
              ACCESS  read-write
              STATUS  mandatory
              DESCRIPTION
                 "Clears all the Section's counters.
                 "
               ::= { sonetSectionCounterEntry 4 }

 
          -- the SONET/SDH Line group

          -- this group consists of 5 tables:
          -- - the SONET/SDH Line Current Table
          -- - the SONET/SDH Line Current Day Table
          -- - the SONET/SDH Line Interval Table
	  -- - the SONET/SDH Line Alarm Table
          -- - the SONET/SDH Line Counter Table
		

          -- the SONET/SDH Line Current Table

          -- The SONET/SDH Line
          -- current table contains various statistics
          -- being collected for the current 15 minute interval.

          cwSonetLineCurrentTable OBJECT-TYPE
              SYNTAX  SEQUENCE OF CwSonetLineCurrentEntry
              ACCESS  not-accessible
              STATUS  mandatory
              DESCRIPTION
                "The SONET/SDH Line Current table."
              ::= { cwsonetLine 1 }

          cwSonetLineCurrentEntry OBJECT-TYPE
              SYNTAX  CwSonetLineCurrentEntry
              ACCESS  not-accessible
              STATUS  mandatory
              DESCRIPTION
                "An entry in the SONET/SDH Line Current table."
              INDEX   { cwSonetLineCurrentLineNum }
              ::= { cwSonetLineCurrentTable 1 }

          CwSonetLineCurrentEntry ::=
              SEQUENCE {
		   cwSonetLineCurrentLineNum   INTEGER,
                   cwSonetLineCurrentStatus    INTEGER,
		   cwSonetLineCurrentValidFlag 	INTEGER,
                   cwSonetLineCurrent15minTimeElapsed    	INTEGER,
                   cwSonetLineCurrentESs       Gauge,
                   cwSonetLineCurrentSESs      Gauge,
                   cwSonetLineCurrentCVs       Gauge,
                   cwSonetLineCurrentUASs      Gauge,
		   cwSonetLineCurrentClrButton INTEGER
               }

         cwSonetLineCurrentLineNum OBJECT-TYPE
                  SYNTAX INTEGER (1..1)
                  ACCESS read-only
                  STATUS mandatory
                  DESCRIPTION
                        " line number.
                          BNM has one line
                        "
                  ::= {cwSonetLineCurrentEntry 1}

          cwSonetLineCurrentStatus OBJECT-TYPE
              SYNTAX  INTEGER(1..30)
              ACCESS  read-only
              STATUS  mandatory
              DESCRIPTION
                 "This variable indicates the status of the sonet line layer.
                 The cwSonetLineCurrentStatus is a bit map represented
                 as a sum, therefore, it can represent multiple defects
                 simultaneously.
                 The sonetLineNoDefect should be set if and only if
                 no other flag is set.

                 The various bit positions are:
                    bit 1 = sonetLineNoDefect
                    bit 2 = sonetLineRcvAIS
                    bit 3 = sonetLineRcvRDI
                    bit 4 = sonetLineXmtAis
                    bit 5 = sonetLineXmtRdi
                  "
               ::= { cwSonetLineCurrentEntry 2 }

         cwSonetLineCurrentValidFlag OBJECT-TYPE
              SYNTAX  INTEGER  {
                          notValid(1),
                          valid(2)
                        }
              ACCESS  read-only
              STATUS  mandatory
              DESCRIPTION
                 "Indicates if the current 15min bucket is valid or not.
                 "
               ::= { cwSonetLineCurrentEntry 3 }

          cwSonetLineCurrent15minTimeElapsed OBJECT-TYPE
              SYNTAX  INTEGER  (1..900)
              ACCESS  read-only
              STATUS  mandatory
              DESCRIPTION
                 "The number of seconds, including partial seconds,
                  that have elapsed since the beginning of the 15min
                  error-measurement period.
                 "
               ::= { cwSonetLineCurrentEntry 4 }

          cwSonetLineCurrentESs OBJECT-TYPE
              SYNTAX  Gauge
              ACCESS  read-only
              STATUS  mandatory
              DESCRIPTION
               "The counter associated with the number of Errored
               Seconds encountered by a SONET/SDH
               Line in the current 15 minute interval."
              ::= { cwSonetLineCurrentEntry 5 }

          cwSonetLineCurrentSESs OBJECT-TYPE
              SYNTAX  Gauge
              ACCESS  read-only
              STATUS  mandatory
              DESCRIPTION
               "The counter associated with the number of
               Severely Errored Seconds
               encountered by a SONET/SDH Line in the current 15
               minute
               interval."
              ::= { cwSonetLineCurrentEntry 6 }

          cwSonetLineCurrentCVs OBJECT-TYPE
              SYNTAX  Gauge
              ACCESS  read-only
              STATUS  mandatory
              DESCRIPTION
               "The counter associated with the number of Coding
               Violations encountered by a
               SONET/SDH Line in the current 15 minute interval."
              ::= { cwSonetLineCurrentEntry 7 }

          cwSonetLineCurrentUASs OBJECT-TYPE
              SYNTAX  Gauge
              ACCESS  read-only
              STATUS  mandatory
              DESCRIPTION
               "The counter associated with the number of
               Unavailable Seconds
               encountered by a SONET/SDH Line in the current 15
               minute
               interval."
              ::= { cwSonetLineCurrentEntry 8 }

       cwSonetLineCurrentClrButton OBJECT-TYPE
              SYNTAX  INTEGER {
                                noAction(1),
                                clear(2)
                        }
              ACCESS  read-write
              STATUS  mandatory
              DESCRIPTION
                 "Clears all the SONET Line's Current15min counters.
                 "
               ::= { cwSonetLineCurrentEntry 9 }

-- -------------------------------------------------------------
--
-- Line Current Day
--
-- -------------------------------------------------------------

         sonetLineCurrentDayTable OBJECT-TYPE
              SYNTAX  SEQUENCE OF SonetLineCurrentDayEntry
              ACCESS  not-accessible
              STATUS  mandatory
              DESCRIPTION
                "The SONET/SDH Line Current Day table."
              ::= { cwsonetLine 2 }

          sonetLineCurrentDayEntry OBJECT-TYPE
              SYNTAX  SonetLineCurrentDayEntry
              ACCESS  not-accessible
              STATUS  mandatory
              DESCRIPTION
                "An entry in the SONET/SDH Line Current Day table."
              INDEX   { lineCurrentDayLineNum }
              ::= { sonetLineCurrentDayTable 1 }

          SonetLineCurrentDayEntry ::=
              SEQUENCE {

                   lineCurrentDayLineNum	INTEGER,
                   sonetLineCurrentDayValidFlag	INTEGER,
                   sonetLineCurrentDayESs       Gauge,
                   sonetLineCurrentDaySESs      Gauge,
                   sonetLineCurrentDayCVs       Gauge,
                   sonetLineCurrentDayFCs       Gauge,
                   sonetLineCurrentDayUASs      Gauge,
                   sonetLineCurrentDayClrButton INTEGER
               } 


          lineCurrentDayLineNum OBJECT-TYPE
                  SYNTAX INTEGER (1..1)
                  ACCESS read-only
                  STATUS mandatory
                  DESCRIPTION
                        " line number.
                          BNM has 1 line
                        "
                  ::= {sonetLineCurrentDayEntry 1}

          sonetLineCurrentDayValidFlag OBJECT-TYPE
              SYNTAX  INTEGER  {
                          notValid(1),
                          valid(2)
                        }
              ACCESS  read-only
              STATUS  mandatory
              DESCRIPTION
                 "Indicates if the current day bucket is valid or not.
                 "
               ::= { sonetLineCurrentDayEntry 2 }

          sonetLineCurrentDayESs OBJECT-TYPE
              SYNTAX  Gauge
              ACCESS  read-only
              STATUS  mandatory
              DESCRIPTION
               "The counter associated with the number of Errored
               Seconds encountered by a SONET/SDH
               Line in the current day interval."
              ::= { sonetLineCurrentDayEntry 3 }
               
          sonetLineCurrentDaySESs OBJECT-TYPE
              SYNTAX  Gauge
              ACCESS  read-only
              STATUS  mandatory
              DESCRIPTION
               "The counter associated with the number of
               Severely Errored Seconds
               encountered by a SONET/SDH Line in the current
               day interval."
              ::= { sonetLineCurrentDayEntry 4 }
               
          sonetLineCurrentDayCVs OBJECT-TYPE
              SYNTAX  Gauge
              ACCESS  read-only
              STATUS  mandatory
              DESCRIPTION
               "The counter associated with the number of Coding
               Violations (BIP-8*N for STS-N) encountered by a
               SONET/SDH Line in the current day interval."
              ::= { sonetLineCurrentDayEntry 5 }
               
          sonetLineCurrentDayFCs OBJECT-TYPE
              SYNTAX  Gauge
              ACCESS  read-only
              STATUS  mandatory
              DESCRIPTION
               "Number of times  that line was in AIS alarm in the
                current day interval.
                "
              ::= { sonetLineCurrentDayEntry 6 }
               
 
          sonetLineCurrentDayUASs OBJECT-TYPE
              SYNTAX  Gauge
              ACCESS  read-only
              STATUS  mandatory
              DESCRIPTION
               "The counter associated with the number of
               Unavailable Seconds
               encountered by a SONET/SDH Line in the current 
               day interval."
              ::= { sonetLineCurrentDayEntry 7 }
               
         sonetLineCurrentDayClrButton OBJECT-TYPE
              SYNTAX  INTEGER {
                                noAction(1),
                                clear(2)
                        }
              ACCESS  read-write
              STATUS  mandatory
              DESCRIPTION
                 "Clears all the SONET Line's CurrentDay counters.
                 "
               ::= { sonetLineCurrentDayEntry 8 }

--  -------------------------------------------------------------
--
-- Line Interval Group
--
-- -------------------------------------------------------------



          -- the SONET/SDH Line Interval Table

          -- The SONET/SDH Line Interval Table

          -- contains various statistics
          -- collected by each system over a maximum
          -- of the previous 24 hours of
          -- operation.  The past 24 hours may be broken into 96
          -- completed 15 minute intervals.
          -- A system is required to store at
          -- least 4 completed 15 minute interval.
          -- The default value is 32 intervals.

          cwSonetLineIntervalTable OBJECT-TYPE
              SYNTAX  SEQUENCE OF CwSonetLineIntervalEntry
              ACCESS  not-accessible
              STATUS  mandatory
              DESCRIPTION
                 "The SONET/SDH Line Interval table."
               ::= { cwsonetLine 3 }

          cwSonetLineIntervalEntry OBJECT-TYPE
              SYNTAX  CwSonetLineIntervalEntry
              ACCESS  not-accessible
              STATUS  mandatory
              DESCRIPTION
                 "An entry in the SONET/SDH Line Interval table."
             INDEX   { cwSonetLineIntervalLineNum,
                       cwSonetLineIntervalNumber }
             ::= { cwSonetLineIntervalTable 1 }

          CwSonetLineIntervalEntry ::=
              SEQUENCE {
                  cwSonetLineIntervalLineNum        INTEGER,
                  cwSonetLineIntervalNumber    INTEGER,
                  cwSonetLineIntervalValidFlag INTEGER,
                  cwSonetLineIntervalESs       Gauge,
                  cwSonetLineIntervalSESs      Gauge,
                  cwSonetLineIntervalCVs       Gauge,
                  cwSonetLineIntervalFCs       Gauge,
                  cwSonetLineIntervalUASs      Gauge
              }


          cwSonetLineIntervalLineNum OBJECT-TYPE
                  SYNTAX INTEGER (1..1)
                  ACCESS read-only
                  STATUS mandatory
                  DESCRIPTION
                        " line number.
                          BNM has one line
                        "
                  ::= {cwSonetLineIntervalEntry 1}

          cwSonetLineIntervalNumber OBJECT-TYPE
              SYNTAX  INTEGER (1..96)
              ACCESS  read-only
              STATUS  mandatory
              DESCRIPTION
                  "A number between 1 and 96, which identifies the
                  interval for which the set of statistics is available.
                  The interval identified by 1 is the most recently
                  completed 15 minute interval,
                  and the interval identified
                  by N is the interval immediately preceding the
                  one identified
                  by N-1."
               ::= { cwSonetLineIntervalEntry 2 }

          cwSonetLineIntervalValidFlag OBJECT-TYPE
              SYNTAX  INTEGER  {
                          notValid(1),
                          valid(2)
                        }
              ACCESS  read-only
              STATUS  mandatory
              DESCRIPTION
                 "Indicates if the bucket specified by the interval
                  is valid or not.
                 "
               ::= { cwSonetLineIntervalEntry 3 }

          cwSonetLineIntervalESs OBJECT-TYPE
              SYNTAX  Gauge
              ACCESS  read-only
              STATUS  mandatory
              DESCRIPTION
                 "The counter associated with the number of
                 Errored Seconds encountered
                 by a SONET/SDH Line in a
                 particular 15-minute interval
                 in the past 24 hours."
               ::= { cwSonetLineIntervalEntry 4 }

          cwSonetLineIntervalSESs OBJECT-TYPE
              SYNTAX  Gauge
              ACCESS  read-only
              STATUS  mandatory
              DESCRIPTION
                 "The counter associated with the number of
                 Severely Errored Seconds
                 encountered by a SONET/SDH Line in a
                 particular 15-minute interval
                 in the past 24 hours."
                ::= { cwSonetLineIntervalEntry 5 }

          cwSonetLineIntervalCVs OBJECT-TYPE
              SYNTAX  Gauge
              ACCESS  read-only
              STATUS  mandatory
              DESCRIPTION
                "The counter associated with the number of Coding
                Violations (BIP-8*N) encountered by a
                SONET/SDH Line in a
                particular 15-minute interval
                in the past 24 hours."
              ::= { cwSonetLineIntervalEntry 6 }

          cwSonetLineIntervalFCs OBJECT-TYPE
              SYNTAX  Gauge
              ACCESS  read-only
              STATUS  mandatory
              DESCRIPTION
                "Number of times  that line was in AIS alarm in the
                particular 15-minute interval
                in the past 24 hours."
              ::= { cwSonetLineIntervalEntry 7 }


          cwSonetLineIntervalUASs OBJECT-TYPE
              SYNTAX  Gauge
              ACCESS  read-only
              STATUS  mandatory
              DESCRIPTION
                "The counter associated with the
                number of Unavailable Seconds
                encountered by a SONET/SDH Line in
                a particular 15-minute interval
                in the past 24 hours."
              ::= { cwSonetLineIntervalEntry 8 }

-- -------------------------------------------------------------
--
-- Line Far End Current 15min
--
-- -------------------------------------------------------------
 


          -- The SONET/SDH Far End Line group.
          -- This group may only be implemented by SONET/SDH (LTEs)
          -- systems that provide for a far end block error (FEBE)
          -- information at the SONET/SDH Line Layer.

          -- This group consists of two tables:
          --    SONET/SDH Far End Line Current Table
          --    SONET/SDH Far End Line Interval Table



          -- The SONET/SDH Far End Line Current Table

          -- The SONET/SDH Far End Line Current table contains
          -- various statistics being
          -- collected for the current 15 minute interval.
          -- The statistics are collected from the far end
          -- block error code (FEBE)
          -- within the third Z2 byte of the Line Overhead
          -- in Broadband ISDN applications.
          -- The definitions are the same as described for
          -- the near-end information.

          cwSonetFarEndLineCurrentTable OBJECT-TYPE
              SYNTAX  SEQUENCE OF CwSonetFarEndLineCurrentEntry
              ACCESS  not-accessible
              STATUS  mandatory
              DESCRIPTION
                "The SONET/SDH Far End Line Current table."
              ::= { cwsonetLine 4 }

          cwSonetFarEndLineCurrentEntry OBJECT-TYPE
              SYNTAX  CwSonetFarEndLineCurrentEntry
              ACCESS  not-accessible
              STATUS  mandatory
              DESCRIPTION
                "An entry in the SONET/SDH Far End Line Current
		 table."
              INDEX   { cwSonetFELineCurrentLineNum }
              ::= { cwSonetFarEndLineCurrentTable 1 }

          CwSonetFarEndLineCurrentEntry ::=
              SEQUENCE {
                  cwSonetFELineCurrentLineNum            		INTEGER,
                  cwSonetFarEndLineCurrentValidFlag 		INTEGER,
                  cwSonetFarEndLineCurrentTimeElapsed	INTEGER,
                  cwSonetFarEndLineCurrentESs       		Gauge,
                  cwSonetFarEndLineCurrentSESs      		Gauge,
                  cwSonetFarEndLineCurrentCVs       		Gauge,
                  cwSonetFarEndLineCurrentFCs       		Gauge,
                  cwSonetFarEndLineCurrentUASs      		Gauge,
		  cwSonetFarEndLineCurrentClrButton 		INTEGER
                 }

          cwSonetFELineCurrentLineNum OBJECT-TYPE
                  SYNTAX INTEGER (1..1)
                  ACCESS read-only
                  STATUS mandatory
                  DESCRIPTION
                        " line number.
                          BNM has one line
                        "
                  ::= {cwSonetFarEndLineCurrentEntry 1}

          cwSonetFarEndLineCurrentValidFlag OBJECT-TYPE
              SYNTAX  INTEGER  {
                          notValid(1),
                          valid(2)
                        }
              ACCESS  read-only
              STATUS  mandatory
              DESCRIPTION
                 "Indicates if the Far End current 15min bucket is
		  valid or not.
                 "
               ::= { cwSonetFarEndLineCurrentEntry 2 }
                  
          cwSonetFarEndLineCurrentTimeElapsed OBJECT-TYPE
              SYNTAX  INTEGER  (1..900)
              ACCESS  read-only
              STATUS  mandatory
              DESCRIPTION
                 "The number of seconds, including partial seconds,
                  that have elapsed since the beginning of the 15min
                  error-measurement period.
                 "
               ::= { cwSonetFarEndLineCurrentEntry 3 }
       
          cwSonetFarEndLineCurrentESs OBJECT-TYPE
             SYNTAX  Gauge
             ACCESS  read-only
             STATUS  mandatory
             DESCRIPTION
                 "The counter associated with the number of Far
                 Far End Errored Seconds encountered by a SONET/SDH
                 interface in the  current 15 minute interval."
             ::= { cwSonetFarEndLineCurrentEntry 4 }

          cwSonetFarEndLineCurrentSESs OBJECT-TYPE
             SYNTAX  Gauge
             ACCESS  read-only
             STATUS  mandatory
             DESCRIPTION
                 "The counter associated with the number of
                 Far End Severely Errored Seconds
                 encountered by a SONET/SDH Medium/Section/Line
                 interface in the current 15 minute
                 interval."
             ::= { cwSonetFarEndLineCurrentEntry 5 }

          cwSonetFarEndLineCurrentCVs OBJECT-TYPE
             SYNTAX  Gauge
             ACCESS  read-only
             STATUS  mandatory
             DESCRIPTION
                 "The counter associated with the number of
                 Far End Coding Violations reported via
                 the far end block error (FEBE) count
                 encountered by a
                 SONET/SDH Medium/Section/Line
                 interface in the current 15 minute interval."
             ::= { cwSonetFarEndLineCurrentEntry 6 }

          cwSonetFarEndLineCurrentFCs OBJECT-TYPE
             SYNTAX  Gauge
             ACCESS  read-only
             STATUS  mandatory   
             DESCRIPTION
                 "The counter associated with the number of
                 RFI failures occurred in the current 15 min.
                 "
             ::= { cwSonetFarEndLineCurrentEntry 7 }
 
          cwSonetFarEndLineCurrentUASs OBJECT-TYPE
             SYNTAX  Gauge
             ACCESS  read-only
             STATUS  mandatory
             DESCRIPTION
                 "The counter associated with the number of
                 Far End Unavailable Seconds
                 encountered by a
                 SONET/SDH Medium/Section/Line
                 interface in the current 15 minute interval."
             ::= { cwSonetFarEndLineCurrentEntry 8 }

         cwSonetFarEndLineCurrentClrButton OBJECT-TYPE
              SYNTAX  INTEGER {
                                noAction(1),
                                clear(2)
                        }
              ACCESS  read-write
              STATUS  mandatory
              DESCRIPTION
                 "Clears all the SONET Far End
		  Line's Current 15min counters.
                 "
               ::= { cwSonetFarEndLineCurrentEntry 9 }
 


 -- -------------------------------------------------------------
--
-- Far End Line Current Day
--
-- -------------------------------------------------------------

          sonetFarEndLineCurrentDayTable OBJECT-TYPE
              SYNTAX  SEQUENCE OF SonetFarEndLineCurrentDayEntry
              ACCESS  not-accessible
              STATUS  mandatory
              DESCRIPTION
                "The SONET/SDH Far End Line CurrentDay table."
              ::= { cwsonetLine 5 }

          sonetFarEndLineCurrentDayEntry OBJECT-TYPE
              SYNTAX  SonetFarEndLineCurrentDayEntry
              ACCESS  not-accessible
              STATUS  mandatory
              DESCRIPTION
                "An entry in the SONET/SDH Far End Line CurrentDay
                 table."
              INDEX   { sonetFELineCurrentDayLineNum }
              ::= { sonetFarEndLineCurrentDayTable 1 }

          SonetFarEndLineCurrentDayEntry ::=
              SEQUENCE {
                  sonetFELineCurrentDayLineNum            INTEGER,
                  sonetFarEndLineCurrentDayValidFlag INTEGER,
                  sonetFarEndLineCurrentDayESs       Gauge,
                  sonetFarEndLineCurrentDaySESs      Gauge,
                  sonetFarEndLineCurrentDayCVs       Gauge,
                  sonetFarEndLineCurrentDayFCs       Gauge,
                  sonetFarEndLineCurrentDayUASs      Gauge,
		  sonetFarEndLineCurrentDayClrButton INTEGER
                 }

          sonetFELineCurrentDayLineNum OBJECT-TYPE
                  SYNTAX INTEGER (1..1)
                  ACCESS read-only
                  STATUS mandatory
                  DESCRIPTION
                        " line number.
                          BNM has one line
                        "
                  ::= {sonetFarEndLineCurrentDayEntry 1}

          sonetFarEndLineCurrentDayValidFlag OBJECT-TYPE
              SYNTAX  INTEGER  {
                          notValid(1),
                          valid(2)
                        }
              ACCESS  read-only
              STATUS  mandatory
              DESCRIPTION
                 "Indicates if the Far End current day bucket is valid
		  or not.
                 "
               ::= { sonetFarEndLineCurrentDayEntry 2 }

          sonetFarEndLineCurrentDayESs OBJECT-TYPE
             SYNTAX  Gauge
             ACCESS  read-only
             STATUS  mandatory
             DESCRIPTION
                 "The counter associated with the number of Far
                 Far End Errored Seconds encountered by a SONET/SDH
                 interface in the  current day interval."
             ::= { sonetFarEndLineCurrentDayEntry 3 }
               
          sonetFarEndLineCurrentDaySESs OBJECT-TYPE
             SYNTAX  Gauge
             ACCESS  read-only
             STATUS  mandatory
             DESCRIPTION
                 "The counter associated with the number of
                 Far End Severely Errored Seconds
                 encountered by a SONET/SDH Medium/Section/Line
                 interface in the current day interval."
             ::= { sonetFarEndLineCurrentDayEntry 4 }
               
          sonetFarEndLineCurrentDayCVs OBJECT-TYPE
             SYNTAX  Gauge
             ACCESS  read-only
             STATUS  mandatory
             DESCRIPTION
                 "The counter associated with the number of
                 Far End Coding Violations reported via
                 the far end block error (FEBE) count
                 encountered by a
                 SONET/SDH Medium/Section/Line
                 interface in the current day interval."
             ::= { sonetFarEndLineCurrentDayEntry 5 }

          sonetFarEndLineCurrentDayFCs OBJECT-TYPE
             SYNTAX  Gauge
             ACCESS  read-only
             STATUS  mandatory
             DESCRIPTION
                 "The counter associated with the number of
                 RFI failures occurred in the current day interval.
                 "
             ::= { sonetFarEndLineCurrentDayEntry 6 }
               
          sonetFarEndLineCurrentDayUASs OBJECT-TYPE
             SYNTAX  Gauge
             ACCESS  read-only
             STATUS  mandatory
             DESCRIPTION
                 "The counter associated with the number of
                 Far End Unavailable Seconds
                 encountered by a
                 SONET/SDH Medium/Section/Line
                 interface in the current day interval."
             ::= { sonetFarEndLineCurrentDayEntry 7 }
               
         sonetFarEndLineCurrentDayClrButton OBJECT-TYPE
              SYNTAX  INTEGER {
                                noAction(1),
                                clear(2)
                        }
              ACCESS  read-write
              STATUS  mandatory
              DESCRIPTION
                 "Clears all the SONET Far End
                  Line's Current Day counters.
                 "
               ::= { sonetFarEndLineCurrentDayEntry 8 }
 
 
 
-- ----------------------------------------------------------
--
-- Far End Line Interval Group
--
-- ----------------------------------------------------------



          -- The SONET/SDH Far End Line Interval Table

          -- The SONET/SDH Far End Line Interval Table
          -- contains various statistics
          -- collected by each system over a maximum
          -- of the previous 24 hours of
          -- operation.  The past 24 hours may be broken into 96
          -- completed 15 minute intervals.
          -- A system is required to store at
          -- least 4 completed 15 minute interval.
          -- The default value is 32 intervals.

          cwSonetFarEndLineIntervalTable OBJECT-TYPE
             SYNTAX  SEQUENCE OF CwSonetFarEndLineIntervalEntry
             ACCESS  not-accessible
             STATUS  mandatory
             DESCRIPTION
                "The SONET/SDH Far End Line Interval table."
             ::= { cwsonetLine 6 }

          cwSonetFarEndLineIntervalEntry OBJECT-TYPE
             SYNTAX  CwSonetFarEndLineIntervalEntry
             ACCESS  not-accessible
             STATUS  mandatory
             DESCRIPTION
               "An entry in the SONET/SDH Far
               End Line Interval table."
             INDEX   { cwSonetFELineIntervalLineNum,
                       cwSonetFarEndLineIntervalNumber }
             ::= { cwSonetFarEndLineIntervalTable 1 }

          CwSonetFarEndLineIntervalEntry ::=
              SEQUENCE {
                   cwSonetFELineIntervalLineNum            INTEGER,
                   cwSonetFarEndLineIntervalNumber    INTEGER,
                   cwSonetFarEndLineIntervalValidFlag INTEGER,
                   cwSonetFarEndLineIntervalESs       Gauge,
                   cwSonetFarEndLineIntervalSESs      Gauge,
                   cwSonetFarEndLineIntervalCVs       Gauge,
                   cwSonetFarEndLineIntervalFCs       Gauge,
                   cwSonetFarEndLineIntervalUASs      Gauge
              }


          cwSonetFELineIntervalLineNum OBJECT-TYPE
                  SYNTAX INTEGER (1..1)
                  ACCESS read-only
                  STATUS mandatory
                  DESCRIPTION
                        " line number.
                          BNM has one line
                        "
                  ::= {cwSonetFarEndLineIntervalEntry 1}

          cwSonetFarEndLineIntervalNumber OBJECT-TYPE
             SYNTAX  INTEGER (1..96)
             ACCESS  read-only
             STATUS  mandatory
             DESCRIPTION
                   "A number between 1 and 96, which identifies the
                   interval for which the set of statistics is available.
                   The interval identified by 1 is the most recently
                   completed 15 minute interval,
                   and the interval identified
                   by N is the interval immediately preceding the
                   one identified
                   by N-1."
             ::= { cwSonetFarEndLineIntervalEntry 2 }

          cwSonetFarEndLineIntervalValidFlag OBJECT-TYPE
              SYNTAX  INTEGER  { 
                          notValid(1),   
                          valid(2)   
                        } 
              ACCESS  read-only  
              STATUS  mandatory 
              DESCRIPTION 
                 "Indicates if the bucket specified by the interval 
                  is valid or not. 
                 " 
               ::= { cwSonetFarEndLineIntervalEntry 3 } 
 
          cwSonetFarEndLineIntervalESs OBJECT-TYPE
             SYNTAX  Gauge
             ACCESS  read-only
             STATUS  mandatory
             DESCRIPTION
                  "The counter associated with the number of
                  Far End Errored Seconds encountered
                  by a SONET/SDH Line
                  interface in a particular 15-minute interval
                  in the past 24 hours."
            ::= { cwSonetFarEndLineIntervalEntry 4 }

          cwSonetFarEndLineIntervalSESs OBJECT-TYPE
             SYNTAX  Gauge
             ACCESS  read-only
             STATUS  mandatory
             DESCRIPTION
                  "The counter associated with the number of
                  Far End Severely Errored Seconds
                  encountered by a SONET/SDH Line
                  interface in a particular 15-minute interval
                  in the past 24 hours."
            ::= { cwSonetFarEndLineIntervalEntry 5 }

          cwSonetFarEndLineIntervalCVs OBJECT-TYPE
              SYNTAX  Gauge
              ACCESS  read-only
              STATUS  mandatory
              DESCRIPTION
                   "The counter associated with the number of
                   Far End Coding Violations reported via
                   the far end block error count
                   encountered by a
                   SONET/SDH Line
                   interface in a particular 15-minute interval
                   in the past 24 hours."
              ::= { cwSonetFarEndLineIntervalEntry 6 }

          cwSonetFarEndLineIntervalFCs OBJECT-TYPE
              SYNTAX  Gauge
              ACCESS  read-only
              STATUS  mandatory
              DESCRIPTION
                   "The counter associated with the number of
                   RFI failures in a particular 15-minute interval
                   in the past 24 hours."
              ::= { cwSonetFarEndLineIntervalEntry 7 }

          cwSonetFarEndLineIntervalUASs OBJECT-TYPE
             SYNTAX  Gauge
             ACCESS  read-only
             STATUS  mandatory
             DESCRIPTION
                 "The counter associated with the number of
                 Far End Unavailable Seconds
                 encountered by a
                 SONET/SDH Line
                 interface in a particular 15-minute interval
                 in the past 24 hours."
             ::= { cwSonetFarEndLineIntervalEntry 8 }


-- ----------------------------------------------------------------
--
-- Line Alarm Group
--
-- ----------------------------------------------------------------

        -- SONET/SDH Line Alarm Group.
	-- Changing any threshold will effect both the Near End and
	-- Far End threshold.

          sonetLineAlarmTable OBJECT-TYPE
              SYNTAX  SEQUENCE OF SonetLineAlarmEntry
              ACCESS  not-accessible
              STATUS  mandatory
              DESCRIPTION
                "The SONET/SDH Line Alarm table."
              ::= { cwsonetLine 7 }

          sonetLineAlarmEntry OBJECT-TYPE
              SYNTAX  SonetLineAlarmEntry
              ACCESS  not-accessible
              STATUS  mandatory
              DESCRIPTION
                "An entry in the SONET/SDH Line Alarm table."
              INDEX   { sonetLineAlarmLineNum }
              ::= { sonetLineAlarmTable 1 }


          SonetLineAlarmEntry ::=
              SEQUENCE {
                  sonetLineAlarmLineNum	                     INTEGER,
                  sonetLineStatisticalAlarmSeverity          INTEGER,
                  sonetLineCurrent15minESsThreshold          INTEGER,
                  sonetLineCurrentDayESsThreshold            INTEGER,
                  sonetLineCurrent15minSESsThreshold         INTEGER,
                  sonetLineCurrentDaySESsThreshold           INTEGER,
                  sonetLineCurrent15minCVsThreshold          INTEGER,
                  sonetLineCurrentDayCVsThreshold            INTEGER,
                  sonetLineCurrent15minUASsThreshold         INTEGER,
                  sonetLineCurrentDayUASsThreshold           INTEGER,
                  sonetLineStatAlarmStatus                   INTEGER
              }
 
 
          sonetLineAlarmLineNum OBJECT-TYPE
                  SYNTAX INTEGER (1..1)
                  ACCESS read-only
                  STATUS mandatory
                  DESCRIPTION
                        " line number.
                         BNM has one line
                        "
                  ::= {sonetLineAlarmEntry 1}
 
          sonetLineStatisticalAlarmSeverity OBJECT-TYPE
              SYNTAX  INTEGER {
                                minor(1),
                                major(2)
                        }
              ACCESS  read-write
              STATUS  mandatory
              DESCRIPTION
                 "When any statistical threshold is exceeded.
                 "
               ::= { sonetLineAlarmEntry 2 }
  
          sonetLineCurrent15minESsThreshold OBJECT-TYPE
              SYNTAX  INTEGER (0..2147483647)
              ACCESS  read-write
              STATUS  mandatory
              DESCRIPTION
                 "The default is set to 20.
		  This threshold is the same for Far End and
		  Near End.
                 "
               ::= { sonetLineAlarmEntry 3 }
  
          sonetLineCurrentDayESsThreshold OBJECT-TYPE
              SYNTAX  INTEGER (0..2147483647)
              ACCESS  read-write
              STATUS  mandatory
              DESCRIPTION
                 "The default is set to 200.
		  This threshold is the same for Far End and
		  Near End.
                 "
               ::= { sonetLineAlarmEntry 4 }
    
          sonetLineCurrent15minSESsThreshold OBJECT-TYPE
              SYNTAX  INTEGER (0..2147483647)
              ACCESS  read-write
              STATUS  mandatory
              DESCRIPTION
                 "The default is set to 3.
		  This threshold is the same for Far End and
		  Near End.
                 "
               ::= { sonetLineAlarmEntry 5 }
    
    
          sonetLineCurrentDaySESsThreshold OBJECT-TYPE
              SYNTAX  INTEGER (0..2147483647)
              ACCESS  read-write
              STATUS  mandatory
              DESCRIPTION
                 "The default is set to 7.
		  This threshold is the same for Far End and
		  Near End.
                 "
               ::= { sonetLineAlarmEntry 6 }

          sonetLineCurrent15minCVsThreshold OBJECT-TYPE
              SYNTAX  INTEGER (0..2147483647)
              ACCESS  read-write
              STATUS  mandatory
              DESCRIPTION
                 "The default is set to 25.
		  This threshold is the same for Far End and
		  Near End.
                 "
               ::= { sonetLineAlarmEntry 7 }
 
          sonetLineCurrentDayCVsThreshold OBJECT-TYPE
              SYNTAX  INTEGER (0..2147483647)
              ACCESS  read-write
              STATUS  mandatory
              DESCRIPTION
                 "The default is set to 250.
		  This threshold is the same for Far End and
		  Near End.
                 "
               ::= { sonetLineAlarmEntry 8 }
 
            sonetLineCurrent15minUASsThreshold OBJECT-TYPE
              SYNTAX  INTEGER (0..2147483647)
              ACCESS  read-write
              STATUS  mandatory
              DESCRIPTION
                 "The default is set to 10.
                  This threshold is the same for Far End and
                  Near End.
                 "
               ::= { sonetLineAlarmEntry 9 }
 
          sonetLineCurrentDayUASsThreshold OBJECT-TYPE
              SYNTAX  INTEGER (0..2147483647)
              ACCESS  read-write
              STATUS  mandatory
              DESCRIPTION
                 "The default is set to 10.
                  This threshold is the same for Far End and
                  Near End.
                 "
               ::= { sonetLineAlarmEntry 10 }
 

          sonetLineStatAlarmStatus OBJECT-TYPE
              SYNTAX  INTEGER (1..'1FFFF'h)
              ACCESS  read-only
              STATUS  mandatory
              DESCRIPTION
                 "This variable indicates the
                 status of the interface.
                 The sonetLineStatAlarmStatus
                 is a bit map represented
                 as a sum, therefore,
                 it can represent multiple defects
                 simultaneously.
                 The sonetLineStatAlarmNoDefect should be
                 set if and only if
                 no other flag is set.
 
                 The various bit positions are:
                  1   	sonetLineStatAlarmNoDefect
                  2	sonetLineCurrent15minESs       
                  3	sonetLineCurrent15minSESs     
                  4	sonetLineCurrent15minCVs     
                  5	sonetLineCurrent15minUASs   
                  6	sonetFarEndLineCurrent15minESs      
                  7	sonetFarEndLineCurrent15minSESs    
                  8	sonetFarEndLineCurrent15minCVs    
                  9	sonetFarEndLineCurrent15minUASs  
                  10	sonetLineCurrentDayESs       
                  11	sonetLineCurrentDaySESs     
                  12	sonetLineCurrentDayCVs     
                  13	sonetLineCurrentDayUASs  
               	  14	sonetFarEndLineCurrentDayESs      
                  15	sonetFarEndLineCurrentDaySESs    
                  16	sonetFarEndLineCurrentDayCVs    
                  17	sonetFarEndLineCurrentDayUASs  
		  "
               ::= { sonetLineAlarmEntry 11 }

-- ----------------------------------------------------------------
--
-- Line Counter Group
--
-- ----------------------------------------------------------------

         sonetLineCounterTable OBJECT-TYPE
              SYNTAX  SEQUENCE OF SonetLineCounterEntry
              ACCESS  not-accessible
              STATUS  mandatory
              DESCRIPTION
                "The SONET/SDH Line Counter table."
              ::= { cwsonetLine 8 }

          sonetLineCounterEntry OBJECT-TYPE
              SYNTAX  SonetLineCounterEntry
              ACCESS  not-accessible
              STATUS  mandatory
              DESCRIPTION
                "An entry in the SONET/SDH Line  table."
              INDEX   { sonetLineCounterLineNum }
              ::= { sonetLineCounterTable 1 }
 
 
          SonetLineCounterEntry ::=
              SEQUENCE {
                  sonetLineCounterLineNum            INTEGER,
                  sonetLineCounterAISs          Gauge,
                  sonetLineCounterRFIs          Gauge,
                  sonetLineCounterClrButton     INTEGER
              }
 
          sonetLineCounterLineNum OBJECT-TYPE
                  SYNTAX INTEGER (1..1)
                  ACCESS read-only
                  STATUS mandatory
                  DESCRIPTION
                        " line number.
                          BNM has one line
                        "
                  ::= {sonetLineCounterEntry 1}
 
          sonetLineCounterAISs OBJECT-TYPE
              SYNTAX  Gauge
              ACCESS  read-only
              STATUS  mandatory
              DESCRIPTION
                 "The counter associated with the number of AISs
                  encountered by a SONET/SDH.
                "
               ::= { sonetLineCounterEntry 2 }
 
 
          sonetLineCounterRFIs OBJECT-TYPE
              SYNTAX  Gauge
              ACCESS  read-only
              STATUS  mandatory
              DESCRIPTION
                 "The counter associated with the number of
                 RFIs encountered by a SONET/SDH Line.
                "
               ::= { sonetLineCounterEntry 3 }
 
          sonetLineCounterClrButton OBJECT-TYPE
              SYNTAX  INTEGER {
                                noAction(1),
                                clear(2)
                        }
              ACCESS  read-write
              STATUS  mandatory
              DESCRIPTION
                 "Clears all the Line's counters.
                 "
               ::= { sonetLineCounterEntry 4 }
 

-- ---------------------------------------------------------
--
-- Path Current 15min Group
--
-- ---------------------------------------------------------

          -- the SONET/SDH Path group


          -- the SONET/SDH Path Current Table

          -- The SONET/SDH Path
          -- current table contains various statistics
          -- being collected for the current 15 minute interval.

          cwSonetPathCurrentTable OBJECT-TYPE
              SYNTAX  SEQUENCE OF CwSonetPathCurrentEntry
              ACCESS  not-accessible
              STATUS  mandatory
              DESCRIPTION
               "The SONET/SDH Path Current table."
          ::= { cwsonetPath 1 }

          cwSonetPathCurrentEntry OBJECT-TYPE
              SYNTAX  CwSonetPathCurrentEntry
              ACCESS  not-accessible
              STATUS  mandatory
              DESCRIPTION
               "An entry in the SONET/SDH Path Current table."
              INDEX   { cwSonetPathCurrentLineNum }
          ::= { cwSonetPathCurrentTable 1 }

          CwSonetPathCurrentEntry ::=
              SEQUENCE {
                  cwSonetPathCurrentLineNum         	INTEGER,
                  cwSonetPathCurrentStatus     	INTEGER,
                  cwSonetPathCurrentValidFlag  	INTEGER,
                  cwSonetPathCurrentTimeElapsed     	INTEGER,
                  cwSonetPathCurrentESs        	Gauge,
                  cwSonetPathCurrentSESs       	Gauge,
                  cwSonetPathCurrentCVs        	Gauge,
                  cwSonetPathCurrentFCs        	Gauge,
                  cwSonetPathCurrentUASs       	Gauge,
                  cwSonetPathCurrentClrButton  	INTEGER
              }


          cwSonetPathCurrentLineNum OBJECT-TYPE
                  SYNTAX INTEGER (1..1)
                  ACCESS read-only
                  STATUS mandatory
                  DESCRIPTION
                        " line number.
                          BNM has 1 line
                        "
                  ::= {cwSonetPathCurrentEntry 1}

          cwSonetPathCurrentStatus OBJECT-TYPE
              SYNTAX  INTEGER (1..1022)
              ACCESS  read-only
              STATUS  mandatory
              DESCRIPTION
                "This variable indicates the status of the sonet path layer.
                The cwSonetPathCurrentStatus is a bit map represented
                as a sum, therefore, it can represent multiple defects
                simultaneously.
                The sonetPathNoDefect should be set if and only if
                no other flag is set.

                The various bit positions are:
                   bit 1 = sonetPathNoDefect
                   bit 2 = sonetPathRcvLOP
                   bit 3 = sonetPathRcvAIS
                   bit 4 = sonetPathRcvRDI
                   bit 5 = sonetPathUnequipted
                   bit 6 = sonetPathSignalLabelMismatch
                   bit 7 = sonetPathTraceFailure
                   bit 8 = sonetPathXmtAis
                   bit 9 = sonetPathXmtRdi
                  bit 10 = sonetPathRcvLOCD
                "
          ::= { cwSonetPathCurrentEntry 2 }

          cwSonetPathCurrentValidFlag OBJECT-TYPE
              SYNTAX  INTEGER  {
                          notValid(1),
                          valid(2)
                        }
              ACCESS  read-only
              STATUS  mandatory
              DESCRIPTION
                 "Indicates if the current 15min bucket is valid or not.
                 "
               ::= { cwSonetPathCurrentEntry 3 }

          cwSonetPathCurrentTimeElapsed OBJECT-TYPE
              SYNTAX  INTEGER  (1..900)
              ACCESS  read-only
              STATUS  mandatory
              DESCRIPTION
                 "The number of seconds, including partial seconds,
                  that have elapsed since the beginning of the 15min
                  error-measurement period.
                 "
               ::= { cwSonetPathCurrentEntry 4 }

          cwSonetPathCurrentESs OBJECT-TYPE
              SYNTAX  Gauge
              ACCESS  read-only
              STATUS  mandatory
              DESCRIPTION
               "The counter associated with the number of Errored
               Seconds encountered by a SONET/SDH
               Path in the current 15 minute interval."
          ::= { cwSonetPathCurrentEntry 5 }

          cwSonetPathCurrentSESs OBJECT-TYPE
              SYNTAX  Gauge
              ACCESS  read-only
              STATUS  mandatory
              DESCRIPTION
               "The counter associated with the number of
               Severely Errored Seconds
               encountered by a SONET/SDH Path in the current 15
               minute
               interval."
          ::= { cwSonetPathCurrentEntry 6 }

          cwSonetPathCurrentCVs OBJECT-TYPE
              SYNTAX  Gauge
              ACCESS  read-only
              STATUS  mandatory
              DESCRIPTION
               "The counter associated with the number of Coding
               Violations (BIP-8) encountered by a
               SONET/SDH Path in the current 15 minute interval."
          ::= { cwSonetPathCurrentEntry 7 }

          cwSonetPathCurrentFCs OBJECT-TYPE
              SYNTAX  Gauge
              ACCESS  read-only
              STATUS  mandatory
              DESCRIPTION
               "Number of times  that Path was in AIS or LOP
		alarm in the current 15 minute interval.
                "
              ::= { cwSonetPathCurrentEntry 8 }

          cwSonetPathCurrentUASs OBJECT-TYPE
              SYNTAX  Gauge
              ACCESS  read-only
              STATUS  mandatory
              DESCRIPTION
               "The counter associated with the number of
               Unavailable Seconds
               encountered by a Path in the current
               15 minute, interval."
          ::= { cwSonetPathCurrentEntry 9 }

         cwSonetPathCurrentClrButton OBJECT-TYPE
              SYNTAX  INTEGER {
                                noAction(1),
                                clear(2)
                        }
              ACCESS  read-write
              STATUS  mandatory
              DESCRIPTION
                 "Clears all the SONET Path's Current counters.
                 "
               ::= { cwSonetPathCurrentEntry 10 }


-- ---------------------------------------------------------
--
-- Path Current Day Group
--
-- ---------------------------------------------------------

          sonetPathCurrentDayTable OBJECT-TYPE
              SYNTAX  SEQUENCE OF SonetPathCurrentDayEntry
              ACCESS  not-accessible
              STATUS  mandatory
              DESCRIPTION
               "The SONET/SDH Path CurrentDay table."
          ::= { cwsonetPath 2 }

          sonetPathCurrentDayEntry OBJECT-TYPE
              SYNTAX  SonetPathCurrentDayEntry
              ACCESS  not-accessible
              STATUS  mandatory
              DESCRIPTION
               "An entry in the SONET/SDH Path CurrentDay table."
              INDEX   { sonetPathCurrentDayLineNum }
          ::= { sonetPathCurrentDayTable 1 }

          SonetPathCurrentDayEntry ::=
              SEQUENCE {
                  sonetPathCurrentDayLineNum         INTEGER,
                  sonetPathCurrentDayValidFlag  INTEGER,
                  sonetPathCurrentDayESs        Gauge,
                  sonetPathCurrentDaySESs       Gauge,
                  sonetPathCurrentDayCVs        Gauge,
                  sonetPathCurrentDayFCs        Gauge,
                  sonetPathCurrentDayUASs       Gauge,
                  sonetPathCurrentDayClrButton  INTEGER
              }


          sonetPathCurrentDayLineNum OBJECT-TYPE
                  SYNTAX INTEGER (1..1)
                  ACCESS read-only
                  STATUS mandatory
                  DESCRIPTION
                        " line number.
                          BNM has one line
                        "
                  ::= {sonetPathCurrentDayEntry 1}
 
          sonetPathCurrentDayValidFlag OBJECT-TYPE
              SYNTAX  INTEGER  {
                          notValid(1),
                          valid(2)
                        }
              ACCESS  read-only
              STATUS  mandatory
              DESCRIPTION
                 "Indicates if the current day bucket is valid or not.
                 "
               ::= { sonetPathCurrentDayEntry 2 }

          sonetPathCurrentDayESs OBJECT-TYPE
              SYNTAX  Gauge
              ACCESS  read-only
              STATUS  mandatory
              DESCRIPTION
               "The counter associated with the number of Errored
               Seconds encountered by a SONET/SDH
               Path in the Current day interval."
          ::= { sonetPathCurrentDayEntry 3 }
 
          sonetPathCurrentDaySESs OBJECT-TYPE
              SYNTAX  Gauge
              ACCESS  read-only
              STATUS  mandatory
              DESCRIPTION
               "The counter associated with the number of
               Severely Errored Seconds
               encountered by a SONET/SDH Path in the Current 
               day interval."
          ::= { sonetPathCurrentDayEntry 4 }
 
          sonetPathCurrentDayCVs OBJECT-TYPE
              SYNTAX  Gauge
              ACCESS  read-only
              STATUS  mandatory
              DESCRIPTION
               "The counter associated with the number of Coding
               Violations (BIP-8) encountered by a
               SONET/SDH Path in the Current day interval."
          ::= { sonetPathCurrentDayEntry 5 }
 
          sonetPathCurrentDayFCs OBJECT-TYPE
              SYNTAX  Gauge
              ACCESS  read-only
              STATUS  mandatory
              DESCRIPTION
               "Number of times  that Path was in AIS or LOP
                alarm in the Current interval.
                "
              ::= { sonetPathCurrentDayEntry 6 }
 
          sonetPathCurrentDayUASs OBJECT-TYPE
              SYNTAX  Gauge
              ACCESS  read-only
              STATUS  mandatory
              DESCRIPTION
               "The counter associated with the number of
               Unavailable Seconds
               encountered by a Path in the Current
               day, interval."
          ::= { sonetPathCurrentDayEntry 7 }
 
         sonetPathCurrentDayClrButton OBJECT-TYPE
              SYNTAX  INTEGER {
                                noAction(1),
                                clear(2)
                        }
              ACCESS  read-write
              STATUS  mandatory
              DESCRIPTION
                 "Clears all the SONET Path's CurrentDay counters.
                 "
               ::= { sonetPathCurrentDayEntry 8 }

-- ---------------------------------------------------------
--
-- Path  Interval Group
--
-- ---------------------------------------------------------
          -- the SONET/SDH Path Interval Table

          -- The SONET/SDH Path Interval Table
          -- contains various statistics
          -- collected by each system over a maximum
          -- of the previous 24 hours of
          -- operation.  The past 24 hours may be broken into 96
          -- completed 15 minute intervals.
          -- A system is required to store at
          -- least 4 completed 15 minute interval.
          -- The default value is 32 intervals.

          cwSonetPathIntervalTable OBJECT-TYPE
              SYNTAX  SEQUENCE OF CwSonetPathIntervalEntry
              ACCESS  not-accessible
              STATUS  mandatory
              DESCRIPTION
               "The SONET/SDH Path Interval table."
          ::= { cwsonetPath 3 }

          cwSonetPathIntervalEntry OBJECT-TYPE
              SYNTAX  CwSonetPathIntervalEntry
              ACCESS  not-accessible
              STATUS  mandatory
              DESCRIPTION
               "An entry in the SONET/SDH Path Interval table."
              INDEX   { cwSonetPathIntervalLineNum,
                        cwSonetPathIntervalNumber }
          ::= { cwSonetPathIntervalTable 1 }


          CwSonetPathIntervalEntry ::=
              SEQUENCE {
                   cwSonetPathIntervalLineNum         INTEGER,
                   cwSonetPathIntervalNumber     INTEGER,
                   cwSonetPathIntervalValidFlag  INTEGER,
                   cwSonetPathIntervalESs        Gauge,
                   cwSonetPathIntervalSESs       Gauge,
                   cwSonetPathIntervalCVs        Gauge,
                   cwSonetPathIntervalFCs        Gauge,
                   cwSonetPathIntervalUASs       Gauge
              }


          cwSonetPathIntervalLineNum OBJECT-TYPE
                  SYNTAX INTEGER (1..1)
                  ACCESS read-only
                  STATUS mandatory
                  DESCRIPTION
                        " line number.
                          BNM has one line
                        "
                  ::= {cwSonetPathIntervalEntry 1}

          cwSonetPathIntervalNumber OBJECT-TYPE
              SYNTAX  INTEGER (1..96)
              ACCESS  read-only
              STATUS  mandatory
              DESCRIPTION
                 "A number between 1 and 96, which identifies the
                 interval for which the set of statistics is available.
                 The interval identified by 1 is the most recently
                 completed 15 minute interval,
                 and the interval identified
                 by N is the interval immediately preceding the
                 one identified
                 by N-1."
          ::= { cwSonetPathIntervalEntry 2 }

          cwSonetPathIntervalValidFlag OBJECT-TYPE
              SYNTAX  INTEGER  {
                          notValid(1),
                          valid(2)
                        }
              ACCESS  read-only
              STATUS  mandatory
              DESCRIPTION
                 "Indicates if the bucket specified by the interval
                  is valid or not.
                 "
               ::= { cwSonetPathIntervalEntry 3 }
  
          cwSonetPathIntervalESs OBJECT-TYPE
              SYNTAX  Gauge
              ACCESS  read-only
              STATUS  mandatory
              DESCRIPTION
               "The counter associated with the number of
               Errored Seconds encountered
               by a SONET/SDH Path in a
               particular 15-minute interval
               in the past 24 hours."
          ::= { cwSonetPathIntervalEntry 4 }

          cwSonetPathIntervalSESs OBJECT-TYPE
              SYNTAX  Gauge
              ACCESS  read-only
              STATUS  mandatory
              DESCRIPTION
               "The counter associated with the number of
               Severely Errored Seconds
               encountered by a SONET/SDH Path in
               a particular 15-minute interval
               in the past 24 hours."
          ::= { cwSonetPathIntervalEntry 5 }

          cwSonetPathIntervalCVs OBJECT-TYPE
              SYNTAX  Gauge
              ACCESS  read-only
              STATUS  mandatory
              DESCRIPTION
               "The counter associated with the number of Coding
               Violations encountered by a
               SONET/SDH Path in a particular 15-minute interval
               in the past 24 hours."
          ::= { cwSonetPathIntervalEntry 6 }

          cwSonetPathIntervalFCs OBJECT-TYPE
              SYNTAX  Gauge
              ACCESS  read-only
              STATUS  mandatory
              DESCRIPTION
               "Number of times  that Path was in AIS or LOP
                alarm in a particular 15-minute interval
               in the past 24 hours."
          ::= { cwSonetPathIntervalEntry 7 }

          cwSonetPathIntervalUASs OBJECT-TYPE
              SYNTAX  Gauge
              ACCESS  read-only
              STATUS  mandatory
              DESCRIPTION
               "The counter associated with the number of
               Unavailable Seconds
               encountered by a Path in a
               particular 15-minute interval
               in the past 24 hours."
          ::= { cwSonetPathIntervalEntry 8 }

-- ----------------------------------------------------------------
--
-- Far End Path Current 15min Group
--
-- ----------------------------------------------------------------

          -- The SONET/SDH Far End Path group

          -- This group consists of two tables:
          --  - SONET/SDH Far End Path Current Table
          --  - SONET/SDH Far End Path Interval Table

          -- The SONET/SDH Far End Path Current Table

          -- The SONET/SDH Far End Path Current table
          -- contains various statistics
          -- being collected for the current 15 minute interval.
          -- The statistics are collected from
          -- the far end block error code
          -- (FEBE) within the G1 byte of the Path Overhead.
          -- The definitions are the same as described for
          -- the near-end information.

          cwSonetFarEndPathCurrentTable OBJECT-TYPE
              SYNTAX  SEQUENCE OF CwSonetFarEndPathCurrentEntry
              ACCESS  not-accessible
              STATUS  mandatory
              DESCRIPTION
                   "The SONET/SDH Far End Path Current table."
              ::= { cwsonetPath 4 }

          cwSonetFarEndPathCurrentEntry OBJECT-TYPE
              SYNTAX  CwSonetFarEndPathCurrentEntry
              ACCESS  not-accessible
              STATUS  mandatory
              DESCRIPTION
                   "An entry in the SONET/SDH Far End Path Current table."
              INDEX   { cwSonetFEPathCurrentLineNum }
              ::= { cwSonetFarEndPathCurrentTable 1 }

          CwSonetFarEndPathCurrentEntry ::=
              SEQUENCE {
                  cwSonetFEPathCurrentLineNum            		INTEGER,
                  cwSonetFarEndPathCurrentValidFlag 		INTEGER,
                  cwSonetFarEndPathCurrentTimeElapsed       	INTEGER,
                  cwSonetFarEndPathCurrentESs       		Gauge,
                  cwSonetFarEndPathCurrentSESs      		Gauge,
                  cwSonetFarEndPathCurrentCVs       		Gauge,
                  cwSonetFarEndPathCurrentFCs       		Gauge,
                  cwSonetFarEndPathCurrentUASs      		Gauge,
                  cwSonetFarEndPathCurrentClrButton 		INTEGER

              }


          cwSonetFEPathCurrentLineNum OBJECT-TYPE
                  SYNTAX INTEGER (1..1)
                  ACCESS read-only
                  STATUS mandatory
                  DESCRIPTION
                        " line number.
                          BNM has one line
                        "
                  ::= {cwSonetFarEndPathCurrentEntry 1}

          cwSonetFarEndPathCurrentValidFlag OBJECT-TYPE
              SYNTAX  INTEGER  {
                          notValid(1),
                          valid(2)
                        }
              ACCESS  read-only
              STATUS  mandatory
              DESCRIPTION
                 "Indicates if the Far End current 15min bucket is
                  valid or not.
                 "
               ::= { cwSonetFarEndPathCurrentEntry 2 }

          cwSonetFarEndPathCurrentTimeElapsed OBJECT-TYPE
              SYNTAX  INTEGER  (1..900)
              ACCESS  read-only
              STATUS  mandatory
              DESCRIPTION
                 "The number of seconds, including partial seconds,
                  that have elapsed since the beginning of the 15min
                  error-measurement period.
                 "
               ::= { cwSonetFarEndPathCurrentEntry 3 }
  
          cwSonetFarEndPathCurrentESs OBJECT-TYPE
              SYNTAX  Gauge
              ACCESS  read-only
              STATUS  mandatory
              DESCRIPTION
                   "The counter associated with the number of Far
                    Far End Errored Seconds encountered by a SONET/SDH
                    interface in the current 15 minute interval.
		   "
              ::= { cwSonetFarEndPathCurrentEntry 4 }
 
          cwSonetFarEndPathCurrentSESs OBJECT-TYPE
              SYNTAX  Gauge
              ACCESS  read-only
              STATUS  mandatory
              DESCRIPTION
                   "The counter associated with the number of
                   Far End Severely Errored Seconds
                   encountered by a SONET/SDH Path
                   interface in the current 15 minute
                   interval."
              ::= { cwSonetFarEndPathCurrentEntry 5 }

          cwSonetFarEndPathCurrentCVs OBJECT-TYPE
              SYNTAX  Gauge
              ACCESS  read-only
              STATUS  mandatory
              DESCRIPTION
                   "The counter associated with the number of
                   Far End Coding Violations reported via
                   the far end block error (FEBE) count
                   encountered by a
                   SONET/SDH Path interface in
                   the current 15 minute interval."
              ::= { cwSonetFarEndPathCurrentEntry 6 }

          cwSonetFarEndPathCurrentFCs OBJECT-TYPE
              SYNTAX  Gauge
              ACCESS  read-only
              STATUS  mandatory
              DESCRIPTION
                   "The counter associated with the number of
 		    RFIs in the current 15 minute interval."
              ::= { cwSonetFarEndPathCurrentEntry 7 }

          cwSonetFarEndPathCurrentUASs OBJECT-TYPE
             SYNTAX  Gauge
             ACCESS  read-only
             STATUS  mandatory
             DESCRIPTION
                 "The counter associated with the number of
                 Far End Unavailable Seconds
                 encountered by a
                 SONET/SDH Path interface in
                 the current 15 minute interval."
             ::= { cwSonetFarEndPathCurrentEntry 8 }

          cwSonetFarEndPathCurrentClrButton OBJECT-TYPE
              SYNTAX  INTEGER {
                                noAction(1),
                                clear(2)
                        }
              ACCESS  read-write
              STATUS  mandatory
              DESCRIPTION
                 "Clears all the Far End Path Current counters.
                 "
               ::= { cwSonetFarEndPathCurrentEntry 9 }



-- ----------------------------------------------------------------
--
-- Far End Path Current Day Group
-- 
-- ----------------------------------------------------------------

          sonetFarEndPathCurrentDayTable OBJECT-TYPE
              SYNTAX  SEQUENCE OF SonetFarEndPathCurrentDayEntry
              ACCESS  not-accessible
              STATUS  mandatory
              DESCRIPTION
                   "The SONET/SDH Far End Path CurrentDay table."
              ::= { cwsonetPath 5 }

          sonetFarEndPathCurrentDayEntry OBJECT-TYPE
              SYNTAX  SonetFarEndPathCurrentDayEntry
              ACCESS  not-accessible
              STATUS  mandatory
              DESCRIPTION
                   "An entry in the SONET/SDH Far End Path
		    CurrentDay table."
              INDEX   { sonetFEPathCurrentDayLineNum }
              ::= { sonetFarEndPathCurrentDayTable 1 }
 
          SonetFarEndPathCurrentDayEntry ::=
              SEQUENCE {
                  sonetFEPathCurrentDayLineNum            INTEGER,
                  sonetFarEndPathCurrentDayValidFlag INTEGER,
                  sonetFarEndPathCurrentDayESs       Gauge,
                  sonetFarEndPathCurrentDaySESs      Gauge,
                  sonetFarEndPathCurrentDayCVs       Gauge,
                  sonetFarEndPathCurrentDayFCs       Gauge,
                  sonetFarEndPathCurrentDayUASs      Gauge,
                  sonetFarEndPathCurrentDayClrButton INTEGER
 
              }
 
 
          sonetFEPathCurrentDayLineNum OBJECT-TYPE
                  SYNTAX INTEGER (1..1)
                  ACCESS read-only
                  STATUS mandatory
                  DESCRIPTION
                        " line number.
                          BNM has one line
                        "
                  ::= {sonetFarEndPathCurrentDayEntry 1}

          sonetFarEndPathCurrentDayValidFlag OBJECT-TYPE
              SYNTAX  INTEGER  {
                          notValid(1),
                          valid(2)
                        }
              ACCESS  read-only
              STATUS  mandatory
              DESCRIPTION
                 "Indicates if the Far End current day bucket is valid
                  or not.
                 "
               ::= { sonetFarEndPathCurrentDayEntry 2 }
 
          sonetFarEndPathCurrentDayESs OBJECT-TYPE
              SYNTAX  Gauge
              ACCESS  read-only
              STATUS  mandatory
              DESCRIPTION
                   "The counter associated with the number of Far
                   Far End Errored Seconds encountered by a SONET/SDH
                   interface in the Current day interval."
              ::= { sonetFarEndPathCurrentDayEntry 3 }
 
          sonetFarEndPathCurrentDaySESs OBJECT-TYPE
              SYNTAX  Gauge
              ACCESS  read-only
              STATUS  mandatory
              DESCRIPTION
                   "The counter associated with the number of
                   Far End Severely Errored Seconds
                   encountered by a SONET/SDH Path
                   interface in the Current day interval."
              ::= { sonetFarEndPathCurrentDayEntry 4 }
 
          sonetFarEndPathCurrentDayCVs OBJECT-TYPE
              SYNTAX  Gauge
              ACCESS  read-only
              STATUS  mandatory
              DESCRIPTION
                   "The counter associated with the number of
                   Far End Coding Violations reported via
                   the far end block error (FEBE) count
                   encountered by a
                   SONET/SDH Path interface in
                   the Current day interval."
              ::= { sonetFarEndPathCurrentDayEntry 5 }
 
          sonetFarEndPathCurrentDayFCs OBJECT-TYPE
              SYNTAX  Gauge
              ACCESS  read-only
              STATUS  mandatory
              DESCRIPTION
                   "The counter associated with the number of
                    RFIs in the Current day interval."
              ::= { sonetFarEndPathCurrentDayEntry 6 }
 
          sonetFarEndPathCurrentDayUASs OBJECT-TYPE
             SYNTAX  Gauge
             ACCESS  read-only
             STATUS  mandatory
             DESCRIPTION
                 "The counter associated with the number of
                 Far End Unavailable Seconds
                 encountered by a
                 SONET/SDH Path interface in
                 the Current day interval."
             ::= { sonetFarEndPathCurrentDayEntry 7 }
 
          sonetFarEndPathCurrentDayClrButton OBJECT-TYPE
              SYNTAX  INTEGER {
                                noAction(1),
                                clear(2)
                        }
              ACCESS  read-write
              STATUS  mandatory
              DESCRIPTION
                 "Clears all the Far End Path CurrentDay counters.
                 "
               ::= { sonetFarEndPathCurrentDayEntry 8 }

 
-- ----------------------------------------------------------------
--
-- Far End Path Interval Group
--
-- ----------------------------------------------------------------
 


          -- The SONET/SDH Far End Path Interval Table

          -- The SONET/SDH Far End Path Interval Table
          -- contains various statistics
          -- collected by each system over a maximum
          -- of the previous 24 hours of
          -- operation.  The past 24 hours may be broken into 96
          -- completed 15 minute intervals.
          -- A system is required to store at
          -- least 4 completed 15 minute interval.
          -- The default value is 32 intervals.

          cwSonetFarEndPathIntervalTable OBJECT-TYPE
              SYNTAX  SEQUENCE OF CwSonetFarEndPathIntervalEntry
              ACCESS  not-accessible
              STATUS  mandatory
              DESCRIPTION
                  "The SONET/SDH Far End Path Interval table."
              ::= { cwsonetPath 6 }

          cwSonetFarEndPathIntervalEntry OBJECT-TYPE
              SYNTAX  CwSonetFarEndPathIntervalEntry
              ACCESS  not-accessible
              STATUS  mandatory
              DESCRIPTION
                 "An entry in the SONET/SDH Far
                 End Path Interval table."
              INDEX   { cwSonetFEPathIntervalLineNum,
                        cwSonetFarEndPathIntervalNumber }
              ::= { cwSonetFarEndPathIntervalTable 1 }

          CwSonetFarEndPathIntervalEntry ::=
              SEQUENCE {
                   cwSonetFEPathIntervalLineNum             INTEGER,
                   cwSonetFarEndPathIntervalNumber     INTEGER,
                   cwSonetFarEndPathIntervalValidFlag  INTEGER,
                   cwSonetFarEndPathIntervalESs        Gauge,
                   cwSonetFarEndPathIntervalSESs       Gauge,
                   cwSonetFarEndPathIntervalCVs        Gauge,
                   cwSonetFarEndPathIntervalFCs        Gauge,
                   cwSonetFarEndPathIntervalUASs       Gauge
              }


          cwSonetFEPathIntervalLineNum OBJECT-TYPE
                  SYNTAX INTEGER (1..1)
                  ACCESS read-only
                  STATUS mandatory
                  DESCRIPTION
                        " line number.
                          BNM has one line
                        "
                  ::= {cwSonetFarEndPathIntervalEntry 1}

          cwSonetFarEndPathIntervalNumber OBJECT-TYPE
             SYNTAX  INTEGER (1..96)
             ACCESS  read-only
             STATUS  mandatory
             DESCRIPTION
                  "A number between 1 and 96, which identifies the
                  interval for which the set of statistics is available.
                  The interval identified by 1 is the most recently
                  completed 15 minute interval,
                  and the interval identified
                  by N is the interval immediately preceding the
                  one identified
                  by N-1."
             ::= { cwSonetFarEndPathIntervalEntry 2 }

          cwSonetFarEndPathIntervalValidFlag OBJECT-TYPE
              SYNTAX  INTEGER  {
                          notValid(1),
                          valid(2)
                        }
              ACCESS  read-only
              STATUS  mandatory
              DESCRIPTION
                 "Indicates if the bucket specified by the interval
                  is valid or not.
                 "
               ::= { cwSonetFarEndPathIntervalEntry 3 }

          cwSonetFarEndPathIntervalESs OBJECT-TYPE
             SYNTAX  Gauge
             ACCESS  read-only
             STATUS  mandatory
             DESCRIPTION
                  "The counter associated with the number of
                  Far End Errored Seconds encountered
                  by a SONET/SDH Path interface in a
                  particular 15-minute interval
                  in the past 24 hours."
             ::= { cwSonetFarEndPathIntervalEntry 4 }

          cwSonetFarEndPathIntervalSESs OBJECT-TYPE
             SYNTAX  Gauge
             ACCESS  read-only
             STATUS  mandatory
             DESCRIPTION
                  "The counter associated with the number of
                  Far End Severely Errored Seconds
                  encountered by a SONET/SDH Path interface
                  in a particular 15-minute interval
                  in the past 24 hours."
             ::= { cwSonetFarEndPathIntervalEntry 5 }

          cwSonetFarEndPathIntervalCVs OBJECT-TYPE
              SYNTAX  Gauge
              ACCESS  read-only
              STATUS  mandatory
              DESCRIPTION
                   "The counter associated with the number of
                   Far End Coding Violations reported via
                   the far end block error count
                   encountered by a
                   SONET/SDH Path interface
                   in a particular 15-minute interval
                   in the past 24 hours."
              ::= { cwSonetFarEndPathIntervalEntry 6 }

          cwSonetFarEndPathIntervalFCs OBJECT-TYPE
              SYNTAX  Gauge
              ACCESS  read-only
              STATUS  mandatory
              DESCRIPTION
                   "The counter associated with the number of
                    RFIs in in a particular 15-minute interval
		    in the past 24 hours."
              ::= { cwSonetFarEndPathIntervalEntry 7 }
 
          cwSonetFarEndPathIntervalUASs OBJECT-TYPE
             SYNTAX  Gauge
             ACCESS  read-only
             STATUS  mandatory
             DESCRIPTION
                 "The counter associated with the number of
                 Far End Unavailable Seconds
                 encountered by a
                 SONET/SDH Path interface in
                 a particular 15-minute interval
                 in the past 24 hours."
             ::= { cwSonetFarEndPathIntervalEntry 8 }


-- ----------------------------------------------------------------
--
-- Path Alarm Group
-- 
-- ----------------------------------------------------------------

        -- SONET/SDH Path Alarm Group.
        -- Changing any threshold will effect both the Near End and
        -- Far End threshold.

          sonetPathAlarmTable OBJECT-TYPE
              SYNTAX  SEQUENCE OF SonetPathAlarmEntry
              ACCESS  not-accessible
              STATUS  mandatory
              DESCRIPTION
                "The SONET/SDH Path Alarm table."
              ::= { cwsonetPath 7 }

          sonetPathAlarmEntry OBJECT-TYPE
              SYNTAX  SonetPathAlarmEntry
              ACCESS  not-accessible
              STATUS  mandatory
              DESCRIPTION
                "An entry in the SONET/SDH Path Alarm table."
              INDEX   { sonetPathAlarmLineNum }
              ::= { sonetPathAlarmTable 1 }


          SonetPathAlarmEntry ::=
              SEQUENCE {
                  sonetPathAlarmLineNum                           INTEGER,
                  sonetPathStatisticalAlarmSeverity          INTEGER,
                  sonetPathCurrent15minESsThreshold          INTEGER,
                  sonetPathCurrentDayESsThreshold            INTEGER,
                  sonetPathCurrent15minSESsThreshold         INTEGER,
                  sonetPathCurrentDaySESsThreshold           INTEGER,
                  sonetPathCurrent15minCVsThreshold          INTEGER,
                  sonetPathCurrentDayCVsThreshold            INTEGER,
                  sonetPathCurrent15minUASsThreshold         INTEGER,
                  sonetPathCurrentDayUASsThreshold           INTEGER,
                  sonetPathTraceSelection	             INTEGER,
                  sonetPathTraceToTransmit	             OCTET STRING,
                  sonetPathTraceToExpect	             OCTET STRING,
                  sonetPathTraceReceived	             OCTET STRING,
                  sonetPathStatAlarmStatus                   INTEGER
              }
 
 
          sonetPathAlarmLineNum OBJECT-TYPE
                  SYNTAX INTEGER (1..1)
                  ACCESS read-only
                  STATUS mandatory
                  DESCRIPTION
                        " line number.
                          BNM has one line
                        "
                  ::= {sonetPathAlarmEntry 1}
 
          sonetPathStatisticalAlarmSeverity OBJECT-TYPE
              SYNTAX  INTEGER {
                                minor(1),
                                major(2)
                        }
              ACCESS  read-write
              STATUS  mandatory
              DESCRIPTION
                 "When any statistical threshold is exceeded.
                 "
               ::= { sonetPathAlarmEntry 2 }
  
          sonetPathCurrent15minESsThreshold OBJECT-TYPE
              SYNTAX  INTEGER (0..2147483647)
              ACCESS  read-write
              STATUS  mandatory
              DESCRIPTION
                 "The default is set to 20.
                  This threshold is the same for Far End and
                  Near End.
                 "
               ::= { sonetPathAlarmEntry 3 }
  
          sonetPathCurrentDayESsThreshold OBJECT-TYPE
              SYNTAX  INTEGER (0..2147483647)
              ACCESS  read-write
              STATUS  mandatory
              DESCRIPTION
                 "The default is set to 200.
                  This threshold is the same for Far End and
                  Near End.
                 "
               ::= { sonetPathAlarmEntry 4 }
    
          sonetPathCurrent15minSESsThreshold OBJECT-TYPE
              SYNTAX  INTEGER (0..2147483647)
              ACCESS  read-write
              STATUS  mandatory
              DESCRIPTION
                 "The default is set to 3.
                  This threshold is the same for Far End and
                  Near End.
                 "
               ::= { sonetPathAlarmEntry 5 }
    
    
          sonetPathCurrentDaySESsThreshold OBJECT-TYPE
              SYNTAX  INTEGER (0..2147483647)
              ACCESS  read-write
              STATUS  mandatory
              DESCRIPTION
                 "The default is set to 7.
                  This threshold is the same for Far End and
                  Near End.
                 "
               ::= { sonetPathAlarmEntry 6 }
 
          sonetPathCurrent15minCVsThreshold OBJECT-TYPE
              SYNTAX  INTEGER (0..2147483647)
              ACCESS  read-write
              STATUS  mandatory
              DESCRIPTION
                 "The default is set to 25.
                  This threshold is the same for Far End and
                  Near End.
                 "
               ::= { sonetPathAlarmEntry 7 }
 
          sonetPathCurrentDayCVsThreshold OBJECT-TYPE
              SYNTAX  INTEGER (0..2147483647)
              ACCESS  read-write
              STATUS  mandatory
              DESCRIPTION
                 "The default is set to 250.
                  This threshold is the same for Far End and
                  Near End.
                 "
               ::= { sonetPathAlarmEntry 8 }
 
            sonetPathCurrent15minUASsThreshold OBJECT-TYPE
              SYNTAX  INTEGER (0..2147483647)
              ACCESS  read-write
              STATUS  mandatory
              DESCRIPTION
                 "The default is set to 10.
                  This threshold is the same for Far End and
                  Near End.
                 "
               ::= { sonetPathAlarmEntry 9 }
 
          sonetPathCurrentDayUASsThreshold OBJECT-TYPE
              SYNTAX  INTEGER (0..2147483647)
              ACCESS  read-write
              STATUS  mandatory
              DESCRIPTION
                 "The default is set to 10.
                  This threshold is the same for Far End and
                  Near End.
                 "
               ::= { sonetPathAlarmEntry 10 }
 
          sonetPathTraceSelection OBJECT-TYPE
              SYNTAX  INTEGER {
                          none(1),
                          sixtyFourBytes(2),
                          sixtyFourBytesCrlf(3),
                          sixteenBytes(4),
                          sixteenBytesCrc7(5),
                          sixteenBytesMsb1(6)
			}
              ACCESS  read-write
              STATUS  mandatory
              DESCRIPTION
                 "Sonet Path Trace Selection.
                 "
               ::= { sonetPathAlarmEntry 11 }
 
          sonetPathTraceToTransmit OBJECT-TYPE 
              SYNTAX  OCTET STRING (SIZE(0..64))
              ACCESS  read-write 
              STATUS  mandatory  
              DESCRIPTION 
                 "Sonet Path Trace To Transmit. 64-bytes String.
		  If 16 byte trace is selected, FW will only 
	  	  use bytes 0-15 of the string.
                 " 
               ::= { sonetPathAlarmEntry 12 } 

          sonetPathTraceToExpect OBJECT-TYPE
              SYNTAX  OCTET STRING (SIZE(0..64))
              ACCESS  read-write 
              STATUS  mandatory
              DESCRIPTION
                 "Sonet Path Trace To Expect. 64-bytes String.
                  If 16 byte trace is selected, FW will only
                  use bytes 0-15 of the string.
                 " 
               ::= { sonetPathAlarmEntry 13 } 
 
          sonetPathTraceReceived OBJECT-TYPE
              SYNTAX  OCTET STRING (SIZE(0..64))
              ACCESS  read-write
              STATUS  mandatory
              DESCRIPTION 
                 "Sonet Path Trace Received. 64-bytes String.
                  The write option is for debugging only.
                 "
               ::= { sonetPathAlarmEntry 14 }

          sonetPathStatAlarmStatus OBJECT-TYPE
              SYNTAX  INTEGER (1..'1FFFF'h)
              ACCESS  read-only
              STATUS  mandatory
              DESCRIPTION
                 "This variable indicates the
                 status of the interface.
                 The sonetPathStatAlarmStatus
                 is a bit map represented
                 as a sum, therefore,
                 it can represent multiple defects
                 simultaneously.
                 The sonetPathStatAlarmNoDefect should be
                 set if and only if
                 no other flag is set.
 
                 The various bit positions are:
                  1     sonetPathStatAlarmNoDefect
                  2     sonetPathCurrent15minESs
                  3     sonetPathCurrent15minSESs
                  4     sonetPathCurrent15minCVs
                  5     sonetPathCurrent15minUASs
                  6    	sonetFarEndPathCurrent15minESs
                  7    	sonetFarEndPathCurrent15minSESs
                  8    	sonetFarEndPathCurrent15minCVs
                  9    	sonetFarEndPathCurrent15minUASs
                  10    sonetPathCurrentDayESs
                  11    sonetPathCurrentDaySESs
                  12    sonetPathCurrentDayCVs
                  13    sonetPathCurrentDayUASs
                  14    sonetFarEndPathCurrentDayESs
                  15    sonetFarEndPathCurrentDaySESs
                  16    sonetFarEndPathCurrentDayCVs
                  17    sonetFarEndPathCurrentDayUASs
                  "
               ::= { sonetPathAlarmEntry 15 }
 
-- ----------------------------------------------------------------
--
-- Path Counter Group
--
-- ----------------------------------------------------------------

         sonetPathCounterTable OBJECT-TYPE
              SYNTAX  SEQUENCE OF SonetPathCounterEntry
              ACCESS  not-accessible
              STATUS  mandatory
              DESCRIPTION
                "The SONET/SDH Path Counter table."
              ::= { cwsonetPath 8 }


          sonetPathCounterEntry OBJECT-TYPE
              SYNTAX  SonetPathCounterEntry
              ACCESS  not-accessible
              STATUS  mandatory
              DESCRIPTION
                "An entry in the SONET/SDH Path  table."
              INDEX   { sonetPathCounterLineNum }
              ::= { sonetPathCounterTable 1 }


          SonetPathCounterEntry ::=
              SEQUENCE {
                  sonetPathCounterLineNum            INTEGER,
                  sonetPathCounterAISs          Gauge,
                  sonetPathCounterRFIs          Gauge,
                  sonetPathCounterClrButton     INTEGER
              }  



          sonetPathCounterLineNum OBJECT-TYPE
                  SYNTAX INTEGER (1..1)
                  ACCESS read-only
                  STATUS mandatory
                  DESCRIPTION
                        " line number.
                          BNM has one line
                        "
                  ::= {sonetPathCounterEntry 1}

          sonetPathCounterAISs OBJECT-TYPE
              SYNTAX  Gauge
              ACCESS  read-only
              STATUS  mandatory
              DESCRIPTION
                 "The counter associated with the number of AISs
                  encountered by a SONET/SDH.
                "
               ::= { sonetPathCounterEntry 2 }
 
 
          sonetPathCounterRFIs OBJECT-TYPE
              SYNTAX  Gauge
              ACCESS  read-only
              STATUS  mandatory
              DESCRIPTION
                 "The counter associated with the number of
                 RFIs encountered by a SONET/SDH Path.
                "
               ::= { sonetPathCounterEntry 3 }
 
          sonetPathCounterClrButton OBJECT-TYPE
              SYNTAX  INTEGER {
                                noAction(1),
                                clear(2)
                        }
              ACCESS  read-write
              STATUS  mandatory
              DESCRIPTION
                 "Clears all the Path's counters.
                 "
               ::= { sonetPathCounterEntry 4 }

-- --------------------------------------------------------------
--
-- Group "SONET"
-- This group standard within the scope of the BASIS system
--
-- --------------------------------------------------------------


-- sonetApsConfig          OBJECT IDENTIFIER ::= { cwsonetObjects 6 } 

-- ----------------------------------------------------------------
--
-- APS Config Group
--
-- ----------------------------------------------------------------

sonetApsConfig          OBJECT IDENTIFIER ::= { cwsonetObjects 6 } 

sonetApsConfigTable OBJECT-TYPE
              SYNTAX  SEQUENCE OF SonetApsConfigEntry
              ACCESS  not-accessible
              STATUS  mandatory
              DESCRIPTION
                "The Sonet APS config table"
              ::= { sonetApsConfig 1 }


sonetApsConfigEntry OBJECT-TYPE
              SYNTAX  SonetApsConfigEntry
              ACCESS  not-accessible
              STATUS  mandatory
              DESCRIPTION
                "An entry in the Sonet APS table. Each Entry is 
                 index by the working Line number.
                "
              INDEX   { apsWorkingLine }
              ::= { sonetApsConfigTable 1 }


SonetApsConfigEntry ::=
              SEQUENCE {
               apsWorkingSlot      INTEGER,
               apsWorkingLine      INTEGER,
               apsProtectionSlot   INTEGER,
               apsProtectionLine   INTEGER,
               apsEnable           INTEGER,
               apsArchMode         INTEGER,
               apsActiveLine       INTEGER,
               apsSFBER            INTEGER,
               apsSDBER            INTEGER,
               apsWtr              INTEGER,
               apsdirection        INTEGER,
               apsRevertive        INTEGER,
               apsK1K2Disable      INTEGER
              }  

apsWorkingSlot OBJECT-TYPE
              SYNTAX    INTEGER (1..32) 
              ACCESS	read-write
              STATUS	mandatory
              DESCRIPTION
              "This object is the chassis slot number of the working line
               MGX 8x50 PXM: can only be slot 7 or 8.
               MGX 8x30 PXM: can only be slot 1 or 2.
               MGX 8x50 SRME: can only be slot 15,16,31 or 32
               MGX 8x30 SRME: can only be slot 7 or 14
              "
		::= { sonetApsConfigEntry 1 }

apsWorkingLine OBJECT-TYPE
              SYNTAX    INTEGER (1..4) 
              ACCESS	read-write
              STATUS	mandatory
              DESCRIPTION
              "This object is the line number of the working line
                OC-3 : sonetLineNum in a range 1..4
                OC-12: sonetLineNum = 1 is the ONLY valid number
              "
		::= { sonetApsConfigEntry 2 }

apsProtectionSlot OBJECT-TYPE
              SYNTAX    INTEGER (1..32) 
              ACCESS	read-write
              STATUS	mandatory
              DESCRIPTION
              "This object is the chassis slot number of the protection line
               MGX 8x50 PXM: can only be slot 7 or 8.
               MGX 8x30 PXM: can only be slot 1 or 2.
               MGX 8x50 SRME: can only be slot 15,16,31 or 32
               MGX 8x30 SRME: can only be slot 7 or 14
              "
		::= { sonetApsConfigEntry 3 }

apsProtectionLine OBJECT-TYPE
              SYNTAX    INTEGER (1..4) 
              ACCESS	read-write
              STATUS	mandatory
              DESCRIPTION
              "This object is the line number of the working line
                OC-3 : sonetLineNum in a range 1..4
                OC-12: sonetLineNum = 1 is the ONLY valid number
              "
		::= { sonetApsConfigEntry 4 }

apsEnable  OBJECT-TYPE
              SYNTAX    INTEGER {
                        apsFeatDisable (1),
                        apsFeatEnable  (2)
              }
              ACCESS	read-write
              STATUS	mandatory
              DESCRIPTION
              "This object is used to enable or disable APS feature
               on the working/protection line pairs. 
              "
		::= { sonetApsConfigEntry 5 }


apsArchMode OBJECT-TYPE
              SYNTAX    INTEGER {
                        singleCardonePlusOne (1),
                        dualCardonePlusOne   (2),
                        singleCardOneToOne   (3),
                        anexBOnePlusOne      (4),
                        anexAOnePlusOne      (5)
              }
              ACCESS	read-write
              STATUS	mandatory
              DESCRIPTION
              "This object is used to configure APS architecture mode
               on the working/protection line pairs. The architecture 
               modes currently supported are 'dualCardonePlusOne' 
               (for GR-253)  and 'anexAOnePlusOne (for G.783 Annex A).
              "
		::= { sonetApsConfigEntry 6 }

apsActiveLine OBJECT-TYPE
              SYNTAX    INTEGER {
                        apsWorkingLine    (1),
                        apsProtectionLine (2)
              }
              ACCESS	read-only
              STATUS	mandatory
              DESCRIPTION
              "This object indicates which line is currently active
               ob the trunk line.
              "
		::= { sonetApsConfigEntry 7 }

apsSFBER OBJECT-TYPE
              SYNTAX    INTEGER (3..13) 
              ACCESS	read-write
              STATUS	mandatory
              DESCRIPTION
              "This object contains the Bit Error Rate threshold for 
              Signal Fault detection on the working line. 
              "
		::= { sonetApsConfigEntry 8 }

apsSDBER OBJECT-TYPE
              SYNTAX    INTEGER (5..13) 
              ACCESS	read-write
              STATUS	mandatory
              DESCRIPTION
              "This object contains the Bit Error Rate threshold for 
              Signal Degrade detection on the working line. If set to
              5, it means SDBER rate = 10 ^^ -5.
              "
		::= { sonetApsConfigEntry 9 }

apsWtr OBJECT-TYPE
              SYNTAX    INTEGER (0..12) 
              ACCESS	read-write
              STATUS	mandatory
              DESCRIPTION
              "This object contains interval (in minute) to wait before  
               attempting to switch back to working line. Not applicable
               if the line configure in non-revertive mode.
              "
		::= { sonetApsConfigEntry 10 }

apsdirection OBJECT-TYPE
              SYNTAX    INTEGER {
                        uniDirectional (1),
                        biDirectional  (2)
              }
              ACCESS	read-write
              STATUS	mandatory
              DESCRIPTION
              "This object is used to configure the switching direction
               which this APS line support. Unidirectional switch only one
               direction. Bidirectional switch in both ends of the line. 
              "
		::= { sonetApsConfigEntry 11 }


apsRevertive OBJECT-TYPE
              SYNTAX    INTEGER {
                        nonrevertive (1),
                        revertive    (2)
              }
              ACCESS	read-write
              STATUS	mandatory
              DESCRIPTION
              "This object is used to configure the APS revertive or
               nonrevertive option. Revertive allows the line to be 
               switch back to  working line after the Wait-To-restore interval
               has expired and the working line SF/SD has been cleared.
              "
		::= { sonetApsConfigEntry 12 }


apsK1K2Disable  OBJECT-TYPE
              SYNTAX    INTEGER {
                        kbandEnable  (1),
                        kbandDisable (2)
              }
              ACCESS	read-write
              STATUS	mandatory
              DESCRIPTION
              "This object is used to enable or disable the K1/K2 inband
               interface on the protection line.
              "
		::= { sonetApsConfigEntry 13 }


apsCardFailureCode OBJECT-TYPE
              SYNTAX  INTEGER {
                      apsProtectBCMissing (1),
                      apsProtectDCMissing (2),
                      apsWorkingBCMissing (3),
                      apsWorkingDCMissing (4),
                      apsWorkingCdMismatch (5),
                      apsProtectCdMismatch (6)
              }
              ACCESS  read-only
              STATUS  mandatory
              DESCRIPTION
                "The Sonet APS card failure code
                  apsProtectBCMissing = protection Back card missing 
                  apsProtectDCMissing = protection Daughter card missing
                  apsWorkingBCMissing = Working Back card missing
                  apsWorkingDCMissing = Working Daughter card missing
                  apsWorkingCdMismatch = Working Card in mismatch/fail state
                  apsProtectCdMismatch = protection card in mismatch/fail state
                "
              ::= { sonetApsConfig 2 }

apsLineFailureCode OBJECT-TYPE
              SYNTAX  INTEGER {
                      apsSignalDegrade (1),
                      apsSignalFailure (2),
                      apsLineAlarm (3),
                      apsLineLoopBack (4)
              }
              ACCESS  read-only
              STATUS  mandatory
              DESCRIPTION
                "The Sonet APS line failure code"
              ::= { sonetApsConfig 3 }

apsLineSwReason OBJECT-TYPE
              SYNTAX  INTEGER {
                      apsRevertive (1),
                      apsManual (2),
                      apsSignalDefectLow (3),
                      apsSignalDefectHigh (4),
                      apsSignalFailureLow (5),
                      apsSignalFailureHigh (6),
                      apsForceSwitch       (7),
                      apsLockOut           (8)
                                            
              }
              ACCESS  read-only
              STATUS  mandatory
              DESCRIPTION
                "The Sonet APS line switch reason code
                "
              ::= { sonetApsConfig 4 }

apsLineSwFailureCode OBJECT-TYPE
              SYNTAX  INTEGER {
                      apsRevertiveSwitchFail (1),
                      apsManualSwitchFail    (2),
                      apsSDLowSwitchFail     (3),
                      apsSDHighSwitchFail    (4),
                      apsSFLowSwitchFail     (5),
                      apsSFHighSwitchFail    (6),
                      apsForceSwitchFail     (7),
                      apsLockOutSwitchFail   (8)
                                                        }
              ACCESS  read-only
              STATUS  mandatory
              DESCRIPTION
                "The Sonet APS line switch failure code"
              ::= { sonetApsConfig 5 }

apsStandbyLineFailureCode OBJECT-TYPE
              SYNTAX  INTEGER {
                      apsSignalDegrade (1),
                      apsSignalFailure (2),
                      apsLineAlarm (3),
                      apsLineLoopBack (4),
                      apsProtectionByteFail (5),
                      apsArchitectureMismatch (6),
                      apsChannelMismatch      (7),
                      apsDirectionMismatch    (8),
                      apsWrongRequest         (9)
                                                        }
              ACCESS  read-only
              STATUS  mandatory
              DESCRIPTION
                "The Sonet APS standby line failure code"
              ::= { sonetApsConfig 6 }
 
END
