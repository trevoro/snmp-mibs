--			Ascend mibpctfi MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBPCTFI-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibpctfiNetworkProfile  OBJECT IDENTIFIER ::= { configuration 18}

	-- The mibpctfiNetworkProfile table
	--
	-- This table contains parameters for the mibpctfiNetworkProfile profile
	--

    mibpctfiNetworkProfileTable	OBJECT-TYPE
	SYNTAX		SEQUENCE OF MibpctfiNetworkProfileEntry
	ACCESS		not-accessible
	STATUS		mandatory
	DESCRIPTION	"A list of mibpctfiNetworkProfile profile entries."
	::= { mibpctfiNetworkProfile 1 }

    mibpctfiNetworkProfileEntry	OBJECT-TYPE
	SYNTAX		MibpctfiNetworkProfileEntry
	ACCESS		not-accessible
	STATUS		mandatory
	DESCRIPTION	"A mibpctfiNetworkProfile entry containing objects that
			 maps to the parameters of mibpctfiNetworkProfile profile."
	INDEX		{ pctfiNetworkProfile-Shelf-o, pctfiNetworkProfile-Slot-o, pctfiNetworkProfile-Item-o }
	::= { mibpctfiNetworkProfileTable 1 }

    MibpctfiNetworkProfileEntry ::=
	SEQUENCE {
	    pctfiNetworkProfile-Shelf-o
		INTEGER,
	    pctfiNetworkProfile-Slot-o
		INTEGER,
	    pctfiNetworkProfile-Item-o
		INTEGER,
	    pctfiNetworkProfile-Name
		DisplayString,
	    pctfiNetworkProfile-PhysicalAddress-Shelf
		INTEGER,
	    pctfiNetworkProfile-PhysicalAddress-Slot
		INTEGER,
	    pctfiNetworkProfile-PhysicalAddress-ItemNumber
		INTEGER,
	    pctfiNetworkProfile-Enabled
		INTEGER,
	    pctfiNetworkProfile-InterfaceVersion
		INTEGER,
	    pctfiNetworkProfile-TraceId0
		INTEGER,
	    pctfiNetworkProfile-TraceId1
		INTEGER,
	    pctfiNetworkProfile-Mode
		INTEGER,
	    pctfiNetworkProfile-Action-o
		INTEGER
	}

    pctfiNetworkProfile-Shelf-o	OBJECT-TYPE
	SYNTAX	INTEGER
	ACCESS	read-only
	STATUS	mandatory
	DESCRIPTION	""
	::= { mibpctfiNetworkProfileEntry 1 }

    pctfiNetworkProfile-Slot-o	OBJECT-TYPE
	SYNTAX	INTEGER
	ACCESS	read-only
	STATUS	mandatory
	DESCRIPTION	""
	::= { mibpctfiNetworkProfileEntry 2 }

    pctfiNetworkProfile-Item-o	OBJECT-TYPE
	SYNTAX	INTEGER
	ACCESS	read-only
	STATUS	mandatory
	DESCRIPTION	""
	::= { mibpctfiNetworkProfileEntry 3 }

    pctfiNetworkProfile-Name	OBJECT-TYPE
	SYNTAX	DisplayString
	ACCESS	read-write
	STATUS	mandatory
	DESCRIPTION	"Name of PCTFI network link."
	::= { mibpctfiNetworkProfileEntry 4 }

    pctfiNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibpctfiNetworkProfileEntry 5 }

    pctfiNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibpctfiNetworkProfileEntry 6 }

    pctfiNetworkProfile-PhysicalAddress-ItemNumber	OBJECT-TYPE
	SYNTAX	INTEGER
	ACCESS	read-write
	STATUS	mandatory
	DESCRIPTION	"A number that specifies an addressable entity within the context of shelf and slot."
	::= { mibpctfiNetworkProfileEntry 7 }

    pctfiNetworkProfile-Enabled	OBJECT-TYPE
	SYNTAX	INTEGER {
		    no (1),
		    yes (2)
		}
	ACCESS	read-write
	STATUS	mandatory
	DESCRIPTION	"TRUE if the link is enabled, otherwise FALSE."
	::= { mibpctfiNetworkProfileEntry 8 }

    pctfiNetworkProfile-InterfaceVersion	OBJECT-TYPE
	SYNTAX	INTEGER {
		    firstOffice (2),
		    pelts (16)
		}
	ACCESS	read-write
	STATUS	mandatory
	DESCRIPTION	"Valid version numbers for PCTFI links."
	::= { mibpctfiNetworkProfileEntry 9 }

    pctfiNetworkProfile-TraceId0	OBJECT-TYPE
	SYNTAX	INTEGER
	ACCESS	read-write
	STATUS	mandatory
	DESCRIPTION	"An enumeration of a terminated PCTFI link from the switch perspective for link 0."
	::= { mibpctfiNetworkProfileEntry 10 }

    pctfiNetworkProfile-TraceId1	OBJECT-TYPE
	SYNTAX	INTEGER
	ACCESS	read-write
	STATUS	mandatory
	DESCRIPTION	"An enumeration of a terminated PCTFI link from the switch perspective for link 1."
	::= { mibpctfiNetworkProfileEntry 11 }

    pctfiNetworkProfile-Mode	OBJECT-TYPE
	SYNTAX	INTEGER {
		    t1 (1),
		    e1 (2)
		}
	ACCESS	read-write
	STATUS	mandatory
	DESCRIPTION	"PCTFI link is provisioned as T1 or E1 mode."
	::= { mibpctfiNetworkProfileEntry 12 }

    pctfiNetworkProfile-Action-o	OBJECT-TYPE
	SYNTAX	INTEGER {
		    noAction (1),
		    createProfile (2),
		    deleteProfile (3)
		}
	ACCESS	read-write
	STATUS	mandatory
	DESCRIPTION	""
	::= { mibpctfiNetworkProfileEntry 13 }

END
