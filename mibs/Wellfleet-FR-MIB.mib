Wellfleet-FR-MIB DEFINITIONS ::= BEGIN

-- Created by mdl2asn version 3.1
-- Creation date: Wed Aug 30 16:41:07 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfFrameRelayGroup
        FROM Wellfleet-COMMON-MIB;


    wfFrDlcmiTable OBJECT-TYPE
        SYNTAX	SEQUENCE OF WfFrDlcmiEntry
        ACCESS	not-accessible
        STATUS	mandatory
        DESCRIPTION
                "The Parameters for the Data Link Connection Management Interface"
        ::= { wfFrameRelayGroup 1 }

    wfFrDlcmiEntry OBJECT-TYPE
        SYNTAX	WfFrDlcmiEntry
        ACCESS	not-accessible
        STATUS	mandatory
        DESCRIPTION
                "The parameters for a particular Data Link Connection Management Interface"
        INDEX	{ wfFr1DlcmiCircuit }
        ::= { wfFrDlcmiTable 1 }

    WfFrDlcmiEntry ::= SEQUENCE {
    	    wfFr1DlcmiDelete
    		INTEGER,
    	    wfFr1DlcmiDisable
    		INTEGER,
    	    wfFr1DlcmiState
    		INTEGER,
    	    wfFr1DlcmiCircuit
    		INTEGER,
    	    wfFr1DlcmiManagementType
    		INTEGER,
    	    wfFr1DlcmiStatus
    		INTEGER,
    	    wfFr1DlcmiAddress
    		INTEGER,
    	    wfFr1DlcmiAddressLen
    		INTEGER,
    	    wfFr1DlcmiPollingInterval
    		INTEGER,
    	    wfFr1DlcmiFullEnquiryInterval
    		INTEGER,
    	    wfFr1DlcmiErrorThreshold
    		INTEGER,
    	    wfFr1DlcmiMonitoredEvents
    		INTEGER,
    	    wfFr1DlcmiMaxSupportedVCs
    		INTEGER,
    	    wfFr1DlcmiMulticast
    		INTEGER,
    	    wfFr1DlcmiSeqCount
    		INTEGER,
    	    wfFr1DlcmiLastReceived
    		INTEGER,
    	    wfFr1DlcmiPassiveSeqCount
    		INTEGER,
    	    wfFr1DlcmiPassiveReceived
    		INTEGER,
    	    wfFr1DlcmiPolls
    		INTEGER,
    	    wfFr1DlcmiAlarmTimer
    		INTEGER,
    	    wfFr1ErrType
    		INTEGER,
    	    wfFr1ErrData
    		OCTET STRING,
    	    wfFr1ErrTime
    		TimeTicks,
    	    wfFr1ErrDiscards
    		Counter,
    	    wfFr1ErrDrops
    		Counter
        }

    wfFr1DlcmiDelete OBJECT-TYPE
        SYNTAX	INTEGER {
    		    created(1),
    		    deleted(2)
    		}
        ACCESS	read-write
        STATUS	mandatory
        DESCRIPTION
                "Indication to delete this frame relay interface"
        DEFVAL	{ created }
        ::= { wfFrDlcmiEntry 1 }

    wfFr1DlcmiDisable OBJECT-TYPE
        SYNTAX	INTEGER {
    		    enabled(1),
    		    disabled(2)
    		}
        ACCESS	read-write
        STATUS	mandatory
        DESCRIPTION
                "Indicates when a dlcmi entry is to be enabled or disabled."
        DEFVAL	{ enabled }
        ::= { wfFrDlcmiEntry 2 }

    wfFr1DlcmiState OBJECT-TYPE
        SYNTAX	INTEGER {
    		    up(1),
    		    down(2),
    		    init(3),
    		    notpresent(4)
    		}
        ACCESS	read-only
        STATUS	mandatory
        DESCRIPTION
                "The current state of Frame Relay. The not present state is not actually
                valid except when the record is first added.  It is included for
                consistency."
        DEFVAL	{ notpresent }
        ::= { wfFrDlcmiEntry 3 }

    wfFr1DlcmiCircuit OBJECT-TYPE
        SYNTAX	INTEGER
        ACCESS	read-only
        STATUS	mandatory
        DESCRIPTION
                "Instance identifier.  The circuit number of this entry"
        ::= { wfFrDlcmiEntry 4 }

    wfFr1DlcmiManagementType OBJECT-TYPE
        SYNTAX	INTEGER {
    		    none(1),
    		    lmi(2),
    		    t1617d(3),
    		    t1617b(4),
    		    annexa(5),
    		    lmiswitch(6),
    		    annexdswitch(7),
    		    annexaswitch(8)
    		}
        ACCESS	read-write
        STATUS	mandatory
        DESCRIPTION
                "This variable indicates which Data Link Connection Management
                scheme is active (and by implication, what DLCI it uses)."
        DEFVAL	{ t1617d }
        ::= { wfFrDlcmiEntry 5 }

    wfFr1DlcmiStatus OBJECT-TYPE
        SYNTAX	INTEGER {
    		    start(1),
    		    running(2),
    		    fault(3),
    		    recovered(4)
    		}
        ACCESS	read-only
        STATUS	mandatory
        DESCRIPTION
                "Indicates the status of the interface.
                FR1_STATUS_START is the state during rebooting or initial
                 start of circuit
                FR1_STATUS_RUNNING1 is the sate after the circuit is up (either LMI
                 successful or there is no DLCMI and the system just comes up).
                FR1_STATUS_FAULT is a transient state indicating that errors have
                 caused the circuit to be disabled until DLCMI recovery.
                FR1_STATUS_RECOVERED indicates that an the system has been in the
                 FR_STATUS_FAULT mode before, but has since recovered."
        DEFVAL	{ start }
        ::= { wfFrDlcmiEntry 6 }

    wfFr1DlcmiAddress OBJECT-TYPE
        SYNTAX	INTEGER {
    		    q921(1),
    		    q922march90(2),
    		    q922november90(3),
    		    q922(4)
    		}
        ACCESS	read-write
        STATUS	mandatory
        DESCRIPTION
                "This states which address format is in use on the FR interface.
                The default is Q922"
        DEFVAL	{ q922 }
        ::= { wfFrDlcmiEntry 7 }

    wfFr1DlcmiAddressLen OBJECT-TYPE
        SYNTAX	INTEGER {
    		    twobyte(2),
    		    threebyte(3),
    		    fourbyte(4)
    		}
        ACCESS	read-write
        STATUS	mandatory
        DESCRIPTION
                "This variable states the address length in octets. In the case
                of Q922 format, the length indicates the entire length of the
                address includeding the control portion."
        DEFVAL	{ twobyte }
        ::= { wfFrDlcmiEntry 8 }

    wfFr1DlcmiPollingInterval OBJECT-TYPE
        SYNTAX	INTEGER(5..30)
        ACCESS	read-write
        STATUS	mandatory
        DESCRIPTION
                "The number of seconds between successive status enquiry messages"
        DEFVAL	{ 10 }
        ::= { wfFrDlcmiEntry 9 }

    wfFr1DlcmiFullEnquiryInterval OBJECT-TYPE
        SYNTAX	INTEGER(1..255)
        ACCESS	read-write
        STATUS	mandatory
        DESCRIPTION
                "The number of status enquiry intervals that pass before issuance
                of a full status enquiry message."
        DEFVAL	{ 6 }
        ::= { wfFrDlcmiEntry 10 }

    wfFr1DlcmiErrorThreshold OBJECT-TYPE
        SYNTAX	INTEGER
        ACCESS	read-write
        STATUS	mandatory
        DESCRIPTION
                "This is the maximum number of unanswered Status Enquiries the
                equipment shall accept before declaring the interface down."
        DEFVAL	{ 3 }
        ::= { wfFrDlcmiEntry 11 }

    wfFr1DlcmiMonitoredEvents OBJECT-TYPE
        SYNTAX	INTEGER
        ACCESS	read-write
        STATUS	mandatory
        DESCRIPTION
                "This is the number of status polling intervals over
                which the error threshold is counted.  For example, if
                within 'MonitoredEvents' number of events the station
                receives 'ErrorThreshold' number of errors, the
                interface is marked as down."
        DEFVAL	{ 4 }
        ::= { wfFrDlcmiEntry 12 }

    wfFr1DlcmiMaxSupportedVCs OBJECT-TYPE
        SYNTAX	INTEGER
        ACCESS	read-only
        STATUS	mandatory
        DESCRIPTION
                "The maximum number of Virtual Circuits allowed for
                this interface.  Usually dictated by the Frame Relay
                network. The system sets this initially."
        ::= { wfFrDlcmiEntry 13 }

    wfFr1DlcmiMulticast OBJECT-TYPE
        SYNTAX	INTEGER {
    		    enabled(1),
    		    disabled(2)
    		}
        ACCESS	read-write
        STATUS	mandatory
        DESCRIPTION
                "This indicates whether the frame relay provider offers a multicast"
        DEFVAL	{ disabled }
        ::= { wfFrDlcmiEntry 14 }

    wfFr1DlcmiSeqCount OBJECT-TYPE
        SYNTAX	INTEGER(1..255)
        ACCESS	read-only
        STATUS	mandatory
        DESCRIPTION
                "This station's sequence counter. It represents the next
                value to send."
        DEFVAL	{ 1 }
        ::= { wfFrDlcmiEntry 15 }

    wfFr1DlcmiLastReceived OBJECT-TYPE
        SYNTAX	INTEGER(1..255)
        ACCESS	read-only
        STATUS	mandatory
        DESCRIPTION
                "The sequence number just received from the switch."
        DEFVAL	{ 1 }
        ::= { wfFrDlcmiEntry 16 }

    wfFr1DlcmiPassiveSeqCount OBJECT-TYPE
        SYNTAX	INTEGER(1..255)
        ACCESS	read-only
        STATUS	mandatory
        DESCRIPTION
                "This station's sequence counter for answering status enquiry."
        DEFVAL	{ 1 }
        ::= { wfFrDlcmiEntry 17 }

    wfFr1DlcmiPassiveReceived OBJECT-TYPE
        SYNTAX	INTEGER(1..255)
        ACCESS	read-only
        STATUS	mandatory
        DESCRIPTION
                "The sequence number just received from the enquring station."
        DEFVAL	{ 1 }
        ::= { wfFrDlcmiEntry 18 }

    wfFr1DlcmiPolls OBJECT-TYPE
        SYNTAX	INTEGER
        ACCESS	read-only
        STATUS	mandatory
        DESCRIPTION
                "This is the counter of where we are in the polling cycle."
        ::= { wfFrDlcmiEntry 19 }

    wfFr1DlcmiAlarmTimer OBJECT-TYPE
        SYNTAX	INTEGER
        ACCESS	read-only
        STATUS	mandatory
        DESCRIPTION
                "This is a counter of 1/2 second timeouts. When it reaches
                2 x the polling interval, an enquiry message is sent."
        ::= { wfFrDlcmiEntry 20 }

    wfFr1ErrType OBJECT-TYPE
        SYNTAX	INTEGER {
    		    unknown(1),
    		    short(2),
    		    long(3),
    		    illegaldlci(4),
    		    unknowndlci(5),
    		    protoerr(6),
    		    unknownie(7),
    		    sequenceerr(8),
    		    unknownrpt(9),
    		    reset(10),
    		    cntrl(11)
    		}
        ACCESS	read-only
        STATUS	mandatory
        DESCRIPTION
                "Indicate the type of the last specific monitored error."
        ::= { wfFrDlcmiEntry 21 }

    wfFr1ErrData OBJECT-TYPE
        SYNTAX	OCTET STRING
        ACCESS	read-only
        STATUS	mandatory
        DESCRIPTION
                "Contains as much of the error packet as possible."
        ::= { wfFrDlcmiEntry 22 }

    wfFr1ErrTime OBJECT-TYPE
        SYNTAX	TimeTicks
        ACCESS	read-only
        STATUS	mandatory
        DESCRIPTION
                "The time the last error occurred."
        ::= { wfFrDlcmiEntry 23 }

    wfFr1ErrDiscards OBJECT-TYPE
        SYNTAX	Counter
        ACCESS	read-only
        STATUS	mandatory
        DESCRIPTION
                "The number of inbound frames dropped because of format or other
                errors or because the VC was not known."
        ::= { wfFrDlcmiEntry 24 }

    wfFr1ErrDrops OBJECT-TYPE
        SYNTAX	Counter
        ACCESS	read-only
        STATUS	mandatory
        DESCRIPTION
                "The number of outbound frames dropped. Usually this is due the
                specified DLCI being unknown or a broadcast packet is too long"
        ::= { wfFrDlcmiEntry 25 }

    wfFrCircuitTable OBJECT-TYPE
        SYNTAX	SEQUENCE OF WfFrCircuitEntry
        ACCESS	not-accessible
        STATUS	mandatory
        DESCRIPTION
                "Frame Relay Circuit table gives information about a virtual circuits."
        ::= { wfFrameRelayGroup 2 }

    wfFrCircuitEntry OBJECT-TYPE
        SYNTAX	WfFrCircuitEntry
        ACCESS	not-accessible
        STATUS	mandatory
        DESCRIPTION
                "An entry in the Frame Relay Circuit table."
        INDEX	{ wfFr1CircuitNumber,
    		  wfFr1CircuitDlci }
        ::= { wfFrCircuitTable 1 }

    WfFrCircuitEntry ::= SEQUENCE {
    	    wfFr1CircuitDelete
    		INTEGER,
    	    wfFr1CircuitNumber
    		INTEGER,
    	    wfFr1CircuitDlci
    		INTEGER,
    	    wfFr1CircuitState
    		INTEGER,
    	    wfFr1CircuitStateSet
    		INTEGER,
    	    wfFr1CircuitReceivedFECNs
    		Counter,
    	    wfFr1CircuitReceivedBECNs
    		Counter,
    	    wfFr1CircuitSentFrames
    		Counter,
    	    wfFr1CircuitSentOctets
    		Counter,
    	    wfFr1CircuitReceivedFrames
    		Counter,
    	    wfFr1CircuitReceivedOctets
    		Counter,
    	    wfFr1CircuitCreationTime
    		TimeTicks,
    	    wfFr1CircuitLastTimeChange
    		TimeTicks,
    	    wfFr1CircuitCommittedBurst
    		INTEGER,
    	    wfFr1CircuitExcessBurst
    		INTEGER,
    	    wfFr1CircuitThroughput
    		INTEGER,
    	    wfFr1CircuitMulticast
    		INTEGER,
    	    wfFr1CircuitDiscards
    		Counter,
    	    wfFr1CircuitDrops
    		Counter,
    	    wfFr1CircuitSubCct
    		INTEGER,
    	    wfFr1CircuitMode
    		INTEGER
        }

    wfFr1CircuitDelete OBJECT-TYPE
        SYNTAX	INTEGER {
    		    created(1),
    		    deleted(2),
    		    system(3)
    		}
        ACCESS	read-write
        STATUS	mandatory
        DESCRIPTION
                "Indication to delete this frame relay interface."
        DEFVAL	{ created }
        ::= { wfFrCircuitEntry 1 }

    wfFr1CircuitNumber OBJECT-TYPE
        SYNTAX	INTEGER
        ACCESS	read-only
        STATUS	mandatory
        DESCRIPTION
                "Instance identifier.  The circuit number of this interface."
        ::= { wfFrCircuitEntry 2 }

    wfFr1CircuitDlci OBJECT-TYPE
        SYNTAX	INTEGER {
    		    twobyteminimum(16),
    		    twobytemaximum(1007),
    		    threebyteminimum(1024),
    		    threebytemaximum(64511),
    		    fourbyteminimum(131072),
    		    fourbytemaximum(8257535)
    		}
        ACCESS	read-only
        STATUS	mandatory
        DESCRIPTION
                "Instance identifier.  This indicates which virtual circuit."
        ::= { wfFrCircuitEntry 3 }

    wfFr1CircuitState OBJECT-TYPE
        SYNTAX	INTEGER {
    		    invalid(1),
    		    active(2),
    		    inactive(3),
    		    xoff(4),
    		    control(5)
    		}
        ACCESS	read-only
        STATUS	mandatory
        DESCRIPTION
                "Indicates the state of the particular virtual circuit."
        DEFVAL	{ invalid }
        ::= { wfFrCircuitEntry 4 }

    wfFr1CircuitStateSet OBJECT-TYPE
        SYNTAX	INTEGER {
    		    invalid(1),
    		    active(2),
    		    inactive(3)
    		}
        ACCESS	read-write
        STATUS	mandatory
        DESCRIPTION
                "User access for setting the state of a virtual circuit"
        DEFVAL	{ invalid }
        ::= { wfFrCircuitEntry 5 }

    wfFr1CircuitReceivedFECNs OBJECT-TYPE
        SYNTAX	Counter
        ACCESS	read-only
        STATUS	mandatory
        DESCRIPTION
                "Number of frames received indicating forward congestion."
        ::= { wfFrCircuitEntry 6 }

    wfFr1CircuitReceivedBECNs OBJECT-TYPE
        SYNTAX	Counter
        ACCESS	read-only
        STATUS	mandatory
        DESCRIPTION
                "Number of frames received indicating backward congestion."
        ::= { wfFrCircuitEntry 7 }

    wfFr1CircuitSentFrames OBJECT-TYPE
        SYNTAX	Counter
        ACCESS	read-only
        STATUS	mandatory
        DESCRIPTION
                "The number of frames sent from this virtual circuit."
        ::= { wfFrCircuitEntry 8 }

    wfFr1CircuitSentOctets OBJECT-TYPE
        SYNTAX	Counter
        ACCESS	read-only
        STATUS	mandatory
        DESCRIPTION
                "The number of octets sent from this virtual circuit."
        ::= { wfFrCircuitEntry 9 }

    wfFr1CircuitReceivedFrames OBJECT-TYPE
        SYNTAX	Counter
        ACCESS	read-only
        STATUS	mandatory
        DESCRIPTION
                "The number of frames received from this virtual circuit."
        ::= { wfFrCircuitEntry 10 }

    wfFr1CircuitReceivedOctets OBJECT-TYPE
        SYNTAX	Counter
        ACCESS	read-only
        STATUS	mandatory
        DESCRIPTION
                "The number of octets received from this virtual circuit."
        ::= { wfFrCircuitEntry 11 }

    wfFr1CircuitCreationTime OBJECT-TYPE
        SYNTAX	TimeTicks
        ACCESS	read-only
        STATUS	mandatory
        DESCRIPTION
                "The value of sysUpTime when the vc was created."
        ::= { wfFrCircuitEntry 12 }

    wfFr1CircuitLastTimeChange OBJECT-TYPE
        SYNTAX	TimeTicks
        ACCESS	read-only
        STATUS	mandatory
        DESCRIPTION
                "The value of sysUpTime when last there was a change in vc state."
        ::= { wfFrCircuitEntry 13 }

    wfFr1CircuitCommittedBurst OBJECT-TYPE
        SYNTAX	INTEGER
        ACCESS	read-write
        STATUS	mandatory
        DESCRIPTION
                "Indicates the maximum amount of data, in bits, that the network
                agrees to transfer under normal conditions, during the measurement
                interval.  Wellfleet does not presently support this."
        ::= { wfFrCircuitEntry 14 }

    wfFr1CircuitExcessBurst OBJECT-TYPE
        SYNTAX	INTEGER
        ACCESS	read-write
        STATUS	mandatory
        DESCRIPTION
                "Indicates teh maximum amount of uncommitted data bits that the network
                will attempt to deliver over the measurement interval.  Wellfleet
                does not presently support this."
        ::= { wfFrCircuitEntry 15 }

    wfFr1CircuitThroughput OBJECT-TYPE
        SYNTAX	INTEGER
        ACCESS	read-write
        STATUS	mandatory
        DESCRIPTION
                "This is the average number of 'Frame Relay Information Field'
                bits transferred per second across a user network interface in one
                direction, measured over the measurement interval.  Wellfleet
                does not presently support this."
        ::= { wfFrCircuitEntry 16 }

    wfFr1CircuitMulticast OBJECT-TYPE
        SYNTAX	INTEGER {
    		    multicast(1),
    		    unicast(2)
    		}
        ACCESS	read-write
        STATUS	mandatory
        DESCRIPTION
                "Indicates whether this DLCI is used for multicast or single destination."
        DEFVAL	{ unicast }
        ::= { wfFrCircuitEntry 17 }

    wfFr1CircuitDiscards OBJECT-TYPE
        SYNTAX	Counter
        ACCESS	read-only
        STATUS	mandatory
        DESCRIPTION
                "The number of inbound frames discarded because of format errors,
                because the VC is inactive or because the protocol was not registered
                for this circuit."
        ::= { wfFrCircuitEntry 18 }

    wfFr1CircuitDrops OBJECT-TYPE
        SYNTAX	Counter
        ACCESS	read-only
        STATUS	mandatory
        DESCRIPTION
                "Indicates how many outbound frames were dropped. Usually these are
                dropped because the VC is not active."
        ::= { wfFrCircuitEntry 19 }

    wfFr1CircuitSubCct OBJECT-TYPE
        SYNTAX	INTEGER
        ACCESS	read-write
        STATUS	mandatory
        DESCRIPTION
                "Circuit number to use for this VC when configured in hybrid
                (for bridging) or direct access (VC as a circuit) mode."
        ::= { wfFrCircuitEntry 20 }

    wfFr1CircuitMode OBJECT-TYPE
        SYNTAX	INTEGER {
    		    group(1),
    		    hybrid(2),
    		    direct(3)
    		}
        ACCESS	read-write
        STATUS	mandatory
        DESCRIPTION
                "The mode of the given VC.
                GROUP - treats the VC as one of many vc's on a circuit.
                HYBRID - treats the VC as one of many vc's on a circuit for
                  protocol traffic, but as a separate circuit for bridging.
                DIRECT - treats the VC as a separate circuit for all applications."
        DEFVAL	{ group }
        ::= { wfFrCircuitEntry 21 }

    END  -- Wellfleet-FR-MIB
