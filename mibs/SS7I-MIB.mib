--******************************************************************
--*
--*         Copyright (c) 1993, 1999 by 3Com Corporation
--*                    All Rights Reserved
--*
--*    $Revision:   7.2  $
--*    $Date:   Aug 13 1999 11:33:38  $
--*
--*    3COM SS7I MIB
--*
--******************************************************************


SS7I-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

ss7i OBJECT IDENTIFIER ::= { nas 35 }

-- The HiPer SS7i Card Configuration Group.

ss7iCfg OBJECT IDENTIFIER ::= { ss7i 1 }

ss7iCfgTable OBJECT-TYPE
SYNTAX SEQUENCE OF Ss7iCfgEntry
ACCESS not-accessible
STATUS mandatory
DESCRIPTION
"The Configuration Table contains an entry for each of the 
manageable HiPer SS7i cards in the chassis.  It contains 
objects that reflect the current configuration of 
parameters that affect the operation of all the entities 
that reside on the given card."
::= { ss7iCfg 1 }

ss7iCfgEntry OBJECT-TYPE
SYNTAX Ss7iCfgEntry
ACCESS not-accessible
STATUS mandatory
DESCRIPTION
"There is one Configuration Table entry per HiPer SS7i Card 
in the chassis."
INDEX { ss7iCfgIndex }
::= { ss7iCfgTable 1 }

Ss7iCfgEntry ::=
SEQUENCE {
ss7iCfgIndex
    INTEGER,
ss7iCfgIpAddr
    IpAddress,
ss7iCfgNetmask
    IpAddress,
ss7iCfgDfltGwIpAddr
    IpAddress,
ss7iCfgProtocol
    INTEGER,
ss7iCfgGwConnStartMethod
    INTEGER,
ss7iCfgGwIpAddr
    IpAddress,
ss7iCfgGwPort
    INTEGER,
ss7iCfgSecGwIpAddr
    IpAddress,
ss7iCfgSecGwPort
    INTEGER,
ss7iCfgHrtbtTimerNearEnd
    INTEGER,
ss7iCfgHrtbtTimerFarEnd
    INTEGER,
ss7iCfgChassisId
    OCTET STRING,
ss7iCfgGwConnRetryCnt
    INTEGER,
ss7iCfgGwConnRetryIntvl
    INTEGER,
ss7iCfgGwMssdHrtbtThrsh
    INTEGER
}

ss7iCfgIndex OBJECT-TYPE
SYNTAX INTEGER
ACCESS read-only
STATUS mandatory
DESCRIPTION
"A unique value for each HiPer SS7i card in the chassis.  
The value of ss7iCfgIndex matches the value of the index 
for the corresponding HiPer SS7i card entity in the entity 
table of the chassis MIB."
::= { ss7iCfgEntry 1 }

ss7iCfgIpAddr OBJECT-TYPE
SYNTAX IpAddress
ACCESS read-write
STATUS mandatory
DESCRIPTION
"The IP address on interface 0 of the HiPer SS7i."
::= { ss7iCfgEntry 2 }

ss7iCfgNetmask OBJECT-TYPE
SYNTAX IpAddress
ACCESS read-write
STATUS mandatory
DESCRIPTION
"The netmask on interface 0 of the HiPer SS7i."
::= { ss7iCfgEntry 3 }

ss7iCfgDfltGwIpAddr OBJECT-TYPE
SYNTAX IpAddress
ACCESS read-write
STATUS mandatory
DESCRIPTION
"The IP address of the default IP  routing gateway."
::= { ss7iCfgEntry 4 }

ss7iCfgProtocol OBJECT-TYPE
SYNTAX INTEGER{
  slapV2(1)
}
ACCESS read-write
STATUS mandatory
DESCRIPTION
"The external signaling protocol running over the TCP/IP 
connection with the external signaling gateway.  Default = 
hss7iSlapV2(1)."
::= { ss7iCfgEntry 5 }

ss7iCfgGwConnStartMethod OBJECT-TYPE
SYNTAX INTEGER{
  lsAuto(1),
  lsManual(2)
}
ACCESS read-write
STATUS mandatory
DESCRIPTION
"The method used by the HiPer SS7i to bring up the TCP/IP 
connection to the external signaling gateway at boot time."
::= { ss7iCfgEntry 6 }

ss7iCfgGwIpAddr OBJECT-TYPE
SYNTAX IpAddress
ACCESS read-write
STATUS mandatory
DESCRIPTION
"The primary external SS7 gateway IP address.  Valid for 
SLAP only."
::= { ss7iCfgEntry 7 }

ss7iCfgGwPort OBJECT-TYPE
SYNTAX INTEGER
ACCESS read-write
STATUS mandatory
DESCRIPTION
"The primary external SS7 gateway port number.  Valid for 
SLAP only."
::= { ss7iCfgEntry 8 }

ss7iCfgSecGwIpAddr OBJECT-TYPE
SYNTAX IpAddress
ACCESS read-write
STATUS mandatory
DESCRIPTION
"The secondary external SS7 gateway IP address.  Valid for 
SLAP only."
::= { ss7iCfgEntry 9 }

ss7iCfgSecGwPort OBJECT-TYPE
SYNTAX INTEGER
ACCESS read-write
STATUS mandatory
DESCRIPTION
"The secondary external SS7 gateway port number.  Valid for 
SLAP only."
::= { ss7iCfgEntry 10 }

ss7iCfgHrtbtTimerNearEnd OBJECT-TYPE
SYNTAX INTEGER (1..86400000)
ACCESS read-write
STATUS mandatory
DESCRIPTION
"The HiPer SS7i heartbeat timer.  Upon expiration, the HiPer 
SS7i will send a heartbeat message to the external SS7 
gateway.  The time should be less than what the gateway 
expects. Valid for SLAP only.  Default = 15000 msec."
::= { ss7iCfgEntry 11 }

ss7iCfgHrtbtTimerFarEnd OBJECT-TYPE
SYNTAX INTEGER (1..86400000)
ACCESS read-write
STATUS mandatory
DESCRIPTION
"The external SS7 gateway heartbeat timer.  Upon expiration 
it causes the HiPer SS7i to commence the connection 
re-establishment procedure to the external SS7 gateway.  
The time should be longer than what the external SS7 
gateway is set to.  Valid for SLAP only.  Default = 15000 
msec."
::= { ss7iCfgEntry 12 }

ss7iCfgChassisId OBJECT-TYPE
SYNTAX OCTET STRING (SIZE(0..4))
ACCESS read-write
STATUS mandatory
DESCRIPTION
"This uniquely identifies logical Chassis under the control 
of the HiPer SS7I, valid for SLAP only. The OCTET STRING 
format must be FF FF FF FF ."
::= { ss7iCfgEntry 13 }

ss7iCfgGwConnRetryCnt OBJECT-TYPE
SYNTAX INTEGER
ACCESS read-write
STATUS mandatory
DESCRIPTION
"The number of times the HiPer SS7i will attempt to 
re-establish the TCP/IP connection to the external SS7 
gateway after the initial failure was detected.  Valid for 
SLAP only.  Default = 3."
::= { ss7iCfgEntry 14 }

ss7iCfgGwConnRetryIntvl OBJECT-TYPE
SYNTAX INTEGER
ACCESS read-write
STATUS mandatory
DESCRIPTION
"The time interval between attempts of the HiPer SS7i to 
re-establish the TCP/IP connection to the external SS7 
gateway.  Valid for SLAP only.  Default = 2 sec."
::= { ss7iCfgEntry 15 }

ss7iCfgGwMssdHrtbtThrsh OBJECT-TYPE
SYNTAX INTEGER
ACCESS read-write
STATUS mandatory
DESCRIPTION
"The number of external SS7 gateway heartbeat timeouts 
allowed before the connection to the gateway is considered 
lost.  A setting of 0 means no attempt will be made to 
re-establish the connection.  Default = 1."

::= { ss7iCfgEntry 16 }

-- The HiPer SS7i Card Command Group.

ss7iCmd OBJECT IDENTIFIER ::= { ss7i 2 }

ss7iCmdTable OBJECT-TYPE
SYNTAX SEQUENCE OF Ss7iCmdEntry
ACCESS not-accessible
STATUS mandatory
DESCRIPTION
"The Command table contains an entry for each of the 
manageable HiPer SS7i cards in the chassis.  It provides a 
means through which to take specific actions on them."
::= { ss7iCmd 1 }

ss7iCmdEntry OBJECT-TYPE
SYNTAX Ss7iCmdEntry
ACCESS not-accessible
STATUS mandatory
DESCRIPTION
"There is one Command Table entry per HiPer SS7i card in the 
chassis."
INDEX { ss7iCmdIndex }
::= { ss7iCmdTable 1 }

Ss7iCmdEntry ::=
SEQUENCE {
ss7iCmdIndex
    INTEGER,
ss7iCmdMgtStationId
    OCTET STRING,
ss7iCmdReqId
    INTEGER,
ss7iCmdFunction
    INTEGER,
ss7iCmdForce
    INTEGER,
ss7iCmdParam
    OCTET STRING,
ss7iCmdResult
    INTEGER,
ss7iCmdCode
    INTEGER
}

ss7iCmdIndex OBJECT-TYPE
SYNTAX INTEGER
ACCESS read-only
STATUS mandatory
DESCRIPTION
"A unique value for each HiPer SS7i card in the chassis.  
The value of this object matches the value of the index of 
the corresponding HiPer SS7i card's entry in the entity 
table of the chassis MIB."
::= { ss7iCmdEntry 1 }

ss7iCmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with ss7iCmdReqId and ss7iCmdResult 
to detect interference from other MSs."
::= { ss7iCmdEntry 2 }

ss7iCmdReqId OBJECT-TYPE
SYNTAX INTEGER
ACCESS read-only
STATUS mandatory
DESCRIPTION
"This object contains the value of the request-id field in 
the SNMP PDU which invoked the current or most recent 
command or test on this HiPer SS7i card.  If the request-id 
is unknown or undefined, this object contains the value 
zero."
::= { ss7iCmdEntry 3 }

ss7iCmdFunction OBJECT-TYPE
SYNTAX INTEGER{
  noCommand(1),
  saveToNVRAM(2),
  restoreFromNVRAM(3),
  restoreFromDefault(4),
  softwareReset(5),
  startSS7GwConn(6),
  shutDownSS7GwConn(7),
  resetSS7Counters(8),
  resetPbusCounters(9),
  startPbusConnToAll(10),
  stopPbusConnToAll(11)
}
ACCESS read-write
STATUS mandatory
DESCRIPTION
"This object contains a value which describes the command 
which is being invoked."
::= { ss7iCmdEntry 4 }

ss7iCmdForce OBJECT-TYPE
SYNTAX INTEGER{
  force(1),
  noForce(2)
}
ACCESS read-write
STATUS mandatory
DESCRIPTION
"In some cases, the HiPer SS7i card may be in a state such 
that certain commands could adversely affect connections.  
In such cases, a command request with this object not 
present or set to noForce will result in a warning.  If the 
operator elects to ignore such warnings, this object can be 
set to force in a subsequent issue of the command to cause 
the command to be carried out regardless of its potentially 
hazzardous effects."
::= { ss7iCmdEntry 5 }

ss7iCmdParam OBJECT-TYPE
SYNTAX OCTET STRING
ACCESS read-write
STATUS mandatory
DESCRIPTION
"This object contains parameters that are specific to the 
particular command being issued.  In some cases, there will 
be no aditional parameters required."
::= { ss7iCmdEntry 6 }

ss7iCmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1) if no 
commands have been requested since the last reset."
::= { ss7iCmdEntry 7 }

ss7iCmdCode OBJECT-TYPE
SYNTAX INTEGER{
  noError(1),
  unable(2),
  unrecognizedCommand(6),
  slotEmpty(8),
  noResponse(12),
  unsupportedCommand(20),
  deviceDisabled(22),
  testFailed(25),
  userInterfaceActive(58),
  pendingSoftwareDownload(73)
}
ACCESS read-only
STATUS mandatory
DESCRIPTION
"The value of this object upon command completion indicates 
a further description of what went wrong if the command was 
unsuccessful.  In the case of tests, a bit mapped result of 
each of the sub-tests performed can be found in the status 
table."
::= { ss7iCmdEntry 8 }

-- The HiPer SS7i Card Trap Enable Group

ss7iTrap OBJECT IDENTIFIER ::= { ss7i 3 }

ss7iTrapTable OBJECT-TYPE
SYNTAX SEQUENCE OF Ss7iTrapEntry
ACCESS not-accessible
STATUS mandatory
DESCRIPTION
"Table containing objects to enable traps on the HiPer SS7i 
cards in the chassis."
::= { ss7iTrap 1 }

ss7iTrapEntry OBJECT-TYPE
SYNTAX Ss7iTrapEntry
ACCESS not-accessible
STATUS mandatory
DESCRIPTION
"There is one entry for each HiPer SS7i card in the 
chassis."
INDEX { ss7iTrapIndex }
::= { ss7iTrapTable 1 }

Ss7iTrapEntry ::=
SEQUENCE {
ss7iTrapIndex
    INTEGER,
ss7iTrapPbusLinkUp
    INTEGER,
ss7iTrapPbusLinkDown
    INTEGER,
ss7iTrapGwConnUp
    INTEGER,
ss7iTrapGwConnDown
    INTEGER
}

ss7iTrapIndex OBJECT-TYPE
SYNTAX INTEGER
ACCESS read-only
STATUS mandatory
DESCRIPTION
"A unique index identifying the HiPer SS7i card to which the 
trap enable objects pertain."
::= { ss7iTrapEntry 1 }

ss7iTrapPbusLinkUp OBJECT-TYPE
SYNTAX INTEGER{
  enableTrap(1),
  disableAll(2),
  enableLog(3),
  enableAll(4)
}
ACCESS read-write
STATUS mandatory
DESCRIPTION
"Enables reporting of a trap and/or log message when the 
ENFAS packet bus signaling link to the HiPer Dsp comes up.  
Default = disableAll(2)."
::= { ss7iTrapEntry 2 }

ss7iTrapPbusLinkDown OBJECT-TYPE
SYNTAX INTEGER{
  enableTrap(1),
  disableAll(2),
  enableLog(3),
  enableAll(4)
}
ACCESS read-write
STATUS mandatory
DESCRIPTION
"Enables reporting of a trap and/or log message when the 
ENFAS packet bus signaling link to the HiPer Dsp goes down. 
 Default = disableAll(2)."
::= { ss7iTrapEntry 3 }

ss7iTrapGwConnUp OBJECT-TYPE
SYNTAX INTEGER{
  enableTrap(1),
  disableAll(2),
  enableLog(3),
  enableAll(4)
}
ACCESS read-write
STATUS mandatory
DESCRIPTION
"Enables reporting of a trap and/or log message when the 
TCP/IP signaling connection to the SS7 (or media) gateway 
comes up.  Default = disableAll(2)."
::= { ss7iTrapEntry 4 }

ss7iTrapGwConnDown OBJECT-TYPE
SYNTAX INTEGER{
  enableTrap(1),
  disableAll(2),
  enableLog(3),
  enableAll(4)
}
ACCESS read-write
STATUS mandatory
DESCRIPTION
"Enables reporting of a trap and/or log message when the 
TCP/IP signaling connection to the SS7 (or media) gateway 
goes down.  Default = disableAll(2)."
::= { ss7iTrapEntry 5 }

-- The HiPer SS7i Card Statistics Group.

ss7iStat OBJECT IDENTIFIER ::= { ss7i 4 }

ss7iStatTable OBJECT-TYPE
SYNTAX SEQUENCE OF Ss7iStatEntry
ACCESS not-accessible
STATUS mandatory
DESCRIPTION
"The Statistics table contains an entry for each of the 
manageable HiPer SS7i cards in the chassis.  It contains 
objects that reflect the current status of the card."
::= { ss7iStat 1 }

ss7iStatEntry OBJECT-TYPE
SYNTAX Ss7iStatEntry
ACCESS not-accessible
STATUS mandatory
DESCRIPTION
"There is one Statistics table entry for each HiPer SS7i 
card in the chassis."
INDEX { ss7iStatIndex }
::= { ss7iStatTable 1 }

Ss7iStatEntry ::=
SEQUENCE {
ss7iStatIndex
    INTEGER,
ss7iStatGwConnStatus
    INTEGER,
ss7iStatGwNumMsgsRcvd
    Counter,
ss7iStatGwNumBytesRcvd
    Counter,
ss7iStatGwNumMsgsSent
    Counter,
ss7iStatGwNumBytesSent
    Counter,
ss7iStatGwMssdHrtbtCnt
    Counter,
ss7iStatGwLinkLostCnt
    Counter,
ss7iStatGwLinkErrCnt
    Counter,
ss7iStatGwLinkDownCause
    INTEGER
}

ss7iStatIndex OBJECT-TYPE
SYNTAX INTEGER
ACCESS read-only
STATUS mandatory
DESCRIPTION
"A unique value for each HiPer SS7i card in the chassis.  
The value of ss7iStatIndex matches the value of the index 
for the corresponding Hiper SS7i card entity in the entity 
table of the chassis MIB."
::= { ss7iStatEntry 1 }

ss7iStatGwConnStatus OBJECT-TYPE
SYNTAX INTEGER{
  up(1),
  down(2)
}
ACCESS read-only
STATUS mandatory
DESCRIPTION
"Status of the TCP/IP connection with the external signaling 
gateway.  Valid for SLAP only."
::= { ss7iStatEntry 2 }

ss7iStatGwNumMsgsRcvd OBJECT-TYPE
SYNTAX Counter
ACCESS read-only
STATUS mandatory
DESCRIPTION
"The number of messages received from the external SS7 
gateway or the Media Gateway Controller."
::= { ss7iStatEntry 3 }

ss7iStatGwNumBytesRcvd OBJECT-TYPE
SYNTAX Counter
ACCESS read-only
STATUS mandatory
DESCRIPTION
"The number of bytes received from the external SS7 gateway 
or the Media Gateway Controller."
::= { ss7iStatEntry 4 }

ss7iStatGwNumMsgsSent OBJECT-TYPE
SYNTAX Counter
ACCESS read-only
STATUS mandatory
DESCRIPTION
"The number of messages sent to the external SS7 gateway or 
the Media Gateway Controller."
::= { ss7iStatEntry 5 }

ss7iStatGwNumBytesSent OBJECT-TYPE
SYNTAX Counter
ACCESS read-only
STATUS mandatory
DESCRIPTION
"The number of bytes sent to the external SS7 gateway or the 
Media Gateway Controller."
::= { ss7iStatEntry 6 }

ss7iStatGwMssdHrtbtCnt OBJECT-TYPE
SYNTAX Counter
ACCESS read-only
STATUS mandatory
DESCRIPTION
"The accumulated number of missed heartbeat messages 
expected to arrive from the external SS7 gateway."
::= { ss7iStatEntry 7 }

ss7iStatGwLinkLostCnt OBJECT-TYPE
SYNTAX Counter
ACCESS read-only
STATUS mandatory
DESCRIPTION
"The accumulated number of times the physical Ethernet 
connection is unplugged or severed."
::= { ss7iStatEntry 8 }

ss7iStatGwLinkErrCnt OBJECT-TYPE
SYNTAX Counter
ACCESS read-only
STATUS mandatory
DESCRIPTION
"The accumulated number of errors encountered sending to or 
receiving from the external SS7 gateway when the TCP/IP 
connection is believed to be healthy."
::= { ss7iStatEntry 9 }

ss7iStatGwLinkDownCause OBJECT-TYPE
SYNTAX INTEGER{
  none(1),
  heartbeatTimeout(2),
  socketSndRcvError(3),
  physicalLinkSevered(4)
}
ACCESS read-only
STATUS mandatory
DESCRIPTION
"The reason the signaling connection to the external SS7 
gateway went down."
::= { ss7iStatEntry 10 }

-- The HiPer SS7i Card HiPer Dsp Statistics Group

ss7iHdm OBJECT IDENTIFIER ::= { ss7i 5 }

ss7iHdmTable OBJECT-TYPE
SYNTAX SEQUENCE OF Ss7iHdmEntry
ACCESS not-accessible
STATUS mandatory
DESCRIPTION
"The ss7iHdm table contains objects for all of the HiPer Dsp 
cards in the chassis."
::= { ss7iHdm 1 }

ss7iHdmEntry OBJECT-TYPE
SYNTAX Ss7iHdmEntry
ACCESS not-accessible
STATUS mandatory
DESCRIPTION
"There is one entry for each HiPer Dsp Card in the chassis."
INDEX { ss7iHdmIndex, ss7iHdmIndex2 }
::= { ss7iHdmTable 1 }

Ss7iHdmEntry ::=
SEQUENCE {
ss7iHdmIndex
    INTEGER,
ss7iHdmIndex2
    INTEGER,
ss7iHdmConnState
    INTEGER,
ss7iHdmSndPktsOkCnt
    Counter,
ss7iHdmSndPktsFailCnt
    Counter,
ss7iHdmRcvPktsOkCnt
    Counter,
ss7iHdmRcvPktsFailCnt
    Counter,
ss7iHdmLinkDownCause
    INTEGER
}

ss7iHdmIndex OBJECT-TYPE
SYNTAX INTEGER
ACCESS read-only
STATUS mandatory
DESCRIPTION
"A unique value for each HiPer SS7i card in the chassis.  
The value of ss7iHdmIndex matches the value of the index 
for the corresponding HiPer SS7i card entity in the entity 
table of the chassis MIB."
::= { ss7iHdmEntry 1 }

ss7iHdmIndex2 OBJECT-TYPE
SYNTAX INTEGER
ACCESS read-only
STATUS mandatory
DESCRIPTION
"The secondary index into the ss7iHdm table.  There is one 
entry for each Hiper Dsp in the chassis.  The value of the 
index is equal to the chassis slot number of a HiPer Dsp 
card."
::= { ss7iHdmEntry 2 }

ss7iHdmConnState OBJECT-TYPE
SYNTAX INTEGER{
  closed(1),
  opening(2),
  opened(3),
  configuring(4),
  ready(5),
  closing(6),
  loopback(7)
}
ACCESS read-only
STATUS mandatory
DESCRIPTION
"The state of the signaling packet bus connection to the 
HiPer Dsp.  There is one connection from the HiPer SS7i 
card to each HiPer Dsp in the chassis."
::= { ss7iHdmEntry 3 }

ss7iHdmSndPktsOkCnt OBJECT-TYPE
SYNTAX Counter
ACCESS read-only
STATUS mandatory
DESCRIPTION
"The number of packets successfully transmitted over the 
signaling packet bus connection."
::= { ss7iHdmEntry 4 }

ss7iHdmSndPktsFailCnt OBJECT-TYPE
SYNTAX Counter
ACCESS read-only
STATUS mandatory
DESCRIPTION
"The number of packets failing to transmit over the 
signaling packet bus connection."
::= { ss7iHdmEntry 5 }

ss7iHdmRcvPktsOkCnt OBJECT-TYPE
SYNTAX Counter
ACCESS read-only
STATUS mandatory
DESCRIPTION
"The number of packets sucessfully received over the 
signaling packet bus connection."
::= { ss7iHdmEntry 6 }

ss7iHdmRcvPktsFailCnt OBJECT-TYPE
SYNTAX Counter
ACCESS read-only
STATUS mandatory
DESCRIPTION
"The number of signaling packet bus connection packets 
rejected by the HiPer SS7i message handler."
::= { ss7iHdmEntry 7 }

ss7iHdmLinkDownCause OBJECT-TYPE
SYNTAX INTEGER{
  none(1),
  missingHdm(2),
  ss7GwLinkDown(3),
  pbusSndRcvError(4)
}
ACCESS read-only
STATUS mandatory
DESCRIPTION
"The reason the packet bus ENFAS signaling link to the HiPer 
Dsp went down."
::= { ss7iHdmEntry 8 }

-- The HiPer SS7i Card Signaling Packet Bus Configuration Group

ss7iSigPb OBJECT IDENTIFIER ::= { ss7i 6 }

ss7iSigPbTable OBJECT-TYPE
SYNTAX SEQUENCE OF Ss7iSigPbEntry
ACCESS not-accessible
STATUS mandatory
DESCRIPTION
"The ss7iSigPb table contains objects for managing the 
signaling packet bus connections to all of the HiPer Dsp 
cards in the chassis."
::= { ss7iSigPb 1 }

ss7iSigPbEntry OBJECT-TYPE
SYNTAX Ss7iSigPbEntry
ACCESS not-accessible
STATUS mandatory
DESCRIPTION
"There is one entry for each HiPer Dsp Card in the chassis."
INDEX { ss7iSigPbIndex, ss7iSigPbIndex2 }
::= { ss7iSigPbTable 1 }

Ss7iSigPbEntry ::=
SEQUENCE {
ss7iSigPbIndex
    INTEGER,
ss7iSigPbIndex2
    INTEGER,
ss7iSigPbConnection
    INTEGER,
ss7iSigPbLoopback
    INTEGER
}

ss7iSigPbIndex OBJECT-TYPE
SYNTAX INTEGER
ACCESS read-only
STATUS mandatory
DESCRIPTION
"A unique value for each HiPer SS7i card in the chassis.  
The value of ss7iSigPbIndex matches the value of the index 
for the corresponding HiPer SS7i card entity in the entity 
table of the chassis MIB."
::= { ss7iSigPbEntry 1 }

ss7iSigPbIndex2 OBJECT-TYPE
SYNTAX INTEGER
ACCESS read-only
STATUS mandatory
DESCRIPTION
"The secondary index into the ss7iSigPb table.  There is one 
entry for each Hiper Dsp in the chassis.  The value of the 
index is equal to the chassis slot number of a HiPer Dsp 
card."
::= { ss7iSigPbEntry 2 }

ss7iSigPbConnection OBJECT-TYPE
SYNTAX INTEGER{
  disable(1),
  enable(2)
}
ACCESS read-write
STATUS mandatory
DESCRIPTION
"The means to enable or disable a signaling packet bus 
connection between the HiPer SS7i and a Hiper Dsp.  Default 
= disable(1)."
::= { ss7iSigPbEntry 3 }

ss7iSigPbLoopback OBJECT-TYPE
SYNTAX INTEGER{
  disable(1),
  enable(2)
}
ACCESS read-write
STATUS mandatory
DESCRIPTION
"The means to enable or disable the loopback state on the 
signaling packet bus connection between the HiPer SS7i and 
a Hiper Dsp.  Default = disable(1)."
::= { ss7iSigPbEntry 4 }

END
