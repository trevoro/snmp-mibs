--
-- HW-IMAPV1NORTHBOUND-TRAP-MIB.mib
-- MIB generated by MG-SOFT Visual MIB Builder Version 4.0 Build 349
-- Tuesday, June 20, 2006 at 15:41:25 
--
-- =================================================================   
-- Copyright (C) 2002 by HUAWEI TECHNOLOGIES. All rights reserved
--
-- Description	: This MIB defines the managed objects that are used
--                   by the function interfaces of the SNMP Northbound 
--                   Interface. The definitions decide what operations
--                   the NMS can do and what network management 
--                   information the NMS can obtain.
-- Reference	: 
-- Version		: V1.00
-- History		:
-- <Ashutosh Jain>,<10 September 2007>,<Created>
-- Modified by Aparna on 03-10-2008
-- =================================================================
--  
	T2000-TRAP-MIB DEFINITIONS ::= BEGIN
 
		IMPORTS
			OBJECT-TYPE			
				FROM RFC-1212			
			TRAP-TYPE			
				FROM RFC-1215			
			IpAddress			
				FROM RFC1155-SMI			
			enterprises			
				FROM SNMPv2-SMI;
	
	
--
-- Node definitions
--
	
--  Node definitions
-- 
-- 1.3.6.1.4.1.2011
		-- 1.3.6.1.4.1.2011
		huawei OBJECT IDENTIFIER ::= { enterprises 2011 }

		
--  1.3.6.1.4.1.2011.2
		-- 1.3.6.1.4.1.2011.2
		products OBJECT IDENTIFIER ::= { huawei 2 }

		
--  1.3.6.1.4.1.2011.2.15
		-- 1.3.6.1.4.1.2011.2.15
		hwNetManagement OBJECT IDENTIFIER ::= { products 15 }

		
--  1.3.6.1.4.1.2011.2.15.1
		-- 1.3.6.1.4.1.2011.2.15.1
		hwNmAgent OBJECT IDENTIFIER ::= { hwNetManagement 1 }

		
		-- 1.3.6.1.4.1.2011.2.15.1.3
		hwNmFault OBJECT IDENTIFIER ::= { hwNmAgent 3 }

		
-- Name        	: thirdNMSFaultFilter 
-- Description	: IP:Port:AlarmSeverityFilter:FaultFlagFilter
--					AlarmSeverityFilter = xxxx (Critical, Major, Minor, Warning) (1 - filter , 0 -report)
--					FaultFlagFilter = yyy (Event, Fault, Recovery) (1 - filter , 0 -report)
--					Both AlarmSeverityFilter and FaultFlagFilter are optional and both or any one can be set
--					E.g.:
--					10.18.17.28:9999:1001:011
--					Only events of major and minor severity will be send to the OSS [10.18.17.28:9999] and rest filtered.
--					The format to specify only AlarmSeverityFilter is:
--					10.18.17.28:9999:1001
--					The format to specify only FaultFlagFilter is:
--					10.18.17.28:9999::011
-- Type     	: Octet string
-- OID			: 1.3.6.1.4.1.2011.2.15.1.3.5
		thirdNMSFaultFilter OBJECT-TYPE
			SYNTAX OCTET STRING 
			ACCESS read-write
			STATUS mandatory
			DESCRIPTION
					"IP:Port:AlarmSeverityFilter:FaultFlagFilter
					AlarmSeverityFilter = xxxx (Critical, Major, Minor, Warning) (1 - filter , 0 -report)
					FaultFlagFilter = yyy (Event, Fault, Recovery) (1 - filter , 0 -report)
					Both AlarmSeverityFilter and FaultFlagFilter are optional and both or any one can be set
					E.g.: 10.18.17.28:9999:1001:011
					Only events of major and minor severity will be send to the OSS [10.18.17.28:9999] and rest filtered.
					The format to specify only AlarmSeverityFilter is:
					10.18.17.28:9999:1001
					The format to specify only FaultFlagFilter is:
					10.18.17.28:9999::011"		
					
			::= { hwNmFault 5 }
          
-- Name        	: hwNmClearAlarms 
-- Description	: This provides the functionality of clearing alarms to third party NMS.
--				The alarms can be cleared based on alarm serial number.
--				Syntax: alarm serial numbers separated by comma (,).
-- Type     	: Octet string
-- OID			: 1.3.6.1.4.1.2011.2.15.1.3.6
		hwNmClearAlarms OBJECT-TYPE
			SYNTAX OCTET STRING
			ACCESS read-write
			STATUS mandatory
			DESCRIPTION
				"This provides the functionality of clearing alarms to third party NMS.
				The alarms can be cleared based on alarm serial number.
				Syntax: alarm serial numbers separated by comma (,)."
			::= { hwNmFault 6 }


-- Name        	: hwNmAcknowledgeAlarms 
-- Description	: This provides the functionality of acknowledging alarms to third party NMS.
--				The alarms can be acknowledged based on alarm serial number.
--				Syntax: alarm serial numbers separated by comma (,).
-- Type     	: Octet string
-- OID			: 1.3.6.1.4.1.2011.2.15.1.3.7
		hwNmAcknowledgeAlarms OBJECT-TYPE
			SYNTAX OCTET STRING
			ACCESS read-write
			STATUS mandatory
			DESCRIPTION
				"This provides the functionality of acknowledging alarms to third party NMS.
				The alarms can be acknowledged based on alarm serial number.
				Syntax: alarm serial numbers separated by comma (,)."
			::= { hwNmFault 7 }

		
-- Name        	: hwNmUnAcknowledgeAlarms 
-- Description	: This provides the functionality of unacknowledging alarms to third party NMS.
--				The alarms can be unacknowledged based on alarm serial number.
--				Syntax: alarm serial numbers separated by comma (,).
-- Type     	: Octet string
-- OID			: 1.3.6.1.4.1.2011.2.15.1.3.8
		hwNmUnAcknowledgeAlarms OBJECT-TYPE
			SYNTAX OCTET STRING
			ACCESS read-write
			STATUS mandatory
			DESCRIPTION
				"This provides the functionality of unacknowledging alarms to third party NMS.
				The alarms can be unacknowledged based on alarm serial number.
				Syntax: alarm serial numbers separated by comma (,)."
			::= { hwNmFault 8 }


		
--  1.3.6.1.4.1.2011.2.15.1.7
		-- 1.3.6.1.4.1.2011.2.15.1.7
		hwNmNorthboundEvent OBJECT IDENTIFIER ::= { hwNmAgent 7 }

		
--  1.3.6.1.4.1.2011.2.15.1.7.1
		-- 1.3.6.1.4.1.2011.2.15.1.7.1
		hwNmNorthboundEventInfo OBJECT IDENTIFIER ::= { hwNmNorthboundEvent 1 }

		
-- Name        	: hwNmNorthboundNEName 
-- Description	: The name of network element,string (255)
-- Type     	: Octet string  (SIZE (1..255))
-- OID			: 1.3.6.1.4.1.2011.2.15.1.7.1.1
	
			hwNmNorthboundNEName OBJECT-TYPE
			SYNTAX OCTET STRING (SIZE (1..255))
			ACCESS read-only
			STATUS mandatory
			DESCRIPTION
				"The name of network element,string (255)"
			::= { hwNmNorthboundEventInfo 1 }

		
-- Name        	: hwNmNorthboundNEType 
-- Description	: Device type of element,string(64)
-- Type     	: Octet string  (SIZE (1..64))
-- OID			: 1.3.6.1.4.1.2011.2.15.1.7.1.2
		hwNmNorthboundNEType OBJECT-TYPE
			SYNTAX OCTET STRING (SIZE (0..64))
			ACCESS read-only
			STATUS mandatory
			DESCRIPTION
				"Device type of element,string(64)"
			::= { hwNmNorthboundEventInfo 2 }

-- Name        	: hwNmNorthboundObjectInstance 
-- Description	: Instance of element,such as number of Rack, Frame, Slot, Subslot, Port and so on,string(255)
-- Type     	: Octet string  (SIZE (1..255))
-- OID			: 1.3.6.1.4.1.2011.2.15.1.7.1.3
		hwNmNorthboundObjectInstance OBJECT-TYPE
			SYNTAX OCTET STRING (SIZE (0..255))
			ACCESS read-only
			STATUS mandatory
			DESCRIPTION
				"Instance of element,such as number of Rack, Frame, Slot, Subslot, Port and so on,string(255)"
			::= { hwNmNorthboundEventInfo 3 }

		
-- Name        	: hwNmNorthboundEventType 
-- Description	: Event type of Network management,string(64)
-- Type     	: Octet string  (SIZE (1..64))
-- OID			: 1.3.6.1.4.1.2011.2.15.1.7.1.4
		hwNmNorthboundEventType OBJECT-TYPE
			SYNTAX OCTET STRING (SIZE (0..64))
			ACCESS read-only
			STATUS mandatory
			DESCRIPTION
				"Event type of Network management,string(64)"
			::= { hwNmNorthboundEventInfo 4 }

		
-- Name        	: hwNmNorthboundEventTime 
-- Description	: Alarm generate time,string(64),format: 2003/03/14 00:00:00
-- Type     	: Octet string  (SIZE (1..64))
-- OID			: 1.3.6.1.4.1.2011.2.15.1.7.1.5
		hwNmNorthboundEventTime OBJECT-TYPE
			SYNTAX OCTET STRING (SIZE (0..64))
			ACCESS read-only
			STATUS mandatory
			DESCRIPTION
				"Alarm generate time,string(64),format: 2003/03/14 00:00:00"
			::= { hwNmNorthboundEventInfo 5 }

		
-- Name        	: hwNmNorthboundProbableCause 
-- Description	: Reason of Probable caused alarm, string(64)
-- Type     	: Octet string  (SIZE (1..64))
-- OID			: 1.3.6.1.4.1.2011.2.15.1.7.1.6
		hwNmNorthboundProbableCause OBJECT-TYPE
			SYNTAX OCTET STRING (SIZE (0..64))
			ACCESS read-only
			STATUS mandatory
			DESCRIPTION
				"Reason of Probable caused alarm, string(64)"
			::= { hwNmNorthboundEventInfo 6 }

		
-- Name        	: hwNmNorthboundSeverity 
-- Description	: RLevel of Alarm, string(64)
-- Type     	: Octet string  (SIZE (1..64))
-- OID			: 1.3.6.1.4.1.2011.2.15.1.7.1.7
		hwNmNorthboundSeverity OBJECT-TYPE
			SYNTAX OCTET STRING (SIZE (0..64))
			ACCESS read-only
			STATUS mandatory
			DESCRIPTION
				"Level of Alarm, string(64)"
			::= { hwNmNorthboundEventInfo 7 }

		
-- Name        	: hwNmNorthboundEventDetail 
-- Description	: Alarm ID and detail information, format: ID+detail infomation, string(255)
-- Type     	: Octet string  (SIZE (1..255))
-- OID			: 1.3.6.1.4.1.2011.2.15.1.7.1.8
		hwNmNorthboundEventDetail OBJECT-TYPE
			SYNTAX OCTET STRING (SIZE (0..255))
			ACCESS read-only
			STATUS mandatory
			DESCRIPTION
				"Alarm ID and detail information, format: ID+detail infomation, string(255)"
			::= { hwNmNorthboundEventInfo 8 }

		
-- Name        	: hwNmNorthboundAdditionalInfo 
-- Description	: Additional infomation of device, such as Country, City and so on, string(255)
-- Type     	: Octet string  (SIZE (1..255))
-- OID			: 1.3.6.1.4.1.2011.2.15.1.7.1.9
		hwNmNorthboundAdditionalInfo OBJECT-TYPE
			SYNTAX OCTET STRING (SIZE (0..255))
			ACCESS read-only
			STATUS mandatory
			DESCRIPTION
				"Additional infomation of device, such as Country, City and so on, string(255)"
			::= { hwNmNorthboundEventInfo 9 }

		
-- Name        	: hwNmNorthboundFaultFlag 
-- Description	: The flag of the fault.Show whether the alarm is an event ,a fault alarm or a recovery alarm.
-- Type     	: Octet string  (SIZE (1..64))
-- OID			: 1.3.6.1.4.1.2011.2.15.1.7.1.10
		hwNmNorthboundFaultFlag OBJECT-TYPE
			SYNTAX OCTET STRING (SIZE (0..64))
			ACCESS read-only
			STATUS mandatory
			DESCRIPTION
				"The flag of the fault.Show whether the alarm is an event ,a fault alarm or a recovery alarm."
			::= { hwNmNorthboundEventInfo 10 }

		
-- Name        	: hwNmNorthboundFaultFunction 
-- Description	: The function type of the alarm.It can be one of these values:'Power','Environment',
--					'Signal','Relay','Hardware','Software','Run','Communication','Service','Processerror',
--					'UNKNOWN_FUNC_TYPE'
-- Type     	: Octet string  (SIZE (1..64))
-- OID			: 1.3.6.1.4.1.2011.2.15.1.7.1.11
		hwNmNorthboundFaultFunction OBJECT-TYPE
			SYNTAX OCTET STRING (SIZE (0..64))
			ACCESS read-only
			STATUS mandatory
			DESCRIPTION
				"The function type of the alarm.It can be one of these values:'Power','Environment','Signal','Relay','Hardware','Software','Run','Communication','Service','Processerror','UNKNOWN_FUNC_TYPE'"
			::= { hwNmNorthboundEventInfo 11 }

		
-- Name        	: hwNmNorthboundDeviceIP 
-- Description	: he IP address of the device
-- Type     	: IpAddress
-- OID			: 1.3.6.1.4.1.2011.2.15.1.7.1.12
		hwNmNorthboundDeviceIP OBJECT-TYPE
			SYNTAX IpAddress
			ACCESS read-only
			STATUS mandatory
			DESCRIPTION
				"The IP address of the device"
			::= { hwNmNorthboundEventInfo 12 }

		
-- Name        	: hwNmNorthboundSerialNo 
-- Description	: The serial number of alarm.
-- Type     	: INTEGER
-- OID			: 1.3.6.1.4.1.2011.2.15.1.7.1.13
		hwNmNorthboundSerialNo OBJECT-TYPE
			SYNTAX INTEGER
			ACCESS read-only
			STATUS mandatory
			DESCRIPTION
				"The serial number of alarm."
			::= { hwNmNorthboundEventInfo 13 }

		
-- Name        	: hwNmNorthboundProbableRepair 
-- Description	: The probable repair advice of the alarm.
-- Type     	: Octet string  (SIZE (0..2048))
-- OID			: 1.3.6.1.4.1.2011.2.15.1.7.1.14
		hwNmNorthboundProbableRepair OBJECT-TYPE
			SYNTAX OCTET STRING (SIZE (0..2048))
			ACCESS read-only
			STATUS mandatory
			DESCRIPTION
				"The probable repair advice of the alarm."
			::= { hwNmNorthboundEventInfo 14 }

		
-- Name        	: hwNmNorthboundResourceIDs 
-- Description	: The ID of the resource.
-- Type     	: Octet string  (SIZE (1..255))
-- OID			: 1.3.6.1.4.1.2011.2.15.1.7.1.15
		hwNmNorthboundResourceIDs OBJECT-TYPE
			SYNTAX OCTET STRING (SIZE (1..255))
			ACCESS read-only
			STATUS mandatory
			DESCRIPTION
				"The ID of the resource."
			::= { hwNmNorthboundEventInfo 15 }

		
-- Name        	: hwNmNorthboundsAdditionalVB1 
-- Description	: Addtional information of the alarm
-- Type     	: Octet string  (SIZE (1..255))
-- OID			: 1.3.6.1.4.1.2011.2.15.1.7.1.16
		hwNmNorthboundsAdditionalVB1 OBJECT-TYPE
			SYNTAX OCTET STRING (SIZE (1..255))
			ACCESS read-only
			STATUS mandatory
			DESCRIPTION
				"Addtional information of the alarm"
			::= { hwNmNorthboundEventInfo 16 }

		
-- Name        	: hwNmNorthboundsAdditionalVB2 
-- Description	: Addtional information of the alarm
-- Type     	: Octet string  (SIZE (1..255))
-- OID			: 1.3.6.1.4.1.2011.2.15.1.7.1.17
		hwNmNorthboundsAdditionalVB2 OBJECT-TYPE
			SYNTAX OCTET STRING (SIZE (1..255))
			ACCESS read-only
			STATUS mandatory
			DESCRIPTION
				"Addtional information of the alarm"
			::= { hwNmNorthboundEventInfo 17 }

		
-- Name        	: hwNmNorthboundsAdditionalVB3 
-- Description	: Addtional information of the alarm
-- Type     	: Octet string  (SIZE (1..255))
-- OID			: 1.3.6.1.4.1.2011.2.15.1.7.1.18
		hwNmNorthboundsAdditionalVB3 OBJECT-TYPE
			SYNTAX OCTET STRING (SIZE (1..255))
			ACCESS read-only
			STATUS mandatory
			DESCRIPTION
				"Addtional information of the alarm"
			::= { hwNmNorthboundEventInfo 18 }

		
-- Name        	: hwNmNorthboundsAdditionalVB4 
-- Description	: Addtional information of the alarm
-- Type     	: Octet string  (SIZE (1..255))
-- OID			: 1.3.6.1.4.1.2011.2.15.1.7.1.19
		hwNmNorthboundsAdditionalVB4 OBJECT-TYPE
			SYNTAX OCTET STRING (SIZE (1..255))
			ACCESS read-only
			STATUS mandatory
			DESCRIPTION
				"Addtional information of the alarm"
			::= { hwNmNorthboundEventInfo 19 }

		
-- Name        	: hwNmNorthboundsAdditionalVB5 
-- Description	: Addtional information of the alarm
-- Type     	: Octet string  (SIZE (1..255))
-- OID			: 1.3.6.1.4.1.2011.2.15.1.7.1.20
		hwNmNorthboundsAdditionalVB5 OBJECT-TYPE
			SYNTAX OCTET STRING (SIZE (1..255))
			ACCESS read-only
			STATUS mandatory
			DESCRIPTION
				"Addtional information of the alarm"
			::= { hwNmNorthboundEventInfo 20 }

		
-- Name        	: hwNmNorthboundsAdditionalVB6 
-- Description	: Addtional information of the alarm
-- Type     	: Octet string  (SIZE (1..255))
-- OID			: 1.3.6.1.4.1.2011.2.15.1.7.1.21
		hwNmNorthboundsAdditionalVB6 OBJECT-TYPE
			SYNTAX OCTET STRING (SIZE (1..255))
			ACCESS read-only
			STATUS mandatory
			DESCRIPTION
				"Addtional information of the alarm"
			::= { hwNmNorthboundEventInfo 21 }

		
-- Name        	: hwNmNorthboundsAdditionalVB7 
-- Description	: Addtional information of the alarm
-- Type     	: Octet string  (SIZE (1..255))
-- OID			: 1.3.6.1.4.1.2011.2.15.1.7.1.22
		hwNmNorthboundsAdditionalVB7 OBJECT-TYPE
			SYNTAX OCTET STRING (SIZE (1..255))
			ACCESS read-only
			STATUS mandatory
			DESCRIPTION
				"Addtional information of the alarm"
			::= { hwNmNorthboundEventInfo 22 }

		
-- Name        	: hwNmNorthboundsAdditionalVB8 
-- Description	: Addtional information of the alarm
-- Type     	: Octet string  (SIZE (1..255))
-- OID			: 1.3.6.1.4.1.2011.2.15.1.7.1.23
		hwNmNorthboundsAdditionalVB8 OBJECT-TYPE
			SYNTAX OCTET STRING (SIZE (1..255))
			ACCESS read-only
			STATUS mandatory
			DESCRIPTION
				"Addtional information of the alarm"
			::= { hwNmNorthboundEventInfo 23 }

		
-- Name        	: hwNmNorthboundEventName 
-- Description	: Addtional information of the alarm
-- Type     	: Octet string  (SIZE (1..255))
-- OID			: 1.3.6.1.4.1.2011.2.15.1.7.1.24
		hwNmNorthboundEventName OBJECT-TYPE
			SYNTAX OCTET STRING (SIZE (1..255))
			ACCESS read-only
			STATUS mandatory
			DESCRIPTION
				"The name of event,string (255)"
			::= { hwNmNorthboundEventInfo 24 }

		
		-- 1.3.6.1.4.1.2011.2.15.1.7.2
		hwNmNorthboundEventKeepAliveInfo OBJECT IDENTIFIER ::= { hwNmNorthboundEvent 2 }

		
		-- 1.3.6.1.4.1.2011.2.15.1.7.7
		hwNmNorthboundEventSynchronization OBJECT IDENTIFIER ::= { hwNmNorthboundEvent 7 }

		
		-- 1.3.6.1.4.1.2011.2.15.1.7.7.1
		hwNmNorthboundEventSynchronizationStart OBJECT IDENTIFIER ::= { hwNmNorthboundEventSynchronization 1 }

		
		-- 1.3.6.1.4.1.2011.2.15.1.7.7.2
		hwNmNorthboundEventSynchronizationQueryResult OBJECT IDENTIFIER ::= { hwNmNorthboundEventSynchronization 2 }

		
		-- 1.3.6.1.4.1.2011.2.15.1.7.7.3
		hwNmNorthboundEventSynchronizationEnd OBJECT IDENTIFIER ::= { hwNmNorthboundEventSynchronization 3 }

		
-- Name        	: hwNmNorthboundEventSynchronizationEndStatus 
-- Description	: It shows the result of alarm synchronization.
--				1 means the alarm synchronization successfully ended.
--				2 means the alarm synchronization is stopped by the NMS's command.
--				3 means some error occured during the alarm synchronization.
-- Type     	: INTEGER
--				{
--				normalEnd(1),
--				stopped(2),
--				error(3)
--				}
-- OID			: 1.3.6.1.4.1.2011.2.15.1.7.7.3.1
		hwNmNorthboundEventSynchronizationEndStatus OBJECT-TYPE
			SYNTAX INTEGER
				{
				normalEnd(1),
				stopped(2),
				error(3)
				}
			ACCESS read-only
			STATUS mandatory
			DESCRIPTION
				"It shows the result of alarm synchronization.
				1 means the alarm synchronization successfully ended.
				2 means the alarm synchronization is stopped by the NMS's command.
				3 means some error occured during the alarm synchronization."
			::= { hwNmNorthboundEventSynchronizationEnd 1 }

		
-- Name        	: hwNmNorthboundEventSynchronizationEndStatusDetail 
-- Description	: The detail description of the alarm synchronization end status.
-- Type     	: OCTET STRING
-- OID			: 1.3.6.1.4.1.2011.2.15.1.7.7.3.2	
		hwNmNorthboundEventSynchronizationEndStatusDetail OBJECT-TYPE
			SYNTAX OCTET STRING
			ACCESS read-only
			STATUS mandatory
			DESCRIPTION
				"The detail description of the alarm synchronization end status."
			::= { hwNmNorthboundEventSynchronizationEnd 2 }

		
-- Name        	: hwNmNorthboundEventSynchronizationCommandStart 
-- Description	: This node is to be set to start the alarm synchronization.
-- Type     	: OCTET STRING
-- OID			: 1.3.6.1.4.1.2011.2.15.1.7.7.4
		hwNmNorthboundEventSynchronizationCommandStart OBJECT-TYPE
			SYNTAX OCTET STRING
			ACCESS read-write
			STATUS mandatory
			DESCRIPTION
				"This node is to be set to start the alarm synchronization.
				
				The format to query alarms is:- 'IP:port:start time:end time'
				Query time can be UTC time, Local time or Local time with timezone.
				Syntax for start time and end time is - YYYYMMDDhhmmss. The interpretation of the start time and end time depends on 
				the configuration file parameter.
				
				Query can be in any of the following formats:
				1. UTC time:
				Format:- 'IP:port:start time:end time'
				Here, the start time and end time will be considered to be UTC format
				
				2. Local time:
				Format:- IP:port:start time:end time
				Here, the start time and end time will be considered to be in local time format.
				
				3. Local time with timezone:
				Format:- IP:port:start time:end time:timezone:dstflag
				Here, the user can mention the timezone and dst flag
				if dstflag is 0 - DST disabled, 1- DST enabled.	
				timezone and DST are optional.
				Format to omit timezone:- IP:port:start time:end time::dstflag
				Format to omit dst flag:- IP:port:start time:end time:timezone
				
				The agent will send alarm synchronization result to the IP and port specified which were raised between start time and end time.
				If start time and end time are missing all alarms are reported. 
				Start time and end time both are optional. 
				If end time is missing current time of the EMS is taken as end time.
				If end time is present start time is not optional, it means you cannot provide end time without specifying the start time.
				If there is already a running alarm synchronization for that IP and port,it will return a commit fail error."
			::= { hwNmNorthboundEventSynchronization 4 }

		
-- Name        	: hwNmNorthboundEventSynchronizationCommandStop 
-- Description	: This node is to be set to stop the alarm synchronization.
--				It should be set as NMS's IP:port,and the agent will stop alarm synchronization for the IP and port specified.
--				If alarm synchronization is not in progress for the specified IP and port,it will return a commit fail error.
-- Type     	: OCTET STRING
-- OID			: 1.3.6.1.4.1.2011.2.15.1.7.7.5		
		hwNmNorthboundEventSynchronizationCommandStop OBJECT-TYPE
			SYNTAX OCTET STRING
			ACCESS read-write
			STATUS mandatory
			DESCRIPTION
				"This node is to be set to stop the alarm synchronization.
				It should be set as NMS's IP:port,and the agent will stop alarm synchronization for the IP and port specified.
				If alarm synchronization is not in progress for the specified IP and port,it will return a commit fail error. "
			::= { hwNmNorthboundEventSynchronization 5 }

		
	
--
-- Trap definitions
--
	
-- Name        	: hwNmNorthboundEventNotify 
-- Description	: Notification for real-time alarm.
-- Type     	: Trap/Inform

		hwNmNorthboundEventNotify TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm."
			::=  1

-- Name        	: hwNmNorthboundEventNotify 
-- Description	: Notification for keep alive traps.
-- Type     	: Trap/Inform

		hwNmNorthboundEventKeepAlive TRAP-TYPE 
			ENTERPRISE hwNmNorthboundEventKeepAliveInfo
			DESCRIPTION 
				"Notification for keep alive traps."
			::=  2
 
-- Name        	: hwNmNorthboundEventNotifyCritical 
-- Description	: Notification for real-time alarm whose level is Critical.
-- Type     	: Trap/Inform

		hwNmNorthboundEventNotifyCritical TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Critical."
			::=  3

-- Name        	: hwNmNorthboundEventNotifyMajor 
-- Description	: Notification for real-time alarm whose level is Major.
-- Type     	: Trap/Inform
		hwNmNorthboundEventNotifyMajor TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Major."
			::=  4

-- Name        	: hwNmNorthboundEventNotifyMinor 
-- Description	: Notification for real-time alarm whose level is Minor.
-- Type     	: Trap/Inform
		hwNmNorthboundEventNotifyMinor TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Minor."
			::=  5

-- Name        	: hwNmNorthboundEventNotifyWarning 
-- Description	: Notification for real-time alarm whose level is Warning.
-- Type     	: Trap/Inform

		hwNmNorthboundEventNotifyWarning TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Warning."
			::=  6

-- Name        	: hwNmNorthboundEventNotifyIndefinitely 
-- Description	: Notification for real-time alarm whose level is Indefinitely.
-- Type     	: Trap/Inform
		hwNmNorthboundEventNotifyIndefinitely TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Indefinitely."
			::=  7

-- Name        	: hwNmNorthboundEventNotifyUnknownSeverity 
-- Description	: Notification for real-time alarm whose level is UnknownSeverity.
-- Type     	: Trap/Inform
		hwNmNorthboundEventNotifyUnknownSeverity TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is UnknownSeverity."
			::=  8
-- Name        	: hwNmNorthboundEventSynchronizationStartNotify 
-- Description	: Notification indicates the beginning of alarm synchronization.
-- Type     	: Trap/Inform

		hwNmNorthboundEventSynchronizationStartNotify TRAP-TYPE 
			ENTERPRISE hwNmNorthboundEventSynchronizationStart
			DESCRIPTION 
				"Notification indicates the beginning of alarm synchronization."
			::=  9
			
-- Name        	: hwNmNorthboundEventSynchronizationQueryResultNotify 
-- Description	: Notification carries the query result of alarm synchronization.
-- Type     	: Trap/Inform

		hwNmNorthboundEventSynchronizationQueryResultNotify TRAP-TYPE 
			ENTERPRISE hwNmNorthboundEventSynchronizationQueryResult
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification carries the query result of alarm synchronization."
			::=  10          
			
-- Name        	: hwNmNorthboundEventSynchronizationEndNotify 
-- Description	: Notification indicates the end of alarm synchronization.
-- Type     	: Trap/Inform
		hwNmNorthboundEventSynchronizationEndNotify TRAP-TYPE 
			ENTERPRISE hwNmNorthboundEventSynchronizationEnd
			VARIABLES { hwNmNorthboundEventSynchronizationEndStatus, hwNmNorthboundEventSynchronizationEndStatusDetail }
			DESCRIPTION 
				"Notification indicates the end of alarm synchronization."
			::=  11

	
	END

--
-- HW-IMAPV1NORTHBOUND-TRAP-MIB.mib
--
