ERI-DNX-T3-MIB DEFINITIONS ::= BEGIN

IMPORTS
	MODULE-IDENTITY, OBJECT-IDENTITY, OBJECT-TYPE, Integer32,
	Unsigned32, IpAddress, NOTIFICATION-TYPE
		FROM SNMPv2-SMI
    DisplayString
        FROM SNMPv2-TC
    eriMibs
        FROM ERI-ROOT-SMI
    LinkPortAddress, dnx, devices, PortStatus, 
    DecisionType, FunctionSwitch, LinkCmdStatus, trapSequence
        FROM ERI-DNX-SMC-MIB;

eriDNXT3MIB MODULE-IDENTITY 
      LAST-UPDATED    "200208190000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX T3 Device."

      REVISION        "200208190000Z"
      DESCRIPTION
              "Nevio Poljak - eri_DnxNest MIB Rev 01.0
               Fixed OID for this module indentity to avoid conflict
               with the LinkTest MIB module."

      REVISION        "200204110000Z"
      DESCRIPTION
              "Nevio Poljak for Release 14.2
               Converted to SMIv2 format."

      REVISION        "200104010000Z"
      DESCRIPTION
              "Nevio Poljak - Release 12.0
               Added new InService-OOS commands for all links."

      REVISION        "200009150000Z"
      DESCRIPTION
              "Nevio Poljak
               Redefined Traps to use enterprise from their own MIB modules"

      REVISION        "200007260000Z"
      DESCRIPTION
              "Nevio Poljak
               Draft Release"

  	::= { eriMibs 3 }

-- *************************************************************************
-- The enterprise OID will be { iso(1) org(3) dod(6) internet(1) private(4)
--                              enterprises(1) virent(644) eri(2) dnx (4) 
--                              devices(2), dnxT3(1) }

-- *************************************************************************
-- The T3 card is currently controlled via the Config or Diag groups.
-- The Configuration branch is used to perform all T3 Port and Link provisioning 
-- functions and the Diagnostic branch is used to run tests and view 
-- associated Statistics. 
-- *************************************************************************

dnxT3      OBJECT IDENTIFIER 	::= { devices 1 }
t3Config   OBJECT IDENTIFIER 	::= { dnxT3 1 }
t3Diag 	   OBJECT IDENTIFIER 	::= { dnxT3 2 }

-- *************************************************************************
-- This table is the T3 Port configuration table

t3PortConfigTable OBJECT-TYPE
        SYNTAX SEQUENCE OF T3PortConfigEntry
        MAX-ACCESS not-accessible
        STATUS current
        DESCRIPTION
            "This is the T3 Port Configuration table which consists
            of an entry for each of the T3 cards.  The total number of
            entries depends on the number of T3 cards in the nest."
        ::= { t3Config 1 }

t3PortConfigEntry OBJECT-TYPE
        SYNTAX T3PortConfigEntry
        MAX-ACCESS not-accessible
        STATUS current
        DESCRIPTION
            "The conceptual row of the T3 Port Configuration table. 
            A row in this table cannot be added or deleted, only modified."
        INDEX { t3CfgAddr }
        ::= { t3PortConfigTable 1 }

T3PortConfigEntry ::=
        SEQUENCE {
                t3CfgAddr           LinkPortAddress,  -- RO
                t3CfgResource       Integer32,        -- RO
                t3CfgCircuitName    DisplayString,
                t3FacilityId        DisplayString,
                t3EquipmentId       DisplayString,
                t3Location          DisplayString,
                t3FrameId           DisplayString,
                t3UnitName          DisplayString,
                t3PortNumber        DisplayString,
                t3Generator         DisplayString,
                t3M13OpMode         INTEGER,
                t3RcvLoopTiming     FunctionSwitch,
                t3ShortCable        DecisionType,
                t3M13RemLoop        INTEGER,
                t3RcvAIS            INTEGER,
                t3XmtAIS            INTEGER,
                t3CmdStatus         LinkCmdStatus
                }

t3CfgAddr OBJECT-TYPE
        SYNTAX LinkPortAddress
        MAX-ACCESS read-only
        STATUS current
        DESCRIPTION
            "This number uniquely identifies a T3 slot/port."
        ::= { t3PortConfigEntry 1 }

t3CfgResource OBJECT-TYPE
        SYNTAX Integer32
        MAX-ACCESS read-only
        STATUS current
        DESCRIPTION
                "Uniquely identifies an T3 Port in the system.
                 This number is provided as key to allow the manager to 
                 map this entry to a corresponding Resource Table entry."
        ::= { t3PortConfigEntry 2 }

t3CfgCircuitName OBJECT-TYPE
        SYNTAX DisplayString (SIZE(0..20))
        MAX-ACCESS read-write
        STATUS current
        DESCRIPTION
            "This is the user friendly text name to identify the circuit."
        ::= { t3PortConfigEntry 3 }

t3FacilityId OBJECT-TYPE
        SYNTAX DisplayString (SIZE(0..37))
        MAX-ACCESS read-write
        STATUS current
        DESCRIPTION
        	"This is a description of the facility where this equipment 
        	 is located."
        ::= { t3PortConfigEntry 4 }

t3EquipmentId OBJECT-TYPE
        SYNTAX DisplayString (SIZE(0..9))
        MAX-ACCESS read-write
        STATUS current
        DESCRIPTION
        	"This is a description of the equipment in use."
        ::= { t3PortConfigEntry 5 }

t3Location OBJECT-TYPE
        SYNTAX DisplayString (SIZE(0..10))
        MAX-ACCESS read-write          
        STATUS current
        DESCRIPTION
        	"This is the user description of the location for this equipment."
        ::= { t3PortConfigEntry 6 }

t3FrameId OBJECT-TYPE
        SYNTAX DisplayString (SIZE(0..9))
        MAX-ACCESS read-write
        STATUS current
        DESCRIPTION
        	"This is the description of the building where this equipment is 
        	located."
        ::= { t3PortConfigEntry 7 }
 
t3UnitName OBJECT-TYPE
        SYNTAX DisplayString (SIZE(0..5))
        MAX-ACCESS read-write
        STATUS current
        DESCRIPTION
        	"This is the description of the bay or device this equipment 
        	 is part of."
        ::= { t3PortConfigEntry 8 }

t3PortNumber OBJECT-TYPE
        SYNTAX DisplayString (SIZE(0..37))
        MAX-ACCESS read-write
        STATUS current
        DESCRIPTION
        	"This is the user description of the DS3 port."
        ::= { t3PortConfigEntry 9 }

t3Generator OBJECT-TYPE
        SYNTAX DisplayString (SIZE(0..37))
        MAX-ACCESS read-write
        STATUS current
        DESCRIPTION
        	"This is the user description of the number generated by this 
        	equipment."
        ::= { t3PortConfigEntry 10 }
        
t3M13OpMode OBJECT-TYPE
        SYNTAX INTEGER {
                c-bit(0),
                bellcoreM13(1)
                }
        MAX-ACCESS read-write
        STATUS current
        DESCRIPTION
           "The framing selection for the DS1 to DS3 multiplexing."
        ::= { t3PortConfigEntry 11 }

t3RcvLoopTiming OBJECT-TYPE
        SYNTAX FunctionSwitch
        MAX-ACCESS read-write
        STATUS current
        DESCRIPTION
           "Enables or disables the DS3 transmit timing provided by the 
           receive clock.  When disabled, timing is provided by an on-board 
           oscillator."
        ::= { t3PortConfigEntry 12 }

t3ShortCable OBJECT-TYPE
        SYNTAX DecisionType
        MAX-ACCESS read-write
        STATUS current
        DESCRIPTION
           "Indicates the line build out of the DS3 transmitter.  'Yes' when 
           attached to a cable less than 50 feet long."
        ::= { t3PortConfigEntry 13 }

t3M13RemLoop OBJECT-TYPE
        SYNTAX INTEGER  {
                third-cbit-inverted (0),
                second-cbit-inverted (1),
                first-cbit-inverted (2),
                third-cbit-stuffbit-inverted (4),
                second-cbit-stuffbit-inverted (5),
                first-cbit-stuffbit-inverted (6),
                stuffbit-inverted (7),
                stuffbit-is-zero (8),
                stuffbit-is-one (9)                
                }
        MAX-ACCESS read-write
        STATUS current
        DESCRIPTION
           "Controls the line codes used to set and reset DS1 remote line
           loopback requests.  This applies the BellCore M13 mode only."
        ::= { t3PortConfigEntry 14 }

t3RcvAIS OBJECT-TYPE
        SYNTAX INTEGER  {
                framed1010-Cbit0-noXbit (0),
                framed1010-Cbit0-Xbit1 (1),
                framed1010-noCbit-noXbit (2),
                framed1111-noCbit-noXbit (3),
                unframed1010 (4),
                unframed-allones (5)
                }
        MAX-ACCESS read-write
        STATUS current
        DESCRIPTION
           "The Received bit pattern that will cause an error."
        ::= { t3PortConfigEntry 15 }

t3XmtAIS OBJECT-TYPE
        SYNTAX INTEGER {
                ansi (0),
                framed-allones-Cbit1 (1),
                unframed1010 (2),
                unframed-allones (3)
                }
        MAX-ACCESS read-write
        STATUS current
        DESCRIPTION
           "The Transmitted bit pattern that will cause an error."
        ::= { t3PortConfigEntry 16 }

t3CmdStatus OBJECT-TYPE
        SYNTAX LinkCmdStatus
        MAX-ACCESS read-write
        STATUS current
        DESCRIPTION
           "The command status for this link configuration row/record.
           The value used in a SET will be replaced by a response
           value in the GET RESPONSE indicating success or failure.
           		
            Default Response State used in GET RESPONSE Command
                ready-for-command (0)
                    initial default status for a row           
                    
            T3 Link Commands used in SET Command (1..99)            
                update-link-config(1),
                    Change existing Link Configuration
               		
            Response States used in GET RESPONSE Command (100..199)
                update-successful (101)
                    Link data has been successfully changed
                                		
            T3 Port Config Error Codes used in GET RESPONSE Command (100..699)
                err-general-link-config-error (400)
                    Unknown link configuration error occurred                
                err-invalid-link-status (401)
                    Unrecognized link status setting
                err-invalid-link-framing (402)         
                    Line framing type not valid for link type
                err-invalid-link-command (403)
                    Unrecognized link command-action
                err-invalid-link-op-mode (407)
                    Configured M13 Op mode not valid for port; verify other
                    link parameters match desired new mode                
                err-invalid-link-rem-loop (408)         
                    Remote Loop type not valid for t3 frame type
                err-invalid-link-ais (409)
                    Unrecognized t3 AIS selection
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
       ::= { t3PortConfigEntry 17}


-- *************************************************************************
-- This table is the T3 T-1 Link configuration table

t3T1LinkConfigTable OBJECT-TYPE
        SYNTAX SEQUENCE OF T3T1LinkConfigEntry
        MAX-ACCESS not-accessible
        STATUS current
        DESCRIPTION
            "This is the T3 T-1 Link Configuration table which consists
            of an entry for each of the card's 28 links.  The total number of
            entries depends on the number of DS3 cards in the nest."
        ::= { t3Config 2 }

t3T1LinkConfigEntry OBJECT-TYPE
        SYNTAX T3T1LinkConfigEntry
        MAX-ACCESS not-accessible
        STATUS current
        DESCRIPTION
            "The conceptual row of the T3 T-1 Link Configuration table. 
            A row in this table cannot be added or deleted, only modified."
        INDEX { t3T1CfgLinkAddr }
        ::= { t3T1LinkConfigTable 1 }

T3T1LinkConfigEntry ::=
        SEQUENCE {
                t3T1CfgLinkAddr     LinkPortAddress,  -- RO
                t3T1CfgResource     Integer32,        -- RO
                t3T1CfgLinkName     DisplayString,
                t3T1Status          PortStatus,
                t3T1Framing         INTEGER,
                t3T1Density         INTEGER,
                t3T1NetLoop         INTEGER,
                t3T1YelAlrm         INTEGER,
                t3T1RecoverTime     INTEGER,
                t3T1EsfFormat       INTEGER,
                t3T1IdleCode        INTEGER,
                t3T1CfgCmdStatus    LinkCmdStatus
                }

t3T1CfgLinkAddr OBJECT-TYPE
        SYNTAX LinkPortAddress
        MAX-ACCESS read-only
        STATUS current
        DESCRIPTION
            "This number uniquely identifies a T3/T-1 link resource. 
            This number will be used throughout the system to identify 
            a unique resource."
        ::= { t3T1LinkConfigEntry 1 }

t3T1CfgResource OBJECT-TYPE
        SYNTAX Integer32
        MAX-ACCESS read-only
        STATUS current
        DESCRIPTION
                "Uniquely identifies an T3 T1 Channel in the system.
                 This number is provided as key to allow the manager to 
                 map this entry to a corresponding Resource Table entry."
        ::= { t3T1LinkConfigEntry 2 }

t3T1CfgLinkName OBJECT-TYPE
        SYNTAX DisplayString (SIZE(0..20))
        MAX-ACCESS read-write
        STATUS current
        DESCRIPTION
        	"This is the user friendly text name to identify the link."
        ::= { t3T1LinkConfigEntry 3 }

t3T1Status OBJECT-TYPE
        SYNTAX PortStatus
        MAX-ACCESS read-write
        STATUS current
        DESCRIPTION
           "Dictates the current status of the link, in-service or 
           out-of-service."
        ::= { t3T1LinkConfigEntry 4 }

t3T1Framing OBJECT-TYPE
        SYNTAX INTEGER {
        	d4 (1),
        	esf (3)
        	}
        MAX-ACCESS read-write
        STATUS current
        DESCRIPTION
           "Determines the type of framing used on the line.  Choose between 
           SuperFrame 'D4' or Extended SuperFrame (ESF)."
        ::= { t3T1LinkConfigEntry 5 }

t3T1Density OBJECT-TYPE
        SYNTAX INTEGER {
        	clear (0),
        	att-62411 (1)
        	}
        MAX-ACCESS read-write
        STATUS current
        DESCRIPTION
           "Determines the type of network signal used on the link.  If line 
           code is B8ZS, choose 'clear'.  If line code is AMI, choose 62411."
        ::= { t3T1LinkConfigEntry 6 }

t3T1NetLoop OBJECT-TYPE
        SYNTAX FunctionSwitch
        MAX-ACCESS read-write
        STATUS current
        DESCRIPTION
           "Determines whether or not the module should respond to loop 
           diagnostic commands received from the network supplier. Select 
           'enable' unless the commands are to be passed to another DS3 
           device."
        ::= { t3T1LinkConfigEntry 7 }

t3T1YelAlrm OBJECT-TYPE
        SYNTAX DecisionType
        MAX-ACCESS read-write
        STATUS current
        DESCRIPTION
           "Causes the module to discard data and send a yellow alarm if it
           is in a red alarm condition after a 3 second period. 'Yes' must
           be chosen if the network supplier is a common carrier, such as a 
           telephone company."
        ::= { t3T1LinkConfigEntry 8 }

t3T1RecoverTime OBJECT-TYPE
        SYNTAX INTEGER {
        	timeout-3-secs (3),
        	timeout-10-secs(10),
        	timeout-15-secs(15)
        	}
        MAX-ACCESS read-write
        STATUS current
        DESCRIPTION
           "This is the red alarm timeout value.  Determines the amount 
           of seconds the port will wait to stop sending the yellow alarm 
           when coming out of a red alarm condition."
        ::= { t3T1LinkConfigEntry 9 }

t3T1EsfFormat OBJECT-TYPE
        SYNTAX INTEGER {
        	att-54016 (0),
        	ansi-t1-403 (1)
        	}
        MAX-ACCESS read-write
        STATUS current
        DESCRIPTION
           "Determines the type of ESF network commands the  T-1 link 
           will respond to. It has no meaning for D4 networks. With ESF 
           networks, this information must be obtained from the network 
           supplier."
        ::= { t3T1LinkConfigEntry 10 }

t3T1IdleCode OBJECT-TYPE
        SYNTAX INTEGER {
        	busy (0),
        	idle (1)
        	}
        MAX-ACCESS read-write
        STATUS current
        DESCRIPTION
           "Determines the whether the code that will be transmitted over 
           the unused links will be 'idle' or 'busy' (all 1's)."
        ::= { t3T1LinkConfigEntry 11 }

t3T1CfgCmdStatus OBJECT-TYPE
        SYNTAX LinkCmdStatus 
        MAX-ACCESS read-write
        STATUS current
        DESCRIPTION
           "The command status for this link configuration row/record.
           The value used in a SET will be replaced by a response
           value in the GET RESPONSE indicating success or failure.
           		
            Default Response State used in GET RESPONSE Command
                ready-for-command (0)
                    initial default status for a row           
                    
            T3-T1 Link Commands used in SET Command (1..99)            
                update-link-config(1)
                    Change existing Link Configuration
                inServiceAll (7)
                    Change Link Status to in-service for all 8 links.
                copyToAll (9)
                    Copy T1 Link configuration to all other links 
                    within the same device
                outOfServiceAll (12)
                    Change Link Status to out-of-service for all 8 links.
               		
            Response States used in GET RESPONSE Command (100..199)
                update-successful (101)
                    Link data has been successfully changed
                insvc-successful (107)
                    All Links have been successfully placed In Service
                copy-successful (109)
                    T1 Link data has been successfully copied to other links
                oos-successful (112)
                    All Links have been successfully placed Out of Service
                                		
            T3-T1 Link Config Error Codes used in GET RESPONSE Command (200..699)
                err-general-link-config-error (400)
                    Unknown link configuration error occurred                
                err-invalid-link-status (401)
                    Unrecognized link status setting
                err-invalid-link-framing (402)         
                    Line framing type not valid for link type
                err-invalid-link-command (403)
                    Unrecognized link command-action
                err-invalid-esf-format (405)
                    ESF type not applicable to link type
                err-invalid-link-density (406)
                    Unrecognized T1 link density setting 
                err-invalid-network-loop (410)
                    Unrecognized network loop setting
                err-invalid-yellow-alrm (411)
                    Unrecognized yellow alarm setting
                err-invalid-red-timeout (412)
                    Unrecognized red alarm timeout
                err-invalid-idle-code (413)
                    Unrecognized idle code
                err-device-in-standby (414)
                    Can't change config for designated Standby device
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big"                                		
        ::= { t3T1LinkConfigEntry 12 }

-- *************************************************************************
--   This is the Trap Definitions section for the T3 MIB. 
-- *************************************************************************

dnxT3Enterprise OBJECT-IDENTITY
      STATUS current
      DESCRIPTION "ERI DNX T3 Enterprise for Alarms/Events"
    ::= { dnxT3 0 }

t3PortConfigTrap NOTIFICATION-TYPE
        OBJECTS {
            trapSequence,
            t3CfgAddr,
            t3CmdStatus
            }
        STATUS current
        DESCRIPTION
              	"This trap is used to notify a NMS that a user has updated 
              	the configuration for a given T3 Port entry."
        ::= { dnxT3Enterprise 1 }

t3T1ConfigTrap NOTIFICATION-TYPE
        OBJECTS {
            trapSequence,
            t3T1CfgLinkAddr,
            t3T1CfgCmdStatus
            }
        STATUS current
        DESCRIPTION
              	"This trap is used to notify a NMS that a user has updated 
              	the Link configuration for a given T3-T1 channel entry."
        ::= { dnxT3Enterprise 2 }
                
END

-- *************************************************************************
--
--  MIB:    ERI-DNX-STS1-MIB
--
--  Purpose:
--          This will be the MIB for the DNX STS-1 Interface 
--          Module. This will provide for Configuration and Diagnostics
--          on any STS1 card in the nest.
--
--  Contact: Eastern Research Inc. 1-800-337-4374  Email: support@erinc.com
--
--  Revised: Sept. 15, 2000 - Nevio Poljak
--           Initial Release
--
--           March 1, 2001 - Nevio Poljak - Release 11.0 
--           Added new GR-303 Facility field 
--
--           April 3, 2001 - Nevio Poljak - Release 12.0 
--           Added new InService-OOS commands for all links. 
--
--           Feb. 5, 2002 - Nevio Poljak - Release 14.1 
--           Added new Tables for STS1 Mapper & LIU Diagnostics. 
--           Also, GR303 Facility field was made obsolete from the T1 Cfg Table.
--
--           April 8, 2002 - Nevio Poljak for Release 14.2
--           Converted to SMIv2 format.
-- *************************************************************************
