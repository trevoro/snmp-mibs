SALIX-RTP-MIB DEFINITIONS ::= BEGIN

IMPORTS
	OBJECT-GROUP FROM SNMPv2-CONF
         MODULE-IDENTITY, OBJECT-TYPE, Integer32,
         IpAddress, Counter32             FROM SNMPv2-SMI
			MODULE-COMPLIANCE FROM SNMPv2-CONF
         
         DisplayString                    FROM RFC1213-MIB         

         platform1                        FROM SALIX-MIB;

salixRtpMIB MODULE-IDENTITY
     LAST-UPDATED "9810130000Z"
     ORGANIZATION "SALIX Technologies"
     CONTACT-INFO "904 Wind River Lane
                   Suite 101
                   Gaithersburg, MD  20878
                   (301)-417-0017"
     DESCRIPTION  "The SALIX-RTP-MIB containts objects for describing
                   RTP Sessions."
     ::= { platform1 1 } 
     
   salixRtpMIBObjects OBJECT IDENTIFIER ::= { salixRtpMIB 1 }
   salixRtpMIBTraps   OBJECT IDENTIFIER ::= { salixRtpMIB 2 }
   salixRtpMIBCompliance OBJECT IDENTIFIER ::= { salixRtpMIB 3 }
   salixRtpMIBTrapPrefix   OBJECT IDENTIFIER ::= { salixRtpMIBTraps 0 }
   
   -- RTP Stats
   
      salixRtpStatsTable OBJECT-TYPE
         SYNTAX      SEQUENCE OF ItxRtpStatsEntry
         MAX-ACCESS  not-accessible   
         STATUS      current
         DESCRIPTION
            "Table to hold statistics on RTP sessions.  For each active
             RTP Session, there will be one entry in the table.
            
             NOTE: Retrieval of RTP statistics is an expensive operation.
                   Please use with care."
      ::= { salixRtpMIBObjects 1 }
      
      salixRtpStatsEntry OBJECT-TYPE
         SYNTAX     ItxRtpStatsEntry
         MAX-ACCESS not-accessible
         STATUS     current
         DESCRIPTION
            "This entry lists statistics on a given RTP session.  The
             session is uniqely identified by the source Ip Address 
             and port, along with the destination Ip Address and UDP Port."
         INDEX { salixRtpStatsSrcIpAddress,
                 salixRtpStatsSrcPort,
                 salixRtpStatsDestIpAddress,
                 salixRtpStatsDestPort }
         ::= { salixRtpStatsTable 1 }         
      
      ItxRtpStatsEntry ::= SEQUENCE {
         salixRtpStatsSrcIpAddress                   IpAddress,
         salixRtpStatsSrcPort                        INTEGER,
         salixRtpStatsDestIpAddress                  IpAddress,
         salixRtpStatsDestPort                       INTEGER,
         salixRtpStatsPktsSent                       Counter32,
         salixRtpStatsPktsRecv                       Counter32,
         salixRtpStatsPktsDropped                    Counter32,
         salixRtpStatsBytesSent                      Counter32,
         salixRtpStatsBytesRecv                      Counter32,
         salixRtpStatsBytesDropped                   Counter32,
         salixRtpStatsSignalPktsSent                 Counter32,
         salixRtpStatsSignalPktsRecv                 Counter32,
         salixRtpStatsSignalPktsDropped              Counter32,
         salixRtpStatsSignalBytesRecv                Counter32,
         salixRtpStatsAudioPktsRecv                  Counter32,
         salixRtpStatsAudioBytesRecv                 Counter32,
         salixRtpStatsEstimatedAvgLatency            Integer32
      }  
      
      salixRtpStatsSrcIpAddress OBJECT-TYPE
         SYNTAX     IpAddress
         MAX-ACCESS not-accessible
         STATUS     current
         DESCRIPTION
            "The Ip Address for the source side of the RTP session.  
             Along with the source UDP Port, these objects identify the 
             RTP session on the source side.  Complete identification 
             of the RTP session also requires a unique identification 
             on the destination side"
         ::= { salixRtpStatsEntry 1 }
               
      salixRtpStatsSrcPort OBJECT-TYPE
         SYNTAX     INTEGER(0..65535)
         MAX-ACCESS not-accessible
         STATUS     current
         DESCRIPTION
            "The UDP Port for the source side of the RTP session.  
             Along with the source Ip Address, these objects identify the 
             RTP session on the source side.  Complete identification 
             of the RTP session also requires a unique identification 
             on the destination side"
         ::= { salixRtpStatsEntry 2 }
               
      salixRtpStatsDestIpAddress OBJECT-TYPE
         SYNTAX     IpAddress
         MAX-ACCESS not-accessible
         STATUS     current
         DESCRIPTION
            "The Ip Address for the destination side of the RTP session.  
             Along with the destination UDP Port, these objects identify the 
             RTP session on the destination side.  Complete identification 
             of the RTP session also requires a unique identification 
             on the source side"
         ::= { salixRtpStatsEntry 3 }
               
      salixRtpStatsDestPort OBJECT-TYPE
         SYNTAX     INTEGER(0..65535)
         MAX-ACCESS not-accessible
         STATUS     current
         DESCRIPTION
            "The UDP Port for the destination side of the RTP session.  
             Along with the destination Ip Address, these objects identify the 
             RTP session on the destination side.  Complete identification 
             of the RTP session also requires a unique identification 
             on the source side"
         ::= { salixRtpStatsEntry 4 }
               
      salixRtpStatsPktsSent OBJECT-TYPE
         SYNTAX     Counter32
         MAX-ACCESS read-only
         STATUS     current
         DESCRIPTION
            "The total number of RTP packets sent during the 
             specified session"
         ::= { salixRtpStatsEntry 5 }
               
      salixRtpStatsPktsRecv OBJECT-TYPE
         SYNTAX     Counter32
         MAX-ACCESS read-only
         STATUS     current
         DESCRIPTION
            "The total number of RTP packets recieved during the 
             specified session"
         ::= { salixRtpStatsEntry 6 }
               
      salixRtpStatsPktsDropped OBJECT-TYPE
         SYNTAX     Counter32
         MAX-ACCESS read-only
         STATUS     current
         DESCRIPTION
            "The total number of RTP packets dropped during the 
             specified session"
         ::= { salixRtpStatsEntry 7 }
               
      salixRtpStatsBytesSent OBJECT-TYPE
         SYNTAX     Counter32
         MAX-ACCESS read-only
         STATUS     current
         DESCRIPTION
            "The total number of bytes sent during the 
             specified session"
         ::= { salixRtpStatsEntry 8 }
               
      salixRtpStatsBytesRecv OBJECT-TYPE
         SYNTAX     Counter32
         MAX-ACCESS read-only
         STATUS     current
         DESCRIPTION
            "The total number of bytes received during the 
             specified session"
         ::= { salixRtpStatsEntry 9 }
               
      salixRtpStatsBytesDropped OBJECT-TYPE
         SYNTAX     Counter32
         MAX-ACCESS read-only
         STATUS     current
         DESCRIPTION
            "The total number of bytes dropped during the 
             specified session"
         ::= { salixRtpStatsEntry 10 }
               
      salixRtpStatsSignalPktsSent OBJECT-TYPE
         SYNTAX     Counter32
         MAX-ACCESS read-only
         STATUS     current
         DESCRIPTION
            "The number of signalling packets 
             sent for the RTP session"
         ::= { salixRtpStatsEntry 11 }
               
      salixRtpStatsSignalPktsRecv OBJECT-TYPE
         SYNTAX     Counter32
         MAX-ACCESS read-only
         STATUS     current
         DESCRIPTION
            "The number of signalling packets 
             received for the RTP session"
         ::= { salixRtpStatsEntry 12 }
               
      salixRtpStatsSignalPktsDropped OBJECT-TYPE
         SYNTAX     Counter32
         MAX-ACCESS read-only
         STATUS     current
         DESCRIPTION
            "The number of signalling packets 
             dropped for the RTP session"
         ::= { salixRtpStatsEntry 13 }
               
      salixRtpStatsSignalBytesRecv OBJECT-TYPE
         SYNTAX     Counter32
         MAX-ACCESS read-only
         STATUS     current
         DESCRIPTION
            "The number of signalling bytes 
             received for the RTP session"
         ::= { salixRtpStatsEntry 14 }
               
      salixRtpStatsAudioPktsRecv OBJECT-TYPE
         SYNTAX     Counter32
         MAX-ACCESS read-only
         STATUS     current
         DESCRIPTION
            "The number of audio packets received
             for the specified RTP session"
         ::= { salixRtpStatsEntry 15 }  
             
      salixRtpStatsAudioBytesRecv OBJECT-TYPE
         SYNTAX     Counter32
         MAX-ACCESS read-only
         STATUS     current
         DESCRIPTION
            "The number of audio bytes received
             for the specified RTP session"
         ::= { salixRtpStatsEntry 16 }
               
      salixRtpStatsEstimatedAvgLatency OBJECT-TYPE
         SYNTAX     Integer32
         MAX-ACCESS read-only
         STATUS     current
         DESCRIPTION
            "The Estimated Average Latency for the
             RTP session"
         ::= { salixRtpStatsEntry 17 }   
   
-- Conformance Statements

salixRtpGroups      OBJECT IDENTIFIER  ::= { salixRtpMIBCompliance 1 }
salixRtpCompliances OBJECT IDENTIFIER  ::= { salixRtpMIBCompliance 2 }            
            
   salixRtpGroup OBJECT-GROUP
      OBJECTS {
         salixRtpStatsPktsSent,          
         salixRtpStatsPktsRecv,       
         salixRtpStatsPktsDropped,
         salixRtpStatsBytesSent,         
         salixRtpStatsBytesRecv,      
         salixRtpStatsBytesDropped,    
         salixRtpStatsSignalPktsSent,    
         salixRtpStatsSignalPktsRecv, 
         salixRtpStatsSignalPktsDropped,
         salixRtpStatsSignalBytesRecv,
         salixRtpStatsAudioPktsRecv,    
         salixRtpStatsAudioBytesRecv,
         salixRtpStatsEstimatedAvgLatency
      }
      STATUS            current
      DESCRIPTION       "Stats Statistics for Rtp Sessions"
      ::= {salixRtpGroups 3}
      
-- Compliance Statements

salixRtpCompliance MODULE-COMPLIANCE
     STATUS       current
     DESCRIPTION
                  "The basic implementation requirements for the SALIX-RTP-MIB."
     MODULE       -- This module
     MANDATORY-GROUPS { salixRtpGroup }
     ::= { salixRtpCompliances 1 }             

END
