--
 -- WWP-MULTI-DHCP-CLIENT-MIB.my
 --
 --

 WWP-MULTI-DHCP-CLIENT-MIB DEFINITIONS ::= BEGIN

 IMPORTS 		
   IpAddress, Integer32, Unsigned32, OBJECT-TYPE, MODULE-IDENTITY			
	    FROM SNMPv2-SMI			
   DisplayString, TruthValue			
	    FROM SNMPv2-TC						
   wwpModules			
	    FROM WWP-SMI;
	
	
 wwpMultiDhcpClientMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module to manage multiple dhcp clients on WWP products."
	    REVISION    "200211011700Z"
	    DESCRIPTION
		    "Initial creation."
	    ::= { wwpModules 42 }
						
 --
 -- Node definitions
 --
	
 wwpMultiDhcpClientMIBObjects OBJECT IDENTIFIER ::= { wwpMultiDhcpClientMIB 1 }
 
 wwpMultiDhcpClient OBJECT IDENTIFIER ::= { wwpMultiDhcpClientMIBObjects 1 }

 		
 -- Notifications 
  
 wwpMultiDhcpClientMIBNotificationPrefix  OBJECT IDENTIFIER ::= { wwpMultiDhcpClientMIB 2 } 
 wwpMultiDhcpClientMIBNotifications       OBJECT IDENTIFIER ::=  
                       { wwpMultiDhcpClientMIBNotificationPrefix 0 }

 -- Conformance information 
 
 wwpMultiDhcpClientMIBConformance OBJECT IDENTIFIER ::= { wwpMultiDhcpClientMIB 3 } 
 wwpMultiDhcpClientMIBCompliances OBJECT IDENTIFIER ::= { wwpMultiDhcpClientMIBConformance 1 } 		
 wwpMultiDhcpClientMIBGroups      OBJECT IDENTIFIER ::= { wwpMultiDhcpClientMIBConformance 2 }

 wwpMultiDhcpClientNumber  OBJECT-TYPE
    SYNTAX      Integer32
    MAX-ACCESS  read-only
    STATUS      current
    DESCRIPTION
            "The number of dhcp clients (regardless of their
            current state) present on this system."
    ::= { wwpMultiDhcpClient 1 }

 -- the Multi dhcp client Table

 wwpMultiDhcpClientTable OBJECT-TYPE
    SYNTAX      SEQUENCE OF WwpMultiDhcpClientEntry
    MAX-ACCESS  not-accessible
    STATUS      current
    DESCRIPTION
            "A list of dhcp client entries.The number of entries is
            given by the value of wwpMultiDhcpClientNumber."
    ::= { wwpMultiDhcpClient 2 }

 wwpMultiDhcpClientEntry OBJECT-TYPE
    SYNTAX      WwpMultiDhcpClientEntry
    MAX-ACCESS  not-accessible
    STATUS      current
    DESCRIPTION
            "An entry containing management information applicable to 
	    dhcp client."
    INDEX   { wwpDhcpIfIndex }
    ::= { wwpMultiDhcpClientTable 1 }

 WwpMultiDhcpClientEntry ::=
    SEQUENCE {
        wwpDhcpIfIndex                     Integer32,
        wwpDhcpIfName                      DisplayString,
        wwpDhcpStatus                      INTEGER,
	wwpDhcpState                       INTEGER,
        wwpDhcpLeaseTimeRequested          Integer32, 
	wwpDhcpLeaseOffered                Integer32,
	wwpDhcpLeaseRemaining              Integer32,
	wwpDhcpDiscoveryMsgInterval        Integer32,
	wwpDhcpRenewalTime                 Integer32,
	wwpDhcpRebindingTime               Integer32,
	wwpDhcpServerAddress               IpAddress,
	wwpDhcpRenewLease                  TruthValue, 
	wwpDhcpReleaseLease                TruthValue
    }

 wwpDhcpIfIndex OBJECT-TYPE
     SYNTAX      Integer32(1..2147483647)
     MAX-ACCESS  read-only
     STATUS      current
     DESCRIPTION
             "The value of the instance of the ifIndex object,
             defined in MIB-II, for the interface corresponding
             to this dhcp interface."
 ::= { wwpMultiDhcpClientEntry 1 }
 
 wwpDhcpIfName   OBJECT-TYPE
     SYNTAX       DisplayString(SIZE (0..32))
     MAX-ACCESS   read-only
     STATUS       current
     DESCRIPTION
             "The ifDesc associated with this ifIndex."
     ::= { wwpMultiDhcpClientEntry 2 }
     
 wwpDhcpStatus     OBJECT-TYPE
     SYNTAX          INTEGER {
                         enable(1),
		         disable(2)
		     }
     MAX-ACCESS      read-write
     STATUS          current
     DESCRIPTION
    	     "Setting this object to 'enable' will enable the 
	     dhcp client on this interface."        
     ::= { wwpMultiDhcpClientEntry 3 } 
     
 wwpDhcpState     OBJECT-TYPE
     SYNTAX          INTEGER {
                         bound(1),
		         disabled(2),
		         inform(3),
		         init(4),
		         rebinding(5),
		         renewing(6),
		         requesting(7),
		         selecting(8),
		         unknown(9)  
		     }
     MAX-ACCESS      read-only
     STATUS          current
     DESCRIPTION
    	     "The current state of the dhcp client on this 
	      interface as per RFC2131."        
     ::= { wwpMultiDhcpClientEntry 4 }       
 				 		 
 wwpDhcpLeaseTimeRequested  OBJECT-TYPE
     SYNTAX          Integer32(0..2147483647)
     UNITS           "seconds"
     MAX-ACCESS      read-write
     STATUS          current     
     DESCRIPTION
             "The requested lease time option to be used with 
	     DHCPDISCOVER or DHCPREQUEST messages on this interface."
     DEFVAL  { 45 }
     ::= { wwpMultiDhcpClientEntry 5 }
     
 wwpDhcpLeaseOffered  OBJECT-TYPE
     SYNTAX          Integer32(0..2147483647)
     UNITS           "seconds"
     MAX-ACCESS      read-only
     STATUS          current     
     DESCRIPTION
             "The lease time authorized by the server."
     ::= { wwpMultiDhcpClientEntry 6 }
     
 wwpDhcpLeaseRemaining  OBJECT-TYPE
     SYNTAX          Integer32(0..2147483647)
     UNITS           "seconds"
     MAX-ACCESS      read-only
     STATUS          current     
     DESCRIPTION
             "The time remaining for the lease to expire."
     ::= { wwpMultiDhcpClientEntry 7 }
 
 wwpDhcpDiscoveryMsgInterval  OBJECT-TYPE
     SYNTAX          Integer32(0..2147483647)
     UNITS           "seconds"
     MAX-ACCESS      read-write
     STATUS          current     
     DESCRIPTION
             "The time interval for discovery messages issued before the client
             receives the first reply."
     DEFVAL  { 30 }
     ::= { wwpMultiDhcpClientEntry 8 }
     
 wwpDhcpRenewalTime  OBJECT-TYPE
     SYNTAX          Integer32(0..2147483647)
     UNITS           "seconds"
     MAX-ACCESS      read-only
     STATUS          current     
     DESCRIPTION
             "The number of seconds before the client begins to renew its 
	     address lease with the dhcp server. This time is a function typically 
	     50% of the full configured duration (or lease time) for a client lease.
	     Referred to as T1 in RFC2131."
     ::= { wwpMultiDhcpClientEntry 9 }
 
 wwpDhcpRebindingTime  OBJECT-TYPE
     SYNTAX          Integer32(0..2147483647)
     UNITS           "seconds"
     MAX-ACCESS      read-only
     STATUS          current     
     DESCRIPTION
             "The number of seconds before the client enters the rebinding state 
	     if it has not renewed its current address lease with the dhcp server. 
             This time is a function (typically, 87.5%) of the full configured 
	     duration (or lease time) for a client lease. 
	     Referred to as T2 in RFC2131."
     ::= { wwpMultiDhcpClientEntry 10 }
     
 wwpDhcpServerAddress  OBJECT-TYPE
     SYNTAX          IpAddress
     MAX-ACCESS      read-only
     STATUS          current     
     DESCRIPTION
             "The IP address that identifies the dhcp server."
     ::= { wwpMultiDhcpClientEntry 11 }
     
 wwpDhcpRenewLease   OBJECT-TYPE
     SYNTAX          TruthValue
     MAX-ACCESS      read-write
     STATUS          current
     DESCRIPTION
    	     "Setting this object to true will force the dhcp 
	     client to renew its lease."
     DEFVAL { false }                
     ::= { wwpMultiDhcpClientEntry 12 }
     
 wwpDhcpReleaseLease OBJECT-TYPE
     SYNTAX          TruthValue
     MAX-ACCESS      read-write
     STATUS          current
     DESCRIPTION
    	     "Setting this object to true will force the dhcp
	     client to release its lease, if the client dhcp
	     is in the bound state"
     DEFVAL { false }                
     ::= { wwpMultiDhcpClientEntry 13 }
     

 END

 --
 -- WWP-MULTI-DHCL-MIB.my
 --
