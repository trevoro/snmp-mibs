ERI-DNX-SMC-MIB DEFINITIONS ::= BEGIN

IMPORTS
	MODULE-IDENTITY, OBJECT-IDENTITY, OBJECT-TYPE, 
	Integer32, Counter32, IpAddress, Unsigned32, TimeTicks, NOTIFICATION-TYPE
		FROM SNMPv2-SMI
    DisplayString, TEXTUAL-CONVENTION
        FROM SNMPv2-TC
    eriMibs, eriProducts
        FROM ERI-ROOT-SMI;

-- *************************************************************************
-- The DNX enterprise OID will be { iso(1) org(3) dod(6) internet(1) private(4)
--                                  enterprises(1) eriEnterpriseRoot(644) 
--                                  eriProducts(2) dnx(4) 
--                                }
-- *************************************************************************

eriDNXSmcMIB MODULE-IDENTITY 
      LAST-UPDATED    "200305190000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX System Manager."

      REVISION        "200305190000Z"
      DESCRIPTION
              "Neeraj Bhatt - eri_DnxRoot MIB Rev 2.2 (SW Rel. 16.0)
               Added severity field to the systemEventTrap."

      REVISION        "200305060000Z"
      DESCRIPTION
              "Nevio Poljak - eri_DnxRoot MIB Rev 2.1 (SW Rel. 15.2)
               Removed SMC Station Clock Traps which are no longer supported.
               Added DS0DP InTest and TestOff Informational Events."

      REVISION        "200303210000Z"
      DESCRIPTION
              "Nevio Poljak - eri_DnxRoot MIB Rev 02.1 (SW Rel. 15.2)
               Added a new field to the System Profile Table to display
               the System Manager Online Time."

      REVISION        "200302250000Z"
      DESCRIPTION
              "Neeraj Bhatt - eri_DnxRoot MIB Rev 02.0
               Added 2 error codes to the connection tables' command
               status and one error code to the LinkCmdStatus."

	  REVISION        "200301280000Z"
      DESCRIPTION
              "Nevio Poljak - eri_DnxRoot MIB Rev 02.0
               Added new Feature Key table and subRate level connection 
               support for DNX-1u. Also added new trap for Feature Key
               provisioning."

      REVISION        "200301100000Z"
      DESCRIPTION
              "Neeraj Bhatt - eri_DnxRoot MIB Rev 01.2
               Appended a new field to the System Profile Table to enable 
               the trap for the Sa4 bit RxTx match. Added a new trap for the
               Laser Off detection."

      REVISION        "200301030000Z"
      DESCRIPTION
              "Nevio Poljak - eri_DnxRoot MIB Rev 01.2
               Added Transcoder Resource Ids and corrected Revision Dates."

      REVISION        "200211180000Z"
      DESCRIPTION
              "Nevio Poljak - eri_DnxRoot MIB Rev 01.2
               Appended new fields to the Trap Destination Table to
               support v2Trap and Inform configuration."

      REVISION        "200210300000Z"
      DESCRIPTION
              "Nevio Poljak - eri_DnxRoot MIB Rev 01.1
               Corrected Description for MibProfile.
               Updated Resource Addr and State descriptions and new
               error codes for Connection table. Added a generic trap 
               for reporting system events."
               
      REVISION        "200209190000Z"
      DESCRIPTION
              "Neeraj Bhatt - eri_DnxRoot MIB Rev 01.1
               Added support to Connection Tables for Dnx-1u Transcoder 
               Sub-Channel connections. Added Trunk Profile Conditioning 
               Table and added support to Connections Tables for the Trunk
               Profile selection. Added the trap for Trunk Conditioning
               Profile Configuration."

      REVISION        "200208200000Z"
      DESCRIPTION
              "Nevio Poljak - eri_DnxRoot MIB Rev 01.0
               Changed Alarm severity of Receiving AIS from Major to 
               Informational for T1/E1, HDS3, STS1, E3, and STM1/OC3 T1/E1.
               Added support to Connection Tables for Dnx-1u Transcoder Voice
               Compression connections.  Added Informational Trap for Sa4
               National Bit Match for all E1 devices."

      REVISION        "200207220000Z"
      DESCRIPTION
              "Nevio Poljak - eri_DnxRoot MIB Rev 01.0
               Corrected Source & Dest TsLineType descriptions in the 
               sysConnTable and actvConnTable."

      REVISION        "200207030000Z"
      DESCRIPTION
              "Nevio Poljak - eri_DnxRoot MIB Rev 01.0
               Added Alarms for Dnx-1u Circuit Card missing and Optical
               Transport Overhead SF and SD detection.
               Removed Alarm for Dnx-1u Power Supply Rear card missing."

      REVISION        "200205310000Z"
      DESCRIPTION
              "Nevio Poljak - eri_DnxRoot MIB Rev 01.0
               Converted history comments to MODULE-IDENTITY REVISION format.
               Added Info Events for Dnx-1u Power Supply Fan Status."

      REVISION        "200205130000Z"
      DESCRIPTION
              "Nevio Poljak - eri_DnxRoot MIB Rev 01.0
               Removed all DNX-88/11 objects to the new ERI-DNX-NEST-SYS-MIB 
               so that only shared objects remain."

      REVISION        "200205060000Z"
      DESCRIPTION
              "Nevio Poljak - Software Release 14.2
               Added IMPORT statement for new ERI Root MIB to avoid problems 
               SMIv1 compilers."

      REVISION        "200204220000Z"
      DESCRIPTION
              "Nevio Poljak - Software Release 14.2
               Converted to SMIv2 format and Added Mac Address object to the
               SysProfile branch."

      REVISION        "200204180000Z"
      DESCRIPTION
              "Nevio Poljak - Software Release 14.1
               Added objects under new dbSyncronize branch to support Database
               Synchronization. Also added supported DB Sync Trap."

      REVISION        "200204120000Z"
      DESCRIPTION
              "Nevio Poljak - Software Release 14.1
               Added new commands to xNestCmdStatus for switch-xcc-cards (6) 
               and switch-xlink-cards (7) in xNestCfgTable."

      REVISION        "200203110000Z"
      DESCRIPTION
              "Nevio Poljak - Software Release 14.1
               Added new Release Version number to Device About Table.
               Added new fields to System and Active Connection Tables to 
               report info about the Src and Dest Timeslot Port type.
               Added new resouce and Alarm for optical Xlink.
               Added new object under xNestTable for Dual DNX Power Supply Cfg."

      REVISION        "200111130000Z"
      DESCRIPTION
              "Nevio Poljak - Software Release 14.0
               Added new object under xSlotTable for Raw Device State
               Added new object under xNdrTable for Dual Psx Power Supply Cfg.
               Added new resources and associated Alarms for E3 device and added
               new commands to xNestTable for swiching SMCs, resetting device
               cards and clearing all device errors within a Nest.
               Added Enterprise MIB for DS0DP Device Card Provisioning.
               Added Enterprise MIB for E3 Device Card Provisioning.
               Added New Tables for Auto Backup to Remote Hosts."

      REVISION        "200109100000Z"
      DESCRIPTION
              "Nevio Poljak - Software Release 13.0
               Added Enterprise MIB for Optical Device Card Provisioning.
               Added new object under SysProfile branch to control Contact Alarm
               audio and modified Nest trap to include Nest Name field."

      REVISION        "200108130000Z"
      DESCRIPTION
              "Nevio Poljak - Software Release 12.4
               Added new resources for SMC System Clock, STM1 and OC3 devices.
               Also added all associated Alarms and events for new resources and
               renamed DS0DP bits resource to clockDs0Dp.  Added Unsigned Integer 
               Textual Convention for bit mask fields."

      REVISION        "200107190000Z"
      DESCRIPTION
              "Nevio Poljak - Software Release 12.2
               Added new Listener connection type and fixed typos in Trap codes."

      REVISION        "200107050000Z"
      DESCRIPTION
              "Nevio Poljak - Software Release 12.1
               Added new Traps codes for X-Link Alarms.
               Added Nest number to Resource Addresses and modified the
               Resource State description for new resources."

      REVISION        "200106230000Z"
      DESCRIPTION
              "Nevio Poljak - Software Release 12.0
               Added new Traps for Nest Configuration and Clock Source.
               Connection Test Mode Object was obsoleted from SysConn and
               ActiveConn Tables but Connection Status was added."

      REVISION        "200106010000Z"
      DESCRIPTION
              "Nevio Poljak - Software Release 12.0
               Updated MIB in preparation for Expansion Nest functionality.
               Added eXpansionNestAdmin branch and new Tables to support a
               Multi-Nest DNX environment. Added new table for Device 
               Hardware & Software version info called Device About Table.
               Also added ESF 96 Interval Table to the Performance Monitoring MIB."
  
      REVISION        "200105210000Z"
      DESCRIPTION
              "Nevio Poljak - Software Release 11.1
               Added new Trap Destination Table and added additional statistics
               to the OHS Test MIB."
           
      REVISION        "200103230000Z"
      DESCRIPTION
              "Nevio Poljak - Software Release 11.0
               Changed Power Supply alarm #601 from Major alarm to Info Event.
               Added PSX Info Events to report Line Card Insertion/Removal and
               Removed PSX Mismatch alarm #1009 and replaced with new Dual 
               Broadband Not Supported alarm reported as #1008."

      REVISION        "200103010000Z"
      DESCRIPTION
              "Nevio Poljak - Software Release 11.0
               Added Enterprise MIB for Octal High Speed Provisioning at
               the Port level and added OHS Diagnostics to TEST MIB."
  
      REVISION        "200101020000Z"
      DESCRIPTION
              "Nevio Poljak - Software Release 10.0
               Renamed sysView to sysMgr since not View-only anymore. Added
               Device WarmStart and PsxMismatch to Alarm Trap.  Also, added
               Enterprise MIBs for Performance Monitoring and Diagnostics at
               the DS1/E1 level."

      REVISION        "200012010000Z"
      DESCRIPTION
              "Nevio Poljak - Software Release 10.0
               Updated redundancy branch with 2nd BroadBand Group Info."

      REVISION        "200010260000Z"
      DESCRIPTION
              "Oliver De Grate - Software Release 10.0
               Added a new table for the triggering of program file downloads 
               between the SMC and the device cards."

      REVISION        "200010020000Z"
      DESCRIPTION
              "Nevio Poljak - Software Release 9.3
               Added new Traps for Map Copying, Connection Purging, NDR Status
               and separated Device data to their own MIB modules."

      REVISION        "200007260000Z"
      DESCRIPTION
              "Nevio Poljak - Software Release 9.3
               Converted SMIv1 types to SMIv2 textual Convention types. Updated 
               Command Status Values to have uniform values and gave addConnID 
               read-write access."

      REVISION        "200005310000Z"
      DESCRIPTION
              "Nevio Poljak - Software Release 9.01
               Added alarm states for STS-1 and Hybrid DS3 Ports."

      REVISION        "200005150000Z"
      DESCRIPTION
              "Nevio Poljak - Software Release 9.00
               Renamed to DNX-SMC MIB to support future MIB expansion.
               Renamed Node Summary Table to Slot Config Table since
               certain fields are now available to use in SET commands.
               Added several new System Connection Tables to support SNMP
               circuit connection provisioning.  Added new System Clock table
               to support system clock setup and clock source configuration.
               Added new configuration traps for Slots, Maps, and Connections."

      REVISION        "200002250000Z"
      DESCRIPTION
              "Nevio Poljak - Software Release 8.00
               Modified System Profile Group to include SMC Type and 
               added new Redundancy Group."

      REVISION        "9912150000Z"
      DESCRIPTION
              "Nevio Poljak - Software Release 8.00
               Modified Node Summary Table to include Redundancy stats, 
               added new System Profile Group, updated traps with NDR events."

      REVISION        "9911090000Z"
      DESCRIPTION
              "Nevio Poljak - Software Release 7.07
              Added alarm states for High Speed Port and fixed label names."
              

      REVISION        "9812150000Z"
      DESCRIPTION
              "Initial Release of this MIB. - Bob Chapin"
  	::= { eriMibs 1 }

-- *************************************************************************
-- The following OIDs form the base of the various sections of the MIB
-- *************************************************************************
dnx             OBJECT IDENTIFIER ::= { eriProducts 4 }

sysMgr          OBJECT IDENTIFIER ::= { dnx 1 }
devices         OBJECT IDENTIFIER ::= { dnx 2 }
traps           OBJECT IDENTIFIER ::= { dnx 3 }

-- *************************************************************************
-- The following two textual conventions are used in this MIB
-- *************************************************************************

DnxResourceType ::= TEXTUAL-CONVENTION
        STATUS  current
        DESCRIPTION
                "Unique code used to identify a system resource."
	    SYNTAX INTEGER {
                slot(0),
                deviceOctalE1T1(1),
                deviceQuadHighSpeed(2),
                deviceOctalHighSpeed(3),
                deviceQuadOcu(4),
                deviceSystemManager(5),
                deviceQuadT1(6),
                deviceT3(7),
                deviceTestAccess(8),
                deviceVoice(9),
                deviceVoiceEM(10),
                deviceVoiceFXO(11),
                deviceVoiceFXS(12),
                powerSupply(14),
                protectionSwitch(15),
                deviceRouterCard(16),
                deviceSts1(17),
                deviceHybridDS3(18),
                deviceGr303(19),
                deviceXCC(20),
                deviceXLC(21),
                deviceNodeManager(22),
                nest(23),
                node(24),
                deviceDs0DP(25),
                deviceSTM1(26),
                deviceOC3(27),
                deviceE3(28),
                deviceXLC-T1E1(29),
                deviceSTM1X(30),
                deviceOC3X(31),
                deviceContact(32),
                deviceVoltage(33),
                deviceAsync(34),
                deviceSync(35),
                deviceWan(36),
                dnx1UQuadT1E1(37),
                deviceTempSensor(38),
                dnx1UPowerSupply(39),
                dnx1USysMgr(40),
                deviceTranscoder(41),
                portOctal-T1E1(100),
                portQuadHighSpeed(101),
                portOctalHighSpeed(102),
                portQuadOcu(103),
                portQuadT1(104),
                portOctalT1(105),
                linkT3-T1(106),
                portT3(107),
                portTestAccess(108),
                portVoiceEM(109),
                portVoiceFXO(110),
                portVoiceFXS(111),
                psxNarrowband (112),
                psxBroadband(113),
                psxNarrowbandSpare(114),
                psxBroadbandSpare(115),
                portRouter(116),
                linkSts1-T1E1(117),
                portSts1(118),
                linkHds3-T1E1(119),
                portHybridDS3(120),
                portGr303(121),
                linkXlink(124),
                portDs0DP(125),
                clockDs0DP(126),
                sysMgrClock(127),
                linkSTM1-T1E1(128),
                linkOC3-T1E1(130),
                payloadSTM1(131),
                overheadSTM1(132),
                payloadOC3(133),
                overheadOC3(134),                
                portE3(135),
                linkE3-E1(136),
                opticalXlink(137),
                portContact(138),
                portVoltage(139),
                portAsync(140),
                linkT1E1(141),
                portHighSpeed(142),
                portVirtualWan(143),
                portTranscoder(144)
                }

AlarmSeverity  ::= TEXTUAL-CONVENTION
		STATUS  current
        DESCRIPTION
                "Determines the Trap Alarm level."
	    SYNTAX INTEGER {
                nominal(0),
                informational(1),
                minor(2),
                major(3),
                critical(4)
                }

DecisionType ::= TEXTUAL-CONVENTION
		STATUS  current
        DESCRIPTION
                "Determines if a setting is on/off."
	    SYNTAX INTEGER {
			no (0),
			yes (1)
			}
				
FunctionSwitch ::= TEXTUAL-CONVENTION
		STATUS  current
        DESCRIPTION
                "Determines if a functionality is on/off."
	    SYNTAX INTEGER {
			disable (0),
			enable (1)
			}
				
CurrentDevStatus ::= TEXTUAL-CONVENTION
		STATUS  current
        DESCRIPTION
                "Determines if a device is on/off."
	    SYNTAX INTEGER {
			inactive (0),
			active (1)
			}

PortStatus ::= TEXTUAL-CONVENTION
		STATUS  current
        DESCRIPTION
                "Determines if a port/link is active or not."
	    SYNTAX INTEGER {
			out-service (0),
			in-service (1)
			}
												
DataSwitch ::= TEXTUAL-CONVENTION
		STATUS  current
        DESCRIPTION
                "Determines if a setting is on/off."
	    SYNTAX INTEGER {
			off (0),
			on (1)
			}
							
TimeSlotAddress	::= TEXTUAL-CONVENTION
		STATUS  current
        DESCRIPTION
                "Used for slot, port, & starting timeslot numbers."
	    SYNTAX IpAddress

LinkPortAddress	::= TEXTUAL-CONVENTION
		STATUS  current
        DESCRIPTION
                "Used for nest, slot, & port/channel numbers."
	    SYNTAX IpAddress

ClockSrcAddress	::= TEXTUAL-CONVENTION
		STATUS  current
        DESCRIPTION
                "Used for slot, port, & station clock configuration."
	    SYNTAX IpAddress

NestSlotAddress	::= TEXTUAL-CONVENTION
		STATUS  current
        DESCRIPTION
                "Used for nest & slot numbers."
	    SYNTAX IpAddress

UnsignedInt	::= TEXTUAL-CONVENTION
		STATUS  current
        DESCRIPTION
                "Used for defining numbers used as bit masks."
	    SYNTAX Unsigned32

ConnectionType ::= TEXTUAL-CONVENTION
		STATUS  current
        DESCRIPTION
                "Determines the type of circuit connection. 
                The fullDuplex and broadcastConnection require both a 
                source and destination port.  The broadcastMaster needs
                only a source port and the listeners need only a dest port."
	    SYNTAX INTEGER {
			fullDuplex(0),
			broadcastConnection(1),
			broadcastMaster(2),
			listenSrc(3),
			listenDest(4),
			listenerConnection(7),  -- Write only field used to add listenSrc or listenDest
			vcmp(8),
			subChannel(9),
			subRate(10)
			}

CommunicationsType ::= TEXTUAL-CONVENTION
		STATUS  current
        DESCRIPTION
                "Determines the type of circuit communication format."
	    SYNTAX INTEGER {
			data(0),
			voice(1),
			voiceAuToMu(2),
			comp16kBitGrp1-2(3),
			comp16kBitGrp3-4(4),
			comp16kBitGrp5-6(5),
			comp16kBitGrp7-8(6),
			comp32kBitGrp1-4(7), 
			comp32kBitGrp5-8(8)
			}

ConnectionState1 ::= TEXTUAL-CONVENTION
		STATUS  current
        DESCRIPTION
                "Determines the primary state level of circuit connection."
	    SYNTAX INTEGER {
			inSrvc(0),
			outOfSrvc(1)			
			}

ConnectionState2 ::= TEXTUAL-CONVENTION
		STATUS  current
        DESCRIPTION
                "Determines the secondary state level of circuit connection."
	    SYNTAX INTEGER {
			ok(1),
			underTest(2),
			cfgError(3)			
			}

MapNumber ::= TEXTUAL-CONVENTION
		STATUS  current
        DESCRIPTION
                "Identifies the system connection maps."
	    SYNTAX INTEGER {
        	activeMap 	(0),
	    	map01		(1),
       		map02		(2),
       		map03		(3),
       		map04		(4),
       		map05		(5)
            }

TestAccess ::= TEXTUAL-CONVENTION
		STATUS  current
        DESCRIPTION
                "Determines the type of test connection is on 
                the circuit."
	    SYNTAX INTEGER {
            none (0),
            monitorSrc(1),
            monitorDest(2),
            monitorSrcNDest(3),
            splitSrc(4),
            splitDest(5),
            splitSrcNDest(6)
            }
            
ConnectionSpeed ::= TEXTUAL-CONVENTION
		STATUS  current
        DESCRIPTION
                "Determines the bandwidth on a circuit connection."
	    SYNTAX INTEGER {
-- format is:   Speed in Kilobytes__Number of DS0s x Kbps per channel
			s48k (0),
			s56k (1),
			s64k (2),
			s112k-2x56 (3),
			s128k-2x64 (4),
			s168k-3x56 (5),
      		s192k-3x64 (6),
      		s224k-4x56 (7),
      		s256k-4x64 (8),
      		s280k-5x56 (9),
      		s320k-5x64 (10),
      		s336k-6x56 (11),
      		s384k-6x64 (12),
			s392k-7x56 (13),
      		s448k-7x64 (14),
      		s448k-8x56 (15),
      		s512k-8x64 (16),
      		s504k-9x56 (17),
      		s576k-9x64 (18),
			s560k-10x56 (19),
      		s640k-10x64 (20),
      		s616k-11x56 (21),
      		s704k-11x64 (22),
      		s672k-12x56 (23),
      		s768k-12x64 (24),
			s728k-13x56 (25),
      		s832k-13x64 (26),
      		s784k-14x56 (27),
      		s896k-14x64 (28),
      		s840k-15x56 (29),
      		s960k-15x64 (30),
      		s896k-16x56 (31),
      		s1024k-16x64 (32),
      		s952k-17x56 (33),
      		s1088k-17x64 (34),
        	s1008k-18x56 (35),
        	s1152k-18x64 (36),
        	s1064k-19x56 (37),
        	s1216k-19x64 (38),
        	s1120k-20x56 (39),
        	s1280k-20x64 (40),	
	        s1176k-21x56 (41),
        	s1344k-21x64 (42),	
        	s1232k-22x56 (43),
        	s1408k-22x64 (44),	
            s1288k-23x56 (45),
        	s1472k-23x64 (46),	
            s1344k-24x56 (47),
        	s1536k-24x64 (48),	
            s1400k-25x56 (49),
        	s1600k-25x64 (50),	
            s1456k-26x56 (51),
        	s1664k-26x64 (52),	
            s1512k-27x56 (53),
        	s1728k-27x64 (54),	
            s1568k-28x56 (55),
            s1792k-28x64 (56),	
            s1624k-29x56 (57),
        	s1856k-29x64 (58),	
			s1680k-30x56 (59),
			s1920k-30x64 (60),
			s1736k-31x56 (61),
			s1984k-31x64 (62),
			s1792k-32x56 (63),
			s2048k-32x64 (64),
			clearT1-25x64 (65),    -- used for framed or unframed modes
			clearE1-32x64 (66),    -- used for framed or unframed modes 
			s32k (67),             -- used for Transcoder & subRate
			s16k (68),			   -- used for Transcoder	
			s9600-baud(96),        -- used for OHS DS0-A Port Mode
			no-connection (99)     -- used for OHS Port Default Speed
			}
				
ConnCmdStatus ::= TEXTUAL-CONVENTION
		STATUS  current
        DESCRIPTION
                "Determines the command action or response status for 
                a connection record/row."
	    SYNTAX INTEGER {
    -- Initial default status for a row
            ready-for-command (0),
    -- Action States used in SET Command (1..99)
            update (1),
       	    delete (2),
            add (3),
            addNsave (4),
            updateNsave (5),
            deleteNsave (6),
                		
    -- Response States used in GET RESPONSE Command (100..199)
            update-successful (101),
            delete-successful (102),
            add-successful (103),
            add-save-successful (104),
            update-save-successful (105),
            del-save-successful (106),
                		
    -- Connection Error Codes used in GET RESPONSE Command (200..799)
            err-general-connection-error (400),
            err-src-broadcast-id-not-found (401),
            err-src-port-in-use (402),
            err-dest-port-in-use (403),
            err-conn-name-in-use (404),
            err-invalid-broadcast-id (405),
            err-invalid-src-slot (406),
            err-invalid-src-port (407),
            err-invalid-src-timeslot (408),
            err-src-port-bandwidth-exceeded (409),
            err-invalid-dest-slot (410),
            err-invalid-dest-port (411),
            err-invalid-dest-timeslot (412),
            err-dest-port-bandwidth-exceeded (413),
            err-invalid-command (414),
            err-not-enough-bts-available(415),
            err-src-port-cannot-be-voice(416),
            err-dest-port-cannot-be-voice(417),
            err-invalid-communications-dev(418),
            err-invalid-communications-type(419),
            err-invalid-conn-name(420),
            err-invalid-conn-type(421),
            err-invalid-conn-speed(422),
            err-invalid-conn-record(423),
            err-conn-test-in-progress(424),
            err-invalid-conn-id(425),            
            err-conn-not-saved-to-map(426),
            err-connection-map-full (427),             
            err-invalid-card-type (428),
			err-invalid-conn-bit-group (429),
			err-conn-max-channels-used (430),
			err-src-xlink-slot-not-assigned(431),
			err-dest-xlink-slot-not-assigned(432), 
			err-protection-grp-conn-error (433),
            err-cannot-chg-net-conn (434),
            err-data-locked-by-another-user(450),
            err-snmp-parse-failed (500),
            err-invalid-snmp-type (501),
            err-invalid-snmp-var-size (502)
			}

LinkCmdStatus ::= TEXTUAL-CONVENTION
		STATUS  current
        DESCRIPTION
                "Determines the command action or response status for 
                a link(port) record/row."
	    SYNTAX INTEGER {
    -- Initial default status for a row
            ready-for-command (0),
    -- Link Commands used in SET Command (1..199)
            update (1),
            inServiceAll (7),
            copyToAll (9),
            outOfServiceAll (12),
                		
    -- Link Response States used in GET RESPONSE Command (100..199)
            update-successful (101),
            insvc-successful (107),
            copy-successful (109),
            oos-successful (112),
                		
    -- Link Config Error Codes used in GET RESPONSE Command (200..799)
            err-general-link-config-error (400),
            err-invalid-link-status (401),
            err-invalid-link-framing (402),
            err-invalid-link-command (403),
            err-invalid-link-lbo (404),
            err-invalid-esf-format (405),
            err-invalid-link-density (406),
            err-invalid-link-op-mode (407),
            err-invalid-link-rem-loop (408),
            err-invalid-link-ais (409),
            err-invalid-network-loop (410),
            err-invalid-yellow-alarm (411),
            err-invalid-red-timeout (412),
            err-invalid-idle-code (413),
            err-device-in-standby (414),
            err-invalid-link-mapping (415),
            err-invalid-link-vt-group (416),
            err-invalid-rcv-clocksrc (417),
            err-invalid-link-name (418),
            err-invalid-interface (419),
            err-invalid-polarity (420),
            err-invalid-clock-timing (421),
            err-invalid-control-signal (422),
            err-dcd-dsr-not-applicable (423),
            err-requires-special-mode (424),
            err-cts-not-applicable (425),
            err-gr303-not-applicable (426),
            err-invalid-link-bits (427),
            err-device-is-protection-module (428),
            err-data-locked-by-another-user (450),
            err-snmp-parse-failed (500),
            err-invalid-snmp-type (501),
            err-invalid-snmp-var-size (502)
        	}

OneByteField ::= TEXTUAL-CONVENTION
		STATUS  current
        DESCRIPTION
                "Used for single byte bit manipulation fields."
	    SYNTAX OCTET STRING (SIZE(1))

DnxTsPortType ::= TEXTUAL-CONVENTION
		STATUS  current
        DESCRIPTION
                "Displays the Port Timeslot Type used when building 
                DNX Cross-Connections."
	    SYNTAX INTEGER {
	        unknown(0),
			e1(1),
			t1(2),
			high-speed(3),
			wan(4),			
			e1-cas(5),
			e1-clear-frm(6),
			t1-clear-frm(7),
			e1-clear-unfrm(8),
			t1-clear-unfrm(9),
			voice(10),
			ds0dp(11),
			ocu(12),
			tam(13)
			}

DnxTrunkProfSelection ::= TEXTUAL-CONVENTION
		STATUS  current
        DESCRIPTION
                "Displays the Trunk Conditioning Profile used to add 
                or display a connection."
	    SYNTAX INTEGER {
            none(0),
            profile-1(1),
            profile-2(2),
            profile-3(3),
            profile-4(4),
            profile-5(5),
            profile-6(6),
            profile-7(7),
            profile-8(8),
            profile-9(9),
            profile-10(10),
            profile-11(11),
            profile-12(12),
            profile-13(13),
            profile-14(14),
            profile-15(15),
            profile-16(16)
			}
			
-- *************************************************************************
-- Complete Resource Table
-- *************************************************************************
-- This table contains information about all the resources in the system

resourceTable OBJECT-TYPE
        SYNTAX SEQUENCE OF ResourceEntry
        MAX-ACCESS not-accessible
        STATUS current
        DESCRIPTION
                "This table contain the resource information of the
                 complete system. This table is the most complete single
                 view of the system."
        ::= { sysMgr 1 }

resourceEntry OBJECT-TYPE
        SYNTAX ResourceEntry
        MAX-ACCESS not-accessible
        STATUS  current
        DESCRIPTION
                "The information about a resource."
        INDEX { resourceKey }
        ::= { resourceTable 1 }

ResourceEntry ::=
        SEQUENCE {
                resourceKey             UnsignedInt,
                resourceAddr            DisplayString,
                resourceType            DnxResourceType,
                resourceState           UnsignedInt,
                resourceCriticalMask    UnsignedInt,
                resourceMajorMask       UnsignedInt,
                resourceMinorMask       UnsignedInt,
                resourceInfoMask        UnsignedInt,
                resourceNominalMask     UnsignedInt,
                resourceTrapMask        UnsignedInt
                }

resourceKey OBJECT-TYPE
        SYNTAX UnsignedInt
        MAX-ACCESS read-only
        STATUS current
        DESCRIPTION
                "This number uniquely identifies a system resource. This
                 number will be used throughout the system to identify a
                 resource."
        ::= { resourceEntry 1 }

resourceAddr OBJECT-TYPE
        SYNTAX DisplayString
        MAX-ACCESS read-only
        STATUS current
        DESCRIPTION
                "This is an ascii text version of the resource key. The
                 strings have the general form of <letter>x.x.x... 
                 where the string x.x.x... is a string of some number of
                 numbers. The following letters are used.
                        S - slot
                        D - device
                        P - port
                        C - channel(i.e. link)
                        CLK - clock
                        O - overhead transport (STM1/OC3)

                 Some examples should make this clear.
                        S1.4      is nest one, slot four
                        D2.4      is the device that is in nest two, slot four
                        P1.4.1    is the first port on the device that is
                                  in slot four, nest one
                        C3.5.1.10 is the tenth channel on port one of the
                                  device that is in slot five, nest three

                 There are  a few forms that are not standard and they
                 are listed here:
                        S1.SMCA   is the slot for the SMC A device, nest one
                        S1.SMCB   is the slot for the SMC B device, nest one
                        S1.PSX    is the slot for the Protection Switch Box, 
                                  nest one
                        D1.SMCA   is the SMC A device, nest one
                        D1.SMCB   is the SMC B device, nest one
                        CLK1.SMCA is the SMC A clock, nest one
                        CLK1.SMCB is the SMC B clock, nest one
                        D1.PSA    is the A power supply, nest one
                        D1.PSB    is the B power supply, nest one
                        O1.2.1    is the Overhead Transport in slot 2, nest one"
        ::= { resourceEntry 2 }

resourceType OBJECT-TYPE
        SYNTAX DnxResourceType
        MAX-ACCESS read-only
        STATUS current
        DESCRIPTION
                "This determines what kind of resource this is."
        ::= { resourceEntry 3 }

resourceState OBJECT-TYPE
        SYNTAX UnsignedInt
        MAX-ACCESS read-only
        STATUS current
        DESCRIPTION
                "Gives the state of the object. This is a bitmap whose
                exact meaning depends on the resource type. Bit zero 
                refers to the rightmost bit.
              
                The following bits are RESERVED for ALL types. 

                    bit 0  No Alarm
                        
                    bit 25 Config Error
                    bit 26 Can't be Clock Source
                    bit 27 Error Counter Non Zero
                    bit 28 Rear card not present
                    bit 29 Clock source
                    bit 30 In test
                    bit 31 Out of service

                NOTE: This does not mean that these bits could be set 
                by all types only that the individual types will not 
                define another bit in the same place.

                 Type slot

                    bit 0 No Alarm              (common)
                    bit 1 Device mismatched     (physical vs. confg.)
                    bit 2 Device missing        (confg but not present)
                    bit 3 Device not present	(absense of data)
                    
             Type deviceOctalE1T1, deviceQuadHighSpeed,
                  deviceOctalHighSpeed, deviceQuadOcu,
                  deviceSystemManager, deviceQuadT1, deviceT3,
                  deviceTestAccess, deviceVoice, deviceVoiceEM,
                  deviceVoiceFXO, deviceVoiceFXS, deviceSts1,
                  deviceRouterCard, deviceHybridT3, deviceDs0DP,
                  deviceGr303, deviceXCC, deviceXLC, deviceE3,
                  deviceNodeManager, deviceSTM1, deviceOC3, 
                  deviceXLC-T1E1, deviceSTM1X, deviceOC3X

                    bit 0 No Alarm                  (common)
                    bit 1 Online                   
                    bit 2 Standby                  
                    bit 3 Frame sync not present
                    bit 4 System clock not present

                    bit 6  Database not in sync     (SMC only)
                    bit 7  Clock free run error     (SMC only)
                    bit 8  Offline
                    bit 9  Defective
                    bit 10 Bus error
             
                    bit 25 Config error             (common)
                    bit 26 Can't be Clock Source    (common)
                    bit 27 Error Counter Non Zero   (common)
                    bit 28 Rear card not present    (common)
                    bit 29 Clock source             (common)
                    bit 30 In test                  (common)
                    bit 31 Out of service           (common)

                Type powerSupply

                    bit 0 No Alarm                  (common)
                    bit 1 Not present
                    bit 2 Not ok
                    
                    bit 25 through 31 Reserved as Common

                Type portOctal-T1E1, portOctalT1, portQuadT1, 
                     linkT3-T1,linkSts1-T1E1,linkHt3-T1E1,
                     linkE3-E1

                    bit 0 No Alarm                  (common)
                    bit 1 Rcv far end LOF (yellow alarm)
                    bit 2 Near end sending LOF
                    bit 3 Far end sending AIS
                    bit 4 Near end sending AIS
                    bit 5 Near end LOF (red alarm)
                    bit 6 Near end loss of signal
                    bit 7 Near end is looped
                    bit 8 E1 TS16 AIS
                    bit 9 Far end sending TS16 LOMF
                    bit 10 Near end sending TS16 LOMF
                    bit 11 Near end detects a test code
                    bit 12 Other line status
                    bit 13 Near end unavailable signal
                    bit 14 Carrier equipment out of service

    				bit 21 Near end tx slip
                    bit 22 Near end rx slip
                    bit 23 Near end severe errored frame
                    bit 24 Change in frame aligmment

                    bit 25 through 31 Reserved as Common

                Type portT3

                    bit 0 No Alarm                  (common)
                    bit 1 Rcv far end LOF (yellow alarm)
                    bit 2 Near end sending LOF
                    bit 3 Far end sending AIS
                    bit 4 Near end sending AIS
                    bit 5 Near end LOF (red alarm)
                    bit 6 Near end loss of signal
                          LIU digital loss of signal
                          LIU analog loss of signal
                    bit 7 Near end is looped

                    bit 11 Near end detects a test code
                    bit 12 Other line status
                    bit 13 Near end unavailable signal
                    bit 14 Carrier equipment out of service
                    bit 15 Near end sever errored frame
                    bit 16 Rx/Tx clock failure
                    bit 17 Tx far end block error
                    bit 18 Tx pbit/cbit parity error
                    bit 19 Fbits and mbits in error
                    bit 20 LIU other status

                    bit 22 LIU excess zeros
                    bit 23 LIU coding violation
                    bit 24 LIU prbs error
 
                    bit 25 through 31 Reserved as Common

                Type portQuadHighSpeed, portOctalHighSpeed

                    bit 0 No Alarm                  (common)
                    bit 1 Detected FIFO error on receive
                    bit 2 Detected FIFO error on transmit
                    bit 3 High Speed Clock Edge error
                    bit 4 Carrier Dropped on link failure
                    
                    bit 7 Near End In loop

                    bit 11 Near end detects a test code
                    bit 12 High Speed Carrier detected

                    bit 24 No Backplane Timeslot assigned

                    bit 25 through 31 Reserved as Common

                Type portQuadOcu

                    bit 0 No Alarm                 (common)

                    bit 6 Near end loss of signal
                    bit 7 Near end looped

                    bit 11 Near end detects test code
                    bit 12 Other line status

                    bit 23 Near end severe errored frame
                    
                    bit 25 through 31 Reserved as Common

                Type portTestAccess

                    bit 0 No Alarm                 (common)

                    bit 7 Near end looped

                    bit 11 Near end detects test code

                    bit 25 through 31 Reserved as Common

                Type portVoiceEm, portVoiceFXO, portVoiceFXS

                    bit 0 No Alarm                 (common)

                    bit 7 Near end looped

                    bit 11 Near end detects test code
                    
                    bit 25 through 31 Reserved as Common

                Type protectionSwitch

                    bit 0 No Alarm                 (common)
                    bit 1 Online                   (common)

                    bit 3 PSX Power Supply (A) bad
                    bit 4 PSX Power Supply (B) bad
                    bit 5 PSX Fan-1 bad
                    bit 6 PSX Fan-2 bad
                    bit 7 PSX Fan-3 bad
                    bit 8 PSX Dual Broadband Not Supported                        
                    bit 9 PSX New Controller
                                            
                    bit 12 PSX New Chassis                        
                        
                    bit 14 PSX Line Card 1 Not Present
                    bit 15 PSX Line Card 2 Not Present
                    bit 16 PSX Line Card 3 Not Present
                    bit 17 PSX Line Card 4 Not Present
                    bit 18 PSX Line Card 5 Not Present
                    bit 19 PSX Line Card 6 Not Present
                    bit 20 PSX Line Card 7 Not Present
                    bit 21 PSX Line Card 8 Not Present
                    bit 22 PSX Line Card 9 Not Present
                    bit 23 PSX Line Card 10 Not Present
                    bit 24 PSX Line Card 11 Not Present

                    bit 25 through 31 Reserved as Common

                Type psxNarrowband, psxNarrowbandSpare, 
                     psxBroadband,  psxBroadbandSpare
                    
                    bit 0 No Alarm                  (common)
                      
                    bit 2 PSX Line Card Relay Switch to Spare
                    bit 3 PSX Line Card Cable Missing
                    bit 4 PSX Line Card Cable Not Present
                    bit 5 PSX Line Card Not Present (not configured, not there)
                    bit 6 PSX Line Card Missing     (standby confg but not there)
                    bit 7 PSX Line Card Mismatch    (oper vs. standby)
                    bit 8 PSX Line Card Relay Malfunction

                    bit 25 through 31 Reserved as Common

                Type portRouter

                    bit 0 No Alarm                  (common)
                    bit 1 User Contact Alarm 1 On
                    bit 2 User Contact Alarm 2 On
                    bit 3 User Contact Alarm 3 On
                                            
                    bit 25 through 31 Reserved as Common

                Type portSts1

                    bit 0 No Alarm                  (common)
                    bit 1 Rcv far end LOF (yellow alarm)
                    bit 2 Near end sending LOF
                    bit 3 Far end sending AIS
                    bit 4 Near end sending AIS
                    bit 5 Near end LOF (red alarm)

                    bit 7 Near end is looped
                    bit 8 Near end loss of pointer
                    bit 9 Near end out of frame
                    bit 10 Near end AIS                    
                    bit 11 Near end detects a test code
                    bit 12 Other line status
                    bit 13 Near end unavailable signal
                    bit 14 Carrier equipment out of service
                    bit 15 Near end sever errored frame
                    bit 16 Rx/Tx clock failure
                    bit 17 Near end loss of multi-frame
                    bit 18 Near end Trace error

                    bit 20 LIU digital loss of signal
                    bit 21 LIU analog loss of signal
                    bit 22 LIU excess zeros
                    bit 23 LIU coding violation
                    bit 24 LIU prbs error

                    bit 25 through 31 Reserved as Common

                Type portHybridT3

                    bit 0 No Alarm                  (common)

                    bit 3 Far end sending AIS
                    bit 4 Near end sending AIS
                    bit 5 Near end out of frame
                    bit 6 Near end loss of signal
                    bit 7 Near end is looped
                    bit 8 Near end LOF (red alarm)
                    bit 9 Far end receive failure

                    bit 11 Near end line code violation
                    bit 12 Near end framing bit error
                    bit 13 Near end excess zeros

                    bit 17 Tx far end block error
                    bit 18 Tx pbit/cbit parity error

                    bit 20 LIU digital loss of signal
                    bit 21 LIU analog loss of signal
                    bit 22 LIU excess zeros
                    bit 23 LIU coding violation
                    bit 24 LIU prbs error

                    bit 25 through 31 Reserved as Common

                Type linkXlink, opticalXlink

                    bit 0 No Alarm                  (common)

                    bit 6  Cable Mismatch Error
                    
                    bit 11 Nest ID bit 0
                    bit 12 Nest ID bit 1
                    bit 13 Nest ID bit 2
                    bit 14 Nest ID bit 3
                    bit 15 Serializer Error
                    bit 16 Framer Error
                    bit 17 Bert Error
                    bit 18 Clock Error
                    
                    bit 20 In Use Error (nest communicating to both xlink ports)
                    bit 21 Crc Error
                                            
                    bit 25 through 31 Reserved as Common

                Type nest

                    bit 0 No Alarm                  (common)
                    bit 1 Nest Mismatch
                    bit 2 Nest Missing
                    bit 3 Nest Not Present
                    bit 4 Nest Online
                    bit 5 Nest Offline
                    bit 6 Nest Critical Alarm
                    bit 7 Nest Major Alarm
                    bit 8 Nest Minor Alarm
                                            
                    bit 25 through 31 Reserved as Common

                Type node

                    bit 0 No Alarm                  (common)
                    bit 1 Node Critical Alarm
                    bit 2 Node Major Alarm
                    bit 3 Node Minor Alarm
                                            
                    bit 25 through 31 Reserved as Common

                Type portDs0DP

                    bit 0 No Alarm                  (common)
                    bit 1 Loss Of Signal
                    bit 2 BiPolar Violation
                    bit 3 Near End is Looped
                    bit 4 Near End Loop Detected
                    bit 5 Bert Error Detected
                    
                    bit 12 through 19 Reserved for internal use
                                            
                    bit 25 through 31 Reserved as Common

                Type clockDs0DP

                    bit 0 No Alarm                  (common)
                    bit 1 Composite Clock Loss Of Signal
                    bit 2 Composite Clock BiPolar Violation
                    bit 3 Composite Clock Offset Changed
                    bit 4 through 19 Reserved for internal use
                                            
                    bit 25 through 31 Reserved as Common

                Type sysMgrClock

                    bit 0 No Alarm                  (common)
                    bit 1 Stratum 3 Clock Defective
                                            
                    bit 25 through 31 Reserved as Common

                Type linkSTM1-T1E1,linkOC3-T1E1

                    bit 0 No Alarm                  (common)
                    bit 1 Red Alarm
                    bit 2 Near end sending LOF
                    bit 3 Far end sending AIS
                    bit 4 Near end sending AIS
                    bit 5 Near end LOF (red alarm)

                    bit 7 Near end is looped
                    bit 8 Near end loss of pointer
                    bit 9 Near end out of frame
                    bit 10 Near end detects AIS
                    bit 11 Near end detects a test code

                    bit 13 Near end loss of signal
                    bit 17 Far end receiving yellow alarm
                    bit 18 Near end severe errored frame
                    bit 19 Tributary Unit TUG2 loss of pointer
                    bit 20 Tributary Unit TUG2 remote defect indication
    				bit 21 Tributary Unit TUG2 remote failure indication
                    bit 22 Tributary Unit TUG2 alarm indication signal
                    bit 23 Tributary Unit TUG2 path signal label mismatch
                    bit 24 Tributary Unit TUG2 path signal label unstable

                    bit 25 through 31 Reserved as Common

                Type payloadSTM1, payloadOC3

                    bit 0 No Alarm                  (common)
                    bit 1 Virtual Tributary near end loss of pointer
                    bit 2 Virtual Tributary near end AIS
                    bit 3 Payload loss of pointer
                    bit 4 Payload alarm indication signal
                    bit 5 Payload remote defect indication

                    bit 7 Payload in near end line loop
                    bit 8 Payload in near end local loop

                    bit 25 through 31 Reserved as Common

                Type overheadSTM1, overheadOC3

                    bit 0 No Alarm                  (common)
                    bit 1 Transport Overhead alarm indication signal
                    bit 2 Transport Overhead remote defect indication
                    bit 3 Transport Overhead out of frame
                    bit 4 Transport Overhead loss of frame
                    bit 5 Transport Overhead loss of signal

                    bit 7 Transport Overhead near end system level line loop
                    bit 8 Transport Overhead near end path level line loop
                    bit 9 Transport Overhead near end local loop

                    bit 25 through 31 Reserved as Common

                Type portE3

                    bit 0 No Alarm                  (common)
                    bit 1 Rcv far end LOF (yellow alarm)
                    bit 2 Near end sending LOF
                    bit 3 Receiving AIS
                    bit 4 Near end sending AIS
                    bit 5 Near end LOF (red alarm)
                    bit 6 Near end loss of signal
                    bit 7 Near end is looped 
                    
                    bit 9 Far end receive failure
                    
                    bit 11 Near end detected test code
                    bit 12 Other line status
                    bit 13 Near end unavailable signal
                    bit 14 Carrier equipment out of service
                    bit 15 Near end sever errored frame
                    bit 16 Rx/Tx clock failure
                    bit 17 Tx far end block error

                    bit 22 LIU Drive Monitor error
                    bit 23 LIU coding violation
                    bit 24 LIU FIFO error

                    bit 25 through 31 Reserved as Common

                Finished."
        ::= { resourceEntry 4 }

resourceCriticalMask OBJECT-TYPE
        SYNTAX UnsignedInt
        MAX-ACCESS read-only
        STATUS current
        DESCRIPTION
                "This is the mask that identifies which bits in the state
                 are critical alarms"
        ::= { resourceEntry 5 }

resourceMajorMask OBJECT-TYPE
        SYNTAX UnsignedInt
        MAX-ACCESS read-only
        STATUS current
        DESCRIPTION
                "This is the mask that identifies which bits in the state
                 are major alarms"
        ::= { resourceEntry 6 }

resourceMinorMask OBJECT-TYPE
        SYNTAX UnsignedInt
        MAX-ACCESS read-only
        STATUS current
        DESCRIPTION
                "This is the mask that identifies which bits in the state
                 are minor alarms"
        ::= { resourceEntry 7 }

resourceInfoMask OBJECT-TYPE
        SYNTAX UnsignedInt
        MAX-ACCESS read-only
        STATUS current
        DESCRIPTION
                "This is the mask that identifies which bits in the state
                 are informational alarms"
        ::= { resourceEntry 8 }

resourceNominalMask OBJECT-TYPE
        SYNTAX UnsignedInt
        MAX-ACCESS read-only
        STATUS current
        DESCRIPTION
                "This is the mask that identifies which bits in the state
                 are nominal alarms"
        ::= { resourceEntry 9 }

resourceTrapMask OBJECT-TYPE
        SYNTAX UnsignedInt
        MAX-ACCESS read-only
        STATUS current
        DESCRIPTION
                "This is the mask that identifies which bits in the state
                 are used to generate traps."
        ::= { resourceEntry 10 }

-- *************************************************************************
-- Alarm Resource Table
-- *************************************************************************
-- This table contains information about the resources in the system that
-- are in an alarm condition

resourceAlarmTable OBJECT-TYPE
        SYNTAX SEQUENCE OF ResourceAlarmEntry
        MAX-ACCESS not-accessible
        STATUS current
        DESCRIPTION
                "This table contain the resource information of the
                 resourses that are in alarm."
        ::= { sysMgr 2 }

resourceAlarmEntry OBJECT-TYPE
        SYNTAX ResourceAlarmEntry
        MAX-ACCESS not-accessible
        STATUS  current
        DESCRIPTION
                "The information about a resource that is in alarm."
        INDEX { resourceAlarmKey }
        ::= { resourceAlarmTable 1 }

ResourceAlarmEntry ::=
        SEQUENCE {
                resourceAlarmKey             UnsignedInt,
                resourceAlarmAddr            DisplayString,
                resourceAlarmType            DnxResourceType,
                resourceAlarmState           UnsignedInt,
                resourceAlarmCriticalMask    UnsignedInt,
                resourceAlarmMajorMask       UnsignedInt,
                resourceAlarmMinorMask       UnsignedInt,
                resourceAlarmInfoMask        UnsignedInt,
                resourceAlarmNominalMask     UnsignedInt,
                resourceAlarmTrapMask        UnsignedInt
                }

resourceAlarmKey OBJECT-TYPE
        SYNTAX UnsignedInt
        MAX-ACCESS read-only
        STATUS current
        DESCRIPTION
                "This number uniquely identifies a system resource. This
                 number will be used throughout the system to identify a
                 resource. This number is the same as resourceKey"
        ::= { resourceAlarmEntry 1 }

resourceAlarmAddr OBJECT-TYPE
        SYNTAX DisplayString
        MAX-ACCESS read-only
        STATUS current
        DESCRIPTION
                "This is an ascii text version of the resource key."
        ::= { resourceAlarmEntry 2 }

resourceAlarmType OBJECT-TYPE
        SYNTAX DnxResourceType
        MAX-ACCESS read-only
        STATUS current
        DESCRIPTION
                "This determines what kind of resource this is."
        ::= { resourceAlarmEntry 3 }

resourceAlarmState OBJECT-TYPE
        SYNTAX UnsignedInt
        MAX-ACCESS read-only
        STATUS current
        DESCRIPTION
                "Gives the state of the object. This is a bitmap whose
                 exact meaning depends on the resource type. See description
                 for Resource State above."
        ::= { resourceAlarmEntry 4 }

resourceAlarmCriticalMask OBJECT-TYPE
        SYNTAX UnsignedInt
        MAX-ACCESS read-only
        STATUS current
        DESCRIPTION
                "This is the mask that identifies which bits in the state
                 are critical alarms"
        ::= { resourceAlarmEntry 5 }

resourceAlarmMajorMask OBJECT-TYPE
        SYNTAX UnsignedInt
        MAX-ACCESS read-only
        STATUS current
        DESCRIPTION
                "This is the mask that identifies which bits in the state
                 are major alarms"
        ::= { resourceAlarmEntry 6 }

resourceAlarmMinorMask OBJECT-TYPE
        SYNTAX UnsignedInt
        MAX-ACCESS read-only
        STATUS current
        DESCRIPTION
                "This is the mask that identifies which bits in the state
                 are minor alarms"
        ::= { resourceAlarmEntry 7 }

resourceAlarmInfoMask OBJECT-TYPE
        SYNTAX UnsignedInt
        MAX-ACCESS read-only
        STATUS current
        DESCRIPTION
                "This is the mask that identifies which bits in the state
                 are informational alarms"
        ::= { resourceAlarmEntry 8 }

resourceAlarmNominalMask OBJECT-TYPE
        SYNTAX UnsignedInt
        MAX-ACCESS read-only
        STATUS current
        DESCRIPTION
                "This is the mask that identifies which bits in the state
                 are nominal alarms"
        ::= { resourceAlarmEntry 9 }

resourceAlarmTrapMask OBJECT-TYPE
        SYNTAX UnsignedInt
        MAX-ACCESS read-only
        STATUS current
        DESCRIPTION
                "This is the mask that identifies which bits in the state
                 are used to generate traps."
        ::= { resourceAlarmEntry 10 }


-- *************************************************************************
-- 		This section is for the System Profile Group objects
-- *************************************************************************
sysProfile OBJECT IDENTIFIER ::= { sysMgr 6 }

unitName OBJECT-TYPE
        SYNTAX DisplayString (SIZE (0..30))
        MAX-ACCESS read-write
        STATUS current
        DESCRIPTION
        	" This is the user friendly name of this system."
        ::= { sysProfile 1 }

unitType OBJECT-TYPE
        SYNTAX INTEGER  {
                dnx4(1),
                dnx11(2),
                dnx11-psx(3),
                dnx88(4),
                dnx1U(5)
        		}	
        MAX-ACCESS read-only
        STATUS current
        DESCRIPTION
        	" This is the type of system node.    
        	
            dnx4       (1) Digital Access Cross-Connect System with
                           4 available device/application slots
            dnx11      (2) Digital Access Cross-Connect System with
                           11 available device/application slots
            dnx11-psx  (3) Digital Access Cross-Connect System with
                           11 available device/application slots and 
                           attached redundancy switching device
            dnx88      (4) Multi-Nest Digital Access Cross-Connect System 
                           with 88 available device/application slots
            dnx1U      (5) Small scale DACS with Routing, T1/E1, Synchronous,
                           and asynchronous capabilities
            "
        ::= { sysProfile 2 }

activeSMC OBJECT-TYPE
        SYNTAX INTEGER {
                smc-A (1),
                smc-B (2)
        	    }
        MAX-ACCESS read-only
        STATUS current
        DESCRIPTION
            " This is the current ONLINE System Manager module. 
              (A= top, B= bottom)"
        ::= { sysProfile 3 }

systemRelease OBJECT-TYPE
        SYNTAX DisplayString (SIZE (1..5))
        MAX-ACCESS read-only
        STATUS current
        DESCRIPTION
            "In the form 'xx.yy' where x is the software version
             number followed by the release number y."
        ::= { sysProfile 4 }

releaseDate OBJECT-TYPE
        SYNTAX DisplayString (SIZE (1..20))
        MAX-ACCESS read-only
        STATUS current
        DESCRIPTION
            "The calendar date of Release x.xx above."
        ::= { sysProfile 5 }                            
        
flashChksum OBJECT-TYPE
        SYNTAX DisplayString (SIZE(6))
        MAX-ACCESS read-only
        STATUS current
        DESCRIPTION
            "The current flash memory checksum result. "
        ::= { sysProfile 6 }
        
xilinxType OBJECT-TYPE
        SYNTAX DisplayString  (SIZE (1..20))
        MAX-ACCESS read-only
        STATUS current
        DESCRIPTION
            "The type of xilinx chip used for the downloadable, 
            programmable flash. "
        ::= { sysProfile 7 }
        
xilinxVersion OBJECT-TYPE
        SYNTAX DisplayString  (SIZE (1..30))
        MAX-ACCESS read-only
        STATUS current
        DESCRIPTION
            "The current version of the xilinx chip used for the flash. "
        ::= { sysProfile 8 }
        
rearModem OBJECT-TYPE
        SYNTAX DecisionType
        MAX-ACCESS read-only
		STATUS current
		DESCRIPTION
            "Indicates the presence (yes) or non-presence (no) of the rear 
            card modem. "
		::= { sysProfile 9 }
				
mibProfile OBJECT-TYPE
        SYNTAX DisplayString (SIZE (1..256))
        MAX-ACCESS read-only
        STATUS current
        DESCRIPTION
            "The current SNMP Enterprise MIB Information for this release.
            The format of this string is 'VARIABLE=VALUE' and each pair is
            terminated by a colon.  This object is used to validate which MIB 
            the Agent is currently supporting. The Agent will respond with
            the names of all supported MIB files and the date supported."
        ::= { sysProfile 10 }

systemMgrType OBJECT-TYPE
        SYNTAX INTEGER {
                smc-I (1),
                smc-II (2),
                xnm (3),
                dnx1u-sys (4)
        	    }
        MAX-ACCESS read-only
        STATUS current
        DESCRIPTION
            " This is the hardware type of System Manager module."            
        ::= { sysProfile 11 }

sysAlarmCutOff OBJECT-TYPE
        SYNTAX INTEGER {
                enabled (0),
                disabled (1)
        	    }
        MAX-ACCESS read-write
        STATUS current
        DESCRIPTION
            "This toggles the ACO (Alarm Cut Off) switch."            
        ::= { sysProfile 12 }

sysMacAddress OBJECT-TYPE
        SYNTAX OCTET STRING (SIZE(6))
        MAX-ACCESS read-only
		STATUS current
		DESCRIPTION
            "Displays the system configured MAC Address in hexidecimal format. "
		::= { sysProfile 13 }

sysSa4RxTxTrap OBJECT-TYPE
        SYNTAX INTEGER {
                enabled (1),
                disabled (0)
        	    }
        MAX-ACCESS read-write
        STATUS current
        DESCRIPTION
            "Provides the option to enable the Sa4-match trap to be sent to the NMS."            
        ::= { sysProfile 14 }

sysCustomerId OBJECT-TYPE
        SYNTAX Integer32 (1..9999)
        MAX-ACCESS read-only
        STATUS current
        DESCRIPTION
            "Unique code to identify the customer."            
        ::= { sysProfile 15 }

sysMgrOnlineTime OBJECT-TYPE
        SYNTAX TimeTicks
        MAX-ACCESS read-only
        STATUS current
        DESCRIPTION
            "The time (in hundredths of a second) since the 
            System Manager was declared ONLINE."
        ::= { sysProfile 16 }

-- *************************************************************************
-- This table is the DNX Feature Keys configuration table

featureKeys  OBJECT IDENTIFIER 	::= { sysProfile 100 }

dnxFeatureKeyTable OBJECT-TYPE
        SYNTAX SEQUENCE OF DnxFeatureKeyEntry
        MAX-ACCESS not-accessible
        STATUS current
        DESCRIPTION
            "This is the DNX Feature Key Configuration table which consists
            of an entry for each of the DNX Feature Sets.  The total number of
            entries depends on the number of available features in the unit."
        ::= { featureKeys 1 }

dnxFeatureKeyEntry OBJECT-TYPE
        SYNTAX DnxFeatureKeyEntry
        MAX-ACCESS not-accessible
        STATUS current
        DESCRIPTION
            "The conceptual row of the DNX Feature Key Configuration table.
            A row in this table cannot be added or deleted, only modified."
        INDEX { featureKeyId }
        ::= { dnxFeatureKeyTable 1 }

DnxFeatureKeyEntry ::=
        SEQUENCE {
                featureKeyId         	Integer32,          -- RO
                featureKeyName      	DisplayString,      -- RO
                featureKeyState         INTEGER, 
                featureKeyCmdStatus     INTEGER
                }

featureKeyId OBJECT-TYPE
        SYNTAX Integer32 (1..8)
        MAX-ACCESS read-only
        STATUS current
        DESCRIPTION
                "The unique Feature Key index number."
        ::= { dnxFeatureKeyEntry 1 }

featureKeyName OBJECT-TYPE
        SYNTAX DisplayString  
        MAX-ACCESS read-only
        STATUS current
        DESCRIPTION
             "The text name describing the type of Feature.
             
              KeyId  Feature Key Name    Description
              -----  ----------------    -----------
               1.    ADPCM Tcoder 		 - Transcoder subsystem
               2.    Subrate Switching   - High and Low Nibble connections
               3.    Monitor and Control - Voltage Measurement, Input/ Output 
                                           Contact Closures, & Ambient Temperature subsystems
               4.    Basic Routing       - Terminal Server, PPP, Channelized Routing,
                                           RIP, NAT, DHCP, & Packet Filtering.
               5.    Advanced Routing    - OSPF, VLAN Mapping & GRE data encapsulation
               6.    APS                 - Automatic Protection Switching
               7.    High Speed Data     - Synchronous subsystem
               8.    High Availablity    - Circuit Protection Groups     
              "
        ::= { dnxFeatureKeyEntry 2 }

featureKeyState OBJECT-TYPE
        SYNTAX INTEGER {
			noKey (0),
			active (1),
			inactive (2)
            }	
        MAX-ACCESS read-write
        STATUS current
        DESCRIPTION
             "Determines if the Feature is active or inactive. This can 
             only be SET after the associated feature key has been
             entered."
        ::= { dnxFeatureKeyEntry 3 }

featureKeyCmdStatus OBJECT-TYPE
        SYNTAX INTEGER {
    -- Initial default status for a row
            ready-for-command (0),
    -- Feature Key Commands used in SET Command (1..99)
            update (1),                		
            deleteKey (2),                		
    -- Response States used in GET RESPONSE Command (100..199)
            update-successful (101),
            delete-successful (102),
                            		
    -- Feature Key Config Error Codes used in GET RESPONSE Command (200..799)
            err-general-key-config-error (400),
            err-invalid-state (401),
            err-data-locked-by-another-user (450),
            err-invalid-cmd-status (451),
            err-snmp-parse-failed (500),
            err-invalid-snmp-type (501),
            err-invalid-snmp-var-size (502)
            }                
        MAX-ACCESS read-write
        STATUS current
        DESCRIPTION
           "The command status for this configuration row/record.
           The value used in a SET will be replaced by a response
           value in the GET RESPONSE indicating success or failure.
           		
            Default Response State used in GET RESPONSE Command
                ready-for-command (0)
                    initial default status for a row           
                    
            Feature Key Commands used in SET Command (1..99)            
                update (1),
                    Update the Feature Key state
                deleteKey (2),
                    Remove the Feature Key from the system
               		
            Response States used in GET RESPONSE Command (100..199)
                update-successful (101)
                    Feature Key has been successfully updated
                delete-successful (102)
                    Feature Key has been successfully deleted
                                		
            Feature Key Config Error Codes used in GET RESPONSE Command (200..799)
                err-general-key-config-error (400)
                    Unknown key configuration error occurred                
                err-invalid-state (401)
                    Unrecognized key state                
                err-data-locked-by-another-user (450)
                    Another administrative user is making changes to this
                    part of the system via a terminal session. Check Event
                    Log for user name.
                err-invalid-cmd-status (451)
                    Invalid or missing command status field 
                err-snmp-parse-failed (500)
                    Agent could not parse variable
                err-invalid-snmp-type (501)
                    Variable ASN type does not match Agent defined type 
                err-invalid-snmp-var-size (502)
                    Variable size is too big"                 		
        ::= { dnxFeatureKeyEntry 4 }

enterNewFeatureKey  OBJECT IDENTIFIER 	::= { featureKeys 2 }

newKeyCode OBJECT-TYPE
        SYNTAX DisplayString --  (SIZE(14)) 
        MAX-ACCESS read-write
        STATUS current
        DESCRIPTION
             "This represents the encrypted Feature Key code number that
             must be entered by an admistrator. Once entered successfully, 
             the corresponding feature entries in the dnxFeatureKeyTable 
             will be updated to an active state."
        ::= { enterNewFeatureKey 1 }

newKeyCodeCmdStatus OBJECT-TYPE
        SYNTAX INTEGER {
    -- Initial default status for a row
            ready-for-command (0),
    -- Feature Key Code Commands used in SET Command (1..99)
            enterKey (1),                		

    -- Response States used in GET RESPONSE Command (100..199)
            key-successful (101),
                            		
    -- Feature Key Code Config Error Codes used in GET RESPONSE Command (200..799)
            err-invalid-key (402),
            err-data-locked-by-another-user (450),
            err-invalid-cmd-status (451),
            err-snmp-parse-failed (500),
            err-invalid-snmp-type (501),
            err-invalid-snmp-var-size (502)
            }                
        MAX-ACCESS read-write
        STATUS current
        DESCRIPTION
           "The command status for this configuration row/record.
           The value used in a SET will be replaced by a response
           value in the GET RESPONSE indicating success or failure.
           		
            Default Response State used in GET RESPONSE Command
                ready-for-command (0)
                    initial default status for a row           
                    
            Feature Key Commands used in SET Command (1..99)            
                enterKey (1),
                    Enter a new Feature Key code
               		
            Response States used in GET RESPONSE Command (100..199)
                key-successful (101)
                    Feature Key has been successfully entered
                                		
            Feature Key Config Error Codes used in GET RESPONSE Command (200..799)
                err-invalid-key (402)
                    Unrecognized feature key code                
                err-data-locked-by-another-user (450)
                    Another administrative user is making changes to this
                    part of the system via a terminal session. Check Event
                    Log for user name.
                err-invalid-cmd-status (451)
                    Invalid or missing command status field 
                err-snmp-parse-failed (500)
                    Agent could not parse variable
                err-invalid-snmp-type (501)
                    Variable ASN type does not match Agent defined type 
                err-invalid-snmp-var-size (502)
                    Variable size is too big"                 		
        ::= { enterNewFeatureKey 2 }

-- *************************************************************************
--  This section is for the System Clock Group objects 

sysClock 		OBJECT IDENTIFIER 	::= { sysMgr 7 }

-- *************************************************************************
-- This is the system Date & Time Configuration Group which allows the user to 
-- to view/set any aspect of the system date/time.  By providing valid values 
-- for the system date & time fields and by also setting the value of 
-- sysTimeCmdStatus to 'update-sys-time', the system clock can be changed. 
-- An 'GenErr' error status will be returned in the GET Response if the 
-- sysTimeCmdStatus is missing from the Set Request.  A 'badValue' error status 
-- will be returned in the Response if one or more fields contain invalid values.
-- *************************************************************************

sysDateTime     OBJECT IDENTIFIER 	::= { sysClock 1 }

sysMonth OBJECT-TYPE
        SYNTAX INTEGER 
            {
            january (1),
            february (2),
            march (3),
            april (4),
            may (5),
            june (6),
            july (7),
            august (8),
            september (9),
            october (10),
            november (11),
            december (12)
            }
        MAX-ACCESS read-write
        STATUS current
        DESCRIPTION
                "The current calendar month. "
        ::= { sysDateTime 1 }
        
sysDay OBJECT-TYPE
        SYNTAX Integer32 (1..31)
        MAX-ACCESS read-write
        STATUS current
        DESCRIPTION
                "The current calendar day in month. "
        ::= { sysDateTime 2 }

sysYear OBJECT-TYPE
        SYNTAX Integer32
        MAX-ACCESS read-write
        STATUS current
        DESCRIPTION
                "The current calendar year. "
        ::= { sysDateTime 3 }
        
sysHour OBJECT-TYPE
        SYNTAX Integer32 (0..23)
        MAX-ACCESS read-write
        STATUS current
        DESCRIPTION
                "The current military standard hour. "
        ::= { sysDateTime 4 }
        
sysMin OBJECT-TYPE
        SYNTAX Integer32 (0..59)
        MAX-ACCESS read-write
        STATUS current
        DESCRIPTION
                "The current system minutes. "
        ::= { sysDateTime 5 }
        
sysSec OBJECT-TYPE
        SYNTAX Integer32 (0..59)
        MAX-ACCESS read-write
        STATUS current
        DESCRIPTION
                "The current system seconds. "
        ::= { sysDateTime 6 }
        
sysWeekday OBJECT-TYPE
        SYNTAX INTEGER {
       		monday (1),
       		tuesday (2),
       		wednesday (3),
       		thursday (4),
       		friday (5),
       		saturday (6),
       		sunday (7)
       		}
        MAX-ACCESS read-write
        STATUS current
        DESCRIPTION
                "The current calendar day of the week. "
        ::= { sysDateTime 7 }

sysTimeCmdStatus OBJECT-TYPE
        SYNTAX INTEGER {
    -- Initial default status for a row
            ready-for-command (0),
    -- System Time Commands used in SET Command (1..99)
            update-sys-time (1),
                		
    -- Response States used in GET RESPONSE Command (100..199)
            update-successful (101),
                		
    -- Time Config Error Codes used in GET RESPONSE Command (200..799)
            err-general-time-date-error (200),
            err-invalid-day (201),
            err-invalid-month (202),
            err-invalid-year (203),
            err-invalid-hours (204),
            err-invalid-minutes (205),
            err-invalid-seconds (206),
            err-invalid-weekday (207),
            err-invalid-calendar (208),
            err-invalid-sys-time-cmd (209),
            err-data-locked-by-another-user (450),
            err-snmp-parse-failed (500),
            err-invalid-snmp-type (501),
            err-invalid-snmp-var-size (502)
            }
        MAX-ACCESS read-write
        STATUS current
        DESCRIPTION
           "The command status for this system Date and Time.
           The value used in a SET will be replaced by a response
           value in the GET RESPONSE indicating success or failure.
           		
            Default Response State used in GET RESPONSE Command
                ready-for-command (0)
                    initial default status for a row           
                    
	        System Time Commands used in SET Command (1..99)
                update-sys-time (1)
                    change the current system date/time
                		
            Response States used in GET RESPONSE Command (100..199)
                update-successful (101)
                    system clock has been successfully changed
                		
            Time Config Error Codes used in GET RESPONSE Command (200..799)
                err-general-time-date-error (200)
                    Unexpected time configuration error occurred
                err-invalid-day (201)
                	Out of range day value
                err-invalid-month (202)
                	Out of range month value
                err-invalid-year (203)
                	Out of range year value
                err-invalid-hours (204)
                	Out of range military hour value
                err-invalid-minutes (205)
                	Out of range minute value
                err-invalid-seconds (206)
                	Out of range second value
                err-invalid-weekday (207)
                	Out of range weekday value
                err-general-calendar-error (208)
                    Incorrect month/day/year combination. Checks for leap year.
                err-invalid-sys-time-command (209)
                	Unrecognized or missing time config command
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
                		
        ::= { sysDateTime 8 }


-- *************************************************************************
-- This is the system Clock Source Configuration Group which allows the user to 
-- configure up to three different sources as a reference for the system 
-- clock.  By providing valid values for the system clock source fields and by 
-- also setting the value of clockSrcCmdStatus to 'update-clock-src', the system 
-- clock configuration can changed. An 'GenErr' error status will be returned in 
-- the GET Response if the clockSrcCmdStatus is missing from a Set Request.  
-- A 'Bad Value' error status will be returned in the Response if one or more 
-- fields contain invalid values.
-- *************************************************************************

clockSrcConfig OBJECT IDENTIFIER ::= { sysClock 2 }

clockSrcActive OBJECT-TYPE
        SYNTAX INTEGER {
      		freerun (0),
      		holdover (1),
       		primary (2),
       		secondary (3),
      		tertiary (4),
      		primary-protected (6),
      		secondary-protected (7),
      		tertiary-protected (8)
       		}           
        MAX-ACCESS read-only
        STATUS current
        DESCRIPTION
            "This is the current clock source in use."
        ::= { clockSrcConfig 1 }

primaryClockSrc OBJECT-TYPE
        SYNTAX ClockSrcAddress
        MAX-ACCESS read-write
        STATUS current
        DESCRIPTION
           "The Primary Clock Source slot/port address or Station 
           Identifier. The format is represented using an IP address 
           syntax (4 byte string) with the first byte unused.
         	 
           The 2nd byte represents the Clock Source Slot Number (1-11).
           A non-zero value in this byte indicates an outside Clock Source
           and should have valid values for the slot number and also the
           port in the third byte. A zero for the 4th byte is expected since 
           the Station Clock is not applicable.
             
           The 3rd byte represents the destination Port Number (1-84).
           A non-zero value in this byte indicates an outside Clock Source
           and should have valid values for the port number and also the
           slot in the previous byte. A zero for the 4th byte is expected since 
           the Station Clock is not applicable.
           
           The 4th byte represents the Station Clock Source.
           A non-zero in this byte indicates whether to use station A (1) 
           or B (2) and should have zero(0) values in the previous bytes
           for slot and port.
           
           NOTE: To designate a Freerun Source or Inactive Clock Source,
           this field should have no slot, port, or station info. The entire
           ClockSrcAddress value would then be 0.0.0.0"
           
        ::= { clockSrcConfig 2 }

secondaryClockSrc OBJECT-TYPE
        SYNTAX ClockSrcAddress
        MAX-ACCESS read-write
        STATUS current
        DESCRIPTION
           "The Secondary Clock Source slot/port address or Station 
           Identifier. The format is represented using an IP address 
           syntax (4 byte string) with the first byte unused.
         	 
           The 2nd byte represents the Clock Source Slot Number (1-11).
           A non-zero value in this byte indicates an outside Clock Source
           and should have valid values for the slot number and also the
           port in the third byte. A zero for the 4th byte is expected since 
           the Station Clock is not applicable.
             
           The 3rd byte represents the destination Port Number (1-84).
           A non-zero value in this byte indicates an outside Clock Source
           and should have valid values for the port number and also the
           slot in the previous byte. A zero for the 4th byte is expected since 
           the Station Clock is not applicable.
           
           The 4th byte represents the Station Clock Source.
           A non-zero in this byte indicates whether to use station A (1) 
           or B (2) and should have zero(0) values in the previous bytes
           for slot and port.
           
           NOTE: To designate a Freerun Source or Inactive Clock Source,
           this field should have no slot, port, or station info. The entire
           ClockSrcAddress value would then be 0.0.0.0"
           
        ::= { clockSrcConfig 3 }

tertiaryClockSrc OBJECT-TYPE
        SYNTAX ClockSrcAddress
        MAX-ACCESS read-write
        STATUS current
        DESCRIPTION
           "The Tertiary Clock Source slot/port address or Station 
           Identifier. The format is represented using an IP address 
           syntax (4 byte string) with the first byte unused.
         	 
           The 2nd byte represents the Clock Source Slot Number (1-11).
           A non-zero value in this byte indicates an outside Clock Source
           and should have valid values for the slot number and also the
           port in the third byte. A zero for the 4th byte is expected since 
           the Station Clock is not applicable.
             
           The 3rd byte represents the destination Port Number (1-84).
           A non-zero value in this byte indicates an outside Clock Source
           and should have valid values for the port number and also the
           slot in the previous byte. A zero for the 4th byte is expected since 
           the Station Clock is not applicable.
           
           The 4th byte represents the Station Clock Source.
           A non-zero in this byte indicates whether to use station A (1) 
           or B (2) and should have zero(0) values in the previous bytes
           for slot and port.
           
           NOTE: To designate a Freerun Source or Inactive Clock Source,
           this field should have no slot, port, or station info. The entire
           ClockSrcAddress value would then be 0.0.0.0"
           
        ::= { clockSrcConfig 4 } 
        
clockSrcMode OBJECT-TYPE
        SYNTAX INTEGER {
      		freerun (0),
       		auto (1),
       		primary (2),
       		secondary (3),
      		tertiary (4)
       		}
        MAX-ACCESS read-write
        STATUS current
        DESCRIPTION
                "The configured system clock source fallback Mode. "
        ::= { clockSrcConfig 5 }

clockSrcCmdStatus OBJECT-TYPE
        SYNTAX INTEGER {
    -- Initial default status for a row
            ready-for-command (0),
    -- Clock Source Commands used in SET Command (1..99)
            update-clock-src (1),
                		
    -- Response States used in GET RESPONSE Command (100..199)
            update-successful (101),
                		
    -- Clock Source Config Error Codes used in GET RESPONSE Command (200..799)
            err-gen-clock-src-config-error (200),
            err-invalid-slot (201),
            err-invalid-port (202),
            err-invalid-clock-src-command (203),
            err-invalid-clock-mode (204),
            err-invalid-station-clock (205),
            err-data-locked-by-another-user (450),
            err-snmp-parse-failed (500),
            err-invalid-snmp-type (501),
            err-invalid-snmp-var-size (502)
            }
        MAX-ACCESS read-write
        STATUS current
        DESCRIPTION
           "The command status for this Clock Source configuration.
           The value used in a SET will be replaced by a response
           value in the GET RESPONSE indicating success or failure.
           		
            Default Response State used in GET RESPONSE Command
                ready-for-command (0)
                    initial default status for a row           
                    
            Clock Source Commands used in SET Command (1..99)            
                update-clock-src (1)
                    Change the source for primary, secondary or tertiary
                    clocks
                		
            Response States used in GET RESPONSE Command (100..199)
                update-successful (101)
                    clock source data has been successfully changed
                		
            Clock Source Error Codes used in GET RESPONSE Command (200..799)
                err-gen-clock-src-config-error (200)
                    Unknown clock src configuration error occurred.
                err-invalid-slot (201)
                    Configured slot not in valid range
                err-invalid-port (202)
                    Configured port not in valid range
                err-invalid-clock-src-command (203,
                    Unrecognized clock src command action
                err-invalid-clock-mode (204)
                    Unrecognized clock src fallback                
                err-invalid-station-clock (205)
                    Configured station not valid
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
                		
        ::= { clockSrcConfig 6 }

-- *************************************************************************
-- 		This section is for the System Connections tables and objects
-- *************************************************************************

connections 	OBJECT IDENTIFIER 	::= { sysMgr 8 }

-- *************************************************************************
-- NOTE: A single SNMP SET Request message from the Manager can refer to 
-- several rows/records from the Active Connection Table however the fields 
-- for each record should be grouped together and each record must be 
-- terminated by the ConnCmdStatus field to denote the end of the "action".
-- This will allow the Agent to know when the record is complete so it can 
-- be applied to the Database. The Agent will return the identical OIDs and 
-- values provided in the SET with the exception of the ConnCmdStatus.  This 
-- field will be changed to reflect the action taken (either a success code 
-- or appropriate error code).
-- *************************************************************************

connInfo OBJECT IDENTIFIER 	::= { connections 1 }

activeMapId	OBJECT-TYPE
        SYNTAX Integer32 (1..5)
        MAX-ACCESS read-only
        STATUS current
        DESCRIPTION
                " This is the ID number for current Connection Map. 
                For details about each Connection Map, use the 
                connMapTable entries."
        ::= { connInfo 1 }

connDBChecksum	OBJECT-TYPE
        SYNTAX UnsignedInt
        MAX-ACCESS read-only
        STATUS current
        DESCRIPTION
                " This is the Connection Database checksum which applies to
                all connections in all Maps. This number is calculated by 
                taking the sum of the Connection Map versions value from 
                each entry in the Connection Map Table.  This value can then
                be used to identify possible discrepancies between the Agent
                and the Network Manager's Connection Data."
        ::= { connInfo 2 }

lastMapCopied  OBJECT-TYPE
        SYNTAX Integer32 (0..5)
        MAX-ACCESS read-only
        STATUS current
        DESCRIPTION
                " This is the ID of the last Connection Map used as a source in
                a Connection Map copy operation to one or more destination maps."
        ::= { connInfo 3 }


-- *************************************************************************
-- This table is the Connection Map Definition table

connMapTable OBJECT-TYPE
        SYNTAX SEQUENCE OF ConnMapEntry
        MAX-ACCESS not-accessible
        STATUS current
        DESCRIPTION
           "This is the Connection Map table which consists of 5 connection 
           configuration map entries."  
        ::= { connections 2 }

connMapEntry OBJECT-TYPE
        SYNTAX ConnMapEntry
        MAX-ACCESS not-accessible
        STATUS  current
        DESCRIPTION
           "The conceptual row of the Connection Map table.  A row in this 
           table can not be created or deleted.  A row in this table can be 
           modified by providing valid values for either the Map Name, 
           Description, or  Map Status.  Changing the Map Status from 
           inactive to active for a map will result in the current active map 
           to be changed to inactive. The connMapCmdStatus field must
           be included as a variable in a SET PDU for the action to 
           take effect. If the connMapCmdStatus is missing from the SET PDU, 
           the GET RESPONSE will contain the SNMP error status of 'genErr' for 
           and an error index equal to the last variable."
        INDEX { connMapID } 
               
        ::= { connMapTable 1 }

ConnMapEntry ::=
        SEQUENCE {
                connMapID           Integer32,
                connMapName         DisplayString,    -- RW
                connMapCurrStatus   INTEGER,          -- RW
                connMapDescription  DisplayString,    -- RW
                connMapCounts       Counter32,
                connMapVersions     Counter32,
                connMapDate         DisplayString,
                connMapCmdStatus    INTEGER,          -- RW
                connMapChecksum     UnsignedInt
                }

connMapID OBJECT-TYPE
        SYNTAX Integer32 (1..5)
        MAX-ACCESS read-only
        STATUS current
        DESCRIPTION
            "This number uniquely identifies a system connection map."
        ::= { connMapEntry 1 }

connMapName OBJECT-TYPE
        SYNTAX DisplayString (SIZE (1..11))
        MAX-ACCESS read-write
        STATUS current
        DESCRIPTION
            "This is the textual name of a specific connection configuration
            map.  The length can be from 1 to 11 characters."
        ::= { connMapEntry 2 }
        
connMapCurrStatus OBJECT-TYPE
	SYNTAX INTEGER {
		active(1),
		non-active(2),
		non-active-tagged(3)
		}
        MAX-ACCESS read-write
        STATUS current
        DESCRIPTION
            "This indicates the current status for a connection map. 
             Only one map can be active at a given time.             
             
             active            (1) - The current active map
                  
             non-active        (2) - The Map is currently not active and 
                                     currently not tagged.
                  
             non-active-tagged (3)- map is currently not active but
                                    tagged as a destination to be copied to.  
             
             NOTE: Tagging allows another map's configuration to be copied 
                   to this map when the copy command is used on the source 
                   map. The source map can be any other map."
        ::= { connMapEntry 3 }

connMapDescription OBJECT-TYPE
        SYNTAX DisplayString (SIZE (0..20))
        MAX-ACCESS read-write
        STATUS current
        DESCRIPTION
            "This is the textual description of the connection configuration 
            map.  The length can be from 1 to 20 characters."
        ::= { connMapEntry 4 }

connMapCounts OBJECT-TYPE
        SYNTAX Counter32
        MAX-ACCESS read-only
        STATUS current
        DESCRIPTION
            "This is the number of system connections configured and saved 
            in this map."
        ::= { connMapEntry 5 }

connMapVersions OBJECT-TYPE
        SYNTAX Counter32
        MAX-ACCESS read-only
        STATUS current
        DESCRIPTION
            "This is the current version number for this map.  Each 
            time the map is permanently saved, the version number will
            be incremented by 1."
        ::= { connMapEntry 6 }

connMapDate OBJECT-TYPE
        SYNTAX DisplayString
        MAX-ACCESS read-only
        STATUS current
        DESCRIPTION
            "This is the calendar date of the last time a configuration 
            change was saved to this map."
        ::= { connMapEntry 7 }

connMapCmdStatus OBJECT-TYPE
  	    SYNTAX INTEGER {
    -- Initial default status for a row
            ready-for-command (0),
    -- Map Commands used in SET Command (1..99)
            update-map (1),
            delete-map (2),
            activate-map (7),
            save-map (8),
            copy-map-to-tagged-maps(9),
                		
    -- Response States used in GET RESPONSE Command (100..199)
            command-in-progress (100),
            update-successful (101),
            delete-successful (102),
            activate-successful (107),
            save-successful (108),
            copy-successful (109),
                		
    -- Map Config Error Codes used in GET RESPONSE Command (200..799)
            err-general-map-config-error (200),
            err-invalid-map-command (202),
            err-invalid-map-name (203),
            err-invalid-map-desc (204),
            err-invalid-map-status (205),
            err-data-locked-by-another-user (450),
            err-snmp-parse-failed (500),
            err-invalid-snmp-type (501),
            err-invalid-snmp-var-size (502)
            }
        MAX-ACCESS read-write
        STATUS current
        DESCRIPTION
           "The command status for this connection map configuration 
           row/record. The value used in a SET will be replaced by a 
           response value in the GET RESPONSE indicating success or failure.
           		
            Default Response State used in GET RESPONSE Command
                ready-for-command (0)
                    initial default status for a row           
                    
            Map Commands used in SET Command (1..99)
                update-map (1)
                    Update the map name and/or map description.
                delete-map (2)
                    Delete all connections from an inactive map.
                activate-map (7)
                    Make this map the active map. Changing the Map Status from 
                    inactive to active for a map will result in the current 
                    active map to be changed to inactive.
                save-map (8)
                    Save the connection data configured for this map.
                    Each time the save-map command is used, the map version and 
                    date will be updated. The maps should be saved after changing 
                    the system connection configuration to avoid losing those 
                    changes in the event of unexpected power loss or system reset.
                copy-map-to-tagged-maps(9)
                    Copy the connection configuration from this map to all other
                    maps tagged as a destination.
                		
            Response States used in GET RESPONSE Command (100..199)
                command-in-progress (100)
                    map command is still working
                update-successful (101)
                    map data has been successfully changed
                delete-successful (102)
                    map connection data has been successfully deleted
                activate-successful (107)
                    connection map has been successfully activated and previous
                    active map has been de-activated.
                save-successful (108)
                    connection map has been successfully saved
                copy-successful (109)
                    connection map has been successfully copied
                		
            Map Config Error Codes used in GET RESPONSE Command (200..799)
                err-general-map-config-error (200)
                    Unknown map configuration error occurred
                err-invalid-map-command (202)
                    Unrecognized map command-action
                err-invalid-map-name (203)
                    Configured map name too long
                err-invalid-map-desc (204)
                    Configured map description too long
                err-invalid-map-status (205)
                    Unrecognized map status or invalid for current map
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
        ::= { connMapEntry 8 }

connMapChecksum OBJECT-TYPE
        SYNTAX UnsignedInt
        MAX-ACCESS read-only
        STATUS current
        DESCRIPTION
            "This is the checksum for the system connection map."
        ::= { connMapEntry 9 }

-- *************************************************************************
-- This table is the System Connection table

sysConnTable OBJECT-TYPE
        SYNTAX SEQUENCE OF SysConnEntry
        MAX-ACCESS not-accessible
        STATUS current
        DESCRIPTION
           "This is the system Connection table which consists of connection 
           entries from all available configuration maps.  There are 5 seperate
           connection maps but only one can be active at a time. The number of 
           entries in this table depends on the number of connections configured.  
           Currently the maximum number of connections is 16224 for a DNX88 system
           or 4056 for a DNX11 (if all connections are half-duplex using a single DS0). 
           If connections require more bandwidth (multiple DS0s or full-duplex), the 
           system bandwidth will be exceeded before you reach the above connection 
           maximums."  
        ::= { connections 3 }

sysConnEntry OBJECT-TYPE
        SYNTAX SysConnEntry
        MAX-ACCESS not-accessible
        STATUS  current
        DESCRIPTION
           "The conceptual row of the system Connection table.  A row in 
           this table can NOT be created.  A row in this table can be 
           modified by providing valid values for one or more writable 
           columns and by setting the value of sysCmdStatus to 'update'.  
           A row in this table can be deleted by setting the value of 
           sysCmdStatus to 'delete'. The sysCmdStatus field must be included 
           as a variable in a SET PDU for the action to take effect.
           If the sysCmdStatus is missing from the SET PDU, the GET RESPONSE 
           will contain the SNMP error status of 'genErr' for and an error index 
           equal to the last variable."
        INDEX { sysMapID, sysConnID } 
               
        ::= { sysConnTable 1 }

SysConnEntry ::=
        SEQUENCE {
                sysMapID              MapNumber,
                sysConnID             Integer32,
                sysConnName           DisplayString,      -- RW
                sysConnType           ConnectionType,
                sysSrcAddr            TimeSlotAddress,
                sysDestAddr           TimeSlotAddress,
                sysComm	              CommunicationsType, -- RW
                sysConnSpeed          ConnectionSpeed,    -- RW
                sysSrcTsBitmap        Integer32,          -- RW
                sysDestTsBitmap       Integer32,          -- RW
                sysBroadSrcId         Integer32,
                sysTestMode           TestAccess,         -- obsolete
                sysCmdStatus          ConnCmdStatus,      -- RW
                sysPrimaryState       ConnectionState1,
                sysSecondaryState     ConnectionState2,
                sysConnInstance       Integer32,
                sysConnChecksum       UnsignedInt,
                sysSrcTsLineType      DnxTsPortType,
                sysDestTsLineType     DnxTsPortType,
                sysSrcTrunkCProfile   DnxTrunkProfSelection,
                sysDestTrunkCProfile  DnxTrunkProfSelection
                }
                                
sysMapID OBJECT-TYPE
        SYNTAX MapNumber
        MAX-ACCESS read-only
        STATUS current
        DESCRIPTION
            "This number uniquely identifies a system connection map. This
            number will be used in conjunction with the connection ID to 
            uniquely identify a connection."
        ::= { sysConnEntry 1 }

sysConnID OBJECT-TYPE
        SYNTAX Integer32 (0..16224)
        MAX-ACCESS read-only
        STATUS current
        DESCRIPTION
            "This number uniquely identifies a connection within a given 
            configuration map. This number will be used in conjunction with 
            the map ID to uniquely identify a system connection."
        ::= { sysConnEntry 2 }

sysConnName OBJECT-TYPE
        SYNTAX DisplayString (SIZE (1..19))
        MAX-ACCESS read-write
        STATUS current
        DESCRIPTION
            "This is the textual description of a connection within a given 
            configuration map.  The length can be from 1 to 20 characters."
        ::= { sysConnEntry 3 }
        
sysConnType OBJECT-TYPE
        SYNTAX ConnectionType
        MAX-ACCESS read-only
        STATUS current
        DESCRIPTION
           "The connection type for this system connection.
            fullDuplex          (0) Bi-directional connection from Source 
                                    port to Destination port and vice-versa.
            broadcastConnection (1) One directional connection from Source 
                                    to Dest ports.
            broadcastMaster     (2) Input connection from Source port to 
                                    backplane only.
            listenSrc           (3) Output connection from backplane to 
                                    Destination port. Must be configured to 
                                    'listen' to an active Source port. 
            listenDest          (4) Output connection from backplane to 
                                    Destination port. Must be configured to 
                                    'listen' to an active Dest port.
			vcmp				(8) Voice Compression - Applicable to DNX-1u supporting 
									Transcoder hardware. Provides cross-connect capability 
									between uncompressed source and compressed destination.
			subChannel			(9) Applicable to DNX-1u supporting Transcoder hardware.
									Connection allowing the user to map source's compressed
									bit group to the destination's bit group.
		    subRate            (10) Sub-rate level switching connection that must use 
		                            ConnectionSpeed of 32k and must specify if high nibble or
		                            low nibble timeslot bits are used for both Src and Dest."
                                     
	::= { sysConnEntry 4 } 
  
sysSrcAddr OBJECT-TYPE
        SYNTAX TimeSlotAddress
        MAX-ACCESS read-only
        STATUS current
        DESCRIPTION
           "The source port timeslot address for this connection.
           The format is represented using an IP address syntax 
           (4 byte string).  Note that the maximum valid port 
           number and starting timeslot will vary depending on the
           specified carrier and framing options. For example, an
           octal T1/E1 device has 8 ports but the T1 link has 24
           timeslots while the E1 link has 32 timeslots.
            
           The 1st byte is reserved for future use
           The 2nd byte represents the source Slot Number (1-11)           
           The 3rd byte represents the source Port Number (1-84)           
           The 4th byte represents the source starting Timeslot (1-232) 
               normal connections use range 1..32
             For subRate connection types:  
               low nibble connections use range  101..132 
               high nibble connections use range 201..232
           "
        ::= { sysConnEntry 5 }

sysDestAddr OBJECT-TYPE
        SYNTAX TimeSlotAddress
        MAX-ACCESS read-only
        STATUS current
        DESCRIPTION
           "The destination port timeslot address for this connection.
           The format is represented using an IP address syntax 
           (4 byte string).  Note that the maximum valid port 
           number and starting timeslot will vary depending on the
           specified carrier and framing options. For example, an
           octal T1/E1 device has 8 ports but the T1 link has 24
           timeslots while the E1 link has 32 timeslots.
            
           The 1st byte is reserved for future use
           The 2nd byte represents the destination Slot Number (1-11)            
           The 3rd byte represents the destination Port Number (1-84)        
           The 4th byte represents the source starting Timeslot (1-232) 
               normal connections use range 1..32
             For subRate connection types:  
               low nibble connections use range  101..132 
               high nibble connections use range 201..232
           "
        ::= { sysConnEntry 6 }

sysComm	OBJECT-TYPE
        SYNTAX CommunicationsType
        MAX-ACCESS read-write
        STATUS current
        DESCRIPTION
           "The type of communications utilized on this system connection.
                
                data		(0) Data only
                voice		(1) Voice only
                voiceAuToMu	(2) Voice with Au-law to Mu-law Conversion
                
            The Bit Group selections for a connection of the VCMP or subChannel 
            type. There are 2 4-bit groups at speed 32 Kbps and 4 2-bit groups 
            at speed 16 Kbps. They specify the position of the compressed 
            data within the selected DS0. Applicable to DNX-1u with Transcoder 
            Hardware.
                
       			comp16kBitGrp1-2(3) vcmp and subChannel only
				comp16kBitGrp3-4(4) vcmp and subChannel only
				comp16kBitGrp5-6(5) vcmp and subChannel only
				comp16kBitGrp7-8(6) vcmp and subChannel only
				comp32kBitGrp1-4(7) vcmp and subChannel only
				comp32kBitGrp5-8(8) vcmp and subChannel only
                "
        
        ::= { sysConnEntry 7 }

sysConnSpeed  OBJECT-TYPE
		SYNTAX ConnectionSpeed
        MAX-ACCESS read-write
        STATUS current
        DESCRIPTION
           "The data transmission speed in kilobytes per second (kbps) for 
           this connection.  The format is:
           -Speed in kbps-number of DS0-kbps per channel
                s48k (0)          - 48k (1 DS0)
                s56k (1)          - 56k (1 DS0)
                s64k (2)          - 64k (1 DS0)
                s112k-2x56 (3)    - 112k/56 (2 DS0s)
                s128k-2x64 (4)    - 128k/64 (2 DS0s)
                s168k-3x56 (5)    - 168k/56 (3 DS0s)
                s192k-3x64 (6)    - 192k/64 (3 DS0s)
                s224k-4x56 (7)    - 224k/56 (4 DS0s)
                s256k-4x64 (8)    - 256k/64 (4 DS0s)
                s280k-5x56 (9)    - 280k/56 (5 DS0s)
                s320k-5x64 (10)   - 320k/64 (5 DS0s)
                s336k-6x56 (11)   - 336k/56 (6 DS0s)
                s384k-6x64 (12)   - 384k/64 (6 DS0s)
                s392k-7x56 (13)   - 392k/56 (7 DS0s)
                s448k-7x64 (14)   - 448k/64 (7 DS0s)
                s448k-8x56 (15)   - 448k/56 (8 DS0s)
                s512k-8x64 (16)   - 512k/64 (8 DS0s)
                s504k-9x56 (17)   - 504k/56 (9 DS0s)
                s576k-9x64 (18)   - 576k/64 (9 DS0s)
                s560k-10x56 (19)  - 560k/56 (10 DS0s)
                s640k-10x64 (20)  - 640k/64 (10 DS0s)
                s616k-11x56 (21)  - 616k/56 (11 DS0s)
                s704k-11x64 (22)  - 704k/64 (11 DS0s)
                s672k-12x56 (23)  - 672k/56 (12 DS0s)
                s768k-12x64 (24)  - 768k/64 (12 DS0s)
                s728k-13x56 (25)  - 728k/56 (13 DS0s)
                s832k-13x64 (26)  - 832k/64 (13 DS0s)
                s784k-14x56 (27)  - 784k/56 (14 DS0s)
                s896k-14x64 (28)  - 896k/64 (14 DS0s)
                s840k-15x56 (29)  - 840k/56 (15 DS0s)
                s960k-15x64 (30)  - 960k/64 (15 DS0s)
                s896k-16x56 (31)  - 896k/56 (16 DS0s)
                s1024k-16x64 (32) - 1024k/64(16 DS0s)
                s952k-17x56 (33)  - 952k/56 (17 DS0s)
                s1088k-17x64 (34) - 1088k/64 (17 DS0s)
                s1008k-18x56 (35) - 1008k/56 (18 DS0s)
                s1152k-18x64 (36) - 1152k/64 (18 DS0s)
                s1064k-19x56 (37) - 1064k/56 (19 DS0s)
                s1216k-19x64 (38) - 1216k/64 (19 DS0s)
                s1120k-20x56 (39) - 1120k/56 (20 DS0s)
                s1280k-20x64 (40) - 1280k/64 (20 DS0s)
                s1176k-21x56 (41) - 1176k/56 (21 DS0s)
                s1344k-21x64 (42) - 1344k/64 (21 DS0s)
                s1232k-22x56 (43) - 1232k/56 (22 DS0s)
                s1408k-22x64 (44) - 1408k/64 (22 DS0s)
                s1288k-23x56 (45) - 1288k/56 (23 DS0s)
                s1472k-23x64 (46) - 1472k/64 (23 DS0s)
                s1344k-24x56 (47) - 1344k/56 (24 DS0s)
                s1536k-24x64 (48) - 1536k/64 (24 DS0s)
                s1400k-25x56 (49) - 1400k/56 (25 DS0s)
                s1600k-25x64 (50) - 1600k/64 (25 DS0s)
                s1456k-26x56 (51) - 1456k/56 (26 DS0s)
                s1664k-26x64 (52) - 1664k/64 (26 DS0s)
                s1512k-27x56 (53) - 1512k/56 (27 DS0s)
                s1728k-27x64 (54) - 1728k/64 (27 DS0s)
                s1568k-28x56 (55) - 1568k/56 (28 DS0s)
                s1792k-28x64 (56) - 1792k/64 (28 DS0s)
                s1624k-29x56 (57) - 1624k/56 (29 DS0s)
                s1856k-29x64 (58) - 1856k/64 (29 DS0s)
                s1680k-30x56 (59) - 1680k/56 (30 DS0s)
                s1920k-30x64 (60) - 1920k/64 (30 DS0s)
                s1736k-31x56 (61) - 1736k/56 (31 DS0s)
                s1984k-31x64 (62) - 1984k/64 (31 DS0s)
                s1792k-32x56 (63) - 1792k/56 (32 DS0s)
                s2048k-32x64 (64) - 2048k/64 (32 DS0s)
                clearT1-25x64(65) - Framed or Unframed 64k (25 DS0s)
                clearE1-32x64(66) - Framed or Unframed 64k (32 DS0s)
                s32k		 (67) - DNX-1u Transcoder/Sub-Rate supported speed
                s16k		 (68) - DNX-1u Transcoder supported speed
                "
				
        ::= { sysConnEntry 8 }
 
sysSrcTsBitmap OBJECT-TYPE
        SYNTAX Integer32
        MAX-ACCESS read-write
        STATUS current
        DESCRIPTION
           "This is a bit field used for the source port timeslots.
           Each bit represents a link timeslot on the source port.
           Setting the bit indicates that timeslot is used for the 
           connection. The number of timeslots utilized depends on the 
           connection speed. Timeslot zero refers to the rightmost bit."
        
        ::= { sysConnEntry 9 }
 
sysDestTsBitmap OBJECT-TYPE
        SYNTAX Integer32
        MAX-ACCESS read-write
        STATUS current
        DESCRIPTION
           "This is a bit field used for the destination port timeslots.
           Each bit represents a link timeslot on the destination port.
           Setting the bit indicates that timeslot is used for the 
           connection. The number of timeslots utilized depends on the 
           connection speed. Timeslot zero refers to the rightmost bit."
        
        ::= { sysConnEntry 10 }
       
sysBroadSrcId OBJECT-TYPE
        SYNTAX Integer32
        MAX-ACCESS read-only
        STATUS current
        DESCRIPTION
            "The connection ID number of the broadcast source connection 
            for a listener connection to read from."
        ::= { sysConnEntry 11 }

-- *************************************************************************
-- The Connection Test Mode is no longer applicable for Connection records 
-- and is not supported by the Agent as of Release 12.0
-- *************************************************************************
sysTestMode OBJECT-TYPE
        SYNTAX TestAccess
        MAX-ACCESS read-only
        STATUS obsolete
        DESCRIPTION
           "This indicates whether the current connection is in test
           mode, and if so, the type of test access being used.  
                none             (0) Connection has no active Tests
                monitorSrc       (1) Connection Source port is monitored 
                                     to a Test port
                monitorDest      (2) Connection Dest port is monitored 
                                     to a Test port
                monitorSrc&Dest  (3) Connection Source and Dest ports are
                                     monitored to Test ports
                splitSrc         (4) Connection Source port is re-routed 
                                     to a Test port
                splitDest        (5) Connection Dest port is re-routed 
                                     to a Test port
                splitSrc&Dest    (6) Connection Source and Dest ports are
                                     re-routed to Test ports" 
           	      
        ::= { sysConnEntry 12 }
        
sysCmdStatus OBJECT-TYPE
        SYNTAX ConnCmdStatus
        MAX-ACCESS read-write
        STATUS current
        DESCRIPTION
           "The command status for this system connection row/record.
           The value used in a SET will be replaced by a response
           value in the GET RESPONSE indicating success or failure.
           		
                ready-for-command (0)
                    initial default status for a row           

            Action States used in SET Command (1..99)
                update (1)
                    change existing connection
                delete (2)
                    remove existing connection
                add (3)
                    add new connection 
                addNsave (4)
                    add new connection and save to file immediately
                updateNsave (5)
                    change existing connection and save to file 
                    immediately 
                deleteNsave (6)
                    delete existing connection and update map file 
                    immediately 
                            		
            Response States used in GET RESPONSE Command (100..199)
                update-successful (101)
                    connection has been successfully modified
                delete-successful (102)
                    connection has been successfully deleted
                add-successful (103)
                    connection has been successfully added
                add-save-successful (104)
                    connection has been successfully added & saved
                update-save-successful (105)
                    connection has been successfully modified & saved
                del-save-successful (106)
                    connection has been successfully removed & saved
                		
            Connection Error Codes used in GET RESPONSE Command (200..799)
                err-general-connection-error (400)
                    An unknown system connection error occurred
                err-src-broadcast-id-not-found (401)
                    Unable to find listener using this broadcast ID
                err-conn-name-in-use (404)
                    Connection name already exists
                err-src-port-bandwidth-exceeded (409)
                	Source port cannot support requested timeslots
                err-dest-port-bandwidth-exceeded (413)
                	Dest port cannot support requested timeslots
                err-invalid-command (414)
                    Unrecognized connection command-action
                err-not-enough-bts-available (415)
                    Not enough available timeslots on Backplane
                err-src-port-cannot-support-voice (416)
                    Device type in source slot does not support voice
                err-dest-port-cannot-support-voice (417)
                    Device type in dest slot does not support voice
                err-invalid-communications-for-device (418)
                    Only E1 devices support Au-law to Mu-law conversion 
                err-invalid-communications-type (419)
                    Unrecognized connection communications
                err-invalid-conn-name (420)
                    Invalid connection name length
                err-invalid-conn-speed (422)
                    Unrecognized connection speed code
                err-invalid-conn-record (423)
                    Connection record contains missing or invalid fields
                err-conn-not-saved-to-map(426)
                    Connection was changed but save to file failed
            	err-invalid-conn-bit-group (429)
                    Invalid bit-group selected for the globally set compression rate.
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big"        
        ::= { sysConnEntry 13 }

sysPrimaryState OBJECT-TYPE
        SYNTAX ConnectionState1	
        MAX-ACCESS read-only
        STATUS current
        DESCRIPTION
           "The Primary level state of this system connection.
 
                inSrvc	   (0) In Service
                outOfSrvc  (1) Not in Service"
        
        ::= { sysConnEntry 14 }
                  
sysSecondaryState OBJECT-TYPE
        SYNTAX ConnectionState2	
        MAX-ACCESS read-only
        STATUS current
        DESCRIPTION
           "The Secondary level state of this system connection.
 
                none	   (0) Default OOS state
                ok         (1) Operational
                underTest  (2) Under Test Mode"
        
        ::= { sysConnEntry 15 }

sysConnInstance OBJECT-TYPE
        SYNTAX Integer32
        MAX-ACCESS read-only
        STATUS current
        DESCRIPTION
            "This is the current instance number for this connection
            record.  Each time the connection is changed, the instance
            number will be changed."
        ::= { sysConnEntry 16 }
                  
sysConnChecksum OBJECT-TYPE
        SYNTAX UnsignedInt
        MAX-ACCESS read-only
        STATUS current
        DESCRIPTION
            "This is the checksum this connection record."
        ::= { sysConnEntry 17 }

sysSrcTsLineType OBJECT-TYPE
        SYNTAX DnxTsPortType	
        MAX-ACCESS read-only
        STATUS current
        DESCRIPTION
            "Determines the Source Port Timeslot Type used when
             building DNX Cross-Connections.
             
			    unknown        (0)  Not Available or unknown
			    e1             (1)  31 Ts available numbered 1..31 w/ Ts0 reserved
			    t1             (2)  24 Ts available numbered 1..24
			    high-speed     (3)  32 Ts available numbering not applicable
			    wan            (4)  32 Ts available numbered 0..31	
			    e1-cas         (5)  30 Ts available numbered 1..30 w/ Ts0 & Ts16 reserved
            	e1-clear-frm   (6)  32 Ts needed numbered 1..31 with Ts0 reserved
			    t1-clear-frm   (7)  25 Ts needed numbered 1..24 w/ Ts25 reserved
			    e1-clear-unfrm (8)  32 Ts needed numbered 0..31
			    t1-clear-unfrm (9)  25 Ts needed numbered 1..25
			    voice          (10) 1 Ts available numbering not applicable
			    ds0dp          (11) 1 Ts available numbering not applicable
			    ocu            (12) 1 Ts available numbering not applicable
			    tam            (13) 1 Ts available numbering not applicable			    
			    "        
        ::= { sysConnEntry 18 }
        
sysDestTsLineType OBJECT-TYPE
        SYNTAX DnxTsPortType	
        MAX-ACCESS read-only
        STATUS current
        DESCRIPTION
            "Determines the Dest Port Timeslot Type used when
             building DNX Cross-Connections.
             
			    unknown        (0)  Not Available or unknown
			    e1             (1)  31 Ts available numbered 1..31 w/ Ts0 reserved
			    t1             (2)  24 Ts available numbered 1..24
			    high-speed     (3)  32 Ts available numbering not applicable
			    wan            (4)  32 Ts available numbered 0..31	
			    e1-cas         (5)  30 Ts available numbered 1..30 w/ Ts0 & Ts16 reserved
            	e1-clear-frm   (6)  32 Ts needed numbered 1..31 with Ts0 reserved
			    t1-clear-frm   (7)  25 Ts needed numbered 1..24 w/ Ts25 reserved
			    e1-clear-unfrm (8)  32 Ts needed numbered 0..31
			    t1-clear-unfrm (9)  25 Ts needed numbered 1..25
			    voice          (10) 1 Ts available numbering not applicable
			    ds0dp          (11) 1 Ts available numbering not applicable
			    ocu            (12) 1 Ts available numbering not applicable
			    tam            (13) 1 Ts available numbering not applicable			    
			    "        
        ::= { sysConnEntry 19 }

sysSrcTrunkCProfile OBJECT-TYPE      
		SYNTAX DnxTrunkProfSelection
        MAX-ACCESS read-write
        STATUS current
        DESCRIPTION
            "This identifies the Trunk Conditioning Profile selection for the 
            source port."
        ::= { sysConnEntry 20 }
        
sysDestTrunkCProfile OBJECT-TYPE	  
		SYNTAX DnxTrunkProfSelection
        MAX-ACCESS read-write
        STATUS current
        DESCRIPTION
            "This identifies the Trunk Conditioning Profile selection for the 
            destination port."
        ::= { sysConnEntry 21 }
        
-- *************************************************************************
-- This table is the Active Map Connection table

actvConnTable OBJECT-TYPE
        SYNTAX SEQUENCE OF ActvConnEntry
        MAX-ACCESS not-accessible
        STATUS current
        DESCRIPTION
           "This is the Active Map Connection table which consists of connection 
           entries from the active configuration map.  There are 5 seperate
           connection maps but only one can be active at a time. The number of 
           entries in this table depends on the number of active connections 
           configured. Currently the maximum number of connections is 16224 for 
           a DNX88 system or 4056 for a DNX11 (if all connections are half-duplex
           using a single DS0). If connections require more bandwidth (multiple 
           DS0s or full-duplex), the system bandwidth will be exceeded before you 
           reach the above connection maximums."  
        ::= { connections 4 }

actvConnEntry OBJECT-TYPE
        SYNTAX ActvConnEntry
        MAX-ACCESS not-accessible
        STATUS  current
        DESCRIPTION
           "The conceptual row of the system Connection table.  A row in 
           this table can NOT be created.  A row in this table can be 
           modified by providing valid values for one or more writable 
           columns and by setting the value of actvCmdStatus to 'update'.
           A row in this table can be deleted by setting the value of 
           actvCmdStatus to 'delete'. The actvCmdStatus field must be 
           included as a variable in a SET PDU for the action to take 
           effect.  If the actvCmdStatus is missing from the SET PDU, the GET 
           RESPONSE will contain the SNMP error status of 'genErr' for and an 
           error index equal to the last variable."
        INDEX { actvMapID, actvConnID } 
               
        ::= { actvConnTable 1 }

ActvConnEntry ::=
        SEQUENCE {
                actvMapID              MapNumber,
                actvConnID             Integer32,
                actvConnName           DisplayString,      -- RW
                actvConnType           ConnectionType,
                actvSrcAddr            TimeSlotAddress,
                actvDestAddr           TimeSlotAddress,
                actvComm               CommunicationsType, -- RW
                actvConnSpeed          ConnectionSpeed,    -- RW
                actvSrcTsBitmap        Integer32,          -- RW
                actvDestTsBitmap       Integer32,          -- RW
                actvBroadSrcId         Integer32,
                actvTestMode           TestAccess,         -- obsolete
                actvCmdStatus          ConnCmdStatus,      -- RW
                actvPrimaryState       ConnectionState1,
                actvSecondaryState     ConnectionState2,
                actvConnInstance       Integer32,
                actvConnChecksum       UnsignedInt,
                actvSrcTsLineType      DnxTsPortType,
                actvDestTsLineType     DnxTsPortType,
                actvSrcTrunkCProfile   DnxTrunkProfSelection,
                actvDestTrunkCProfile  DnxTrunkProfSelection
                }

actvMapID OBJECT-TYPE
        SYNTAX MapNumber
        MAX-ACCESS read-only
        STATUS current
        DESCRIPTION
            "This number uniquely identifies the Active connection map."
        ::= { actvConnEntry 1 }

actvConnID OBJECT-TYPE
        SYNTAX Integer32 (0..16224)
        MAX-ACCESS read-only
        STATUS current
        DESCRIPTION
            "This number uniquely identifies an Active Map connection."
        ::= { actvConnEntry 2 }

actvConnName OBJECT-TYPE
        SYNTAX DisplayString (SIZE (1..19))
        MAX-ACCESS read-write
        STATUS current
        DESCRIPTION
            "This is the textual description of a connection within a given 
            configuration map.  The length can be from 1 to 20 characters."
        ::= { actvConnEntry 3 }
        
actvConnType OBJECT-TYPE
        SYNTAX ConnectionType
        MAX-ACCESS read-only
        STATUS current
        DESCRIPTION
           "The connection type for this system connection.
            fullDuplex          (0) Bi-directional connection from Source 
                                    port to Destination port and vice-versa.
            broadcastConnection (1) One directional connection from Source 
                                    to Dest ports.
            broadcastMaster     (2) Input connection from Source port to 
                                    backplane only.
            listenSrc           (3) Output connection from backplane to 
                                    Destination port. Must be configured to 
                                    'listen' to an active Source port. 
            listenDest          (4) Output connection from backplane to 
                                    Destination port. Must be configured to 
                                    'listen' to an active Dest port.
			vcmp				(8) Voice Compression - Applicable to DNX-1u supporting 
									Transcoder hardware. Provides cross-connect capability 
									between uncompressed source and compressed destination.
			subChannel			(9) Applicable to DNX-1u supporting Transcoder hardware.
									Connection allowing the user to map source's compressed
									bit group to the destination's bit group.
		    subRate            (10) Sub-rate level switching connection that must use 
		                            ConnectionSpeed of 32k and must specify if high nibble or
		                            low nibble timeslot bits are used for both Src and Dest."
		                                    
		::= { actvConnEntry 4 } 
  
actvSrcAddr OBJECT-TYPE
        SYNTAX TimeSlotAddress
        MAX-ACCESS read-only
        STATUS current
        DESCRIPTION
           "The source port timeslot address for this connection.
           The format is represented using an IP address syntax 
           (4 byte string).  Note that the maximum valid port 
           number and starting timeslot will vary depending on the
           specified carrier and framing options. For example, an
           octal T1/E1 device has 8 ports but the T1 link has 24
           timeslots while the E1 link has 32 timeslots.
            
           The 1st byte is reserved for future use
           The 2nd byte represents the source Slot Number (1-11)           
           The 3rd byte represents the source Port Number (1-84)           
           The 4th byte represents the source starting Timeslot (1-232) 
               normal connections use range 1..32
             For subRate connection types:  
               low nibble connections use range  101..132 
               high nibble connections use range 201..232
           "
        ::= { actvConnEntry 5 }

actvDestAddr OBJECT-TYPE
        SYNTAX TimeSlotAddress
        MAX-ACCESS read-only
        STATUS current
        DESCRIPTION
           "The destination port timeslot address for this connection.
           The format is represented using an IP address syntax 
           (4 byte string).  Note that the maximum valid port 
           number and starting timeslot will vary depending on the
           specified carrier and framing options. For example, an
           octal T1/E1 device has 8 ports but the T1 link has 24
           timeslots while the E1 link has 32 timeslots.
            
           The 1st byte is reserved for future use
           The 2nd byte represents the destination Slot Number (1-11)            
           The 3rd byte represents the destination Port Number (1-84)           
           The 4th byte represents the source starting Timeslot (1-232) 
               normal connections use range 1..32
             For subRate connection types:  
               low nibble connections use range  101..132 
               high nibble connections use range 201..232
           "
        ::= { actvConnEntry 6 }

actvComm OBJECT-TYPE
        SYNTAX CommunicationsType
        MAX-ACCESS read-write
        STATUS current
        DESCRIPTION
           "The type of communications utilized on this system connection.
                
                data		(0) Data only
                voice		(1) Voice only
                voiceAuToMu	(2) Voice with Au-law to Mu-law Conversion
                
            The Bit Group selections for a connection of the VCMP or subChannel 
            type. There are 2 4-bit groups at speed 32 Kbps and 4 2-bit groups 
            at speed 16 Kbps. They specify the position of the compressed 
            data within the selected DS0. Applicable to DNX-1u with Transcoder 
            Hardware.
                
       			comp16kBitGrp1-2(3) vcmp and subChannel only
				comp16kBitGrp3-4(4) vcmp and subChannel only
				comp16kBitGrp5-6(5) vcmp and subChannel only
				comp16kBitGrp7-8(6) vcmp and subChannel only
				comp32kBitGrp1-4(7) vcmp and subChannel only
				comp32kBitGrp5-8(8) vcmp and subChannel only
			"
        ::= { actvConnEntry 7 }
        
actvConnSpeed  OBJECT-TYPE
        SYNTAX ConnectionSpeed
        MAX-ACCESS read-write
        STATUS current
        DESCRIPTION
           "The data transmission speed in kilobytes per second (kbps) for 
           this connection.  The format is:
           -Speed in kbps-number of DS0-kbps per channel
                s48k (0)          - 48k (1 DS0)
                s56k (1)          - 56k (1 DS0)
                s64k (2)          - 64k (1 DS0)
                s112k-2x56 (3)    - 112k/56 (2 DS0s)
                s128k-2x64 (4)    - 128k/64 (2 DS0s)
                s168k-3x56 (5)    - 168k/56 (3 DS0s)
                s192k-3x64 (6)    - 192k/64 (3 DS0s)
                s224k-4x56 (7)    - 224k/56 (4 DS0s)
                s256k-4x64 (8)    - 256k/64 (4 DS0s)
                s280k-5x56 (9)    - 280k/56 (5 DS0s)
                s320k-5x64 (10)   - 320k/64 (5 DS0s)
                s336k-6x56 (11)   - 336k/56 (6 DS0s)
                s384k-6x64 (12)   - 384k/64 (6 DS0s)
                s392k-7x56 (13)   - 392k/56 (7 DS0s)
                s448k-7x64 (14)   - 448k/64 (7 DS0s)
                s448k-8x56 (15)   - 448k/56 (8 DS0s)
                s512k-8x64 (16)   - 512k/64 (8 DS0s)
                s504k-9x56 (17)   - 504k/56 (9 DS0s)
                s576k-9x64 (18)   - 576k/64 (9 DS0s)
                s560k-10x56 (19)  - 560k/56 (10 DS0s)
                s640k-10x64 (20)  - 640k/64 (10 DS0s)
                s616k-11x56 (21)  - 616k/56 (11 DS0s)
                s704k-11x64 (22)  - 704k/64 (11 DS0s)
                s672k-12x56 (23)  - 672k/56 (12 DS0s)
                s768k-12x64 (24)  - 768k/64 (12 DS0s)
                s728k-13x56 (25)  - 728k/56 (13 DS0s)
                s832k-13x64 (26)  - 832k/64 (13 DS0s)
                s784k-14x56 (27)  - 784k/56 (14 DS0s)
                s896k-14x64 (28)  - 896k/64 (14 DS0s)
                s840k-15x56 (29)  - 840k/56 (15 DS0s)
                s960k-15x64 (30)  - 960k/64 (15 DS0s)
                s896k-16x56 (31)  - 896k/56 (16 DS0s)
                s1024k-16x64 (32) - 1024k/64(16 DS0s)
                s952k-17x56 (33)  - 952k/56 (17 DS0s)
                s1088k-17x64 (34) - 1088k/64 (17 DS0s)
                s1008k-18x56 (35) - 1008k/56 (18 DS0s)
                s1152k-18x64 (36) - 1152k/64 (18 DS0s)
                s1064k-19x56 (37) - 1064k/56 (19 DS0s)
                s1216k-19x64 (38) - 1216k/64 (19 DS0s)
                s1120k-20x56 (39) - 1120k/56 (20 DS0s)
                s1280k-20x64 (40) - 1280k/64 (20 DS0s)
                s1176k-21x56 (41) - 1176k/56 (21 DS0s)
                s1344k-21x64 (42) - 1344k/64 (21 DS0s)
                s1232k-22x56 (43) - 1232k/56 (22 DS0s)
                s1408k-22x64 (44) - 1408k/64 (22 DS0s)
                s1288k-23x56 (45) - 1288k/56 (23 DS0s)
                s1472k-23x64 (46) - 1472k/64 (23 DS0s)
                s1344k-24x56 (47) - 1344k/56 (24 DS0s)
                s1536k-24x64 (48) - 1536k/64 (24 DS0s)
                s1400k-25x56 (49) - 1400k/56 (25 DS0s)
                s1600k-25x64 (50) - 1600k/64 (25 DS0s)
                s1456k-26x56 (51) - 1456k/56 (26 DS0s)
                s1664k-26x64 (52) - 1664k/64 (26 DS0s)
                s1512k-27x56 (53) - 1512k/56 (27 DS0s)
                s1728k-27x64 (54) - 1728k/64 (27 DS0s)
                s1568k-28x56 (55) - 1568k/56 (28 DS0s)
                s1792k-28x64 (56) - 1792k/64 (28 DS0s)
                s1624k-29x56 (57) - 1624k/56 (29 DS0s)
                s1856k-29x64 (58) - 1856k/64 (29 DS0s)
                s1680k-30x56 (59) - 1680k/56 (30 DS0s)
                s1920k-30x64 (60) - 1920k/64 (30 DS0s)
                s1736k-31x56 (61) - 1736k/56 (31 DS0s)
                s1984k-31x64 (62) - 1984k/64 (31 DS0s)
                s1792k-32x56 (63) - 1792k/56 (32 DS0s)
                s2048k-32x64 (64) - 2048k/64 (32 DS0s)
                clearT1-25x64(65) - Framed or Unframed 64k (25 DS0s)
                clearE1-32x64(66) - Framed or Unframed 64k (32 DS0s)
                s32k		 (67) - DNX-1u Transcoder/Sub-Rate supported speed
                s16k		 (68) - DNX-1u Transcoder supported speed
                "
				
        ::= { actvConnEntry 8 }
 
actvSrcTsBitmap OBJECT-TYPE
        SYNTAX Integer32
        MAX-ACCESS read-write
        STATUS current
        DESCRIPTION
           "This is a bit field used for the source port timeslots.
           Each bit represents a link timeslot on the source port.
           Setting the bit indicates that timeslot is used for the 
           connection. The number of timeslots utilized depends on the 
           connection speed."
        
        ::= { actvConnEntry 9 }
 
actvDestTsBitmap OBJECT-TYPE
        SYNTAX Integer32
        MAX-ACCESS read-write
        STATUS current
        DESCRIPTION
           "This is a bit field used for the destination port timeslots.
           Each bit represents a link timeslot on the destination port.
           Setting the bit indicates that timeslot is used for the 
           connection. The number of timeslots utilized depends on the 
           connection speed."
        
        ::= { actvConnEntry 10 }

actvBroadSrcId OBJECT-TYPE
        SYNTAX Integer32
        MAX-ACCESS read-only
        STATUS current
        DESCRIPTION
                "The connection ID number of the broadcast source connection 
                for a listener connection to read from."
        ::= { actvConnEntry 11 }

-- *************************************************************************
-- The Connection Test Mode is no longer applicable for Connection records 
-- and is not supported by the Agent as of Release 12.0
-- *************************************************************************
actvTestMode OBJECT-TYPE
        SYNTAX TestAccess
        MAX-ACCESS read-only
        STATUS obsolete
        DESCRIPTION
           "This indicates whether the current connection is in test
           mode, and if so, the type of test access being used.  
                none             (0) Connection has no active Tests
                monitorSrc       (1) Connection Source port is monitored 
                                     to a Test port
                monitorDest      (2) Connection Dest port is monitored 
                                     to a Test port
                monitorSrc&Dest  (3) Connection Source and Dest ports are
                                     monitored to Test ports
                splitSrc         (4) Connection Source port is re-routed 
                                     to a Test port
                splitDest        (5) Connection Dest port is re-routed 
                                     to a Test port
                splitSrc&Dest    (6) Connection Source and Dest ports are
                                     re-routed to Test ports" 
           	      
        ::= { actvConnEntry 12 }
        
actvCmdStatus OBJECT-TYPE
        SYNTAX ConnCmdStatus
        MAX-ACCESS read-write
        STATUS current
        DESCRIPTION
           "The command status for this system connection row/record.
           The value used in a SET will be replaced by a response
           value in the GET RESPONSE indicating success or failure.
           		
                ready-for-command (0)
                    initial default status for a row           

            Action States used in SET Command (1..99)
                update (1)
                    change existing connection
                delete (2)
                    remove existing connection
                add (3)
                    add new connection 
                addNsave (4)
                    add new connection and save to file immediately
                updateNsave (5)
                    change existing connection and save to file 
                    immediately 
                deleteNsave (6)
                    delete existing connection and update map file 
                    immediately 
                            		
            Response States used in GET RESPONSE Command (100..199)
                update-successful (101)
                    connection has been successfully modified
                delete-successful (102)
                    connection has been successfully deleted
                add-successful (103)
                    connection has been successfully added
                add-save-successful (104)
                    connection has been successfully added & saved
                update-save-successful (105)
                    connection has been successfully modified & saved
                del-save-successful (106)
                    connection has been successfully removed & saved
                		
            Connection Error Codes used in GET RESPONSE Command (200..799)
                err-general-connection-error (400)
                    An unknown system connection error occurred
                err-src-broadcast-id-not-found (401)
                    Unable to find listener using this broadcast ID
                err-conn-name-in-use (404)
                    Connection name already exists
                err-src-port-bandwidth-exceeded (409)
                	Source port cannot support requested timeslots
                err-dest-port-bandwidth-exceeded (413)
                	Dest port cannot support requested timeslots
                err-invalid-command (414)
                    Unrecognized connection command-action
                err-not-enough-bts-available (415)
                    Not enough available timeslots on Backplane
                err-src-port-cannot-support-voice (416)
                    Device type in source slot does not support voice
                err-dest-port-cannot-support-voice (417)
                    Device type in dest slot does not support voice
                err-invalid-communications-for-device (418)
                    Only E1 devices support Au-law to Mu-law conversion 
                err-invalid-communications-type (419)
                    Unrecognized connection communications
                err-invalid-conn-name (420)
                    Invalid connection name length
                err-invalid-conn-speed (422)
                    Unrecognized connection speed code
                err-invalid-conn-record (423)
                    Connection record contains missing or invalid fields
                err-conn-not-saved-to-map(426)
                    Connection was changed but save to file failed
                err-invalid-conn-bit-group (429)
                    Invalid bit-group selected for the globally set compression rate.
				err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big"         
        ::= { actvConnEntry 13 }

actvPrimaryState OBJECT-TYPE
        SYNTAX ConnectionState1	
        MAX-ACCESS read-only
        STATUS current
        DESCRIPTION
           "The Primary level state of this system connection.
 
                inSrvc	   (0) In Service
                outOfSrvc  (1) Not in Service"
        
        ::= { actvConnEntry 14 }
                  
actvSecondaryState OBJECT-TYPE
        SYNTAX ConnectionState2	
        MAX-ACCESS read-only
        STATUS current
        DESCRIPTION
           "The Secondary level state of this system connection.
 
                none	   (0) Default OOS state
                ok         (1) Operational
                underTest  (2) Under Test Mode"
        
        ::= { actvConnEntry 15 }
                  
actvConnInstance OBJECT-TYPE
        SYNTAX Integer32
        MAX-ACCESS read-only
        STATUS current
        DESCRIPTION
            "This is the current instance number for this connection
            record.  Each time the connection is changed, the instance
            number will be changed."
        ::= { actvConnEntry 16 }
                  
actvConnChecksum OBJECT-TYPE
        SYNTAX UnsignedInt
        MAX-ACCESS read-only
        STATUS current
        DESCRIPTION
            "This is the checksum this connection record."
        ::= { actvConnEntry 17 }

actvSrcTsLineType OBJECT-TYPE
        SYNTAX DnxTsPortType	
        MAX-ACCESS read-only
        STATUS current
        DESCRIPTION
            "Determines the Source Port Timeslot Type used when
             building DNX Cross-Connections.
             
			    unknown        (0)  Not Available or unknown
			    e1             (1)  31 Ts available numbered 1..31 w/ Ts0 reserved
			    t1             (2)  24 Ts available numbered 1..24
			    high-speed     (3)  32 Ts available numbering not applicable
			    wan            (4)  32 Ts available numbered 0..31	
			    e1-cas         (5)  30 Ts available numbered 1..30 w/ Ts0 & Ts16 reserved
            	e1-clear-frm   (6)  32 Ts needed numbered 1..31 with Ts0 reserved
			    t1-clear-frm   (7)  25 Ts needed numbered 1..24 w/ Ts25 reserved
			    e1-clear-unfrm (8)  32 Ts needed numbered 0..31
			    t1-clear-unfrm (9)  25 Ts needed numbered 1..25
			    voice          (10) 1 Ts available numbering not applicable
			    ds0dp          (11) 1 Ts available numbering not applicable
			    ocu            (12) 1 Ts available numbering not applicable
			    tam            (13) 1 Ts available numbering not applicable			    
			    "        
        ::= { actvConnEntry 18 }
        
actvDestTsLineType OBJECT-TYPE
        SYNTAX DnxTsPortType	
        MAX-ACCESS read-only
        STATUS current
        DESCRIPTION
            "Determines the Dest Port Timeslot Type used when
             building DNX Cross-Connections.
             
			    unknown        (0)  Not Available or unknown
			    e1             (1)  31 Ts available numbered 1..31 w/ Ts0 reserved
			    t1             (2)  24 Ts available numbered 1..24
			    high-speed     (3)  32 Ts available numbering not applicable
			    wan            (4)  32 Ts available numbered 0..31	
			    e1-cas         (5)  30 Ts available numbered 1..30 w/ Ts0 & Ts16 reserved
            	e1-clear-frm   (6)  32 Ts needed numbered 1..31 with Ts0 reserved
			    t1-clear-frm   (7)  25 Ts needed numbered 1..24 w/ Ts25 reserved
			    e1-clear-unfrm (8)  32 Ts needed numbered 0..31
			    t1-clear-unfrm (9)  25 Ts needed numbered 1..25
			    voice          (10) 1 Ts available numbering not applicable
			    ds0dp          (11) 1 Ts available numbering not applicable
			    ocu            (12) 1 Ts available numbering not applicable
			    tam            (13) 1 Ts available numbering not applicable			    
			    "        
        ::= { actvConnEntry 19 }   

actvSrcTrunkCProfile OBJECT-TYPE      
		SYNTAX DnxTrunkProfSelection
        MAX-ACCESS read-write
        STATUS current
        DESCRIPTION
            "This identifies the Trunk Conditioning Profile selection for the 
            source port."
        ::= { actvConnEntry 20 }
        
actvDestTrunkCProfile OBJECT-TYPE	  
		SYNTAX DnxTrunkProfSelection
        MAX-ACCESS read-write
        STATUS current
        DESCRIPTION
            "This identifies the Trunk Conditioning Profile selection for the 
            destination port."
        ::= { actvConnEntry 21 }
        
-- *************************************************************************
-- This is the Add Connection record Group
--
-- This group of records consists of a blank System Connection entry and
-- should be primary used in a Set Request with multiple variables containing
-- the required fields in a connection. The purpose of this group is to add new 
-- connections to any one of the 5 connection maps.  By providing valid values 
-- for the source address, destination address, speed, type, and timeslot bitmaps 
-- and by also setting the value of addCmdStatus to 'create', a row will be added 
-- to the System Connection Table and if applicable, a row will be added to the 
-- Active Connection Table.  An 'GenErr' error status will be returned in 
-- the Response if the addCmdStatus is missing from the Set Request.  A 'badValue' 
-- error status will be returned in the Response if not all required fields are 
-- included in the Set Request or if one or more fields contain invalid values. 
-- *************************************************************************

addConnRecord OBJECT IDENTIFIER ::= { connections 5 }

addMapID OBJECT-TYPE
        SYNTAX MapNumber
        MAX-ACCESS read-write
        STATUS current
        DESCRIPTION
            "This number identifies the connection map where 
            the new Connection is to be added. A value of zero will
            cause the system to add the connection to the current
            active map."
        ::= { addConnRecord 1 }

addConnID OBJECT-TYPE
        SYNTAX Integer32 (0..16224)
        MAX-ACCESS read-write
        STATUS current
        DESCRIPTION
            "This number defaults to connection ID zero, which if used in
            a SET PDU, notifies the system to find and use the next available
            Connection ID.  If this number is SET to a non-zero value, the
            system will attempt to use that number for the Connection ID of
            the new Connection being added. If the ID is already in use with
            different Connection parameters, an error in the CmdStatus will be 
            returned."
        ::= { addConnRecord 2 }

addConnName OBJECT-TYPE
        SYNTAX DisplayString (SIZE (1..19))
        MAX-ACCESS read-write
        STATUS current
        DESCRIPTION
            "This is the textual description of a connection within a given 
            configuration map.  This name is optional and will be generated
            by the system if not provided in the SET PDU."
        ::= { addConnRecord 3 }
        
addConnType OBJECT-TYPE
        SYNTAX ConnectionType
        MAX-ACCESS read-write
        STATUS current
        DESCRIPTION
           "The connection type for this system connection.
	        fullDuplex          (0) Bi-directional connection from Source 
                                    port to Destination port and vice-versa.
            broadcastConnection (1) One directional connection from Source 
                                    to Dest ports.
            broadcastMaster     (2) Input connection from Source port to 
                                    backplane only.
            listenSrc           (3) Output connection from backplane to 
                                    Destination port. Must be configured to 
                                    'listen' to an active Source port. 
            listenDest          (4) Output connection from backplane to 
                                    Destination port. Must be configured to 
                                    'listen' to an active Dest port.
            listenerConnection  (7) Creates listenSrc or listenDest by providing
                                    addSrcAddr rather than addBroadSrcId.
			vcmp				(8) Voice Compression - Applicable to DNX-1u supporting 
									Transcoder hardware. Provides cross-connect capability 
									between uncompressed source and compressed destination.
			subChannel			(9) Applicable to DNX-1u supporting Transcoder hardware.
									Connection allowing the user to map source's compressed
									bit group to the destination's bit group.
		    subRate            (10) Sub-rate level switching connection that must use 
		                            ConnectionSpeed of 32k and must specify if high nibble or
		                            low nibble timeslot bits are used for both Src and Dest."
		::= { addConnRecord 4 } 
  
addSrcAddr OBJECT-TYPE
        SYNTAX TimeSlotAddress
        MAX-ACCESS read-write
        STATUS current
        DESCRIPTION
           "The source port timeslot address for this new connection.
           The format is represented using an IP address syntax 
           (4 byte string).  Note that the maximum valid port 
           number and starting timeslot will vary depending on the
           specified carrier and framing options. For example, an
           octal T1/E1 device has 8 ports but the T1 link has 24
           timeslots while the E1 link has 32 timeslots.
            
           The 1st byte is reserved for future use
           The 2nd byte represents the source Slot Number (1-11)           
           The 3rd byte represents the source Port Number (1-84)           
           The 4th byte represents the source starting Timeslot (1-232) 
               normal connections use range 1..32
             For subRate connection types:  
               low nibble connections use range  101..132 
               high nibble connections use range 201..232
           "
        ::= { addConnRecord 5 }

addDestAddr OBJECT-TYPE
        SYNTAX TimeSlotAddress
        MAX-ACCESS read-write
        STATUS current
        DESCRIPTION
           "The destination port timeslot address for this new connection.
           The format is represented using an IP address syntax 
           (4 byte string).  Note that the maximum valid port 
           number and starting timeslot will vary depending on the
           specified carrier and framing options. For example, an
           octal T1/E1 device has 8 ports but the T1 link has 24
           timeslots while the E1 link has 32 timeslots.
            
           The 1st byte is reserved for future use            
           The 2nd byte represents the destination Slot Number (1-11)          
           The 3rd byte represents the destination Port Number (1-84)          
           The 4th byte represents the source starting Timeslot (1-232) 
               normal connections use range 1..32
             For subRate connection types:  
               low nibble connections use range  101..132 
               high nibble connections use range 201..232
           "
        ::= { addConnRecord 6 }

addComm	OBJECT-TYPE
        SYNTAX CommunicationsType
        MAX-ACCESS read-write
        STATUS current
        DESCRIPTION
           "The type of communications utilized on this system connection.
                
                data		(0) Data only
                voice		(1) Voice only
                voiceAuToMu	(2) Voice with Au-law to Mu-law Conversion
                
            The Bit Group selections for a connection of the VCMP or subChannel 
            type. There are 2 4-bit groups at speed 32 Kbps and 4 2-bit groups 
            at speed 16 Kbps. They specify the position of the compressed 
            data within the selected DS0. Applicable to DNX-1u with Transcoder 
            Hardware.
                
       			comp16kBitGrp1-2(3) vcmp and subChannel only
				comp16kBitGrp3-4(4) vcmp and subChannel only
				comp16kBitGrp5-6(5) vcmp and subChannel only
				comp16kBitGrp7-8(6) vcmp and subChannel only
				comp32kBitGrp1-4(7) vcmp and subChannel only
				comp32kBitGrp5-8(8) vcmp and subChannel only
			"
        ::= { addConnRecord 7 }
        
addConnSpeed  OBJECT-TYPE
		SYNTAX ConnectionSpeed
        MAX-ACCESS read-write
        STATUS current
        DESCRIPTION
           "The data transmission speed in kilobytes per second (kbps) for 
           this connection.  The format is:
           -Speed in kbps-number of DS0-kbps per channel
                s48k (0)          - 48k (1 DS0)
                s56k (1)          - 56k (1 DS0)
                s64k (2)          - 64k (1 DS0)
                s112k-2x56 (3)    - 112k/56 (2 DS0s)
                s128k-2x64 (4)    - 128k/64 (2 DS0s)
                s168k-3x56 (5)    - 168k/56 (3 DS0s)
                s192k-3x64 (6)    - 192k/64 (3 DS0s)
                s224k-4x56 (7)    - 224k/56 (4 DS0s)
                s256k-4x64 (8)    - 256k/64 (4 DS0s)
                s280k-5x56 (9)    - 280k/56 (5 DS0s)
                s320k-5x64 (10)   - 320k/64 (5 DS0s)
                s336k-6x56 (11)   - 336k/56 (6 DS0s)
                s384k-6x64 (12)   - 384k/64 (6 DS0s)
                s392k-7x56 (13)   - 392k/56 (7 DS0s)
                s448k-7x64 (14)   - 448k/64 (7 DS0s)
                s448k-8x56 (15)   - 448k/56 (8 DS0s)
                s512k-8x64 (16)   - 512k/64 (8 DS0s)
                s504k-9x56 (17)   - 504k/56 (9 DS0s)
                s576k-9x64 (18)   - 576k/64 (9 DS0s)
                s560k-10x56 (19)  - 560k/56 (10 DS0s)
                s640k-10x64 (20)  - 640k/64 (10 DS0s)
                s616k-11x56 (21)  - 616k/56 (11 DS0s)
                s704k-11x64 (22)  - 704k/64 (11 DS0s)
                s672k-12x56 (23)  - 672k/56 (12 DS0s)
                s768k-12x64 (24)  - 768k/64 (12 DS0s)
                s728k-13x56 (25)  - 728k/56 (13 DS0s)
                s832k-13x64 (26)  - 832k/64 (13 DS0s)
                s784k-14x56 (27)  - 784k/56 (14 DS0s)
                s896k-14x64 (28)  - 896k/64 (14 DS0s)
                s840k-15x56 (29)  - 840k/56 (15 DS0s)
                s960k-15x64 (30)  - 960k/64 (15 DS0s)
                s896k-16x56 (31)  - 896k/56 (16 DS0s)
                s1024k-16x64 (32) - 1024k/64(16 DS0s)
                s952k-17x56 (33)  - 952k/56 (17 DS0s)
                s1088k-17x64 (34) - 1088k/64 (17 DS0s)
                s1008k-18x56 (35) - 1008k/56 (18 DS0s)
                s1152k-18x64 (36) - 1152k/64 (18 DS0s)
                s1064k-19x56 (37) - 1064k/56 (19 DS0s)
                s1216k-19x64 (38) - 1216k/64 (19 DS0s)
                s1120k-20x56 (39) - 1120k/56 (20 DS0s)
                s1280k-20x64 (40) - 1280k/64 (20 DS0s)
                s1176k-21x56 (41) - 1176k/56 (21 DS0s)
                s1344k-21x64 (42) - 1344k/64 (21 DS0s)
                s1232k-22x56 (43) - 1232k/56 (22 DS0s)
                s1408k-22x64 (44) - 1408k/64 (22 DS0s)
                s1288k-23x56 (45) - 1288k/56 (23 DS0s)
                s1472k-23x64 (46) - 1472k/64 (23 DS0s)
                s1344k-24x56 (47) - 1344k/56 (24 DS0s)
                s1536k-24x64 (48) - 1536k/64 (24 DS0s)
                s1400k-25x56 (49) - 1400k/56 (25 DS0s)
                s1600k-25x64 (50) - 1600k/64 (25 DS0s)
                s1456k-26x56 (51) - 1456k/56 (26 DS0s)
                s1664k-26x64 (52) - 1664k/64 (26 DS0s)
                s1512k-27x56 (53) - 1512k/56 (27 DS0s)
                s1728k-27x64 (54) - 1728k/64 (27 DS0s)
                s1568k-28x56 (55) - 1568k/56 (28 DS0s)
                s1792k-28x64 (56) - 1792k/64 (28 DS0s)
                s1624k-29x56 (57) - 1624k/56 (29 DS0s)
                s1856k-29x64 (58) - 1856k/64 (29 DS0s)
                s1680k-30x56 (59) - 1680k/56 (30 DS0s)
                s1920k-30x64 (60) - 1920k/64 (30 DS0s)
                s1736k-31x56 (61) - 1736k/56 (31 DS0s)
                s1984k-31x64 (62) - 1984k/64 (31 DS0s)
                s1792k-32x56 (63) - 1792k/56 (32 DS0s)
                s2048k-32x64 (64) - 2048k/64 (32 DS0s)
                clearT1-25x64(65) - Framed or Unframed 64k (25 DS0s)
                clearE1-32x64(66) - Framed or Unframed 64k (32 DS0s)
                s32k		 (67) - DNX-1u Transcoder/Sub-Rate supported speed
                s16k		 (68) - DNX-1u Transcoder supported speed
                "
				
		::= { addConnRecord 8 }

addSrcTsBitmap OBJECT-TYPE
        SYNTAX Integer32
        MAX-ACCESS read-write
        STATUS current
        DESCRIPTION
           "This is a bit field used for the source port timeslots.
           Each bit represents a link timeslot on the source port.
           Setting the bit indicates that timeslot is used for the 
           connection. The number of timeslots utilized depends on the 
           connection speed."        
        ::= { addConnRecord 9 }
 
addDestTsBitmap OBJECT-TYPE
        SYNTAX Integer32
        MAX-ACCESS read-write
        STATUS current
        DESCRIPTION
           "This is a bit field used for the destination port timeslots.
           Each bit represents a link timeslot on the destination port.
           Setting the bit indicates that timeslot is used for the 
           connection. The number of timeslots utilized depends on the 
           connection speed."       
        ::= { addConnRecord 10 }

addBroadSrcId OBJECT-TYPE
        SYNTAX Integer32 (0..16224)
        MAX-ACCESS read-write
        STATUS current
        DESCRIPTION
            "The connection ID number of the broadcast source connection 
            for a listener connection to read from."
        ::= { addConnRecord 11 }

addTestMode OBJECT-TYPE
        SYNTAX TestAccess
        MAX-ACCESS read-only
        STATUS current
        DESCRIPTION
           "This indicates whether the current connection is in test
           mode, and if so, the type of test access being used.  
                none             (0) Connection has no active Tests
                monitorSrc       (1) Connection Source port is monitored 
                                     to a Test port
                monitorDest      (2) Connection Dest port is monitored 
                                     to a Test port
                monitorSrc&Dest  (3) Connection Source and Dest ports are
                                     monitored to Test ports
                splitSrc         (4) Connection Source port is re-routed 
                                     to a Test port
                splitDest        (5) Connection Dest port is re-routed 
                                     to a Test port
                splitSrc&Dest    (6) Connection Source and Dest ports are
                                     re-routed to Test ports" 
           	      
        ::= { addConnRecord 12 }
        
addCmdStatus OBJECT-TYPE
        SYNTAX ConnCmdStatus
        MAX-ACCESS read-write
        STATUS current
        DESCRIPTION
           "The command status for this system connection row/record.
           The value used in a SET will be replaced by a response
           value in the GET RESPONSE indicating success or failure.
        		
                    ready-for-command (0)
                        initial default status for a row
				        
            Action States used in SET Command (1..99)
                    delete (2)
                        remove existing connection
                    create (3)
                        add new connection 
                    createNsave (4)
                    	add new connection and save to file immediately
                    deleteNsave (6)
                        delete existing connection and update map file 
                        immediately 
                            		
            Response States used in GET RESPONSE Command (100..199)
                    delete-successful (102)
                        connection has been successfully deleted
                    add-successful (103)
                        connection has been successfully added
                    add-save-successful (104)
                        connection has been successfully added & saved
                    del-save-successful (106)
                        connection has been successfully removed & saved
            
            Connection Error Codes used in GET RESPONSE Command (200..799)
                    err-general-connection-error (400)
                        An unknown system connection error occurred
                    err-src-broadcast-id-not-found (401)
                        Unable to find listener using this broadcast ID
                    err-src-port-in-use (402)
                        Source port cannot support multiple connections
                    err-dest-port-in-use (403)
                        Dest port cannot support multiple connections
                    err-conn-name-in-use (404)
                        Connection name already exists
                    err-invalid-broadcast-id (405)
                        Broadcast connection id out of valid range
                    err-invalid-src-slot (406)
                        Source slot number out of valid range
                    err-invalid-src-port (407)
                        Source port number out of valid range
                    err-invalid-src-timeslot (408)
                        Source timeslot number out of valid range
                    err-src-port-bandwidth-exceeded (409)
                        Source port cannot support requested timeslots
                    err-invalid-dest-slot (410)
                        Destination slot number out of valid range
                    err-invalid-dest-port (411)
                        Destination port number out of valid range
                    err-invalid-dest-timeslot (412)
                        Destination timeslot number out of valid range
                    err-dest-port-bandwidth-exceeded (413)
                	    Dest port cannot support requested timeslots
                    err-invalid-command (414)
                        Unrecognized connection command-action
                    err-not-enough-bts-available (415)
                        Not enough available timeslots on Backplane
                    err-src-port-cannot-support-voice (416)
                        Device type in source slot does not support voice
                    err-dest-port-cannot-support-voice (417)
                        Device type in dest slot does not support voice
                    err-invalid-communications-for-device (418)
                        Only E1 devices support Au-law to Mu-law conversion 
                    err-invalid-communications-type (419)
                        Unrecognized connection communications
                    err-invalid-conn-name (420)
                        Invalid connection name length
                    err-invalid-conn-type (421)
                        Unrecognized connection type
               	    err-invalid-conn-speed (422)
               	        Unrecognized connection speed code
                    err-invalid-conn-record (423)
                        Connection record contains missing or invalid fields
                    err-invalid-conn-id(425)
                        Connection Id out of range or already in use.            
                    err-conn-not-saved-to-map(426)
                        Connection was added but save to file failed
                    err-connection-map-full (427)
                        No connections available for the map
            		err-invalid-card-type (428)
						Invalid card type used for making the connection.
					err-invalid-conn-bit-group (429)
                    	Invalid bit-group selected for the globally set compression rate.
					err-conn-max-channels-used (430)
                    	All compression channels are in use
                    err-src-xlink-slot-not-assigned(431)
                        STM1X/OC3X virtual nest nbr undefined for src slot
                    err-dest-xlink-slot-not-assigned(432)
                        STM1X/OC3X virtual nest nbr undefined for dest slot
                    err-data-locked-by-another-user (450)
                        Another administrative user is making changes to this
                        part of the system via a terminal session. Check Event
                        Log for user name
                    err-snmp-parse-failed (500)
                        Agent could not parse variable
                    err-invalid-snmp-type (501)
                        Variable ASN type does not match Agent defined type 
                    err-invalid-snmp-var-size (502)
                        Variable size is too big"         
        ::= { addConnRecord 13 } 

addSrcTrunkCProfile OBJECT-TYPE      
		SYNTAX DnxTrunkProfSelection
        MAX-ACCESS read-write
        STATUS current
        DESCRIPTION
            "This identifies the hex value used for the start of signaling.
            The valid values are in hex format 0 through f."
        ::= { addConnRecord 14 }
        
addDestTrunkCProfile OBJECT-TYPE	  
		SYNTAX DnxTrunkProfSelection
        MAX-ACCESS read-write
        STATUS current
        DESCRIPTION
            "This identifies the hex value used for the end of signaling.
            The valid values are in hex format 0 through f."
        ::= { addConnRecord 15 }

-- *************************************************************************
-- This table is the Trunk Conditioning Profile table

trunkCProfileTable OBJECT-TYPE
        SYNTAX SEQUENCE OF TrunkCProfileEntry
        MAX-ACCESS not-accessible
        STATUS current
        DESCRIPTION
           "This is the Trunk Conditioning Profile table which consists of  
           16 entries of configured signaling data profiles. "  
        ::= { connections 6 }

trunkCProfileEntry OBJECT-TYPE
        SYNTAX TrunkCProfileEntry
        MAX-ACCESS not-accessible
        STATUS  current
        DESCRIPTION
           "The conceptual row of the Trunk Conditioning Profile table.  A 
           row in this table can NOT be created.  A row in this table can be 
           modified by providing valid values for one or more writable 
           columns and by setting the value of trunkCmdStatus to 'update'.  
           The trunkCmdStatus field must be included as a variable in a SET 
           PDU for the action to take effect. If the trunkCmdStatus is missing 
           from the SET PDU, the GET RESPONSE will contain the SNMP error 
           status of 'genErr' and an error index equal to the last 
           variable."
        INDEX { trunkProfileID }        
        ::= { trunkCProfileTable 1 }

TrunkCProfileEntry ::=
        SEQUENCE {
                trunkProfileID         	Integer32,   
                trunkSignalStart		OCTET STRING,
                trunkSignalEnd			OCTET STRING, 
                trunkData				OCTET STRING,
                trunkCmdStatus         	INTEGER      -- RW
                }
                                
trunkProfileID OBJECT-TYPE
        SYNTAX Integer32 (1..16)
        MAX-ACCESS read-only
        STATUS current
        DESCRIPTION
            "This number uniquely identifies a Trunk Conditioning Profile."
        ::= { trunkCProfileEntry 1 }
        
trunkSignalStart OBJECT-TYPE
        SYNTAX OCTET STRING (SIZE(1))
        MAX-ACCESS read-write
        STATUS current
        DESCRIPTION
            "Identifies the hex value used for the start of signaling. The valid
            values are 0 through f in Hex format."
        ::= { trunkCProfileEntry 2 }       
        
trunkSignalEnd OBJECT-TYPE
        SYNTAX OCTET STRING (SIZE(1))
        MAX-ACCESS read-write
        STATUS current
        DESCRIPTION
            "Identifies the hex value used for the end of signaling.The valid
            values are 0 through f in Hex format."
        ::= { trunkCProfileEntry 3 }       

trunkData OBJECT-TYPE
        SYNTAX OCTET STRING (SIZE(1))
        MAX-ACCESS read-write
        STATUS current
        DESCRIPTION
            "Identifies the hex value used for the data.The valid
            values are 0 through ff in Hex format."
        ::= { trunkCProfileEntry 4 }       

trunkCmdStatus OBJECT-TYPE
        SYNTAX INTEGER {
    -- Initial default status for a row
            ready-for-command (0),
    -- Trunk Conditioning Profile Commands used in SET Command (1..99)
            update (1),                		
    -- Response States used in GET RESPONSE Command (100..199)
            update-successful (101),
                            		
    -- Trunk Conditioning Profile Error Codes used in GET RESPONSE Command (200..799)
            err-general-trunk-error (200),
            err-invalid-command (208),
            err-general-config-error (400),
            err-invalid-trunk-value (404),
            err-data-locked-by-another-user (450),
            err-snmp-parse-failed (500),
            err-invalid-snmp-type (501),
            err-invalid-snmp-var-size (502)
            }                
        MAX-ACCESS read-write
        STATUS current
        DESCRIPTION
           "The command status for this configuration row/record.
           The value used in a SET will be replaced by a response
           value in the GET RESPONSE indicating success or failure.
           		
            Default Response State used in GET RESPONSE Command
                ready-for-command (0)
                    initial default status for a row           
                    
            Trunk Conditioning Profile Commands used in SET Command (1..99)            
                update (1),
                    Change existing Trunk Conditioning Profile Configuration
               		
            Response States used in GET RESPONSE Command (100..199)
                update-successful (101)
                    Trunk Conditioning data/value has been successfully changed
                                		
            Trunk Conditioning Profile Config Error Codes used in GET RESPONSE 
            Command (200..799)
                err-general-trunk-error (200)
                    Unknown Trunk Conditioning Profile Error occurred
                err-invalid-command (208)
                    Unrecognized voltage channel command-action
                err-general-config-error (400)
                    Unknown configuration error occurred                
                err-invalid-trunk-limit (404)
                    Invalid upper or lower boundary limit
                err-data-locked-by-another-user (450)
                    Another administrative user is making changes to this
                    part of the system via a terminal session. Check Event
                    Log for user name.
                err-snmp-parse-failed (500)
                    Agent could not parse variable
                err-invalid-snmp-type (501)
                    Variable ASN type does not match Agent defined type 
                err-invalid-snmp-var-size (502)
                    Variable size is too big"                 		
        ::= { trunkCProfileEntry 5 }       

-- *************************************************************************
--      This section is for the system Utilities.
-- *************************************************************************
utilities     OBJECT IDENTIFIER 	::= { sysMgr 12 }

database      OBJECT IDENTIFIER 	::= { utilities 1 }

dbBackup      OBJECT IDENTIFIER 	::= { database 1 }

-- *************************************************************************
--   This section is for the Automatic Database Backup Configuration.
-- *************************************************************************
dbAutoBackup OBJECT-TYPE
        SYNTAX DecisionType
        MAX-ACCESS read-write
        STATUS current
        DESCRIPTION
            "Enables or disables the Automatic Backup utility."
        ::= { dbBackup 1 }

dbBackupOccurrence OBJECT-TYPE
        SYNTAX INTEGER {
                weekly (0),
                daily (1)
                }
        MAX-ACCESS read-write
        STATUS current
        DESCRIPTION
            "The frequency mode of the DB backup schedule."
        ::= { dbBackup 2 }

dbBackupDayOfWeek OBJECT-TYPE
        SYNTAX INTEGER {
     		monday (1),
       		tuesday (2),
       		wednesday (3),
       		thursday (4),
       		friday (5),
       		saturday (6),
       		sunday (7)
       		}
        MAX-ACCESS read-write
        STATUS current
        DESCRIPTION
                "The day of the week for weekly backups to execute.
                If the dbBackupOccurance is set to 'daily', this field
                is ignored by the Backup utility."
        ::= { dbBackup 3 }

dbBackupHour OBJECT-TYPE
        SYNTAX Integer32 (0..23)
        MAX-ACCESS read-write
        STATUS current
        DESCRIPTION
                "The configured hour for backups to execute.
                Hours should be entered using 24 hour format."
        ::= { dbBackup 4 }
        
dbBackupMin OBJECT-TYPE
        SYNTAX Integer32 (0..59)
        MAX-ACCESS read-write
        STATUS current
        DESCRIPTION
                "The configured minute for backups to execute."
        ::= { dbBackup 5 }

-- *************************************************************************
--   This section is for the Database Remote Host Save and Restore utility.
-- *************************************************************************

dbRemoteHostTable OBJECT-TYPE
        SYNTAX SEQUENCE OF DbRemoteHostTableEntry
        MAX-ACCESS not-accessible
        STATUS current
        DESCRIPTION
            "This is the Database Backup & Restore Remote Host table which 
            consists of an entry for each of the 3 supported DB backup Host 
            locations. Changes to the dbRemoteHostTable must be made
            on a record or row by row basis.  This means that any use of the 
            Set command on writable fields must include the dbHostCmdStatus
            field with a value of 'update' or 'clear' as the last 
            variable in the SET PDU."
        ::= { dbBackup 10 }

dbRemoteHostTableEntry OBJECT-TYPE
        SYNTAX DbRemoteHostTableEntry
        MAX-ACCESS not-accessible
        STATUS current
        DESCRIPTION
            "The conceptual row of the Database Backup & Restore Remote Host table. 
            A row in this table can not be created or deleted.  A row in this table 
            can be modified using the dbHostCmdStatus field with the value of 'update'
            in the SET PDU along with one or more valid values for the Remote Host
            location fields. The dbHostCmdStatus field must be included as a 
            variable in a SET PDU for the action to take effect. If the 
            dbHostCmdStatus is missing from the SET PDU, the GET RESPONSE will 
            contain the SNMP error status of 'genErr' for and an error index equal 
            to the last variable."
        INDEX { dbHostIndex }
        ::= { dbRemoteHostTable 1 }

DbRemoteHostTableEntry ::=
        SEQUENCE {
                dbHostIndex         Integer32, 		
                dbHostIp            IpAddress,
                dbHostDirectory     DisplayString,
                dbHostFilename      DisplayString,  
                dbHostCmdStatus     INTEGER         
                }

dbHostIndex OBJECT-TYPE
        SYNTAX Integer32 (1..3)
        MAX-ACCESS read-only
        STATUS current
        DESCRIPTION
                "The remote Host index number."
        ::= { dbRemoteHostTableEntry 1 }

dbHostIp OBJECT-TYPE
        SYNTAX IpAddress
        MAX-ACCESS read-write
        STATUS current
        DESCRIPTION
                "The IP Address of the remote host where the backup file
                will be saved or restored from."
        ::= { dbRemoteHostTableEntry 2 }

dbHostDirectory OBJECT-TYPE
        SYNTAX DisplayString(SIZE(0..45))
        MAX-ACCESS read-write
        STATUS current
        DESCRIPTION
                "The directory path of the backup file on the remote host."
        ::= { dbRemoteHostTableEntry 3 }
        
dbHostFilename OBJECT-TYPE
        SYNTAX DisplayString(SIZE(0..8))
        MAX-ACCESS read-write
        STATUS current
        DESCRIPTION
                "The filename of the backup file on the remote host."
        ::= { dbRemoteHostTableEntry 4 }

dbHostCmdStatus OBJECT-TYPE
  	    SYNTAX INTEGER {
    -- Initial default status for a row
            ready-for-command (0),
    -- Host Commands used in SET Command (1..99)
            update-host (1),
            clear-host (2),
            saveDB (8),
            saveDBToAll (9),
            restoreDB (11),
                		
    -- Response States used in GET RESPONSE Command (100..199)
            command-in-progress (100),
            update-successful (101),
            clear-successful (102),
            save-successful (108),
            save-all-successful (109),
            restore-successful (111),
                		
    -- Host Config Error Codes used in GET RESPONSE Command (200..799)
            err-general-host-config-error (200),
            err-invalid-host-command (201),
            err-invalid-host-addr (202),
            err-invalid-host-name (203),
            err-invalid-host-dir (204),
            err-backup-file-creation-failed (210),
            err-backup-file-transfer-failed (211),
            err-data-locked-by-another-user (450),
            err-snmp-parse-failed (500),
            err-invalid-snmp-type (501),
            err-invalid-snmp-var-size (502)
            }
        MAX-ACCESS read-write
        STATUS current
        DESCRIPTION
           "The command status for this remote host configuration 
           row/record. The value used in a SET will be replaced by a 
           response value in the GET RESPONSE indicating success or failure.
           		
            Default Response State used in GET RESPONSE Command
                ready-for-command (0)
                    initial default status for a row           
                    
            Host Commands used in SET Command (1..99)

                update-host (1)
                    Update the host addr, dir, and/or host name.
                clear-host (2)
                    Clear all host info for the host entry.
                save-db (8)                    
                    Save the DNX Configuration Database file to this host.
                saveDBToAll (9)
                    Save the DNX Configuration Database file to all hosts.
                restore-db (11)
                    Restore the DNX Configuration Database file from this host
                    Upon restoring the file, the SMC/XNM card will reset itself
                    and SNMP communication will be temporarily lost until either
                    a Standby SMC/XNM takes over or until the restored system 
                    manager comes back online.
                		
            Response States used in GET RESPONSE Command (100..199)
                command-in-progress (100)
                    host command is still working
                update-successful (101)
                    host data has been successfully changed
                clear-successful (102)
                    remote host data has been successfully removed
                save-successful (108)
                    Database has been successfully saved
                save-all-successful (109)
                    Database has been successfully saved to all hosts
                restore-successful (111)
                    Database has been successfully restored, system will reset!
                		
            Host Config Error Codes used in GET RESPONSE Command (200..799)
                err-general-host-config-error (200)
                    Unknown remote host configuration error occurred
                err-invalid-host-command (201)
                    Unrecognized host command request
                err-invalid-host-addr (202)
                    Invalid IP address values
                err-invalid-host-name (203)
                    Configured host file name too long
                err-invalid-host-dir (204)
                    Configured host directory name too long
                err-backup-file-creation-failed (210)
                    Couldn't Create Backup File, Operation Aborted
                err-backup-file-transfer-failed (211)
                    Couldn't TFTP Backup File to/from host                    
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
        ::= { dbRemoteHostTableEntry 5 }


-- *************************************************************************
--   This is the Trap Definitions section for the SMC MIB. 
-- *************************************************************************

trapSequence OBJECT-TYPE
        SYNTAX Counter32
        MAX-ACCESS read-only
        STATUS current
        DESCRIPTION
                "A number used to identify the last generated trap 
                 message.  This is also included in each Trap PDU
                 to help allow the NMS to realize if a trap has 
                 been missed."
        ::= { traps 1}

-- *************************************************************************
-- The following variables are not accessible from the MIB tree since they
-- no longer apply to all Traps, only the Sequence number above is applicable
-- to all traps.  These variables are still included in each Alarm Trap PDU
-- and eventually this information may be placed in a Table to allow the NMS
-- to poll for a list of the last 'n' traps sent.
-- *************************************************************************

trapResourceKey OBJECT-TYPE
        SYNTAX Integer32
        MAX-ACCESS accessible-for-notify
        STATUS current
        DESCRIPTION
                "This is a number that uniquely identifies a system
                 resource. Much in the line of ifIndex. "
        ::= { traps 2}

trapTime OBJECT-TYPE
        SYNTAX DisplayString
        MAX-ACCESS accessible-for-notify
        STATUS current
        DESCRIPTION
                "The time as (HH:MM:SS MM/DD/YY)"
        ::= { traps 3}

trapResourceAddress OBJECT-TYPE
        SYNTAX DisplayString
        MAX-ACCESS accessible-for-notify
        STATUS current
        DESCRIPTION
                "This is the address of the ultimate source of the trap."
        ::= { traps 4}

trapResourceType OBJECT-TYPE
        SYNTAX DnxResourceType
        MAX-ACCESS accessible-for-notify
        STATUS current
        DESCRIPTION
                "This identifies what the trapAddress is the address of."
        ::= { traps 5}

trapType OBJECT-TYPE
        SYNTAX INTEGER {
-- slot base 100
                setSlotMismatch(101),
                setSlotMissing(102),
                clearSlotMismatch(141),
                clearSlotMissing(142),
-- device base 200
                setDevFrameSyncNotPresent(203),
                setDevSystemClockNotPresent(204),
                setDevDataBaseNotInsync(206),
                setDevFreeRunError(207),
                setDevOffline(208),
                setDevDefective(209),
                setDevBusError(210),
                setDevStratum3ClkFailure(216),
                setDevCircuitCardMissing(219),
                setDevConfigError(225),
                setDevNoRearCard(228),
                clearDevFrameSyncNotPresent(243),
                clearDevSystemClockNotPresent(244),
                clearDevDataBaseNotInsync(246),
                clearDevFreeRunError(247),
                clearDevOffline(248),
                clearDevDefective(249),
                clearDevBusError(250),
                clearDevStratum3ClkFailure(256),
                clearDevCircuitCardMissing(259),
                clearDevConfigError(265),
                clearDevNoRearCard(268),
-- port T1/E1 base 300
                setT1E1RcvFarEndLOF(301),
                setT1E1NearEndSendLOF(302),
                setT1E1NearEndSendingAIS(304),
                setT1E1NearEndLOF(305),
                setT1E1NearEndLossOfSignal(306),
                setT1E1Ts16AIS(308),
                setT1E1FarEndSendingTs16LOMF(309),
                setT1E1NearEndSendingTs16LOMF(310),
                setT1E1OtherLineStatus(312),
                setT1E1NearEndUnavailableSig(313),
                setT1E1NearEndTxSlip(321),
                setT1E1NearEndRxSlip(322),
                setT1E1NearEndSeverErroredFrame(323),
                setT1E1ChangeFrameAlignment(324),
                setT1E1ConfigError(325),
                clearT1E1RcvFarEndLOF(341),
                clearT1E1NearEndSendLOF(342),
                clearT1E1NearEndSendingAIS(344),
                clearT1E1NearEndLOF(345),
                clearT1E1NearEndLossOfSignal(346),
                clearT1E1Ts16AIS(348),
                clearT1E1FarEndSendingTs16LOMF(349),
                clearT1E1NearEndSendingTs16LOMF(350),
                clearT1E1OtherLineStatus(352),
                clearT1E1NearEndUnavailableSig(353),
                clearT1E1NearEndTxSlip(361),
                clearT1E1NearEndRxSlip(362),
                clearT1E1NearEndSeverErroredFrame(363),
                clearT1E1ChangeFrameAlignment(364),
                clearT1E1ConfigError(365),
--  port High Speed base 400
                setHsRcvFIFOError(401), 
                setHsXmtFIFOError(402), 
                setHsClockEdgeError(403), 
                setHsCarrierFailure(404), 
                setHsConfigError(425),
                clearHsRcvFIFOError(441), 
                clearHsXmtFIFOError(442), 
                clearHsClockEdgeError(443), 
                clearHsCarrierFailure(444), 
                clearHsConfigError(465),
--  port T3 base 500
                setT3RcvFarEndLOF(501),
                setT3NearEndSendLOF(502),
                setT3FarEndSendingAIS(503),
                setT3NearEndSendingAIS(504),
                setT3NearEndLOF(505),
                setT3NearEndLossOfSignal(506),
                setT3OtherLineStatus(512),
                setT3NearEndUnavailableSig(513),
                setT3NearEndSeverErroredFrame(515),
                setT3TxRxClockFailure(516),
                setT3FarEndBlockError(517),
                setT3PbitCbitParityError(518),
                setT3MbitsInError(519),
                setT3LIUOtherStatus(520),
                setT3LIUExcessZeros(522),
                setT3LIUCodingViolation(523),
                setT3LIUPrbsError(524),
                setT3ConfigError(525),
                clearT3RcvFarEndLOF(541),
                clearT3NearEndSendLOF(542),
                clearT3FarEndSendingAIS(543),
                clearT3NearEndSendingAIS(544),
                clearT3NearEndLOF(545),
                clearT3NearEndLossOfSignal(546),
                clearT3OtherLineStatus(552),
                clearT3NearEndUnavailableSig(553),
                clearT3NearEndSeverErroredFrame(555),
                clearT3TxRxClockFailure(556),
                clearT3FarEndBlockError(557),
                clearT3PbitCbitParityError(558),
                clearT3MbitsInError(559),
                clearT3LIUOtherStatus(560),
                clearT3LIUExcessZeros(562),
                clearT3LIUCodingViolation(563),
                clearT3LIUPrbsError(564),
                clearT3ConfigError(565),
-- Power Supply base 600
                setPowerSupplyNotPresent(601),
                setPowerSupplyProblem(602),
                clearPowerSupplyNotPresent(641),
                clearPowerSupplyProblem(642),
-- Port Quad OCU base 700
                setOcuNearEndLOS(706),
                setOcuOtherLineStatus(712),
                setOcuNearEndSeverErroredFrame(723),
                setOcuConfigError(725),
                clearOcuNearEndLOS(746),
                clearOcuOtherLineStatus(752),
                clearOcuNearEndSeverErroredFrame(763),
                clearOcuConfigError(765),
-- Port Test Access base 800
                setTamConfigError(825),
                clearTamConfigError(865),
-- Port Voice base 900
                setVoiceConfigError(925),
                clearVoiceConfigError(965),
-- Protection Switch base 1000
                setPsxPowerSupplyANotOk(1003),
                setPsxPowerSupplyBNotOk(1004),
                setPsxFan01NotOk(1005),
                setPsxFan02NotOk(1006),
                setPsxFan03NotOk(1007),
                setPsxDualBroadbandNotSupported(1008),
                clearPsxPowerSupplyANotOk(1043),
                clearPsxPowerSupplyBNotOk(1044),
                clearPsxFan01NotOk(1045),
                clearPsxFan02NotOk(1046),
                clearPsxFan03NotOk(1047),
                clearPsxDualBroadbandNotSupported(1048),
-- Protection Switch Line Cards base 1100
                setPsxLineCardRelaySwitchToSpare(1102),
                setPsxLineCardCableMissing(1103),
                setPsxLineCardMissing(1106),
                setPsxLineCardMismatch(1107),
                setPsxLineCardRelayMalfunction(1108),
                clearPsxLineCardRelaySwitchToSpare(1142),
                clearPsxLineCardCableMissing(1143),
                clearPsxLineCardMissing(1146),
                clearPsxLineCardMismatch(1147),
                clearPsxLineCardRelayMalfunction(1148),
-- Port Router Card base 1200
                setRtrUserAlarm1(1201),
                setRtrUserAlarm2(1202),
                setRtrUserAlarm3(1203),
                setRtrConfigError(1225),
                clearRtrUserAlarm1(1241),
                clearRtrUserAlarm2(1242),
                clearRtrUserAlarm3(1243),                
                clearRtrConfigError(1265),
--  port STS-1 base 1300
                setSts1RcvFarEndLOF(1301),
                setSts1NearEndSendLOF(1302),
                setSts1NearEndSendingAIS(1304),
                setSts1NearEndLOF(1305),
                setSts1NearEndLOP(1308),
                setSts1NearEndOOF(1309),
                setSts1NearEndAIS(1310),
                setSts1OtherLineStatus(1312),
                setSts1NearEndUnavailableSig(1313),
                setSts1TxRxClockFailure(1316),
                setSts1NearEndLOMF(1317),
                setSts1NearEndTraceError(1318),
                setSts1LIUDigitalLOS(1320),
                setSts1LIUAnalogLOS(1321),
                setSts1LIUExcessZeros(1322),
                setSts1LIUCodingViolation(1323),
                setSts1LIUPrbsError(1324),
                setSts1ConfigError(1325),
                clearSts1RcvFarEndLOF(1341),
                clearSts1NearEndSendLOF(1342),
                clearSts1NearEndSendingAIS(1344),
                clearSts1NearEndLOF(1345),
                clearSts1NearEndLOP(1348),
                clearSts1NearEndOOF(1349),
                clearSts1NearEndAIS(1350),
                clearSts1OtherLineStatus(1352),
                clearSts1NearEndUnavailableSig(1353),
                clearSts1TxRxClockFailure(1356),
                clearSts1NearEndLOMF(1357),
                clearSts1NearEndTraceError(1358),
                clearSts1LIUDigitalLOS(1360),
                clearSts1LIUAnalogLOS(1361),
                clearSts1LIUExcessZeros(1362),
                clearSts1LIUCodingViolation(1363),
                clearSts1LIUPrbsError(1364),
                clearSts1ConfigError(1365),
--  port Hybrid T3 base 1400
                setHt3NearEndSendingAIS(1404),
                setHt3NearEndOOF(1405),
                setHt3NearEndLossOfSignal(1406),
                setHt3NearEndLOF(1408),
                setHt3FarEndRcvFailure(1409),
                setHt3NearEndLCVError(1411),
                setHt3NearEndFERRError(1412),
                setHt3NearEndExcessZeros(1413),
                setHt3FarEndBlockError(1417),
                setHt3PbitCbitParityError(1418),
                setHt3ChangeInFrameAlignment(1419),
                setHt3LIUDigitalLOS(1420),
                setHt3LIUAnalogLOS(1421),
                setHt3LIUExcessZeros(1422),
                setHt3LIUCodingViolation(1423),
                setHt3LIUPrbsError(1424),
                setHt3ConfigError(1425),
                clearHt3NearEndSendingAIS(1444),
                clearHt3NearEndOOF(1445),
                clearHt3NearEndLossOfSignal(1446),
                clearHt3NearEndLOF(1448),                
                clearHt3FarEndRcvFailure(1449),
                clearHt3NearEndLCVError(1451),
                clearHt3NearEndFERRError(1452),
                clearHt3NearEndExcessZeros(1453),
                clearHt3FarEndBlockError(1457),
                clearHt3PbitCbitParityError(1458),
                clearHt3ChangeInFrameAlignment(1459),
                clearHt3LIUDigitalLOS(1460),
                clearHt3LIUAnalogLOS(1461),
                clearHt3LIUExcessZeros(1462),
                clearHt3LIUCodingViolation(1463),
                clearHt3LIUPrbsError(1464),
                clearHt3ConfigError(1465),
-- port X-Link 1600
                setXlinkCableMismatch(1606),
                setXlinkSerializerError(1615),
                setXlinkFramerError(1616),
                setXlinkBertError(1617),
                setXlinkClockError(1618),
                setXlinkInUseError(1620),
                setXlinkCrcError(1621),
                clearXlinkCableMismatch(1646),
                clearXlinkSerializerError(1655),
                clearXlinkFramerError(1656),
                clearXlinkBertError(1657),
                clearXlinkClockError(1658),
                clearXlinkInUseError(1660),
                clearXlinkCrcError(1661),
--  nest base 1700
                setNestMismatch(1701),
                setNestMissing(1702),
                setNestOffline(1705),
                setNestCriticalAlarm(1706),
                setNestMajorAlarm(1707),
                setNestMinorAlarm(1708),
                setNestSwMismatch(1709),
                clearNestMismatch(1741),
                clearNestMissing(1742),
                clearNestOffline(1745),
                clearNestCriticalAlarm(1746),
                clearNestMajorAlarm(1747),
                clearNestMinorAlarm(1748),
                clearNestSwMismatch(1749),
--  node base 1800
                setNodeCriticalAlarm(1801),
                setNodeMajorAlarm(1802),
                setNodeMinorAlarm(1803),
                clearNodeCriticalAlarm(1841),
                clearNodeMajorAlarm(1842),
                clearNodeMinorAlarm(1843),
-- port DS0DP 1900
                setDs0DpPortLossOfSignal(1901),
                setDs0DpPortBPV(1902),
                setDs0DpPortConfigError(1925),
                clearDs0DpPortLossOfSignal(1941),
                clearDs0DpPortBPV(1942),
                clearDs0DpPortConfigError(1965),
-- composite clock DS0DP 2000
                setDs0DpClockLossOfSignal(2001),
                setDs0DpClockBPV(2002),
                clearDs0DpClockLossOfSignal(2041),
                clearDs0DpClockBPV(2042),
-- optical T1/E1 link base 2200
                setOpticalT1E1RedAlarm(2201),
                setOpticalT1E1NearEndSendLOF(2202),
                setOpticalT1E1NearEndSendingAIS(2204),
                setOpticalT1E1NearEndLOF(2205),
                setOpticalT1E1LossOfPointer(2208),
                setOpticalT1E1OutOfFrame(2209),
                setOpticalT1E1DetectedAIS(2210),
                setOpticalT1E1NearEndLOS(2213),
                setOpticalT1E1RcvFarEndYellow(2217),
                setOpticalT1E1NearEndSEF(2218),
                setOpticalT1E1Tug2LOP(2219),
                setOpticalT1E1Tug2RDI(2220),
                setOpticalT1E1Tug2RFI(2221),
                setOpticalT1E1Tug2AIS(2222),
                setOpticalT1E1Tug2PSLM(2223),
                setOpticalT1E1Tug2PSLU(2224),               
                setOpticalT1E1ConfigError(2225),
                clearOpticalT1E1RedAlarm(2241),
                clearOpticalT1E1NearEndSendLOF(2242),
                clearOpticalT1E1NearEndSendingAIS(2244),
                clearOpticalT1E1NearEndLOF(2245),
                clearOpticalT1E1LossOfPointer(2248),
                clearOpticalT1E1OutOfFrame(2249),
                clearOpticalT1E1DetectedAIS(2250),
                clearOpticalT1E1NearEndLOS(2253),
                clearOpticalT1E1RcvFarEndYellow(2257),
                clearOpticalT1E1NearEndSEF(2258),
                clearOpticalT1E1Tug2LOP(2259),
                clearOpticalT1E1Tug2RDI(2260),
                clearOpticalT1E1Tug2RFI(2261),
                clearOpticalT1E1Tug2AIS(2262),
                clearOpticalT1E1Tug2PSLM(2263),
                clearOpticalT1E1Tug2PSLU(2264),               
                clearOpticalT1E1ConfigError(2265),
-- optical payload base 2300
                setVtNearEndLOP(2301),
                setVtNearEndAIS(2302),
                setPayloadPathLOP(2303),
                setPayloadPathAIS(2304),
                setPayloadPathRDI(2305),
                clearVtNearEndLOP(2341),
                clearVtNearEndAIS(2342),
                clearPayloadPathLOP(2343),
                clearPayloadPathAIS(2344),
                clearPayloadPathRDI(2345),
-- optical Transport Overhead base 2400
                setTransOverheadAIS(2401),
                setTransOverheadRDI(2402),
                setTransOverheadOOF(2403),
                setTransOverheadLOF(2404),
                setTransOverheadLOS(2405),
                setTransOverheadSfDetect(2413),
                setTransOverheadSdDetect(2414),
                setTransOverheadLaserOffDetect(2415),
                clearTransOverheadAIS(2441),
                clearTransOverheadRDI(2442),
                clearTransOverheadOOF(2443),
                clearTransOverheadLOF(2444),
                clearTransOverheadLOS(2445),
                clearTransOverheadSfDetect(2453),
                clearTransOverheadSdDetect(2454),
                clearTransOverheadLaserOffDetect(2455),
--  port E3 base 2500
                setE3RcvFarEndLOF(2501),
                setE3NearEndSendLOF(2502),
                setE3NearEndSendingAIS(2504),
                setE3NearEndLOF(2505),
                setE3NearEndLossOfSignal(2506),
                setE3OtherLineStatus(2512),
                setE3NearEndUnavailableSig(2513),
                setE3NearEndSeverErroredFrame(2515),
                setE3TxRxClockFailure(2516),
                setE3FarEndBlockError(2517),
                setE3MbitsInError(2519),
                setE3LIUOtherStatus(2520),
                setE3LIUCodingViolation(2523),
                setE3ConfigError(2525),
                clearE3RcvFarEndLOF(2541),
                clearE3NearEndSendLOF(2542),
                clearE3NearEndSendingAIS(2544),
                clearE3NearEndLOF(2545),
                clearE3NearEndLossOfSignal(2546),
                clearE3OtherLineStatus(2552),
                clearE3NearEndUnavailableSig(2553),
                clearE3NearEndSeverErroredFrame(2555),
                clearE3TxRxClockFailure(2556),
                clearE3FarEndBlockError(2557),
                clearE3MbitsInError(2559),
                clearE3LIUOtherStatus(2560),
                clearE3LIUCodingViolation(2563),
                clearE3ConfigError(2565),
-- Dnx-1u Contact Closure base 2600
                setContactClosureInputAlarm(2601),
                setContactClosureCfgError(2625),
                clearContactClosureInputAlarm(2641),
                clearContactClosureCfgError(2665),
-- Dnx-1u Voltage Measurement base 2700
                setVoltMeasureAlarm(2701),
                setVoltMeasureCfgError(2725),
                clearVoltMeasureAlarm(2741),
                clearVoltMeasureCfgError(2765),
-- Dnx-1u Asynchronous Port base 2800
                setAsyncRxFifoError(2801),
                setAsyncTxFifoError(2802),
                setAsyncOverrunError(2803),
                setAsyncParityError(2804),
                setAsyncFramingError(2805),
                clearAsyncRxFifoError(2841),
                clearAsyncTxFifoError(2842),
                clearAsyncOverrunError(2843),
                clearAsyncParityError(2844),
                clearAsyncFramingError(2845),
-- Dnx-1u Temperature Sensor base 2900
                setTempSensorOutOfRange(2901),
                clearTempSensorOutOfRange(2941),
-- Dnx-1u Router Virual Wan base 3000
                setVWanError(3001),
                setVWanCfgError(3025),
                clearVWanError(3041),
                clearVWanCfgError(3065),
-- Dnx-1u Power Supply base 3100
                set1uPowerSupplyOffline(3108),
                set1uPowerSupplyDefective(3109),
                set1uPowerSupplyFanFailure(3110),
                set1uPowerSupplyCircuitMissing(3119),
                set1uPowerSupplyCfgMismatch(3125),
                clear1uPowerSupplyOffline(3148),
                clear1uPowerSupplyDefective(3149),
                clear1uPowerSupplyCircuitMissing(3159),
                clear1uPowerSupplyFanFailure(3150),
                clear1uPowerSupplyCfgMismatch(3165),
-- Informational Events from all system resources
                evntDevColdStart(1),
                evntDevWarmStart(2),
                evntDevOnline(201),
                evntDevStandby(202),
                evntDevOutOfService(231),
                evntDevNotOnline(241),
                evntDevNotStandby(242),
                evntDevInService(271),
                evntT1E1RcvingAIS(303),
                evntT1E1NearEndLooped(307),
                evntT1E1CarrierEquipOutOfService(314),
                evntE1NationalSa4TxRxSame(316),
                evntT1E1InTest(330),
                evntT1E1OutOfService(331),
                evntT1E1StoppedRcvingAIS(343),
                evntT1E1NearEndLoopOff(347),
                evntT1E1CarrierEquipInService(354),
                evntE1NationalSa4TxRxDiff(356),
                evntT1E1TestOff(370),
                evntT1E1InService(371),
                evntHsNearEndLooped(407),
                evntHsNoBtsAssigned(424),                
                evntHsInTest(430),
                evntHsOutOfService(431),
                evntHsNearEndLoopOff(447),
                evntHsBtsAssigned(464),
                evntHsTestOff(470),
                evntHsInService(471),
                evntT3NearEndLooped(507),
                evntT3CarrierEquipOutOfService(514),
                evntT3InTest(530),
                evntT3OutOfService(531),
                evntT3NearEndLoopOff(547),
                evntT3CarrierEquipInService(554),
                evntT3TestOff(570),
                evntT3InService(571),
                evntOcuOutOfService(731),
                evntOcuInService(771),
                evntTamOutOfService(831),
                evntTamInService(871),
                evntVoiceOutOfService(931),
                evntVoiceInService(971),
                evntPsxDevOnline(1001),
                evntPsxNewControllerRev(1009),    -- kept for backwards compatibilty
                evntPsxLineCard01Missing(1014),
                evntPsxLineCard02Missing(1015),
                evntPsxLineCard03Missing(1016),
                evntPsxLineCard04Missing(1017),
                evntPsxLineCard05Missing(1018),
                evntPsxLineCard06Missing(1019),
                evntPsxLineCard07Missing(1020),
                evntPsxLineCard08Missing(1021),
                evntPsxLineCard09Missing(1022),
                evntPsxLineCard10Missing(1023),
                evntPsxLineCard11Missing(1024),
                evntPsxLineCard01Present(1054),
                evntPsxLineCard02Present(1055),
                evntPsxLineCard03Present(1056),
                evntPsxLineCard04Present(1057),
                evntPsxLineCard05Present(1058),
                evntPsxLineCard06Present(1059),
                evntPsxLineCard07Present(1060),
                evntPsxLineCard08Present(1061),
                evntPsxLineCard09Present(1062),
                evntPsxLineCard10Present(1063),
                evntPsxLineCard11Present(1064),
                evntRtrOutOfService(1231),
                evntRtrInService(1271),
                evntSts1RcvingAIS(1303),
                evntSts1NearEndLooped(1307),
                evntSts1CarrierEquipOutOfService(1314),
                evntSts1InTest(1330),
                evntSts1OutOfService(1331),
                evntSts1StoppedRcvingAIS(1343),
                evntSts1NearEndLoopOff(1347),
                evntSts1CarrierEquipInService(1354),
                evntSts1TestOff(1370),
                evntSts1InService(1371),
                evntHt3RcvingAIS(1403),
                evntHt3NearEndLooped(1407),
                evntHt3CarrierEquipOutOfService(1414),
                evntHt3InTest(1430),
                evntHt3OutOfService(1431),
                evntHt3StoppedRcvingAIS(1443),
                evntHt3NearEndLoopOff(1447),
                evntHt3CarrierEquipInService(1454),
                evntHt3TestOff(1470),
                evntHt3InService(1471),
                evntGr303OutOfService(1531),
                evntGr303InService(1571),                
                evntDs0DpPortInTest(1930),
                evntDs0DpPortOutOfService(1931),
                evntDs0DpPortTestOff(1970),
                evntDs0DpPortInService(1971),
                evntOpticalT1E1RcvingAIS(2203),
                evntOpticalT1E1NearEndLooped(2207),
                evntOpticalE1NationalSa4TxRxSame(2216),
                evntOpticalT1E1InTest(2230),
                evntOpticalT1E1OutOfService(2231),
                evntOpticalT1E1StoppedRcvingAIS(2243),
                evntOpticalT1E1NearEndLoopOff(2247),
                evntOpticalE1NationalSa4TxRxDiff(2256),
                evntOpticalT1E1TestOff(2270),
                evntOpticalT1E1InService(2271),
                evntPayloadNearEndLineLooped(2307),
                evntPayloadNearEndLocalLooped(2308),
                evntPayloadInTest(2330),
                evntPayloadNearEndLineLoopOff(2347),
                evntPayloadNearEndLocalLoopOff(2348),
                evntPayloadTestOff(2370),
                evntTransOverheadNearEndSysLineLooped(2407),
                evntTransOverheadNearEndPathLineLooped(2408),
                evntTransOverheadNearEndLocalLooped(2409),
                evntTransOverheadInTest(2430),
                evntTransOverheadNearEndSysLineLoopOff(2447),
                evntTransOverheadNearEndPathLineLoopOff(2448),
                evntTransOverheadNearEndLocalLoopOff(2449),
                evntTransOverheadTestOff(2470),
                evntE3RcvingAIS(2503),
                evntE3NearEndLooped(2507),
                evntE3CarrierEquipOutOfService(2514),
                evntE3InTest(2530),
                evntE3OutOfService(2531),
                evntE3StoppedRcvingAIS(2543),
                evntE3NearEndLoopOff(2547),
                evntE3CarrierEquipInService(2554),
                evntE3TestOff(2570),
                evntE3InService(2571),
                evnt1uPowerSupplyFanOn(3116),
                evnt1uPowerSupplyFanOff(3156)
                }
        MAX-ACCESS accessible-for-notify
        STATUS current
        DESCRIPTION
             "This is the specific Trap Code that represents the type 
             of alarm or event that occurred.  Each alarm type has a code
             that sets the trap as active and a corresponding code that 
             clears the trap to simulate an alarm.  The event type codes
             are have the prefix 'evnt' but also occur at the start of 
             and end of the event.  Each Type code has base number that
             represents the resource type followed by the bit number from
             the resource extended device state. Each event or alarm will
             have a trap for the start equal to the bit number plus the base
             number and then a trap at the end of the event/alarm equal to
             the bit number plus the base number plus 40.  
             For example, clearSlotMissing(142) represents a SLOT resource 
             which has a base 100, bit 2 for slot missing, plus 40 to signify
             the end of the alarm.  The exception to this is General Events 
             such as evntColdStart (1)."
        ::= { traps 6}

trapState OBJECT-TYPE
        SYNTAX Integer32
        MAX-ACCESS accessible-for-notify
        STATUS current
        DESCRIPTION
                "This is the current status of the resource reporting the
                 trap."
        ::= { traps 7}

trapSeverity OBJECT-TYPE
        SYNTAX AlarmSeverity
        MAX-ACCESS accessible-for-notify
        STATUS current
        DESCRIPTION
        	"The importance of the trap event.
                nominal         (0) Normal message, not used.                  
                informational   (1) Informative message, not an error.
                minor           (2) Error that serves as a warning to user.
                major           (3) Error that requires user intervention.
                critical        (4) Severe error. Device failure could result.
            "
        ::= { traps 8}
        
trapSysEvent OBJECT-TYPE
        SYNTAX DisplayString
        MAX-ACCESS accessible-for-notify
        STATUS current
        DESCRIPTION
        	"This is the text message from the resource reporting the trap."
        ::= { traps 9}        

-- *************************************************************************
-- Trap Client Destination Table
-- *************************************************************************
-- The following table contains the destination addresses for trap clients.
-- This is the information that appears in the terminal console under the
-- SNMP Agent Configuration menu.

trapCfg OBJECT IDENTIFIER   ::= { traps 20 }


trapDestinationTable OBJECT-TYPE
        SYNTAX SEQUENCE OF TrapDestinationEntry
        MAX-ACCESS not-accessible
        STATUS current
        DESCRIPTION
            "This is the Trap Client Destination table which consists
            of an entry for each of the supported trap destinations.
            Changes to the trapDestinationTable must be made
            on a record or row by row basis.  This means that any use of the 
            Set command on writable fields must include the trapDestCmdStatus
            field with a value of 'update', 'delete', or 'create' as the last 
            variable in the SET PDU."
        ::= { trapCfg 1 }

trapDestinationEntry OBJECT-TYPE
        SYNTAX TrapDestinationEntry
        MAX-ACCESS not-accessible
        STATUS current
        DESCRIPTION
            "The conceptual row of the Trap Client Destination table. 
            A row in this table can be added by providing a valid trapDestAddr
            value along with the trapDestCmdStatus value of 'create' in a SET
            PDU.  A row in this table can be deleted by providing a 
            trapDestCmdStatus value of 'delete' in a SET PDU. A row can be 
            modified using the trapDestCmdStatus field with the value of 'update'
            in the SET PDU. The trapDestCmdStatus field must be included as a 
            variable in a SET PDU for the action to take effect. If the 
            trapDestCmdStatus is missing from the SET PDU, the GET RESPONSE will 
            contain the SNMP error status of 'genErr' for and an error index equal 
            to the last variable."
        INDEX { trapDestAddr }
        ::= { trapDestinationTable 1 }

TrapDestinationEntry ::=
        SEQUENCE {
                trapDestAddr        IpAddress, 		
                trapDestName        DisplayString,  
                trapDestCmdStatus   INTEGER,
                trapDestPduType		INTEGER,
                trapDestMaxRetry	Integer32,
                trapDestTimeout		INTEGER         
                }

trapDestAddr OBJECT-TYPE
        SYNTAX IpAddress
        MAX-ACCESS read-write
        STATUS current
        DESCRIPTION
                "The Trap Destination IP Address where all Trap PDUs 
                are sent for this Client."
        ::= { trapDestinationEntry 1 }

trapDestName OBJECT-TYPE
        SYNTAX DisplayString (SIZE (0..35))
        MAX-ACCESS read-write
        STATUS current
        DESCRIPTION
                "The Trap Destination Community String which is 
                included in all Trap PDUs sent to this Client."
        ::= { trapDestinationEntry 2 }

trapDestCmdStatus OBJECT-TYPE
        SYNTAX INTEGER {
    -- Initial default status for a row
            ready-for-command (0),
    -- Trap Dest Commands used in SET Command (1..99)
            update-trap-dest (1),
            delete-trap-dest (2),
            create-trap-dest (3),
                		
    -- Response States used in GET RESPONSE Command (100..199)
            update-successful (101),
            delete-successful (102),
            create-successful (103),
                		
    -- Trap Dest Error Codes used in GET RESPONSE Command (200..799)
            err-general-trap-dest-cfg-error (200),
            err-invalid-trap-dest-addr (201),
            err-invalid-trap-dest-cmd (202),
            err-invalid-trap-dest-name (203),
            err-invalid-trap-dest-pdu (204),
            err-invalid-trap-dest-retry (205),
            err-invalid-trap-dest-tmout (206),
            err-data-locked-by-another-user (450),
            err-snmp-parse-failed (500),
            err-invalid-snmp-type (501),
            err-invalid-snmp-var-size (502)
            }
        MAX-ACCESS read-write
        STATUS current
        DESCRIPTION
           "The command status for this trap dest configuration row/record.
           The value used in a SET will be replaced by a response
           value in the GET RESPONSE indicating success or failure.
           		
            Default Response State used in GET RESPONSE Command
                ready-for-command (0)
                    Initial default status for a row           
                    
            Trap Dest Commands used in SET Command (1..99)            
                update-trap-dest (1)
                    Change an aspect of current trap destination
                delete-trap-dest (2)
                    Delete Trap Destination entry from table.
                create-trap-dest (3)
                    Add New Trap Destination entry to the table.
                                    		
            Response States used in GET RESPONSE Command (100..199)
                update-successful (101)
                    Trap dest has been successfully changed
                delete-successful (102)
                    Trap dest has been successfully removed
                create-successful (103)
                    Trap dest has been successfully added
                		
            Trap Dest Error Codes used in GET RESPONSE Command (200..799)
                err-general-trap-dest-cfg-error (200)
                    Unknown configuration error occurred.
                err-invalid-trap-dest-addr (201)
                    Invalid Destination IP address
                err-invalid-trap-dest-cmd (202)         
                    Unrecognized trap command action
                err-invalid-trap-dest-name (203)
                    Configured trap community name too long
                err-invalid-trap-dest-pdu (204)         
                    Unrecognized trap PDU type settings
                err-invalid-trap-dest-retry (205)         
                    Invalid trap Max Retry range
                err-invalid-trap-dest-tmout (206)         
                    Unrecognized trap timeout setting
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
                		
        ::= { trapDestinationEntry 3 }

trapDestPduType OBJECT-TYPE
        SYNTAX INTEGER {
                v1Trap (0),
                v2Trap (1),
                inform (2)
                }
        MAX-ACCESS read-write
        STATUS current
        DESCRIPTION
                "The message format for all traps sent to the Trap Destination."
        ::= { trapDestinationEntry 4 }

trapDestMaxRetry OBJECT-TYPE
        SYNTAX Integer32 (0..10)
        MAX-ACCESS read-write
        STATUS current
        DESCRIPTION
                "The number of times to attempt to retransmit the Trap 
                message to the Client before discarding it."
        ::= { trapDestinationEntry 5 }

trapDestTimeout OBJECT-TYPE
        SYNTAX INTEGER {
        		none (0),
                secs-5 (5),
                secs-10 (10),
                secs-15 (15),
                secs-20 (20)
                }
        MAX-ACCESS read-write
        STATUS current
        DESCRIPTION
                "The number of seconds between retries."
        ::= { trapDestinationEntry 6 }

-- *************************************************************************
-- Now for the Enterprise Specific Traps.
-- *************************************************************************

-- *************************************************************************
-- Original ERI Enterprise Specific Traps.
-- *************************************************************************
eriTrapEnterprise OBJECT-IDENTITY
      STATUS current
      DESCRIPTION "ERI Global Trap Enterprise for Alarms/Events"
    ::= { eriProducts 0 }

alarmTrap NOTIFICATION-TYPE
        OBJECTS {
            trapSequence,
            trapResourceKey,
            trapTime,
            trapResourceAddress,
            trapResourceType,
            trapType,
            trapState,
            trapSeverity
            }
        STATUS current
        DESCRIPTION
                "This the generic trap is for sending alarms to NMS."
        ::= { eriTrapEnterprise 1 }

deleteResourceTrap NOTIFICATION-TYPE
        OBJECTS {
            resourceKey, 
            trapSequence
            }
        STATUS current
        DESCRIPTION
              	"This trap is used to notify a NMS that a resource
                 has been deleted."
        ::= { eriTrapEnterprise 2 }
      
-- *************************************************************************
-- DNX Enterprise Specific Traps.
-- *************************************************************************
dnxTrapEnterprise OBJECT-IDENTITY
      STATUS current
      DESCRIPTION "ERI DNX Trap Enterprise for Events"
    ::= { dnx 0 }

connectionEventTrap NOTIFICATION-TYPE
        OBJECTS {
            trapSequence,
            sysMapID,
            sysConnID,
            sysCmdStatus
            }
        STATUS current
        DESCRIPTION
              	"This trap is used to notify a NMS that a connection
                 has been changed, added, or deleted."
        ::= { dnxTrapEnterprise 3 }

        
connMapMgrTrap NOTIFICATION-TYPE
        OBJECTS { 
            trapSequence,
            connMapID,
            connMapCmdStatus
            }
        STATUS current
        DESCRIPTION
              	"This trap is used to notify a NMS that a new connection
        		map has been activated or that a connection map has been
        		successfully copied to another inactive map."
        ::= { dnxTrapEnterprise 4 }

connMapCopyTrap NOTIFICATION-TYPE
        OBJECTS {
            trapSequence,
            lastMapCopied,
            connMapID
            }
        STATUS current
        DESCRIPTION
              	"This trap is used to notify a NMS that a user has 
              	copied all connections from a source map (lastMapCopied)
              	to another destination map indicated by connMapID."
        ::= { dnxTrapEnterprise 6 }

bulkConnPurgeTrap NOTIFICATION-TYPE
        OBJECTS {
            trapSequence,
            resourceKey,
            connMapID,
            connMapCounts
            }
        STATUS current
        DESCRIPTION
              	"This trap is used to notify users that due to a change in 
              	device/port configuration, all connections affected by the 
              	changed resource have been purged.  The Resource key can be
              	used to identify which resource was re-configured causing 
              	connections to be removed and the Map ID identifies which 
              	Connection Map was purged.  The ConnMapCounts field indicates 
              	the total number of connections deleted."
        ::= { dnxTrapEnterprise 7 }

clockSrcChgTrap NOTIFICATION-TYPE
        OBJECTS {
            trapSequence,
            clockSrcActive,
            primaryClockSrc,
            secondaryClockSrc,
            tertiaryClockSrc,
            clockSrcCmdStatus
            }
        STATUS current
        DESCRIPTION
              	"This trap is used to notify a NMS that the system 
              	has detected a change in the Clock Source settings.
              	These changes can result from either an automatic 
              	system fallback due to failure or a user configured  
              	clock source modification."
        ::= { dnxTrapEnterprise 10 }

trunkCondProfTrap NOTIFICATION-TYPE
        OBJECTS {
            trapSequence,
            trunkProfileID,
            trunkCmdStatus
            }
        STATUS current
        DESCRIPTION
              	"This trap is used to notify a NMS that the system 
              	has detected a change in the trunk Conditioning Profile
              	settings. These changes are user configured."
        ::= { dnxTrapEnterprise 13 }

systemEventTrap NOTIFICATION-TYPE
        OBJECTS {
            trapSequence,
            trapSysEvent,
            trapSeverity  
            }
        STATUS current
        DESCRIPTION
              	"This trap is used to notify a NMS that a generic event 
              	has occured in the system which is reported as a text message."
        ::= { dnxTrapEnterprise 14 }

trapDestCfgTrap NOTIFICATION-TYPE
        OBJECTS {
            trapSequence,
            trapDestAddr,
            trapDestCmdStatus
            }
        STATUS current
        DESCRIPTION
               "This trap is used to notify a NMS that a user has 
                updated the configuration for a given Trap Destination entry."
        ::= { dnxTrapEnterprise 15 }

featureKeyCfgTrap NOTIFICATION-TYPE
        OBJECTS {
            trapSequence,
            featureKeyName,
            featureKeyState, 
            featureKeyCmdStatus
            }
        STATUS current
        DESCRIPTION
               "This trap is used to notify a NMS that a user has 
                added to or modified the configuration of the system Feature Keys."
        ::= { dnxTrapEnterprise 16 }

END

-- *************************************************************************
--
--  MIB:    ERI-DNX-PERF-MONT-MIB
--
--	Purpose:
--          This will be the MIB for the DNX Performance Monitoring
--          Statistics Module. This will provide for vital statistical 
--          data for each DS1 or E1 link in the system.
--
--  Contact: Eastern Research Inc. 1-800-337-4374  Email: support@erinc.com
--
--  Revised: December 28, 2000 - Nevio Poljak
--           Initial Release
--
--           March 03, 2001 - Nevio Poljak for Release 11.0  
--           Renamed all Counter types to Gauge32 to support range specifics
--
--           April 03, 2001 - Oliver DeGrate for Release 12.0  
--           Added ESF 96 Interval Register Table 
--
--           July 17, 2001 - Nevio Poljak for Release 12.2  
--           Added UAS field to G.826 Table 
--
--           April 11, 2002 - Nevio Poljak for Release 14.2
--           Converted to SMIv2 format.
-- *************************************************************************
