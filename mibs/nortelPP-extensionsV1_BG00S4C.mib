Nortel-Magellan-Passport-ExtensionsMIB
DEFINITIONS ::= BEGIN

IMPORTS


      OBJECT-TYPE
   FROM RFC-1212

      RowPointer
   FROM Nortel-Magellan-Passport-StandardTextualConventionsMIB

      components, passportMIBs
   FROM Nortel-Magellan-Passport-UsefulDefinitionsMIB

      ifIndex
   FROM RFC1213-MIB;

-- LAST-UPDATED "9603010000Z"
-- ORGANIZATION "Nortel"
-- CONTACT-INFO "
--         Nortel Magellan Network Management
--
--         Postal: P.O. Box 5080, Station F
--                 Ottawa, Ontario
--                 Canada  K2C 3T1
--
--         Email:  nm_plm@nt.com"
-- DESCRIPTION
--    "The MIB module describing the Nortel Magellan Passport enterprise 
--    extensions to standard Mibs."

extensionsMIB OBJECT IDENTIFIER  ::= { passportMIBs 5 }

extensions OBJECT IDENTIFIER ::= { components 4 }

extensionIfTable    OBJECT-TYPE
   SYNTAX     SEQUENCE OF ExtensionIfEntry
   ACCESS     not-accessible
   STATUS     mandatory
   DESCRIPTION
      "A table which provides enterprise extensions to the standard 
       ifTable."
   ::= { extensions 1 }

extensionIfEntry     OBJECT-TYPE
   SYNTAX      ExtensionIfEntry 
   ACCESS      not-accessible
   STATUS     mandatory
   DESCRIPTION
      " An entry containing enterprise extensions to the standard
	ifEntry."
   INDEX  { ifIndex }
   ::= {extensionIfTable 1}

 ExtensionIfEntry ::=
    SEQUENCE {
       ifRowPointer    RowPointer
       }

 ifRowPointer    OBJECT-TYPE
    SYNTAX       RowPointer
    ACCESS       read-only 
    STATUS       mandatory
    DESCRIPTION
       "A pointer to the RowStatus variable for the component 
        represented by the ifTable entry."
    ::= { extensionIfEntry 1 }


--
-- Version and Compliance statements
--
 
 
-- Object-Group Statement:
 
-- OBJECTS   { ifRowPointer }
-- STATUS     current
-- DESCRIPTION
--       "A list of all current accessible leaf objects."

extensionsGroup OBJECT IDENTIFIER ::= { extensionsMIB 1 }
extensionsGroupBC OBJECT IDENTIFIER ::= { extensionsGroup 3 }
extensionsGroupBC02 OBJECT IDENTIFIER ::= { extensionsGroupBC 2 }
extensionsGroupBC02A OBJECT IDENTIFIER ::= { extensionsGroupBC02 2 }

 
-- Agent-Capabilities Statement:
 
-- PRODUCT-RELEASE "Passport Release 3.2 Standard MIB Extensions."
-- STATUS          current
-- DESCRIPTION
--    "Standard MIB Extensions: MIB Version BC02A."
-- SUPPORTS        Nortel-Magellan-Passport-ExtensionsMIB
-- INCLUDES        { extensionsGroupBC02A }

extensionsCapabilities OBJECT IDENTIFIER ::= { extensionsMIB 3 }
extensionsCapabilitiesBC OBJECT IDENTIFIER ::= { extensionsCapabilities 3 }
extensionsCapabilitiesBC02 OBJECT IDENTIFIER ::= { extensionsCapabilitiesBC 2 }
extensionsCapabilitiesBC02A OBJECT IDENTIFIER ::= { extensionsCapabilitiesBC02 2 }


END
