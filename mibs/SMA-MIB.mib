-- extracted from draft-ietf-ipoib-subnet-mgmt-agent-mib-05.txt
-- at Tue Jun 24 06:13:40 2003

SMA-MIB DEFINITIONS ::= BEGIN 
    
IMPORTS  
   MODULE-IDENTITY, OBJECT-TYPE, experimental,  
   Counter32, NOTIFICATION-TYPE, 
   Integer32, Unsigned32, Gauge32                         FROM SNMPv2-SMI  
   TEXTUAL-CONVENTION,  
   TruthValue, DisplayString                     FROM SNMPv2-TC  
   SnmpAdminString                               FROM SNMP-FRAMEWORK-MIB 
   MODULE-COMPLIANCE, OBJECT-GROUP,  
   NOTIFICATION-GROUP                            FROM SNMPv2-CONF  
   InterfaceIndex                                FROM IF-MIB  
   IbDataPort, IbDataPortAndInvalid, IbGuid, 
   IbUnicastLid, IbMulticastLid, 
   IbSmPortList, infinibandMIB                   FROM IB-TC-MIB;
    
ibSmaMIB MODULE-IDENTITY  
   LAST-UPDATED    "200306061200Z"   -- June 6, 2003
   ORGANIZATION    "IETF IP Over IB Working Group
                    Email: ipoib@ietf.org"
   CONTACT-INFO  
       "Sean Harnedy (sharnedy@mangrovesystems.com)
        Mangrove Systems, Inc.

        Bhargavi Shah (bshah@infiniswitch.com)
        InfiniSwitch Corporation

        Bill Swortwood"
   DESCRIPTION  
      "This module contains managed object definitions for 
       the Subnet Management Agent instrumentation for an 
       InfiniBand Subnet Management Agent (SMA)."  
   REVISION    
      "200306061200Z"  
   DESCRIPTION 
      "Removed IBA Trap numbers 64, 65, 66 and 67 as per IBTA 
       spec version 1.1.  These traps are only sent by Subnet 
       manager and not by Subnet Management Agent"
   REVISION    
      "200301011200Z"  
   DESCRIPTION 
      "Updated MIB for new IBTA spec version 1.1."
   REVISION    
      "200209161200Z"  
   DESCRIPTION 
      "Corrected ranges for number of entries, updated names,
       fixed several enum values, and added LMC object to 
       Port Info table (-03)." 
   REVISION    
      "200207311200Z"  
   DESCRIPTION 
      "Removed ibSmaNodeTrapBuffer; added explicit var bind objects
       and corrected notifications to use them (-03)."
   REVISION    
      "200207181200Z"  
   DESCRIPTION 
      "Syntax corrections (to build with Omegaband tools).
       (-03)."
   REVISION    
      "200205101200Z"  
   DESCRIPTION 
      "Fixed TC assignments; LED table; GUID table index; (-02)."
   REVISION    
      "200203011200Z"  
   DESCRIPTION 
      "Added IANA SMI value; moved TCs to separate ID; renamed OIDs
       (-01)."
   REVISION    
      "200110200000Z"  
   DESCRIPTION 
      "Initial IETF Draft Revision (-00)."  
   ::= { infinibandMIB 3 }
    
--**************************************************************** 
--  Object Indentifiers for the IPOIB SMA MIB  
--**************************************************************** 
   ibSmaObjects         OBJECT IDENTIFIER ::= { ibSmaMIB 1 }  
   ibSmaNotifications   OBJECT IDENTIFIER ::= { ibSmaMIB 2 }  
   ibSmaConformance     OBJECT IDENTIFIER ::= { ibSmaMIB 3 }  

--**************************************************************** 
-- Node Info Group
--**************************************************************** 
   ibSmaNodeInfo        OBJECT IDENTIFIER ::= { ibSmaObjects 1 } 

--**************************************************************** 
-- NodeInfo Scalars Group
--
-- DESCRIPTION: This group contains scalar variables that describe
--    information about the node. It also contains objects that can
--    be used to monitor the behavior of this node via information 
--    provided by the SMA.
--**************************************************************** 
ibSmaNodeString  OBJECT-TYPE 
   SYNTAX      DisplayString(SIZE(1..64))  
   MAX-ACCESS  read-only 
   STATUS      current 
   DESCRIPTION   
      "The node description. This is the Node description string
       from the NodeDescription attribute. The contents of the 
       NodeDescription attribute is the same for all ports on a 
       node."
   REFERENCE
      "InfiniBand Architecture Release 1.1. Vol 1.
       Section 14.2.5.2; Table 127 NodeDescription."
   ::= { ibSmaNodeInfo 1 } 

ibSmaNodeBaseVersion  OBJECT-TYPE 
   SYNTAX      Integer32(1..255) 
   MAX-ACCESS  read-only 
   STATUS      current 
   DESCRIPTION 
      "The supported Management Datagram (MAD) base version.
       This value indicates that the node supports up to and
       including this version. This value is the same for all
       ports on a node. (NOTE: for InfiniBand Release 1 this
       value should be set to 1.)" 
   REFERENCE
      "InfiniBand Architecture Release 1.1. Vol 1.
       Section 14.2.5.3; Table 128 NodeInfo."
   ::= { ibSmaNodeInfo 2 } 

ibSmaNodeClassVersion  OBJECT-TYPE 
   SYNTAX      Integer32(1..255) 
   MAX-ACCESS  read-only 
   STATUS      current 
   DESCRIPTION 
      "The supported Subnet Management Class (SMP) version.
       This value indicates that the node supports up to and
       including this version. This value is the same for all
       ports on a node. (NOTE: for InfiniBand Release 1 this
       value should be set to 1.)" 
   REFERENCE
      "InfiniBand Architecture Release 1.1. Vol 1.
       Section 14.2.5.3; Table 128 NodeInfo."
   ::= { ibSmaNodeInfo 3 } 

ibSmaNodeType  OBJECT-TYPE 
   SYNTAX      INTEGER 
               { 
               channelAdapter(1), 
               switch(2), 
               router(3), 
               other(4) 
               } 
   MAX-ACCESS  read-only 
   STATUS      current 
   DESCRIPTION 
      "Type of IBA device this SMA is supporting. Types are 
            1: Channel Adapter 
            2: Switch 
            3: Router 
           0,4-255: reserved 
       NOTE: all reserved values are reported as other." 
   REFERENCE
      "InfiniBand Architecture Release 1.1. Vol 1.
       Section 14.2.5.3; Table 128 NodeInfo."
   ::= { ibSmaNodeInfo 4 } 

ibSmaNodeNumPorts  OBJECT-TYPE 
   SYNTAX      Integer32(1..254) 
   MAX-ACCESS  read-only 
   STATUS      current 
   DESCRIPTION 
      "The number of physical InfiniBand ports on this node."
   REFERENCE
      "InfiniBand Architecture Release 1.1. Vol 1.
       Section 14.2.5.3; Table 128 NodeInfo."
   ::= { ibSmaNodeInfo 5 } 

ibSmaSystemImageGuid  OBJECT-TYPE 
   SYNTAX      IbGuid
   MAX-ACCESS  read-only 
   STATUS      current 
   DESCRIPTION 
      "The GUID of this node that associates this node with
       other nodes in the same administrative domain. These
       nodes are controlled by common supervisory code.
       This object provides a way for system software to
       indicate the availability of multiple paths to the
       same destination via multiple nodes. If this value is
       0, there is no association. This object may be equal 
       to the ibSmaNodeGuid of one of the associated nodes 
       if that node is not field-replaceable." 
   REFERENCE
      "InfiniBand Architecture Release 1.1. Vol 1.
       Section 14.2.5.3; Table 128 NodeInfo."
   ::= { ibSmaNodeInfo 6 } 

ibSmaNodeGuid  OBJECT-TYPE 
   SYNTAX      IbGuid
   MAX-ACCESS  read-only 
   STATUS      current 
   DESCRIPTION 
      "The GUID of this node. The node can be an HCA, TCA,
       switch, or router. All ports on the same node shall
       report the same NodeGUID value. This provides a means
       for uniquely identifing a node within a subnet and helps 
       to determine the co-location of the ports." 
   REFERENCE
      "InfiniBand Architecture Release 1.1. Vol 1.
       Section 14.2.5.3; Table 128 NodeInfo."
   ::= { ibSmaNodeInfo 7 } 
 
ibSmaNodePortGuid  OBJECT-TYPE 
   SYNTAX      IbGuid
   MAX-ACCESS  read-only 
   STATUS      current 
   DESCRIPTION 
      "The GUID of this port. One port within a node can return
       the NodeGUID as its PortGUID if the port is an integral
       part of the node and is not field-replaceable." 
   REFERENCE
      "InfiniBand Architecture Release 1.1. Vol 1.
       Section 14.2.5.3; Table 128 NodeInfo."
   ::= { ibSmaNodeInfo 8 } 
 
ibSmaNodePartitionTableNum  OBJECT-TYPE 
   SYNTAX      Integer32(1..65535) 
   MAX-ACCESS  read-only 
   STATUS      current 
   DESCRIPTION 
      "Number of entries in the Partition Table for CA, router, and    
       the switch management port. This is at a minimum set to 1 
       for all nodes including switches. This value shall be the same
       for all ports on a node."
   REFERENCE
      "InfiniBand Architecture Release 1.1. Vol 1.
       Section 14.2.5.3; Table 128 NodeInfo."
   ::= { ibSmaNodeInfo 9 } 

ibSmaNodeDeviceId  OBJECT-TYPE 
   SYNTAX      OCTET STRING (SIZE(2)) 
   MAX-ACCESS  read-only 
   STATUS      current 
   DESCRIPTION 
      "Device ID information as assigned by the device manufacturer. 
       This value shall be the same for all ports on a node."
   REFERENCE
      "InfiniBand Architecture Release 1.1. Vol 1.
       Section 14.2.5.3; Table 128 NodeInfo."
   ::= { ibSmaNodeInfo 10 } 

ibSmaNodeRevision  OBJECT-TYPE 
   SYNTAX      OCTET STRING (SIZE(4)) 
   MAX-ACCESS  read-only 
   STATUS      current 
   DESCRIPTION 
      "Device revision as assigned by manufacturer.
       This value shall be the same for all ports on a node."
   REFERENCE
      "InfiniBand Architecture Release 1.1. Vol 1.
       Section 14.2.5.3; Table 128 NodeInfo."
   ::= { ibSmaNodeInfo 11 } 

ibSmaNodeLocalPortNumOrZero  OBJECT-TYPE 
   SYNTAX      Integer32(0..254) 
   MAX-ACCESS  read-only 
   STATUS      current 
   DESCRIPTION 
      "The number of the IBA port which received this SNMP request.     
       If the port is unknown a 0 is returned." 
   REFERENCE
      "InfiniBand Architecture Release 1.1. Vol 1.
       Section 14.2.5.3; Table 128 NodeInfo."
   ::= { ibSmaNodeInfo 12 } 
    
ibSmaNodeVendorId  OBJECT-TYPE 
   SYNTAX      OCTET STRING (SIZE(3)) 
   MAX-ACCESS  read-only 
   STATUS      current 
   DESCRIPTION 
      "Device vendor Identifier as specified by the IEEE.
       This value shall be the same for all ports on a node."
   REFERENCE
      "InfiniBand Architecture Release 1.1. Vol 1.
       Section 14.2.5.3; Table 128 NodeInfo."
   ::= { ibSmaNodeInfo 13 } 

--
-- Objects required for Notification variable binding lists.
--

ibSmaNodeLid  OBJECT-TYPE 
   SYNTAX       Integer32 (0..65535)
   MAX-ACCESS   accessible-for-notify 
   STATUS       current 
   DESCRIPTION  
      "Local Identifier value. Used for notification var bind 
       list object. Retrieved from InfiniBand traps 128, 129, 130, 
       131, 144, 145, 256, 257, 258, and 259."
   REFERENCE
      "InfiniBand Architecture Release 1.1. Vol 1.
       Section 14.2.5.1; Tables 119--126 Traps and Notice Data 
       Details For Traps nnn."
   ::= { ibSmaNodeInfo 14 } 

ibSmaNodePortNum  OBJECT-TYPE
   SYNTAX       IbDataPort
   MAX-ACCESS   accessible-for-notify 
   STATUS       current 
   DESCRIPTION  
      "Port number. Used for notification var bind list object. 
       Retrieved from InfiniBand traps 129, 130, 131, and 259."
   REFERENCE
      "InfiniBand Architecture Release 1.1. Vol 1.
       Section 14.2.5.1; Tables 119--126 Traps and Notice Data 
       Details For Traps nnn."
   ::= { ibSmaNodeInfo 15 } 

ibSmaNodeMethod  OBJECT-TYPE
   SYNTAX       Integer32(0..255)
   MAX-ACCESS   accessible-for-notify 
   STATUS       current 
   DESCRIPTION  
      "Method. Used for notification var bind list object. 
       Retrieved from InfiniBand trap 256."
   REFERENCE
      "InfiniBand Architecture Release 1.1. Vol 1.
       Section 14.2.5.1; Tables 119--126 Traps and Notice Data 
       Details For Traps nnn."
   ::= { ibSmaNodeInfo 16 } 

ibSmaNodeAttributeId  OBJECT-TYPE
   SYNTAX       Unsigned32(0..65535)
   MAX-ACCESS   accessible-for-notify 
   STATUS       current 
   DESCRIPTION  
      "Attribute ID. Used for notification var bind list object. 
       Retrieved from InfiniBand trap 256."
   REFERENCE
      "InfiniBand Architecture Release 1.1. Vol 1.
       Section 14.2.5.1; Tables 119--126 Traps and Notice Data 
       Details For Traps nnn."
   ::= { ibSmaNodeInfo 17 } 

ibSmaNodeAttributeModifier OBJECT-TYPE
   SYNTAX       Unsigned32(0..4294967295)
   MAX-ACCESS   accessible-for-notify 
   STATUS       current 
   DESCRIPTION  
      "Attribute Modifier. Used for notification var bind list object. 
       Retrieved from InfiniBand trap 256."
   REFERENCE
      "InfiniBand Architecture Release 1.1. Vol 1.
       Section 14.2.5.1; Tables 119--126 Traps and Notice Data 
       Details For Traps nnn."
   ::= { ibSmaNodeInfo 18 } 

ibSmaNodeKey  OBJECT-TYPE
   SYNTAX       OCTET STRING (SIZE(8)) 
   MAX-ACCESS   accessible-for-notify 
   STATUS       current 
   DESCRIPTION  
      "M_Key, Q_Key or P_Key. Used for notification var bind list 
       object. Retrieved from InfiniBand traps 256, 257, 258, and 259.
       Note: If it is a P_Key, the 16 most significant bits of the field
       shall be set to 0 and the least significant bits of the field 
       will be set to the P_Key."
   REFERENCE
      "InfiniBand Architecture Release 1.1. Vol 1.  Section 14.2.5.1; 
       Tables 119--126 Traps and Notice Data Details For Traps nnn."
   ::= { ibSmaNodeInfo 19 } 

ibSmaNodeLid2  OBJECT-TYPE
   SYNTAX       Integer32 (0..65535)
   MAX-ACCESS   accessible-for-notify 
   STATUS       current 
   DESCRIPTION  
      "To Local Identifier (LID). Used for notification var bind list
       object. Retrieved from InfiniBand traps 257, 258, and 259." 
   REFERENCE
      "InfiniBand Architecture Release 1.1. Vol 1.
       Section 14.2.5.1; Tables 119--126 Traps and Notice Data 
       Details For Traps nnn."
   ::= { ibSmaNodeInfo 20 } 

ibSmaNodeServiceLevel  OBJECT-TYPE
   SYNTAX       Integer32 (0..15)
   MAX-ACCESS   accessible-for-notify 
   STATUS       current 
   DESCRIPTION  
      "Service Level. Used for notification var bind list object. 
       Retrieved from InfiniBand traps 257, 258, and 259."
   REFERENCE
      "InfiniBand Architecture Release 1.1. Vol 1.
       Section 14.2.5.1; Tables 119--126 Traps and Notice Data 
       Details For Traps nnn."
   ::= { ibSmaNodeInfo 21 } 

ibSmaNodeQueuePair1  OBJECT-TYPE
   SYNTAX       Integer32 (0..16777215)
   MAX-ACCESS   accessible-for-notify 
   STATUS       current 
   DESCRIPTION  
      "Queue Pair (QP) 1. Used for notification var bind list object. 
       Retrieved from InfiniBand traps 257, 258, and 259."
   REFERENCE
      "InfiniBand Architecture Release 1.1. Vol 1.
       Section 14.2.5.1; Tables 119--126 Traps and Notice Data 
       Details For Traps nnn."
   ::= { ibSmaNodeInfo 22 } 

ibSmaNodeQueuePair2  OBJECT-TYPE
   SYNTAX       Integer32 (0..16777215)
   MAX-ACCESS   accessible-for-notify 
   STATUS       current 
   DESCRIPTION  
      "Queue Pair (QP) 2. Used for notification var bind list object. 
       Retrieved from InfiniBand traps 257, 258, and 259."
   REFERENCE
      "InfiniBand Architecture Release 1.1. Vol 1.
       Section 14.2.5.1; Tables 119--126 Traps and Notice Data 
       Details For Traps nnn."
   ::= { ibSmaNodeInfo 23 } 

ibSmaNodeGid1  OBJECT-TYPE
   SYNTAX       OCTET STRING (SIZE(16)) 
   MAX-ACCESS   accessible-for-notify 
   STATUS       current 
   DESCRIPTION  
      "Global Identifier 1. Used for notification var bind list object.
       Retrieved from InfiniBand traps 64, 65, 66, 67, 257, 258, and 
       259. Note: If no GRH is present in the offending packet, this 
       value will be 0."
   REFERENCE
      "InfiniBand Architecture Release 1.1. Vol 1.
       Section 14.2.5.1; Tables 119--126 Traps and Notice Data 
       Details For Traps nnn."
   ::= { ibSmaNodeInfo 24 } 

ibSmaNodeGid2  OBJECT-TYPE
   SYNTAX       OCTET STRING (SIZE(16)) 
   MAX-ACCESS   accessible-for-notify 
   STATUS       current 
   DESCRIPTION  
      "Global Identifier 2. Used for notification var bind list object. 
       Retrieved from InfiniBand traps 257, 258, and 258. Note: If no 
       GRH is present in the offending packet, this value will be 0."
   REFERENCE
      "InfiniBand Architecture Release 1.1. Vol 1.
       Section 14.2.5.1; Tables 119--126 Traps and Notice Data 
       Details For Traps nnn."
   ::= { ibSmaNodeInfo 25 } 
    
ibSmaNodeCapMask  OBJECT-TYPE
   SYNTAX       OCTET STRING (SIZE(4)) 
   MAX-ACCESS   accessible-for-notify 
   STATUS       current 
   DESCRIPTION  
      "Contents of Capability Mask. Retrieved from InfiniBand trap 144."
   REFERENCE
      "InfiniBand Architecture Release 1.1. Vol 1.
       Section 14.2.5.1; Tables 119--126 Traps and Notice Data 
       Details For Traps nnn."
   ::= { ibSmaNodeInfo 26 } 

ibSmaNodeSwitchLid  OBJECT-TYPE
   SYNTAX       Integer32 (0..65535)
   MAX-ACCESS   accessible-for-notify 
   STATUS       current 
   DESCRIPTION  
      "The switch Local Identifier (LID). Used for notification var 
       bind list object. Retrieved from InfiniBand traps 259."
   REFERENCE
      "InfiniBand Architecture Release 1.1. Vol 1.
       Section 14.2.5.1; Tables 119--126 Traps and Notice Data 
       Details For Traps nnn."
   ::= { ibSmaNodeInfo 27 } 

ibSmaNodeDataValid  OBJECT-TYPE
   SYNTAX       OCTET STRING (SIZE(2)) 
   MAX-ACCESS   accessible-for-notify 
   STATUS       current 
   DESCRIPTION  
      "Data valid field retrieved from InfiniBand trap 259.
       It is a bit mask. If the bit is set, the field is valid.
          bit 0: LIDADDR1
          bit 1: LIDADDR2
          bit 2: PKEY
          bit 3: SL
          bit 4: QP1
          bit 5: QP2
          bit 6: GIDADDR1
          bit 7: GIDADDR2
          bit 8-15: reserved (0)."
   REFERENCE
      "InfiniBand Architecture Release 1.1. Vol 1.
       Section 14.2.5.1; Tables 119--126 Traps and Notice Data 
       Details For Traps nnn."
   ::= { ibSmaNodeInfo 28 } 

--**************************************************************** 
-- Switch Info Group
--**************************************************************** 
ibSmaSwitchInfo         OBJECT IDENTIFIER ::= { ibSmaObjects 2 } 

--**************************************************************** 
-- SwitchInfo Scalars Group
--
-- DESCRIPTION: This group contains scalar variables that describe
--    information about an InfiniBand switch. This table shall be 
--    implemented by all switches.
--**************************************************************** 
ibSmaSwLinearFdbTableNum  OBJECT-TYPE 
   SYNTAX      Integer32(0..49151) 
   MAX-ACCESS  read-only 
   STATUS      current 
   DESCRIPTION 
      "Number of entries in the Linear Forwarding Data Base. This
       counts the number of entries supported in the Linear Unicast
       Forwarding Table (starting at LID=0x0000 and going up). 
       The InfiniBand SwitchInfo component is called LinearFDBCap.
       When this count is 0, this indicates that there is no Linear 
       Forwarding Database present." 
   REFERENCE
      "InfiniBand Architecture Release 1.1. Vol 1.
       Section 14.2.5.4; Table 129 SwitchInfo."
   ::= { ibSmaSwitchInfo 1 } 
    
ibSmaSwRandomFdbTableNum  OBJECT-TYPE 
   SYNTAX      Integer32(0..49151) 
   MAX-ACCESS  read-only 
   STATUS      current 
   DESCRIPTION 
      "Number of entries in the Random Forwarding Data Base. This
       counts the number of entries supported in the Random Unicast 
       Forwarding Table. The InfiniBand SwitchInfo component is 
       called RandomFDBCap. When this count is 0, this indicates 
       that there is no Random Forwarding Database present." 
   REFERENCE
      "InfiniBand Architecture Release 1.1. Vol 1.
       Section 14.2.5.4; Table 129 SwitchInfo."
   ::= { ibSmaSwitchInfo 2 } 
    
ibSmaSwMulticastFdbTableNum  OBJECT-TYPE 
   SYNTAX      Integer32(0..16383) 
   MAX-ACCESS  read-only 
   STATUS      current 
   DESCRIPTION 
      "Number of entries in the Multicast Forwarding Data Base. This
       counts the number of entries supported in the Multicast 
       Forwarding Table (starting at LID=0xC000 and going up). 
       The InfiniBand SwitchInfo component is called MulticastFDBCap."
   REFERENCE
      "InfiniBand Architecture Release 1.1. Vol 1.
       Section 14.2.5.4; Table 129 SwitchInfo."
   ::= { ibSmaSwitchInfo 3 } 

ibSmaSwLinearFdbTop  OBJECT-TYPE 
   SYNTAX      Integer32(0..49151) 
   MAX-ACCESS  read-only 
   STATUS      current 
   DESCRIPTION  
      "Indicates the top of the linear forwarding database. Packets 
       received with unicast DLIDs greater than this value are 
       discarded by the switch. A valid LinearFdbTop is less than
       LinearFdbCap. This component applies only to switches that 
       implement linear forwarding tables and is ignored by switches 
       that implement random forwarding tables. For the latter cases 
       a 0 is returned." 
   REFERENCE
      "InfiniBand Architecture Release 1.1. Vol 1.
       Section 14.2.5.4; Table 129 SwitchInfo."
   ::= { ibSmaSwitchInfo 4 } 
    
ibSmaSwDefaultPort  OBJECT-TYPE 
   SYNTAX      Integer32(0..254) 
   MAX-ACCESS  read-only 
   STATUS      current 
   DESCRIPTION  
      "Default forwarding port for unicast packets from the other 
       ports whose DLID does not exist in the random forwarding 
       table. If the port number is unknown, a 0 is returned.
       If this object is set to a non-existent port, subsequent 
       responses may contain any non-existent port number."  
   REFERENCE
      "InfiniBand Architecture Release 1.1. Vol 1.
       Section 14.2.5.4; Table 129 SwitchInfo."
   ::= { ibSmaSwitchInfo 5 } 
 
ibSmaSwDefMcastPriPort  OBJECT-TYPE 
   SYNTAX      Integer32(0..254) 
   MAX-ACCESS  read-only 
   STATUS      current 
   DESCRIPTION  
      "Default forwarding port for multicast packets from the other 
       ports whose DLID does not exist in the forwarding table. If 
       port number is unknown, a 0 is returned. If this object is 
       set to a non-existent port, subsequent responses may contain 
       any non-existent port number."  
   REFERENCE
      "InfiniBand Architecture Release 1.1. Vol 1.
       Section 14.2.5.4; Table 129 SwitchInfo. Also section
       18.2.4.3.3 on Required Multicast Relay."
   ::= { ibSmaSwitchInfo 6 } 

ibSmaSwDefMcastNotPriPort  OBJECT-TYPE 
   SYNTAX      Integer32(0..254) 
   MAX-ACCESS  read-only 
   STATUS      current 
   DESCRIPTION  
      "Forward to this port all the multicast packets from the 
       Default Primary port whose DLID does not exist in the 
       forwarding table. If it is unknown, a 0 is returned.
       If this object is set to a non-existent port, subsequent 
       responses may contain any non-existent port number."  
   REFERENCE
      "InfiniBand Architecture Release 1.1. Vol 1.
       Section 14.2.5.4; Table 129 SwitchInfo. Also section
       18.2.4.3.3 on Required Multicast Relay."
   ::= { ibSmaSwitchInfo 7 } 
 
ibSmaSwLifeTimeValue  OBJECT-TYPE 
   SYNTAX      Integer32(0..31) 
   MAX-ACCESS  read-only 
   STATUS      current 
   DESCRIPTION  
      "Sets the time a packet can live in the switch. This Lifetime
       Value (LV) is used as a parameter to calculate Switch Lifetime
       Limit (SLL) value. To calculate a valid SLL, the LV must be
       between 0 and 19, inclusive. If the LV value is greater than
       19, the SLL is to be interpreted as infinite."
   REFERENCE
      "InfiniBand Architecture Release 1.1. Vol 1.
       Section 14.2.5.4; Table 129 SwitchInfo. Also section
       18.2.5.4 on Transmitter Queueing."
   ::= { ibSmaSwitchInfo 8 } 

ibSmaSwPortStateChange  OBJECT-TYPE 
   SYNTAX      Integer32(0..1) 
   MAX-ACCESS  read-only 
   STATUS      current 
   DESCRIPTION  
      "This object is set to 1 whenever the PortState component
       makes any of the following state changes in the link FSM:

       Down-->Initialize,
       Initialize-->Down,
       Armed-->Down, or
       Active-->Down

       Also, changes in PortState resulting from SubnSet IBA command
       do not change this bit. This object is set to 0 when the SMA
       writes a 1; writing a 0 is ignored." 
   REFERENCE
      "InfiniBand Architecture Release 1.1. Vol 1.
       Section 14.2.5.4; Table 129 SwitchInfo."
   ::= { ibSmaSwitchInfo 9 } 

ibSmaSwLidsPerPort  OBJECT-TYPE 
   SYNTAX      Integer32(0..65535)
   MAX-ACCESS  read-only 
   STATUS      current 
   DESCRIPTION  
      "Specifies the number of LID/LMC combinations that may be  
       assigned to a given external port for switches that support  
       the Random Forwarding table."  
   REFERENCE
      "InfiniBand Architecture Release 1.1. Vol 1.
       Section 14.2.5.4; Table 129 SwitchInfo."
   ::= { ibSmaSwitchInfo 10 } 
 
ibSmaSwPartitionEnforceNum  OBJECT-TYPE 
   SYNTAX      Integer32(0..65535) 
   MAX-ACCESS  read-only 
   STATUS      current 
   DESCRIPTION  
      "Specifies the number of entries in the partition enforcement 
       table per physical IBA port. The 0 value indicates that 
       partition enforcement is not supported by the switch." 
   REFERENCE
      "InfiniBand Architecture Release 1.1. Vol 1.
       Section 14.2.5.4; Table 129 SwitchInfo."
   ::= { ibSmaSwitchInfo 11 } 
 
ibSmaSwInboundEnforceCap  OBJECT-TYPE 
   SYNTAX      TruthValue 
   MAX-ACCESS  read-only 
   STATUS      current 
   DESCRIPTION  
      "Flag that indicates whether the switch is capable 
       of partition enforcement on received packets." 
   REFERENCE
      "InfiniBand Architecture Release 1.1. Vol 1.
       Section 14.2.5.4; Table 129 SwitchInfo."
   ::= { ibSmaSwitchInfo 12 } 
    
ibSmaSwOutboundEnforceCap  OBJECT-TYPE 
   SYNTAX      TruthValue 
   MAX-ACCESS  read-only 
   STATUS      current 
   DESCRIPTION  
      "Flag that indicates whether the switch is capable 
       of partition enforcement on transmitted packets." 
   REFERENCE
      "InfiniBand Architecture Release 1.1. Vol 1.
       Section 14.2.5.4; Table 129 SwitchInfo."
   ::= { ibSmaSwitchInfo 13 } 

ibSmaSwFilterRawPktInputCap  OBJECT-TYPE 
   SYNTAX      TruthValue 
   MAX-ACCESS  read-only 
   STATUS      current 
   DESCRIPTION  
      "Flag to indicate whether the switch is capable of 
       raw packet enforcement on received packets."  
   REFERENCE
      "InfiniBand Architecture Release 1.1. Vol 1.
       Section 14.2.5.4; Table 129 SwitchInfo."
   ::= { ibSmaSwitchInfo 14 } 
 
ibSmaSwFilterRawPktOutputCap  OBJECT-TYPE 
   SYNTAX      TruthValue 
   MAX-ACCESS  read-only 
   STATUS      current 
   DESCRIPTION  
      "Flag to indicate whether the switch is capable of 
       raw packet enforcement on transmitted packets." 
   REFERENCE
      "InfiniBand Architecture Release 1.1. Vol 1.
       Section 14.2.5.4; Table 129 SwitchInfo."
   ::= { ibSmaSwitchInfo 15 } 

ibSmaSwEnhancedPort0  OBJECT-TYPE 
   SYNTAX      TruthValue 
   MAX-ACCESS  read-only 
   STATUS      current 
   DESCRIPTION  
      "Flag to indicate whether switch port 0 supports enhanced
       functions (TCA port). If false, switch port 0 is a base
       switch port 0."
   REFERENCE
      "InfiniBand Architecture Release 1.1. Vol 1.
       Section 14.2.5.4; Table 129 SwitchInfo."
   ::= { ibSmaSwitchInfo 16 } 

--**************************************************************** 
-- The GUID Info Group
--**************************************************************** 
ibSmaGuidInfo             OBJECT IDENTIFIER ::= { ibSmaObjects 3 } 

-- *************************************************************
-- The Global Unique Identifier (GUID) Info Group
--
-- DESCRIPTION: The Global Unique Identifier Table.
-- *************************************************************
ibSmaGuidInfoTable OBJECT-TYPE
   SYNTAX       SEQUENCE OF IbGuidInfoEntry
   MAX-ACCESS   not-accessible  
   STATUS       current 
   DESCRIPTION 
      "A table containing SMA GUID information." 
   ::= { ibSmaGuidInfo 1 } 

ibGuidInfoEntry OBJECT-TYPE
   SYNTAX       IbGuidInfoEntry      
   MAX-ACCESS   not-accessible 
   STATUS       current 
   DESCRIPTION 
      "A conceptual row of the ibSmaGuidInfoTable containing 
       information about a particular GUID entry."
   INDEX   { ibSmaGuidPortIndex, ibSmaGuidIndex }  
   ::= { ibSmaGuidInfoTable 1 } 

IbGuidInfoEntry ::= SEQUENCE { 
   ibSmaGuidPortIndex                        IbDataPort,
   ibSmaGuidIndex                            Integer32,
   ibSmaGuidVal                              IbGuid
   }

ibSmaGuidPortIndex   OBJECT-TYPE 
   SYNTAX      IbDataPort
   MAX-ACCESS  not-accessible 
   STATUS      current 
   DESCRIPTION  
      "Index that identifies IB port assoicated with this GUID table."
   ::= { ibGuidInfoEntry 1 }

ibSmaGuidIndex  OBJECT-TYPE  
   SYNTAX      Integer32(1..255) 
   MAX-ACCESS  not-accessible 
   STATUS      current  
   DESCRIPTION  
      "Index that identifies the GUID entry for this port.  For any IB  
       port there can be multiple 64 bit GUIDs assigned. The maximum 
       number is implementationdependent. If the port does not have a 
       GUID assigned to it, the row will have 1 entry with a 0 value." 
   ::= { ibGuidInfoEntry 2 }
     
ibSmaGuidVal OBJECT-TYPE
   SYNTAX       IbGuid
   MAX-ACCESS   read-only
   STATUS       current
   DESCRIPTION
      "The Global Unique Identifier (GUID) for this port entity."
   REFERENCE
      "InfiniBand Architecture Release 1.1. Vol 1.  Section 14.2.5.5; 
       Table 130 GUIDInfo and Table 131 GUID Block Element." 
   ::= { ibGuidInfoEntry 3 }

--**************************************************************** 
-- The Port Info Group
--**************************************************************** 
ibSmaMgmtPortInfo         OBJECT IDENTIFIER ::= { ibSmaObjects 4 } 

ibSmaDataPortInfo         OBJECT IDENTIFIER ::= { ibSmaObjects 5 } 

--**************************************************************** 
-- PortInfo Management Port Scalars Group
--
-- DESCRIPTION: This Group contains Subnet Management Information
--    about the Management Port (InfiniBand Port 0).
--**************************************************************** 

ibSmaPortMKey  OBJECT-TYPE 
   SYNTAX       OCTET STRING (SIZE(8)) 
   MAX-ACCESS   read-only 
   STATUS       current 
   DESCRIPTION  
      "The 8-byte management key that is kept locally
       on each port. If the value is 0's, no authentication
       is done."  
   REFERENCE
      "InfiniBand Architecture Release 1.1. Vol 1.
       Section 14.2.5.6; Table 132 PortInfo. Also
       see Section 14.2.4."
   ::= { ibSmaMgmtPortInfo 1 } 
    
ibSmaPortGidPrefix  OBJECT-TYPE 
   SYNTAX           OCTET STRING (SIZE(8)) 
   MAX-ACCESS       read-only 
   STATUS           current 
   DESCRIPTION  
      "GID prefix for this port."  
   REFERENCE
      "InfiniBand Architecture Release 1.1. Vol 1.
       Section 14.2.5.6; Table 132 PortInfo."
   ::= { ibSmaMgmtPortInfo 2 } 
    
ibSmaPortLid  OBJECT-TYPE 
   SYNTAX      Integer32(0..49151) 
   MAX-ACCESS  read-only 
   STATUS      current 
   DESCRIPTION  
      "The base LID of this port." 
   REFERENCE
      "InfiniBand Architecture Release 1.1. Vol 1.
       Section 14.2.5.6; Table 132 PortInfo."
   ::= { ibSmaMgmtPortInfo 3 } 

ibSmaPortMasterSmLid  OBJECT-TYPE 
   SYNTAX      Integer32(0..49151) 
   MAX-ACCESS  read-only 
   STATUS      current 
   DESCRIPTION  
      "The LID of the master SM that is managing this port."  
   REFERENCE
      "InfiniBand Architecture Release 1.1. Vol 1.
       Section 14.2.5.6; Table 132 PortInfo."
   ::= { ibSmaMgmtPortInfo 4 } 

ibSmaPortIsSubnetManager  OBJECT-TYPE
   SYNTAX      TruthValue 
   MAX-ACCESS  read-only 
   STATUS      current 
   DESCRIPTION  
      "Capability flag for this node: Is Subnet Manager?"
   REFERENCE
      "InfiniBand Architecture Release 1.1. Vol 1.
       Section 14.2.5.6; Table 132 PortInfo."
   ::= { ibSmaMgmtPortInfo 5 } 
 
ibSmaPortIsNoticeSupported  OBJECT-TYPE
   SYNTAX      TruthValue 
   MAX-ACCESS  read-only 
   STATUS      current 
   DESCRIPTION  
      "Capability flag for this node: Are Notices Supported?"
   REFERENCE
      "InfiniBand Architecture Release 1.1. Vol 1.
       Section 14.2.5.6; Table 132 PortInfo."
   ::= { ibSmaMgmtPortInfo 6 } 
    
ibSmaPortIsTrapSupported  OBJECT-TYPE
   SYNTAX      TruthValue 
   MAX-ACCESS  read-only 
   STATUS      current 
   DESCRIPTION  
      "Capability flag for this node: Are IBA Traps Supported?"
   REFERENCE
      "InfiniBand Architecture Release 1.1. Vol 1.
       Section 14.2.5.6; Table 132 PortInfo."
   ::= { ibSmaMgmtPortInfo 7 } 

ibSmaPortIsAutoMigrateSupported  OBJECT-TYPE 
   SYNTAX      TruthValue 
   MAX-ACCESS  read-only 
   STATUS      current 
   DESCRIPTION  
      "Capability flag for this node: Is Automatic Migration
       Supported?"
   REFERENCE
      "InfiniBand Architecture Release 1.1. Vol 1.
       Section 14.2.5.6; Table 132 PortInfo."
   ::= { ibSmaMgmtPortInfo 8 } 
 
ibSmaPortIsSlMappingSupported  OBJECT-TYPE
   SYNTAX      TruthValue 
   MAX-ACCESS  read-only 
   STATUS      current 
   DESCRIPTION  
      "Capability flag for this node: Is SL Mapping Supported?"
   REFERENCE
      "InfiniBand Architecture Release 1.1. Vol 1.
       Section 14.2.5.6; Table 132 PortInfo."
   ::= { ibSmaMgmtPortInfo 9 } 
 
ibSmaPortIsMKeyNvram  OBJECT-TYPE
   SYNTAX      TruthValue 
   MAX-ACCESS  read-only 
   STATUS      current 
   DESCRIPTION  
      "Capability flag for this node: Is M_Key in NVRAM?"
   REFERENCE
      "InfiniBand Architecture Release 1.1. Vol 1.
       Section 14.2.5.6; Table 132 PortInfo."
   ::= { ibSmaMgmtPortInfo 10 } 
 
ibSmaPortIsPKeyNvram  OBJECT-TYPE
   SYNTAX      TruthValue 
   MAX-ACCESS  read-only 
   STATUS      current 
   DESCRIPTION  
      "Capability flag for this node: Is P_Key in NVRAM?"
   REFERENCE
      "InfiniBand Architecture Release 1.1. Vol 1.
       Section 14.2.5.6; Table 132 PortInfo."
   ::= { ibSmaMgmtPortInfo 11 } 

ibSmaPortIsLedInfoSupported  OBJECT-TYPE
   SYNTAX      TruthValue 
   MAX-ACCESS  read-only 
   STATUS      current 
   DESCRIPTION  
      "Capability flag for this node: Is LED Information
       Supported?"
   REFERENCE
      "InfiniBand Architecture Release 1.1. Vol 1.
       Section 14.2.5.6; Table 132 PortInfo."
   ::= { ibSmaMgmtPortInfo 12 } 
 
ibSmaPortIsSmDisabled  OBJECT-TYPE
   SYNTAX      TruthValue 
   MAX-ACCESS  read-only 
   STATUS      current 
   DESCRIPTION  
      "Capability flag for this node: Is Subnet Manager Disabeld?"
   REFERENCE
      "InfiniBand Architecture Release 1.1. Vol 1.
       Section 14.2.5.6; Table 132 PortInfo."
   ::= { ibSmaMgmtPortInfo 13 } 

ibSmaPortIsSysImgGuidSupported  OBJECT-TYPE
   SYNTAX      TruthValue 
   MAX-ACCESS  read-only 
   STATUS      current 
   DESCRIPTION  
      "Capability flag for this node: Is System Image GUID Supported?"
   REFERENCE
      "InfiniBand Architecture Release 1.1. Vol 1.
       Section 14.2.5.6; Table 132 PortInfo."
   ::= { ibSmaMgmtPortInfo 14 } 

ibSmaPortIsPKeyExtPortTrapSup  OBJECT-TYPE
   SYNTAX      TruthValue 
   MAX-ACCESS  read-only 
   STATUS      current 
   DESCRIPTION  
      "Capability flag for this node: Is P_Key Switch External Port
       Trap supported?"
   REFERENCE
      "InfiniBand Architecture Release 1.1. Vol 1.
       Section 14.2.5.6; Table 132 PortInfo."
   ::= { ibSmaMgmtPortInfo 15 } 

ibSmaPortIsCommManageSupported  OBJECT-TYPE
   SYNTAX      TruthValue 
   MAX-ACCESS  read-only 
   STATUS      current 
   DESCRIPTION  
      "Capability flag for this node: Is Communication Management
       Supported?"
   REFERENCE
      "InfiniBand Architecture Release 1.1. Vol 1.
       Section 14.2.5.6; Table 132 PortInfo."
   ::= { ibSmaMgmtPortInfo 16 } 
 
ibSmaPortIsSnmpTunnelSupported  OBJECT-TYPE
   SYNTAX      TruthValue 
   MAX-ACCESS  read-only 
   STATUS      current 
   DESCRIPTION  
      "Capability flag for this node: Is SNMP Tunneling
       Supported?"
   REFERENCE
      "InfiniBand Architecture Release 1.1. Vol 1.
       Section 14.2.5.6; Table 132 PortInfo."
   ::= { ibSmaMgmtPortInfo 17 } 

ibSmaPortIsReinitSupported  OBJECT-TYPE
   SYNTAX      TruthValue 
   MAX-ACCESS  read-only 
   STATUS      current 
   DESCRIPTION  
      "Capability flag for this node: Is Reinitialization Supported?"
   REFERENCE
      "InfiniBand Architecture Release 1.1. Vol 1.
       Section 14.2.5.6; Table 132 PortInfo."
   ::= { ibSmaMgmtPortInfo 18 } 

ibSmaPortIsDevManageSupported  OBJECT-TYPE
   SYNTAX      TruthValue 
   MAX-ACCESS  read-only 
   STATUS      current 
   DESCRIPTION  
      "Capability flag for this node: Is Device Management
       Supported?"
   REFERENCE
      "InfiniBand Architecture Release 1.1. Vol 1.
       Section 14.2.5.6; Table 132 PortInfo."
   ::= { ibSmaMgmtPortInfo 19 } 

ibSmaPortIsVendorClassSupported  OBJECT-TYPE
   SYNTAX      TruthValue 
   MAX-ACCESS  read-only 
   STATUS      current 
   DESCRIPTION  
      "Capability flag for this node: Is Vendor Class Supported?"
   REFERENCE
      "InfiniBand Architecture Release 1.1. Vol 1.
       Section 14.2.5.6; Table 132 PortInfo."
   ::= { ibSmaMgmtPortInfo 20 } 


ibSmaPortIsDrNoticeSupported  OBJECT-TYPE
   SYNTAX      TruthValue 
   MAX-ACCESS  read-only 
   STATUS      current 
   DESCRIPTION  
      "Capability flag for this node: Is DR Notice Supported?"
   REFERENCE
      "InfiniBand Architecture Release 1.1. Vol 1.
       Section 14.2.5.6; Table 132 PortInfo."
   ::= { ibSmaMgmtPortInfo 21 } 

ibSmaPortIsCapMaskNoticSupported  OBJECT-TYPE
   SYNTAX      TruthValue 
   MAX-ACCESS  read-only 
   STATUS      current 
   DESCRIPTION  
      "Capability flag for this node: Is Capability Mask Notice 
       Supported?"
   REFERENCE
      "InfiniBand Architecture Release 1.1. Vol 1.
       Section 14.2.5.6; Table 132 PortInfo."
   ::= { ibSmaMgmtPortInfo 22 } 

ibSmaPortIsBootMgmtSupported  OBJECT-TYPE
   SYNTAX      TruthValue 
   MAX-ACCESS  read-only 
   STATUS      current 
   DESCRIPTION  
      "Capability flag for this node: Is Boot Management Supported?"
   REFERENCE
      "InfiniBand Architecture Release 1.1. Vol 1.
       Section 14.2.5.6; Table 132 PortInfo."
   ::= { ibSmaMgmtPortInfo 23 } 

ibSmaPortMKeyLeasePeriod  OBJECT-TYPE 
   SYNTAX        Integer32(0..65535) 
   UNITS         "seconds"
   MAX-ACCESS    read-only 
   STATUS        current 
   DESCRIPTION  
      "Specifies the initial value of the lease period timer (in 
       seconds). The lease period is the length of time that the 
       M_Key Protection bits are to remain non-zero after a 
       SubnSet(PortInfo) fails the M_Key authentication check.
       When the value is 0, the lease period shall never expire."
   REFERENCE
      "InfiniBand Architecture Release 1.1. Vol 1.
       Section 14.2.5.6; Table 132 PortInfo; Also Section 
       14.2.4.2."
   ::= { ibSmaMgmtPortInfo 24 } 

ibSmaPortMKeyProtectBits  OBJECT-TYPE 
   SYNTAX      INTEGER { 
                   noMKeyProtection(1), 
                   succeedWithReturnKey(2), 
                   succeedWithReturnZeroes(3), 
                   failOnNoMatch(4) 
                   }
   MAX-ACCESS  read-only 
   STATUS      current 
   DESCRIPTION  
      "Management Key (M_Key) protection bits. Management Key
       must have a non-zero value." 
   REFERENCE
      "InfiniBand Architecture Release 1.1. Vol 1.  Section 14.2.5.6; 
       Table 132 PortInfo; Also Section 14.2.4.1; Table 115 explains
       the Protection Levels."
   ::= { ibSmaMgmtPortInfo 25 } 
 
ibSmaPortMasterSmSl  OBJECT-TYPE 
   SYNTAX      Integer32(0..15) 
   MAX-ACCESS  read-only 
   STATUS      current 
   DESCRIPTION  
      "The administrative Service Level of the master SM that 
       is managing this port. "       
   REFERENCE
      "InfiniBand Architecture Release 1.1. Vol 1.
       Section 14.2.5.6; Table 132 PortInfo."
   ::= { ibSmaMgmtPortInfo 26 } 

ibSmaPortInitTypeLoad  OBJECT-TYPE 
   SYNTAX      TruthValue 
   MAX-ACCESS  read-only 
   STATUS      current 
   DESCRIPTION  
      "The initialization type flags indicate the type of 
       intialization requested by this port before SM moves it 
       to Active or Armed state.

       Initialization Type flag: NoLoad. If the value is false(2),
       the attributes should be initialized. If the value is true(1),
       no data should be loaded into the attributes at all, asserting
       that the last-loaded data still exists and is valid."
   REFERENCE
      "InfiniBand Architecture Release 1.1. Vol 1.
       Section 14.2.5.6; Table 132 PortInfo."
   ::= { ibSmaMgmtPortInfo 27 } 

ibSmaPortInitTypeContent  OBJECT-TYPE 
   SYNTAX      TruthValue 
   MAX-ACCESS  read-only 
   STATUS      current 
   DESCRIPTION  
      "Initialization Type flag: PreserveContent. If the value is
       false(2), the port makes no request regarding the content 
       of the data that is loaded into its attributes. If it is 
       true(1), the port is requesting that all such data, if loaded,
       be set to the most recent content loaded by the SM."
   REFERENCE
      "InfiniBand Architecture Release 1.1. Vol 1.
       Section 14.2.5.6; Table 132 PortInfo."
   ::= { ibSmaMgmtPortInfo 28 } 

ibSmaPortInitTypePresence  OBJECT-TYPE 
   SYNTAX      TruthValue 
   MAX-ACCESS  read-only 
   STATUS      current 
   DESCRIPTION  
      "Initialization Type flag: PreservePresence. If the value is
       false(2), the port is requesting that all settable SA attributes
       referencing this port be removed prior to activating this port
       and Traps 64/65 be sent. If the value is true(1), the port is
       requesting that all such data be preserved, and that the traps
       not be sent."
   REFERENCE
      "InfiniBand Architecture Release 1.1. Vol 1.
       Section 14.2.5.6; Table 132 PortInfo."
   ::= { ibSmaMgmtPortInfo 29 } 

ibSmaPortInitTypeResuscitate  OBJECT-TYPE 
   SYNTAX      TruthValue 
   MAX-ACCESS  read-only 
   STATUS      current 
   DESCRIPTION  
      "Initialization Type flag: DoNotResuscitate. If the value is
       false(2), ibSmaPortInitTypeLoad, ibSmaPortInitTypeContent, and
       ibSmaPortInitTypePresence ARE valid. If the value is true(1),
       ibSmaPortInitTypeLoad, ibSmaPortInitTypeContent, and
       ibSmaPortInitTypePresence ARE NOT valid. The port is requesting
       that reinitialization of this port and the in/out of service
       traps (64/65) be delayed until this flag is set to false(1)."
   REFERENCE
      "InfiniBand Architecture Release 1.1. Vol 1.
       Section 14.2.5.6; Table 132 PortInfo."
   ::= { ibSmaMgmtPortInfo 30 } 

ibSmaPortInitNoLoadReply  OBJECT-TYPE 
   SYNTAX      TruthValue 
   MAX-ACCESS  read-only 
   STATUS      current 
   DESCRIPTION  
      "The Init Reply flags are written by the SM prior to
       changing the port to Active or Armed state.

       Initialization Type Reply flag: NoLoadReply. If this value
       is false(2), the port attributes were initialized. If the
       value is true(1), no data was loaded into the port attributes."
   REFERENCE
      "InfiniBand Architecture Release 1.1. Vol 1.
       Section 14.2.5.6; Table 132 PortInfo."
   ::= { ibSmaMgmtPortInfo 31 } 

ibSmaPortInitPreserveContReply  OBJECT-TYPE 
   SYNTAX      TruthValue 
   MAX-ACCESS  read-only 
   STATUS      current 
   DESCRIPTION  
      "Initialization Type flag: PreserveContentReply. If this value
       is false(2), no information is available regarding the content
       of the data loaded into the port attributes. If the value is
       true(1), the data loaded into the port attributes was set 
       to the content most recently loaded by the SM."
   REFERENCE
      "InfiniBand Architecture Release 1.1. Vol 1.
       Section 14.2.5.6; Table 132 PortInfo."
   ::= { ibSmaMgmtPortInfo 32 } 

ibSmaPortInitPreservePresReply  OBJECT-TYPE 
   SYNTAX      TruthValue 
   MAX-ACCESS  read-only 
   STATUS      current 
   DESCRIPTION  
      "Initialization Type Reply flag: PreservePresenceReply. If this 
       value is false(2), all settable SA attributes referencing this
       port were removed prior to activating this port and the in/out 
       service traps 64 and 65 were sent. If the value is true(1), 
       all such data existing when this port was last active was not 
       removed and the traps 64/65 were not sent."
   REFERENCE
      "InfiniBand Architecture Release 1.1. Vol 1.
       Section 14.2.5.6; Table 132 PortInfo."
   ::= { ibSmaMgmtPortInfo 33 } 

ibSmaPortMKeyViolations  OBJECT-TYPE 
   SYNTAX           Gauge32(0..65535) 
   MAX-ACCESS       read-only 
   STATUS           current 
   DESCRIPTION  
      "Counts the number of SMP packets that have been received at 
       this port that have invalid M_Keys. This object is a 
       latching gauge, in that whenever the maximum gauge value is
       encounterd (i.e., the count reaches all 1's), the SMA must
       reset the gauge to 0, before this object begins incrementing
       its count again."
   REFERENCE
      "InfiniBand Architecture Release 1.1. Vol 1.
       Section 14.2.5.6; Table 132 PortInfo."
   ::= { ibSmaMgmtPortInfo 34 } 
 
ibSmaPortPKeyViolations  OBJECT-TYPE 
   SYNTAX           Gauge32(0..65535) 
   MAX-ACCESS       read-only 
   STATUS           current 
   DESCRIPTION  
      "Counts the number of SMP packets that have been received at 
       this port that have invalid P_Keys. This object is a 
       latching gauge, in that whenever the maximum gauge value is
       encounterd (i.e., the count reaches all 1's), the SMA must
       reset the gauge to 0, before this object begins incrementing
       its count again."
   REFERENCE
      "InfiniBand Architecture Release 1.1. Vol 1.
       Section 14.2.5.6; Table 132 PortInfo; Also Section 10.9.4."
   ::= { ibSmaMgmtPortInfo 35 } 

ibSmaPortQKeyViolations  OBJECT-TYPE 
   SYNTAX           Gauge32(0..65535) 
   MAX-ACCESS       read-only 
   STATUS           current 
   DESCRIPTION 
      "Counts the number of SMP packets that have been received at 
       this port that have invalid Q_Keys. This object is a 
       latching gauge, in that whenever the maximum gauge value is
       encounterd (i.e., the count reaches all 1's), the SMA must
       reset the gauge to 0, before this object begins incrementing
       its count again."
   REFERENCE
      "InfiniBand Architecture Release 1.1. Vol 1.
       Section 14.2.5.6; Table 132 PortInfo; Also see Section 
       10.2.4."
   ::= { ibSmaMgmtPortInfo 36 } 
 
ibSmaPortNumGuid  OBJECT-TYPE 
   SYNTAX      Integer32(0..255) 
   MAX-ACCESS  read-only 
   STATUS      current 
   DESCRIPTION  
      "Number of GUID entries supported in the GUIDInfo attribute 
       for this port." 
   REFERENCE
      "InfiniBand Architecture Release 1.1. Vol 1.
       Section 14.2.5.6; Table 132 PortInfo."
   ::= { ibSmaMgmtPortInfo 37 } 
 
ibSmaPortSubnetTimeout  OBJECT-TYPE 
   SYNTAX      Integer32(0..31) 
   MAX-ACCESS  read-only 
   STATUS      current 
   DESCRIPTION  
      "Specifies the maximum expected subnet propagation delay, 
       which depends upon the configuration of the switches, to 
       reach any other port in the subnet and shall also be used 
       to determine the maximum rate which SubnTraps() can be sent 
       from this port by the SMA." 
   REFERENCE
      "InfiniBand Architecture Release 1.1. Vol 1.
       Section 14.2.5.6; Table 132 PortInfo."
   ::= { ibSmaMgmtPortInfo 38 } 

ibSmaPortResponseTimeValue  OBJECT-TYPE 
   SYNTAX           Integer32(0..31) 
   MAX-ACCESS       read-only 
   STATUS           current 
   DESCRIPTION  
      "Specifies the expected maximum time between the port reception 
       of a SMP and the transmission of the associated 
       response." 
   REFERENCE
      "InfiniBand Architecture Release 1.1. Vol 1.
       Section 14.2.5.6; Table 132 PortInfo."
   ::= { ibSmaMgmtPortInfo 39 } 

--**************************************************************** 
-- PortInfo InfiniBand Data Port Group
--
-- DESCRIPTION: This Group contains a table that contains the Subnet
--    Management Information about each InfiniBand data port.
--**************************************************************** 

ibSmaPortInfoTable  OBJECT-TYPE 
   SYNTAX       SEQUENCE OF IbSmaPortInfoEntry 
   MAX-ACCESS   not-accessible  
   STATUS       current 
   DESCRIPTION 
      "A table containing SMA PortInfo information." 
   ::= { ibSmaDataPortInfo 1 } 
 
ibSmaPortInfoEntry  OBJECT-TYPE 
   SYNTAX       IbSmaPortInfoEntry 
   MAX-ACCESS   not-accessible 
   STATUS       current 
   DESCRIPTION 
      "A conceptual row of the ibSmaPortInfoTable containing 
       information about a particular data port and its attributes." 
   INDEX   { ibSmaPortIndex }  
   ::= { ibSmaPortInfoTable 1 } 

IbSmaPortInfoEntry ::= SEQUENCE { 
   ibSmaPortIndex                           IbDataPort,
   ibSmaPortLinkWidthEnabled                INTEGER,
   ibSmaPortLinkWidthSupported              INTEGER,
   ibSmaPortLinkWidthActive                 INTEGER,
   ibSmaPortLinkSpeedSupported              INTEGER,
   ibSmaPortLinkState                       INTEGER,
   ibSmaPortPhysState                       INTEGER,
   ibSmaPortLinkDownDefaultState            INTEGER,
   ibSmaPortLidMaskCount                    Integer32,
   ibSmaPortLinkSpeedActive                 INTEGER,
   ibSmaPortLinkSpeedEnabled                INTEGER,
   ibSmaPortNeighborMtu                     INTEGER,
   ibSmaPortVirtLaneSupport                 INTEGER,
   ibSmaPortVlHighPriorityLimit             Integer32,
   ibSmaPortVlArbHighCapacity               Integer32,
   ibSmaPortVlArbLowCapacity                Integer32,
   ibSmaPortMtuCapacity                     INTEGER,
   ibSmaPortVlStallCount                    Integer32,
   ibSmaPortHeadOfQueueLife                 Integer32,
   ibSmaPortOperationalVls                  INTEGER,
   ibSmaPortPartEnforceInbound              TruthValue,
   ibSmaPortPartEnforceOutbound             TruthValue,
   ibSmaPortFilterRawPktInbound             TruthValue,
   ibSmaPortFilterRawPktOutbound            TruthValue,
   ibSmaPortLocalPhysErrorThreshold         Integer32,
   ibSmaPortOverrunErrorThreshold           Integer32
   } 
 
ibSmaPortIndex  OBJECT-TYPE 
   SYNTAX      IbDataPort 
   MAX-ACCESS  not-accessible 
   STATUS      current 
   DESCRIPTION  
      "Index that identifies the InfiniBand data port."
   ::= { ibSmaPortInfoEntry 1 } 
 
ibSmaPortLinkWidthEnabled  OBJECT-TYPE 
   SYNTAX      INTEGER {
                    noStateChange(1),
                    oneX(2),       
                    fourX(3),       
                    oneXOr4X(4),  
                    twelveX(5),  
                    oneXOr12X(6), 
                    fourXOr12X(7), 
                    oneX4XOr12X(8),
                    linkWidthSupported(9),     
                    other(10)  
                    }
   MAX-ACCESS  read-only 
   STATUS      current 
   DESCRIPTION  
      "Enabled link width, indicated as follows:  
       0: No State Change (NOP)  
       1: 1x  
       2: 4x  
       3: 1x or 4x  
       8: 12x  
       9: 1x or 12x  
       10: 4x or 12x  
       11: 1x, 4x or 12x  
       4 - 7, 12 - 254: Reserved (Ignored)  
       255: Set to LinkWidthSupported value."
   REFERENCE
      "InfiniBand Architecture Release 1.1. Vol 1.
       Section 14.2.5.6; Table 132 PortInfo."
   ::= { ibSmaPortInfoEntry 2 } 

ibSmaPortLinkWidthSupported  OBJECT-TYPE 
   SYNTAX      INTEGER {
                    oneX(1),      
                    oneXOr4X(2),  
                    oneX4XOr12X(3),
                    other(4)
                    } 
   MAX-ACCESS  read-only 
   STATUS      current 
   DESCRIPTION  
      "Supported link width for this port.
       This is indicated as follows by the SMA:
            1: 1x  
            3: 1x or 4x  
            11: 1x, 4x or 12x  
            0, 2, 4-10, 12-255: Reserved." 
   REFERENCE
      "InfiniBand Architecture Release 1.1. Vol 1.
       Section 14.2.5.6; Table 132 PortInfo."
   ::= { ibSmaPortInfoEntry 3 } 

ibSmaPortLinkWidthActive  OBJECT-TYPE 
   SYNTAX      INTEGER {
                    oneX(1),  
                    fourX(2), 
                    twelveX(3),
                    other(4)
                    } 
   MAX-ACCESS  read-only 
   STATUS      current 
   DESCRIPTION 
      "Currently active link width on this port. 
       This is indicated as follows by the SMA:  
            1: 1x  
            2: 4x  
            8: 12x  
            0, 3, 4-7, 9-255: Reserved." 
   REFERENCE
      "InfiniBand Architecture Release 1.1. Vol 1.
       Section 14.2.5.6; Table 132 PortInfo."
   ::= { ibSmaPortInfoEntry 4 } 

ibSmaPortLinkSpeedSupported  OBJECT-TYPE 
   SYNTAX      INTEGER {
                    twoPoint5Gbps(1),
                    other(2) 
                    } 
   MAX-ACCESS  read-only 
   STATUS      current 
   DESCRIPTION 
      "Supported link speed, indicated as follows:  
            1: 2.5Gbps  
            0, 2 - 15: reserved " 
   REFERENCE
      "InfiniBand Architecture Release 1.1. Vol 1.
       Section 14.2.5.6; Table 132 PortInfo."
   ::= { ibSmaPortInfoEntry 5 } 

ibSmaPortLinkState  OBJECT-TYPE 
   SYNTAX      INTEGER { 
                    noChange(1), 
                    down(2), 
                    init(3), 
                    armed(4), 
                    active(5), 
                    other(6)      
                    } 
   MAX-ACCESS  read-only 
   STATUS      current 
   DESCRIPTION  
      "The state of the link on this port.
            0: No state change
            1: Down (includes failed links)
            2: Initialize
            3: Armed
            4: Active
            5-15: Reserved"
   REFERENCE
      "InfiniBand Architecture Release 1.1. Vol 1. 
       Section 14.2.5.6; Table 132 PortInfo."
   ::= { ibSmaPortInfoEntry 6 } 

ibSmaPortPhysState  OBJECT-TYPE 
   SYNTAX      INTEGER { 
                    noChange(1), 
                    sleep(2), 
                    polling(3), 
                    disabled(4), 
                    portConfigTraining(5), 
                    linkUp(6), 
                    linkErrorRecovery(7), 
                    other(8) 
                    } 
    MAX-ACCESS  read-only 
    STATUS      current 
    DESCRIPTION  
       "Physical Port State. Enumerated as:
            0: No state change 
            1: Sleep 
            2: Polling 
            3: Disabled 
            4: PortConfigurationTraining 
            5: LinkUp 
            6: LinkErrorRecovery 
            7 - 15: Reserved"
   REFERENCE
      "InfiniBand Architecture Release 1.1. Vol 1.
       Section 14.2.5.6; Table 132 PortInfo."
   ::= { ibSmaPortInfoEntry 7 } 
 
ibSmaPortLinkDownDefaultState  OBJECT-TYPE 
   SYNTAX      INTEGER { 
                    noChange(1), 
                    sleep(2), 
                    polling(3), 
                    other(4)      
                    } 
   MAX-ACCESS  read-only 
   STATUS      current 
   DESCRIPTION  
      "LinkDownDefault-State  
          0: No state change 
          1: Sleep 
          2: Polling 
          3-15: Reserved"
   REFERENCE
      "InfiniBand Architecture Release 1.1. Vol 1.
       Section 14.2.5.6; Table 132 PortInfo."
   ::= { ibSmaPortInfoEntry 8 } 

ibSmaPortLidMaskCount  OBJECT-TYPE 
   SYNTAX      Integer32(0..7) 
   MAX-ACCESS  read-only 
   STATUS      current 
   DESCRIPTION 
      "LID Mask Control count for multipath support for CA
       and router ports."
   REFERENCE
      "InfiniBand Architecture Release 1.1. Vol 1.
       Section 14.2.5.6; Table 132 PortInfo. Also Section
       7.11.1 Multipathing Requirements on End Node."
   ::= { ibSmaPortInfoEntry 9 } 
  
ibSmaPortLinkSpeedActive  OBJECT-TYPE 
   SYNTAX      INTEGER {
                    twoPoint5Gbps(1),
                    other(2) 
                    } 
   MAX-ACCESS  read-only 
   STATUS      current 
   DESCRIPTION 
      "Currently active link speed, indicated as follows: 
            1: 2.5Gbps 
            0, 2 - 15: reserved." 
   REFERENCE
      "InfiniBand Architecture Release 1.1. Vol 1.
       Section 14.2.5.6; Table 132 PortInfo."
   ::= { ibSmaPortInfoEntry 10 } 
  
ibSmaPortLinkSpeedEnabled  OBJECT-TYPE 
   SYNTAX      INTEGER {
                    noStateChange(1),
                    twoPoint5Gbps(2),
                    linkSpeedSupported(3),
                    other(4) 
                    } 
   MAX-ACCESS  read-only 
   STATUS      current 
   DESCRIPTION  
       "Enabled link speed, indicated as follows: 
          0: No State Change (NOP) 
          1: 2.5 Gbps 
          2 - 14: Reserved (Ignored) 
          15: Set to LinkSpeedSupported value." 
   REFERENCE
      "InfiniBand Architecture Release 1.1. Vol 1.
       Section 14.2.5.6; Table 132 PortInfo."
   ::= { ibSmaPortInfoEntry 11 } 

ibSmaPortNeighborMtu  OBJECT-TYPE 
   SYNTAX      INTEGER { 
                    mtu256(1), 
                    mtu512(2), 
                    mtu1024(3), 
                    mtu2048(4), 
                    mtu4096(5), 
                    other(6) 
                    } 
   MAX-ACCESS  read-only 
   STATUS      current 
   DESCRIPTION  
       "Active maximum MTU enabled on this port for transmit: 
           1: 256 bytes 
           2: 512 bytes 
           3: 1024 bytes 
           4: 2048 bytes 
           5: 4096 bytes 
           0, 6 - 15: reserved " 
   REFERENCE
      "InfiniBand Architecture Release 1.1. Vol 1.
       Section 14.2.5.6; Table 132 PortInfo."
   ::= { ibSmaPortInfoEntry 12 } 
 
ibSmaPortVirtLaneSupport  OBJECT-TYPE 
   SYNTAX  INTEGER { 
                vl0(1),    
                vl0ToVl1(2),
                vl0ToVl3(3), 
                vl0ToVl7(4),
                vl0ToVl14(5),
                other(6)     
                } 
   MAX-ACCESS  read-only 
   STATUS      current 
   DESCRIPTION  
      "Virtual Lane configuration supported on this port.
       Indicated as as follows by the SMA: 
           1: VL0 
           2: VL0, VL1 
           3: VL0 - VL3 
           4: VL0 - VL7 
           5: VL0 - VL14  
           0, 6 - 15: reserved." 
   REFERENCE
      "InfiniBand Architecture Release 1.1. Vol 1.
       Section 14.2.5.6; Table 132 PortInfo."
   ::= { ibSmaPortInfoEntry 13 } 

ibSmaPortVlHighPriorityLimit  OBJECT-TYPE 
   SYNTAX      Integer32(0..255) 
   MAX-ACCESS  read-only 
   STATUS      current 
   DESCRIPTION  
      "Limit of High Priority component of VL Arbitration Table.
       This object indicates the amount of high priority packets
       that can be trasnmitted wihout an opportunity to send a
       low priority packet. Specifically, the number of bytes
       that can be sent is this value times 4K bytes. A 255 value
       means the byte limit is unbounded and a value of 0 means
       that only a single packet from the high-priority table
       may be sent before an opportunity is given to the low-
       priority table."
   REFERENCE
      "InfiniBand Architecture Release 1.1. Vol 1.
       Section 14.2.5.6; Table 132 PortInfo; See also Section 7.6.9."
   ::= { ibSmaPortInfoEntry 14 } 
 
ibSmaPortVlArbHighCapacity  OBJECT-TYPE 
   SYNTAX      Integer32(0..64) 
   MAX-ACCESS  read-only 
   STATUS      current 
   DESCRIPTION  
      "VL/Weight pairs supported on this port in the VLArbitration 
       table for high priority. Shall be 1 to 64 if more than one 
       data VL is supported on this port, 0 otherwise."
   REFERENCE
      "InfiniBand Architecture Release 1.1. Vol 1.
       Section 14.2.5.6; Table 132 PortInfo; Also Section 7.6.9."
   ::= { ibSmaPortInfoEntry 15 } 
 
ibSmaPortVlArbLowCapacity  OBJECT-TYPE 
   SYNTAX      Integer32(0..64) 
   MAX-ACCESS  read-only 
   STATUS      current 
   DESCRIPTION  
      "VL/Weight pairs supported on this port in the VLArbitration 
       table for low priority. Shall be N to 64 if more than one 
       data VL is supported on this port, 0 otherwise, N being the 
       number of data VLs supported."
   REFERENCE
      "InfiniBand Architecture Release 1.1. Vol 1.
       Section 14.2.5.6; Table 132 PortInfo; Also see Section 7.6.9."
     ::= { ibSmaPortInfoEntry 16 } 

ibSmaPortMtuCapacity  OBJECT-TYPE 
   SYNTAX      INTEGER { 
                   mtu256(1), 
                   mtu512(2), 
                   mtu1024(3), 
                   mtu2048(4), 
                   mtu4096(5), 
                   other(6) 
                   } 
   MAX-ACCESS  read-only 
   STATUS      current 
   DESCRIPTION  
      "Maximum MTU supported by this port. 
           1: 256 bytes 
           2: 512 bytes 
           3: 1024 bytes 
           4: 2048 bytes 
           5: 4096 bytes 
           0, 6 - 15: reserved " 
   REFERENCE
     "InfiniBand Architecture Release 1.1. Vol 1.
      Section 14.2.5.6; Table 132 PortInfo."
   ::= { ibSmaPortInfoEntry 17 } 

ibSmaPortVlStallCount  OBJECT-TYPE 
   SYNTAX      Integer32(0..7) 
   MAX-ACCESS  read-only 
   STATUS      current 
   DESCRIPTION  
      "Specifies the number of sequential packets dropped that 
       causes the port to enter the VLStalled state. The result
       of setting this value to 0 is undefined."
   REFERENCE
      "InfiniBand Architecture Release 1.1. Vol 1.
       Section 14.2.5.6; Table 132 PortInfo; Section 18.2.4.4."
   ::= { ibSmaPortInfoEntry 18 } 
 
ibSmaPortHeadOfQueueLife  OBJECT-TYPE 
   SYNTAX      Integer32(0..31) 
   MAX-ACCESS  read-only 
   STATUS      current 
   DESCRIPTION  
      "Sets the time a packet can live at the head of a 
       Virtual Lane queue. This variable (HL) is used to
       compute the Head of the Queue Lifetime Limit (HLL). 
       It is used in the formula when the HL value is between
       0 and 19, inclusive. When HL is greater than 19, the
       HLL is to be interpreted as infinite."
   REFERENCE
      "InfiniBand Architecture Release 1.1. Vol 1.
       Section 14.2.5.6; Table 132 PortInfo; Also Section 18.2.5.4."
   ::= { ibSmaPortInfoEntry 19 } 

ibSmaPortOperationalVls  OBJECT-TYPE 
   SYNTAX  INTEGER { 
                vl0(1),     
                vl0ToVl1(2), 
                vl0ToVl3(3),
                vl0ToVl7(4), 
                vl0ToVl14(5),
                other(6)     
                } 
   MAX-ACCESS  read-only 
   STATUS      current 
   DESCRIPTION  
      "Virtual Lanes operational on this port, indicated 
       as follows: 
            0: No change 
            1: VL0 
            2: VL0 - VL1 
            3: VL0 - VL3 
            4: VL0 - VL7 
            5: VL0 - VL14 
            6 - 15: reserved" 
   REFERENCE
     "InfiniBand Architecture Release 1.1. Vol 1.
      Section 14.2.5.6; Table 132 PortInfo."
   ::= { ibSmaPortInfoEntry 20 } 
 
ibSmaPortPartEnforceInbound  OBJECT-TYPE 
   SYNTAX      TruthValue 
   MAX-ACCESS  read-only 
   STATUS      current 
   DESCRIPTION  
      "Indicates support of optional inbound partition enforcement.
       If true, partition enforcement on packets received on this 
       port is enabled. If false partition enforcement on 
       packets received from this port is disabled." 
   REFERENCE
      "InfiniBand Architecture Release 1.1. Vol 1.
       Section 14.2.5.6; Table 132 PortInfo."
   ::= { ibSmaPortInfoEntry 21 } 
 
ibSmaPortPartEnforceOutbound  OBJECT-TYPE 
   SYNTAX          TruthValue 
   MAX-ACCESS      read-only 
   STATUS          current 
   DESCRIPTION  
      "Indicates support of optional outbound partition 
       enforcement. If true, partition enforcement on packets 
       transmitted on this port is enabled. If false partition 
       enforcement on packets transmitted from this port is 
       disabled." 
   REFERENCE
   "InfiniBand Architecture Release 1.1. Vol 1.
       Section 14.2.5.6; Table 132 PortInfo."
   ::= { ibSmaPortInfoEntry 22 } 

ibSmaPortFilterRawPktInbound  OBJECT-TYPE 
   SYNTAX           TruthValue 
   MAX-ACCESS       read-only 
   STATUS           current 
   DESCRIPTION 
      "Indicates support of optional inbound raw packet 
       enforcement. If true, raw packets arriving on this port 
       are discarded. If false, raw enforcement on packets received
       from this port is disabled." 
   REFERENCE
      "InfiniBand Architecture Release 1.1. Vol 1.
       Section 14.2.5.6; Table 132 PortInfo."
   ::= { ibSmaPortInfoEntry 23 } 

ibSmaPortFilterRawPktOutbound  OBJECT-TYPE 
   SYNTAX            TruthValue 
   MAX-ACCESS        read-only 
   STATUS            current 
   DESCRIPTION 
      "Indicates support of optional outbound raw packet 
       enforcement. If true, raw packets departing on this port 
       are discarded. If false, raw enforcement on packets leaving
       from this port is disabled." 
   REFERENCE
      "InfiniBand Architecture Release 1.1. Vol 1.
       Section 14.2.5.6; Table 132 PortInfo."
   ::= { ibSmaPortInfoEntry 24 } 
  
ibSmaPortLocalPhysErrorThreshold OBJECT-TYPE 
   SYNTAX          Integer32(0..15) 
   MAX-ACCESS      read-only 
   STATUS          current 
   DESCRIPTION  
      "Local Physical Error threshold value. When the count of 
       marginal link errors exceeds this threshold, the local 
       link integrity error shall be detected."
   REFERENCE
      "InfiniBand Architecture Release 1.1. Vol 1.
       Section 14.2.5.6; Table 132 PortInfo; Also Section 7.12.2."
   ::= { ibSmaPortInfoEntry 25 } 
 
ibSmaPortOverrunErrorThreshold  OBJECT-TYPE 
   SYNTAX       Integer32(0..15) 
   MAX-ACCESS   read-only 
   STATUS       current 
   DESCRIPTION  
      "Overrun error threshold value. When the count of buffer 
       overruns over consecutive flow control update periods 
       exceeds this threshold, the excessive buffer overrun 
       error shall be detected."
   REFERENCE
      "InfiniBand Architecture Release 1.1. Vol 1.
       Section 14.2.5.6; Table 132 PortInfo; Also Section 7.12.2."
   ::= { ibSmaPortInfoEntry 26 } 

--**************************************************************** 
-- The Partition Key Group
--**************************************************************** 
ibSmaPKeyInfo         OBJECT IDENTIFIER ::= { ibSmaObjects 6 } 

-- *************************************************************
-- The Partition Key (P_Key) Table
--
-- DESCRIPTION: This table contains SMA information about the 
--    Partition Key Table. 
-- *************************************************************

ibSmaPKeyTable OBJECT-TYPE
   SYNTAX       SEQUENCE OF IbSmaPKeyEntry
   MAX-ACCESS   not-accessible
   STATUS       current
   DESCRIPTION
      "This table contains SMA Partition Key information for
       this port."
   ::= { ibSmaPKeyInfo 1 }
 
ibSmaPKeyEntry OBJECT-TYPE
   SYNTAX     IbSmaPKeyEntry
   MAX-ACCESS not-accessible
   STATUS     current
   DESCRIPTION
      "A conceptual row of the ibPKeyTable containing 
       information about the partition keys."
   INDEX   { ibSmaPKeyIBAPortIndex, ibSmaPKeyIndex }
   ::= { ibSmaPKeyTable 1 }
 
IbSmaPKeyEntry ::= SEQUENCE {
    ibSmaPKeyIBAPortIndex       IbDataPortAndInvalid,
    ibSmaPKeyIndex              Integer32,
    ibSmaPKeyMembership         INTEGER,
    ibSmaPKeyBase               Integer32
}
 
ibSmaPKeyIBAPortIndex  OBJECT-TYPE
   SYNTAX       IbDataPortAndInvalid
   MAX-ACCESS   not-accessible
   STATUS       current
   DESCRIPTION
      "The IB data port index for the switch data ports.
       For switch management port 0 and for CAs and routers,
       the index value should be 255. This indicates that
       the entry is not referring to a valid switch
       data port. (In the IB attribute modifier the upper
       16 bits indicate the data port, else it is 0)."
   ::= { ibSmaPKeyEntry 1 }

ibSmaPKeyIndex     OBJECT-TYPE
   SYNTAX       Integer32 (1..65505)
   MAX-ACCESS   not-accessible
   STATUS       current
   DESCRIPTION
      "The 1-based entry Identifier for each Partition Key 
       defined on a port. (The IB spec specifies 0..2047 
       blocks of 32 entries each for a total of 65,504 maximum
       entries, although the implemented limit is defined by 
       PartitionCap for CAs, routers, and switch port 0,
       and by PartitionEnforcementCap for the switch data
       ports)."
   ::= { ibSmaPKeyEntry 2 }
 
ibSmaPKeyMembership OBJECT-TYPE
   SYNTAX     INTEGER {
                       none(1),
                       limited(2),
                       full(3)
                }
   MAX-ACCESS   read-only
   STATUS       current
   DESCRIPTION
      "If the P_Key type is limitedi(2), the switch may accept a
       packet with a matching full P_Key, but may not accept a
       packet with a matching limited key. If the P_Key type
       is full(3), the switch can accept packets with either a
       full or limited P_Key. If the P_Key type is none(1),
       there is no associated Key Base value."
   REFERENCE
      "InfiniBand Architecture Release 1.1. Vol 1.
       Section 14.2.5.7; Table 134 P_KeyTable and
       Table 135 P_Key Block Element."
   ::= { ibSmaPKeyEntry 3 }

ibSmaPKeyBase OBJECT-TYPE
   SYNTAX       Integer32 (0..65527)
   MAX-ACCESS   read-only
   STATUS       current
   DESCRIPTION
      "15-bit base value of the P_Key that the switch will use to 
       check against incoming packets."
   REFERENCE
      "InfiniBand Architecture Release 1.1. Vol 1.
       Section 14.2.5.7; Table 134 P_KeyTable and
       Table 135 P_Key Block Element."
   ::= { ibSmaPKeyEntry 4 }

--**************************************************************** 
-- The Service-Level-to-Virtual-Lane-Mapping Group
--**************************************************************** 
ibSmaSlToVlMapInfo    OBJECT IDENTIFIER ::= { ibSmaObjects 7 } 
-- *************************************************************
-- The Service Level to Virtual Lane Configuration Mapping Table
--
-- DESCRIPTION: This table reflects the current Service Level
--    value for the input port/output port/virtual lane.
-- *************************************************************

ibSmaSL2VLMapTable OBJECT-TYPE
   SYNTAX       SEQUENCE OF IbSmaSL2VLMapEntry
   MAX-ACCESS   not-accessible
   STATUS       current
   DESCRIPTION
      "This table provides the virtual lane value for the
       output port/input port/service level mapping.
       Each output port contains a VL mapping for the 
       next hop based on the input port the packet arrived
       on and its SL value." 
   ::= { ibSmaSlToVlMapInfo 1 }
 
ibSmaSL2VLMapEntry OBJECT-TYPE
   SYNTAX     IbSmaSL2VLMapEntry
   MAX-ACCESS not-accessible
   STATUS     current
   DESCRIPTION
      "Column definitions for the VL from output/input/SL entry."
   INDEX       { ibSmaIBAOutPortIndex, ibSmaIBAInPortIndex, 
                 ibSmaServiceLevelIndex }
   ::= { ibSmaSL2VLMapTable 1 }
 
IbSmaSL2VLMapEntry ::= SEQUENCE {
   ibSmaIBAOutPortIndex          IbDataPortAndInvalid,
   ibSmaIBAInPortIndex           IbDataPortAndInvalid,
   ibSmaServiceLevelIndex        Integer32,
   ibSmaVirtualLane              Integer32
   }
 
ibSmaIBAOutPortIndex  OBJECT-TYPE
   SYNTAX       IbDataPortAndInvalid
   MAX-ACCESS   not-accessible
   STATUS       current
   DESCRIPTION
      "The egress port index for the service level mapping. A
       value of 255 indicates the switch management port 0."
   ::= { ibSmaSL2VLMapEntry 1 }

ibSmaIBAInPortIndex  OBJECT-TYPE
   SYNTAX       IbDataPortAndInvalid
   MAX-ACCESS   not-accessible
   STATUS       current
   DESCRIPTION
      "The ingress port index for the service level mapping. A
       value of 255 indicates the switch management port 0."
   ::= { ibSmaSL2VLMapEntry 2 }

ibSmaServiceLevelIndex  OBJECT-TYPE
   SYNTAX        Integer32 (1..16)
   MAX-ACCESS    not-accessible
   STATUS        current
   DESCRIPTION
      "The (1-based) Service Level value index for this mapping."
   ::= { ibSmaSL2VLMapEntry 3 }

ibSmaVirtualLane  OBJECT-TYPE
   SYNTAX       Integer32 (0..15)
   MAX-ACCESS   read-only
   STATUS       current
   DESCRIPTION
      "The outgoing packet's Virtual Lane value for 
       this Service Level Mapping."
   REFERENCE
      "InfiniBand Architecture Release 1.1. Vol 1.
       Section 14.2.5.8.; Table 136 SLtoVLMappingTable."
   ::= { ibSmaSL2VLMapEntry 4 }

--**************************************************************** 
-- The Virtual Lane Arbitration Group
--**************************************************************** 
ibSmaVLArbitInfo      OBJECT IDENTIFIER ::= { ibSmaObjects 8 } 

-- *************************************************************
-- The Virtual Lane High Priority Arbitration Table
--
-- DESCRIPTION: This table contains the VL High Priority
--    Arbitration Table. The second index is the list index
--    that allows for the viewing of the configuration of the 
--    VL/weight pairs configured by the SM.
-- *************************************************************

ibSmaHiPriVlArbTable OBJECT-TYPE
   SYNTAX       SEQUENCE OF IbSmaHiPriVlArbEntry
   MAX-ACCESS   not-accessible
   STATUS       current
   DESCRIPTION
      "This table provides visibility into the High Priority
       Arbitration process for configuring VL/Weight pairs for
       the IB data ports."
   ::= { ibSmaVLArbitInfo 1 }
 
ibSmaHiPriVlArbEntry OBJECT-TYPE
   SYNTAX     IbSmaHiPriVlArbEntry
   MAX-ACCESS not-accessible
   STATUS     current
   DESCRIPTION
      "Column definitions for High Priority Arbitration Table."
   INDEX     { ibSmaHiPriIBAPortIndex, ibSmaHiPriNIndex }
   ::= { ibSmaHiPriVlArbTable 1 }

IbSmaHiPriVlArbEntry ::= SEQUENCE {
   ibSmaHiPriIBAPortIndex       IbDataPort,
   ibSmaHiPriNIndex             Integer32,
   ibSmaHiPriVirtLane           Integer32,
   ibSmaHiPriWeight             Integer32
}

ibSmaHiPriIBAPortIndex  OBJECT-TYPE
   SYNTAX       IbDataPort
   MAX-ACCESS   not-accessible
   STATUS       current
   DESCRIPTION
      "The index for the IBA port that is being configured."
   ::= { ibSmaHiPriVlArbEntry 1 }

ibSmaHiPriNIndex  OBJECT-TYPE
   SYNTAX       Integer32 (1..64)
   MAX-ACCESS   not-accessible
   STATUS       current
   DESCRIPTION
      "The High Priority list index."
    ::= { ibSmaHiPriVlArbEntry 2 }
 
ibSmaHiPriVirtLane  OBJECT-TYPE
   SYNTAX       Integer32(0..14)
   MAX-ACCESS   read-only
   STATUS       current
   DESCRIPTION
      "The virtual lane this entry applies to."
   ::= { ibSmaHiPriVlArbEntry 3 }
 
ibSmaHiPriWeight   OBJECT-TYPE
   SYNTAX       Integer32 (0..255)
   MAX-ACCESS   read-only
   STATUS       current
   DESCRIPTION
      "Number of 64-byte units that may be transmitted from this
       VL when its turn in the arbitration process occurs. A weight
       of 0 indicates that the entry should be skipped."
   REFERENCE
      "InfiniBand Architecture Release 1.1. Vol 1.
       Section 14.2.5.9; Table 137 VLArbitrationTable."
   ::= { ibSmaHiPriVlArbEntry 4 }

-- *************************************************************
-- The Virtual Lane Low Priority Arbitration Table
--
-- DESCRIPTION: This table contains the VL Low Priority Arbitration 
--    Table. The second index is the list index that allows for the 
--    viewing of the configuration of the VL/weight pairs done by SM.
-- *************************************************************
ibSmaLowPriVlArbTable OBJECT-TYPE
   SYNTAX       SEQUENCE OF IbSmaLowPriVlArbEntry
   MAX-ACCESS   not-accessible
   STATUS       current
   DESCRIPTION
      "This table provides visibility into the Low Priority
       Arbitration process."
   ::= { ibSmaVLArbitInfo 2 }
 
ibSmaLowPriVlArbEntry OBJECT-TYPE
   SYNTAX     IbSmaLowPriVlArbEntry
   MAX-ACCESS not-accessible
   STATUS     current
   DESCRIPTION
     "Column definitions for Low Priority Arbitration Table."
   INDEX       { ibSmaLowPriIBAPortIndex, ibSmaLowPriNIndex }
   ::= { ibSmaLowPriVlArbTable 1 }
 
IbSmaLowPriVlArbEntry ::= SEQUENCE {
   ibSmaLowPriIBAPortIndex      IbDataPort,
   ibSmaLowPriNIndex            Integer32,
   ibSmaLowPriVirtLane          Integer32,
   ibSmaLowPriWeight            Integer32
}
 
ibSmaLowPriIBAPortIndex  OBJECT-TYPE
   SYNTAX       IbDataPort
   MAX-ACCESS   not-accessible
   STATUS       current
   DESCRIPTION
      "The index for the IB data port that is being configured."
   ::= { ibSmaLowPriVlArbEntry 1 }

ibSmaLowPriNIndex    OBJECT-TYPE
   SYNTAX       Integer32(1..64)
   MAX-ACCESS   not-accessible
   STATUS       current
   DESCRIPTION
      "The Low Priority list index."
   ::= { ibSmaLowPriVlArbEntry 2 }
 
ibSmaLowPriVirtLane  OBJECT-TYPE
   SYNTAX       Integer32(0..14)
   MAX-ACCESS   read-only
   STATUS       current
   DESCRIPTION
     "The Virtual Lane this entry applies to."
   ::= { ibSmaLowPriVlArbEntry 3 }

ibSmaLowPriWeight   OBJECT-TYPE
   SYNTAX       Integer32(0..255)
   MAX-ACCESS   read-only
   STATUS       current
   DESCRIPTION
      "Number of 64-byte units that may be transmitted from this VL
       when its turn in the arbitration process occurs. A weight
       of 0 indicates that the entry should be skipped."
   REFERENCE
      "InfiniBand Architecture Release 1.1. Vol 1.
       Section 14.2.5.9; Table 137 VLArbitrationTable."
   ::= { ibSmaLowPriVlArbEntry 4 }                                          

--**************************************************************** 
-- The Linear Forwarding Group
--**************************************************************** 
ibSmaLFTInfo          OBJECT IDENTIFIER ::= { ibSmaObjects 9 } 

--****************************************************************
-- Linear Forwarding Table Group: ibSmaLinForTable
--
-- DESCRIPTION: This table contains information about the Linear
--    Forwarding Table. 
--****************************************************************
 
ibSmaLinForTable OBJECT-TYPE
   SYNTAX       SEQUENCE OF IbSmaLinForEntry
   MAX-ACCESS   not-accessible
   STATUS       current
   DESCRIPTION
      "A table containing information about the Linear Forwarding
       Table."
   ::= { ibSmaLFTInfo 1 }
 
ibSmaLinForEntry OBJECT-TYPE
   SYNTAX     IbSmaLinForEntry
   MAX-ACCESS not-accessible
   STATUS     current
   DESCRIPTION
      "Current unicast forwarding Table entry configured by the
       Subnet Manager based on destination LID."
   INDEX       { ibSmaLinDestDLIDIndex }
   ::= { ibSmaLinForTable 1 }

IbSmaLinForEntry ::= SEQUENCE {
   ibSmaLinDestDLIDIndex           IbUnicastLid,
   ibSmaLinForwEgressPort          IbDataPortAndInvalid
}
ibSmaLinDestDLIDIndex     OBJECT-TYPE
   SYNTAX       IbUnicastLid
   MAX-ACCESS   not-accessible
   STATUS       current
   DESCRIPTION
      "Index that identifies Destination Local Identifier (DLID) 
       that the forwarding entry refers to in the Linear Forwarding
       Table."
   REFERENCE 
       "InfiniBand Architecture Release 1.1 Vol 1.
        Section 14.2.5.10 LinearForwardingTable; Table 139 and
        Table 140."
   ::= { ibSmaLinForEntry 1 }  

ibSmaLinForwEgressPort OBJECT-TYPE
   SYNTAX       IbDataPortAndInvalid 
   MAX-ACCESS   read-only
   STATUS       current
   DESCRIPTION
      "The port to which packets with the LID corresponding to
       this entry are to be forwarded."
   REFERENCE 
       "InfiniBand Architecture Release 1.1 Vol 1.
        Section 14.2.5.10 LinearForwardingTable; Table 139 and
        Table 140."
   ::= { ibSmaLinForEntry 2 }   

--**************************************************************** 
-- The Random Forwarding Group
--**************************************************************** 
ibSmaRFTInfo          OBJECT IDENTIFIER ::= { ibSmaObjects 10 } 

--**************************************************************** 
-- Random Forwarding Table
--
-- DESCRIPTION: This Table contains Subnet Management Information
--    about the Random Forwarding Table.
--**************************************************************** 

ibSmaRandomForwardingTable  OBJECT-TYPE 
   SYNTAX       SEQUENCE OF IbSmaRandomForwardingEntry 
   MAX-ACCESS   not-accessible  
   STATUS       current 
   DESCRIPTION 
      "A table containing SMA Random Forwarding information." 
   ::= { ibSmaRFTInfo 1 } 

ibSmaRandomForwardingEntry  OBJECT-TYPE 
   SYNTAX       IbSmaRandomForwardingEntry 
   MAX-ACCESS   not-accessible 
   STATUS       current 
   DESCRIPTION 
      "A conceptual row of the ibSmaRandomForwardingTable 
       containing information about the Random Forwarding Table."
   INDEX   { ibSmaRandomForwardingPortIndex }  
   ::= { ibSmaRandomForwardingTable 1 } 

IbSmaRandomForwardingEntry ::= SEQUENCE { 
   ibSmaRandomForwardingPortIndex     IbDataPort,
   ibSmaRandomDestLID                 Integer32,  
   ibSmaRandomForwEgressPort          IbDataPort, 
   ibSmaRandomLMC                     Integer32, 
   ibSmaRandomIsValid                 TruthValue         
}  

ibSmaRandomForwardingPortIndex  OBJECT-TYPE
   SYNTAX           IbDataPort 
   MAX-ACCESS       not-accessible 
   STATUS           current 
   DESCRIPTION 
      "The port index value." 
   ::= { ibSmaRandomForwardingEntry 1 } 
      
ibSmaRandomDestLID   OBJECT-TYPE 
   SYNTAX       Integer32(1..49152)
   MAX-ACCESS   read-only 
   STATUS       current 
   DESCRIPTION 
      "Identifies Destination Local Identifier (DLID) that the 
       forwarding entry refers to." 
   REFERENCE 
       "InfiniBand Architecture Release 1.1. Vol 1.
        Section 14.2.5.11 RandomForwardingTable; Table 141 and
        Table 142."
   ::= { ibSmaRandomForwardingEntry 2 } 

ibSmaRandomForwEgressPort OBJECT-TYPE 
   SYNTAX           IbDataPort 
   MAX-ACCESS       read-only 
   STATUS           current 
   DESCRIPTION 
      "The port to which packets with the LID corresponding to this 
       entry are to be forwarded." 
   REFERENCE 
       "InfiniBand Architecture Release 1.1. Vol 1.
        Section 14.2.5.11 RandomForwardingTable; Table 141 and
        Table 142."
   ::= { ibSmaRandomForwardingEntry 3 } 

ibSmaRandomLMC OBJECT-TYPE 
   SYNTAX           Integer32(0..7) 
   MAX-ACCESS       read-only 
   STATUS           current 
   DESCRIPTION  
      "The LID Mask Control (LMC) of this LID. The LMC specifies
       the number of Path Bits in the Local Identifier." 
   REFERENCE 
       "InfiniBand Architecture Release 1.1. Vol 1.
        Section 14.2.5.11 RandomForwardingTable; Table 141 and
        Table 142."
   ::= { ibSmaRandomForwardingEntry 4 } 


ibSmaRandomIsValid OBJECT-TYPE 
   SYNTAX           TruthValue 
   MAX-ACCESS       read-only 
   STATUS           current 
   DESCRIPTION  
      "If true this LID/Port pair is valid. Note that when the SMA
       sets this parameter to 0, entries can be removed." 
   REFERENCE 
       "InfiniBand Architecture Release 1.1. Vol 1.
        Section 14.2.5.11 RandomForwardingTable; Table 141 and
        Table 142."
   ::= { ibSmaRandomForwardingEntry 5 } 
     
--**************************************************************** 
-- The Multicast Forwarding Group
--**************************************************************** 
ibSmaMFTInfo          OBJECT IDENTIFIER ::= { ibSmaObjects 11 } 

--****************************************************************
-- Multicast Forwarding Table Group: ibMulForTable
--
-- DESCRIPTION: This table contains information about the Multicast
--    Forwarding Table. 
--****************************************************************
 
ibSmaMulForTable OBJECT-TYPE
   SYNTAX       SEQUENCE OF IbSmaMulForEntry
   MAX-ACCESS   not-accessible
   STATUS       current
   DESCRIPTION
      "A table containing information about the Multicast Forwarding
       Table."
   ::= { ibSmaMFTInfo 1 }

ibSmaMulForEntry OBJECT-TYPE
   SYNTAX     IbSmaMulForEntry
   MAX-ACCESS not-accessible
   STATUS     current
   DESCRIPTION
      "Current multicast forwarding table entry as configured by the 
       Subnet Manager based on destination LID."
   INDEX       { ibSmaMulDestDLIDIndex }
   ::= { ibSmaMulForTable 1 }

IbSmaMulForEntry ::= SEQUENCE {
   ibSmaMulDestDLIDIndex       IbMulticastLid,
   ibSmaMulForwMask            IbSmPortList
}

ibSmaMulDestDLIDIndex  OBJECT-TYPE
   SYNTAX       IbMulticastLid
   MAX-ACCESS   not-accessible
   STATUS       current
   DESCRIPTION
      "Identifies Destination Local Identifier (DLID) that the
       forwarding entry refers to in the Multicast Forwarding Table."
   ::= { ibSmaMulForEntry 1 }
 
ibSmaMulForwMask   OBJECT-TYPE
   SYNTAX       IbSmPortList
   MAX-ACCESS   read-only
   STATUS       current
   DESCRIPTION
      "A 256-bit mask that represents the port list. An incoming 
       packet with this LID table entry will be forwarded to all 
       ports for which the bit in the port mask is set to 1."
   REFERENCE 
      "InfiniBand Architecture Release 1.1. Vol 1.
       Section 14.2.5.12 MulticastForwardingTable; Table 143 and
       Table 144."
   ::= { ibSmaMulForEntry 2 }

--**************************************************************** 
-- The Subnet Manager Info Group
--**************************************************************** 
ibSmaSMInfo           OBJECT IDENTIFIER ::= { ibSmaObjects 12 } 

--**************************************************************** 
-- Subnet Manager Information Table Group
--**************************************************************** 
ibSmaSubMgrInfo   OBJECT IDENTIFIER ::= { ibSmaSMInfo 1 } 
--**************************************************************** 
-- Subnet Manager Information Table
--
-- DESCRIPTION: This Table contains Subnet Management Information
--    about the Subnet Managers on this subnet. This information
--    is available on a port where a Subnet Manager resides.
--    This information is used by SMs to exchange information 
--    during subnet discovery and polling.
--**************************************************************** 

ibSmaSmInfoTable  OBJECT-TYPE 
   SYNTAX       SEQUENCE OF IbSmaSmInfoEntry 
   MAX-ACCESS   not-accessible  
   STATUS       current 
   DESCRIPTION 
      "A table containing SMA Subnet Manager information." 
   ::= { ibSmaSubMgrInfo 1 } 

ibSmaSmInfoEntry  OBJECT-TYPE 
   SYNTAX       IbSmaSmInfoEntry 
   MAX-ACCESS   not-accessible 
   STATUS       current 
   DESCRIPTION 
      "A conceptual row of the ibSmaSmInfoTable containing 
       information about the Subnet Manager Table."
   INDEX   { ibSmaSmInfoPortIndex }  
   ::= { ibSmaSmInfoTable 1 } 

IbSmaSmInfoEntry ::= SEQUENCE { 
   ibSmaSmInfoPortIndex                     IbDataPort,
   ibSmaSmGuid                              OCTET STRING,
   ibSmaSmSmKey                             OCTET STRING,
   ibSmaSmSmpCount                          Counter32,
   ibSmaSmPriority                          Integer32,
   ibSmaSmState                             INTEGER
   } 
    
ibSmaSmInfoPortIndex  OBJECT-TYPE
   SYNTAX           IbDataPort 
   MAX-ACCESS       not-accessible 
   STATUS           current 
   DESCRIPTION 
      "The port index value." 
   ::= { ibSmaSmInfoEntry 1 } 

ibSmaSmGuid  OBJECT-TYPE 
   SYNTAX       IbGuid
   MAX-ACCESS   read-only 
   STATUS       current 
   DESCRIPTION  
      "The Port GUID of the port where the SM resides."
   REFERENCE
      "InfiniBand Architecture Release 1.1. Vol 1.
       Section 14.2.5.13; Table 145 SMInfo Table."
   ::= { ibSmaSmInfoEntry 2 } 
    
ibSmaSmSmKey  OBJECT-TYPE 
   SYNTAX       OCTET STRING (SIZE(8))
   MAX-ACCESS   read-only 
   STATUS       current 
   DESCRIPTION  
      "Key for this SM. This is shown as zeroes unless the
       requesting SM is proven to be the master, or the
       requester is otherwise authenticated."
   REFERENCE
      "InfiniBand Architecture Release 1.1. Vol 1.
       Section 14.2.5.13; Table 145 SMInfo Table."
   ::= { ibSmaSmInfoEntry 3 } 

ibSmaSmSmpCount  OBJECT-TYPE 
   SYNTAX       Counter32
   MAX-ACCESS   read-only 
   STATUS       current 
   DESCRIPTION  
      "Counter that increments each time the SM issues an
       SMP or performs other management activities. This
       counter is used as a heartbeat indicator by standby SMs."
   REFERENCE
      "InfiniBand Architecture Release 1.1. Vol 1.
       Section 14.2.5.13; Table 145 SMInfo Table."
   ::= { ibSmaSmInfoEntry 4 } 
   
ibSmaSmPriority  OBJECT-TYPE 
   SYNTAX       Integer32(0..15)
   MAX-ACCESS   read-only 
   STATUS       current 
   DESCRIPTION  
      "Administratively assigned priority for this SM. This
       can be reset by master SM. 0 is the lowest priority.
       An out-of-band mechanism shall be provided to set this
       value. The default value shall be 0."
   REFERENCE
      "InfiniBand Architecture Release 1.1. Vol 1.
       Section 14.2.5.13; Table 145 SMInfo Table."
   ::= { ibSmaSmInfoEntry 5 } 

ibSmaSmState  OBJECT-TYPE 
   SYNTAX       INTEGER
                {
                unknown(1),
                notActive(2),
                discovering(3),
                standby(4),
                master(5)
                } 
   MAX-ACCESS   read-only 
   STATUS       current 
   DESCRIPTION  
      "Enumerated value indicating this SM's state.
       The InfiniBand enumeration values are:
       0 - not active
       1 - discovering
       2 - standby
       3 - master
       4-15 - reserved.
       Note: a value of reserved returns unknown(1)." 
   REFERENCE
      "InfiniBand Architecture Release 1.1. Vol 1.
       Section 14.2.5.13; Table 145 SMInfo Table."
   ::= { ibSmaSmInfoEntry 6 } 
    
--**************************************************************** 
-- The Vendor Diagnostics Group
--**************************************************************** 
ibSmaVendDiagInfo     OBJECT IDENTIFIER ::= { ibSmaObjects 13 } 

--**************************************************************** 
-- Vendor Diagnostics Information Table
--
-- DESCRIPTION: This Table contains Subnet Management Information
--    about the Vendor Diagnostics.
--**************************************************************** 

ibSmaVendDiagInfoTable  OBJECT-TYPE 
   SYNTAX       SEQUENCE OF IbSmaVendDiagInfoEntry 
   MAX-ACCESS   not-accessible  
   STATUS       current 
   DESCRIPTION 
      "A table containing SMA Vendor Diagnostic Info information." 
   ::= { ibSmaVendDiagInfo 1 } 
 
ibSmaVendDiagInfoEntry  OBJECT-TYPE 
   SYNTAX       IbSmaVendDiagInfoEntry 
   MAX-ACCESS   not-accessible 
   STATUS       current 
   DESCRIPTION 
      "A conceptual row of the ibSmaVendDiagInfoTable containing 
       information about a particular data port's diagnostic status."
   INDEX   { ibSmaVendDiagPortIndex }  
   ::= { ibSmaVendDiagInfoTable 1 } 

IbSmaVendDiagInfoEntry ::= SEQUENCE { 
   ibSmaVendDiagPortIndex                  IbDataPortAndInvalid,
   ibSmaPortGenericDiagCode                INTEGER, 
   ibSmaPortVendorDiagCode                 Integer32, 
   ibSmaPortVendorDiagIndexFwd             TruthValue, 
   ibSmaPortVendorDiagData                 OCTET STRING 
   }

ibSmaVendDiagPortIndex  OBJECT-TYPE 
   SYNTAX      IbDataPortAndInvalid
   MAX-ACCESS  not-accessible 
   STATUS      current 
   DESCRIPTION  
      "Index that identifies the port for the diagnostics. If the 
       index value is 255, information about the management port 
       is returned."
   ::= { ibSmaVendDiagInfoEntry 1 } 

ibSmaPortGenericDiagCode  OBJECT-TYPE 
   SYNTAX      INTEGER {
                  portReady(1),
                  performingSelfTest(2),
                  initializing(3),
                  softError(4),
                  hardError(5),
                  other(6)
                  }
   MAX-ACCESS   read-only 
   STATUS       current 
   DESCRIPTION  
      "The generic portion of the Port Info Diagnostic code."
   REFERENCE
      "InfiniBand Architecture Release 1.1. Vol 1.
       Section 14.2.5.6; Table 132 PortInfo. Also see Section
       14.2.5.6.1; Table 133: Standard Encoding of DiagCode
       Bits 3-0."
   ::= { ibSmaVendDiagInfoEntry 2 } 
 
ibSmaPortVendorDiagCode  OBJECT-TYPE 
   SYNTAX       Integer32(0..2047)
   MAX-ACCESS   read-only 
   STATUS       current 
   DESCRIPTION  
      "The vendor specific portion of the Port Info Diagnostic 
       code."
   REFERENCE
      "InfiniBand Architecture Release 1.1. Vol 1.
       Section 14.2.5.6; Table 132 PortInfo. Also see Section
       14.2.5.6.1 and Figure 188."
   ::= { ibSmaVendDiagInfoEntry 3 } 

ibSmaPortVendorDiagIndexFwd  OBJECT-TYPE 
   SYNTAX       TruthValue
   MAX-ACCESS   read-only 
   STATUS       current 
   DESCRIPTION  
      "Flag to control ibSmaPortVendorDiagData data buffer. If 
       this boolean is true(1), the data buffer contains meaningful
       vendor-supplied additional diagnostic information. If this
       object is false(2), the buffer is empty."
   REFERENCE
      "InfiniBand Architecture Release 1.1. Vol 1.
       Section 14.2.5.14 and Table 146 VendorDiag."
   ::= { ibSmaVendDiagInfoEntry 4 } 
 
ibSmaPortVendorDiagData  OBJECT-TYPE 
   SYNTAX       OCTET STRING (SIZE(124))
   MAX-ACCESS   read-only 
   STATUS       current 
   DESCRIPTION  
      "Data buffer that can contain additional vendor-specific
       diagnostic information. The ibSmaPortVendorDiagIndexFwd flag
       controls whether this object contains meaningful data. Note:
       in IB, this buffer comprises n number of 62 byte buffers. 
       This object defines a buffer that can hold up to 2 of these
       IB chained buffers."
   REFERENCE
      "InfiniBand Architecture Release 1.1. Vol 1.
       Section 14.2.5.6; Table 132 PortInfo. Also see Section
       14.2.5.6.1 and Figure 188."
   ::= { ibSmaVendDiagInfoEntry 5 } 

--**************************************************************** 
-- The LED Info Group
--**************************************************************** 
ibSmaLedInfo          OBJECT IDENTIFIER ::= { ibSmaObjects 14 } 

--**************************************************************** 
-- LED Information Table
--
-- DESCRIPTION: This Table contains Subnet Management Information
--    about the LEDs. Note that a CA, router, or switch indicates
--    support for this attribute in the PortInfo::CapabilityMask
--    object.
--**************************************************************** 

ibSmaLedInfoTable  OBJECT-TYPE 
   SYNTAX       SEQUENCE OF IbSmaLedInfoEntry 
   MAX-ACCESS   not-accessible  
   STATUS       current 
   DESCRIPTION 
      "A table containing SMA LED Info information." 
   ::= { ibSmaLedInfo 1 } 

ibSmaLedInfoEntry  OBJECT-TYPE 
   SYNTAX       IbSmaLedInfoEntry 
   MAX-ACCESS   not-accessible 
   STATUS       current 
   DESCRIPTION 
      "A conceptual row of the ibSmaLedInfoTable containing 
       information about a particular data port's LED status."
   INDEX   { ibSmaLedIndex }  
   ::= { ibSmaLedInfoTable 1 } 

IbSmaLedInfoEntry ::= SEQUENCE { 
   ibSmaLedIndex                           IbDataPort,
   ibSmaLedState                           INTEGER
   }

ibSmaLedIndex  OBJECT-TYPE 
   SYNTAX      IbDataPort
   MAX-ACCESS  not-accessible 
   STATUS      current 
   DESCRIPTION  
      "Index that identifies the IB data port that can have an 
       LED associated with it."
   ::= { ibSmaLedInfoEntry 1 } 

ibSmaLedState  OBJECT-TYPE 
   SYNTAX       INTEGER
                {
                unknown(1),
                on(2),
                off(3)
                }
   MAX-ACCESS  read-only 
   STATUS      current 
   DESCRIPTION  
      "State of the LED."
   REFERENCE
      "InfiniBand Architecture Release 1.1. Vol 1.
       Section 14.2.5.15 LedInfo; Table 147 LedInfo Table."
   ::= { ibSmaLedInfoEntry 2 } 

--**************************************************************** 
-- Notifications Group
--**************************************************************** 
ibSmaNotificationPrefix OBJECT IDENTIFIER ::= { ibSmaNotifications 0 }
    
--**************************************************************** 
-- Notifications 
--
-- DESCRIPTION: The Notifications Group contains the set of SMA 
--    Traps that will be translated into SNMP notifications and
--    sent to the registered NMS managers.
--**************************************************************** 
ibSmaPortLinkStateChange  NOTIFICATION-TYPE
   OBJECTS
      {
      ibSmaNodeLid
      }
   STATUS   current
   DESCRIPTION
      "This notification translates InfiniBand SMA Trap 128:
       Link State of at least one port of switch at <LIDADDR>
       has changed." 
   REFERENCE
      "InfiniBand Architecture Release 1.1. Vol 1.
       Section 14.2.5.1; Table 118 and 120."
   ::= { ibSmaNotifications 1 }

ibSmaLinkIntegrityThresReached  NOTIFICATION-TYPE
   OBJECTS
      {
      ibSmaNodeLid,
      ibSmaNodePortNum
      }
   STATUS   current
   DESCRIPTION
      "This notification translates InfiniBand SMA Trap 129:
       Local Link Integrity threshold reached at <LIDADDR><PORTNO>." 
   REFERENCE
      "InfiniBand Architecture Release 1.1. Vol 1.
       Section 14.2.5.1; Table 118 and 121."
   ::= { ibSmaNotifications 2 }

ibSmaExcessBuffOverrunThres  NOTIFICATION-TYPE
   OBJECTS
      {
      ibSmaNodeLid,
      ibSmaNodePortNum
      }
   STATUS   current
   DESCRIPTION
      "This notification translates InfiniBand SMA Trap 130:
       Exccessive Buffer Overrun threshold reached at 
       <LIDADDR><PORTNO>." 
   REFERENCE
      "InfiniBand Architecture Release 1.1. Vol 1.
       Section 14.2.5.1; Table 118 and 121."
   ::= { ibSmaNotifications 3 }

ibSmaFlowCntrlUpdateTimerExpire  NOTIFICATION-TYPE
   OBJECTS
      {
      ibSmaNodeLid,
      ibSmaNodePortNum
      }
   STATUS   current
   DESCRIPTION
      "This notification translates InfiniBand SMA Trap 131:
       Switch Flow Control Update watchdog timer expired at 
       <LIDADDR><PORTNO>." 
   REFERENCE
      "InfiniBand Architecture Release 1.1. Vol 1.
       Section 14.2.5.1; Table 118 and 121."
   ::= { ibSmaNotifications 4 }

ibSmaCapabilityMaskModified  NOTIFICATION-TYPE
   OBJECTS
      {
      ibSmaNodeLid,
      ibSmaNodeCapMask
      }
   STATUS   current
   DESCRIPTION
      "This notification translates InfiniBand SMA Trap 144:
       The capability mask at <LIDADDR> has been modified to
       <CAPMASK>."
   REFERENCE
      "InfiniBand Architecture Release 1.1. Vol 1.
       Section 14.2.5.1; Table 118 and 122."
   ::= { ibSmaNotifications 5 }

ibSmaSysImageGuidModified  NOTIFICATION-TYPE
   OBJECTS
      {
      ibSmaNodeLid,
      ibSmaSystemImageGuid
      }
   STATUS   current
   DESCRIPTION
      "This notification translates InfiniBand SMA Trap 145:
       The System Image GUID at <LIDADDR> has been modified to
       <SYSTEMIMAGEGUID>."
   REFERENCE
      "InfiniBand Architecture Release 1.1. Vol 1.
       Section 14.2.5.1; Table 118 and 123."
   ::= { ibSmaNotifications 6 }

ibSmaBadManagementKey  NOTIFICATION-TYPE
   OBJECTS
      {
      ibSmaNodeKey,
      ibSmaNodeLid,
      ibSmaNodeMethod,
      ibSmaNodeAttributeId,
      ibSmaNodeAttributeModifier
      }
   STATUS   current
   DESCRIPTION
      "This notification translates InfiniBand SMA Trap 256:
       Bad M_Key, <KEY> from <LIDADDR> attempted <METHOD> 
       with <ATTRIBUTEID> and <ATTRIBUTEMODIFIER>." 
   REFERENCE
      "InfiniBand Architecture Release 1.1. Vol 1.
       Section 14.2.5.1; Table 118 and 124."
   ::= { ibSmaNotifications 7 }

ibSmaBadPartitionKey  NOTIFICATION-TYPE
   OBJECTS
      {
      ibSmaNodeKey,
      ibSmaNodeLid,
      ibSmaNodeGid1,
      ibSmaNodeQueuePair1,
      ibSmaNodeLid2,
      ibSmaNodeGid2,
      ibSmaNodeQueuePair2,
      ibSmaNodeServiceLevel
      }
   STATUS   current
   DESCRIPTION
      "This notification translates InfiniBand SMA Trap 257:
       Bad P_Key, <KEY> from <LIDADDR1> /<GIDADDR1>/<QP1> to   
       <LIDADDR2>/<GIDADDR2>/<QP2> on <SL>." 
   REFERENCE
      "InfiniBand Architecture Release 1.1. Vol 1.
       Section 14.2.5.1; Table 118 and 125."
   ::= { ibSmaNotifications 8 }

ibSmaBadQueueKey  NOTIFICATION-TYPE
   OBJECTS
      {
      ibSmaNodeKey,
      ibSmaNodeLid,
      ibSmaNodeGid1,
      ibSmaNodeQueuePair1,
      ibSmaNodeLid2,
      ibSmaNodeGid2,
      ibSmaNodeQueuePair2,
      ibSmaNodeServiceLevel
      }
   STATUS   current
   DESCRIPTION
      "This notification translates InfiniBand SMA Trap 258:
       Bad Q_Key, <KEY> from <LIDADDR1>/<GIDADDR1>/<QP1> to   
       <LIDADDR2>/<GIDADDR2>/<QP2> on <SL>." 
   REFERENCE
      "InfiniBand Architecture Release 1.1. Vol 1.
       Section 14.2.5.1; Table 118 and 125."
   ::= { ibSmaNotifications 9 }

ibSmaBadPKeyAtSwitchPort  NOTIFICATION-TYPE
   OBJECTS
      {
      ibSmaNodeKey,
      ibSmaNodeLid,
      ibSmaNodeGid1,
      ibSmaNodeQueuePair1,
      ibSmaNodeLid2,
      ibSmaNodeGid2,
      ibSmaNodeQueuePair2,
      ibSmaNodeServiceLevel,
      ibSmaNodeSwitchLid,
      ibSmaNodeDataValid
      }
   STATUS   current
   DESCRIPTION
      "This notification translates InfiniBand SMA Trap 259:
       Bad P_Key, <KEY> from <LIDADDR1> /<GIDADDR1>/<QP1> to   
       <LIDADDR2>/<GIDADDR2>/<QP2> on <SL> at switch <LIDADRR>
       external port <PORTNO>, where the validity of the fields
       is indicated by <DataValid>." 
   REFERENCE
      "InfiniBand Architecture Release 1.1. Vol 1.
       Section 14.2.5.1; Table 118 and 126."
   ::= { ibSmaNotifications 10 }

--**************************************************************** 
-- Module Conformance Statement 
--
-- DESCRIPTION: The module conformance statement includes the
--    compliance statements and the units of conformance
--    section.
--**************************************************************** 
ibSmaCompliances OBJECT IDENTIFIER ::= { ibSmaConformance 1 }

ibSmaGroups OBJECT IDENTIFIER      ::= { ibSmaConformance 2 }

--**************************************************************** 
-- Compliance Statements 
--**************************************************************** 

ibSmaBasicNodeCompliance  MODULE-COMPLIANCE
   STATUS current
   DESCRIPTION
      "The basic node implementation requirements for agents that
       support the IPOIB SMA MIB."
   MODULE -- this module
       MANDATORY-GROUPS { 
                        ibSmaNodeGroup
                        }
   ::= { ibSmaCompliances 1 }

ibSmaFullSwitchCompliance  MODULE-COMPLIANCE
   STATUS current
   DESCRIPTION
      "The full node implementation requirements for agents that
       support the IPOIB SMA MIB for InfiniBand switches."
   MODULE -- this module
       MANDATORY-GROUPS { 
                        ibSmaNodeGroup,
                        ibSmaSwitchGroup,
                        ibSmaGuidGroup,
                        ibSmaMgmtPortGroup,
                        ibSmaDataPortGroup,
                        ibSmaPKeyGroup,
                        ibSmaSlToVlMapGroup,
                        ibSmaVLArbitGroup,
                        ibSmaLFTGroup,
                        ibSmaRFTGroup,
                        ibSmaMFTGroup,
                        ibSmaSMGroup,
                        ibSmaVendDiagGroup,
                        ibSmaLedGroup,
                        ibSmaNotificationsGroup
                        }
   ::= { ibSmaCompliances 2 }

ibSmaFullRouterCACompliance  MODULE-COMPLIANCE
   STATUS current
   DESCRIPTION
      "The full node implementation requirements for agents that
       support the IPOIB SMA MIB for InfiniBand CAs and routers."
   MODULE -- this module
       MANDATORY-GROUPS { 
                        ibSmaNodeGroup,
                        ibSmaGuidGroup,
                        ibSmaMgmtPortGroup,
                        ibSmaDataPortGroup,
                        ibSmaPKeyGroup,
                        ibSmaSlToVlMapGroup,
                        ibSmaVLArbitGroup,
                        ibSmaSMGroup,
                        ibSmaVendDiagGroup,
                        ibSmaLedGroup,
                        ibSmaNotificationsGroup
                        }
   ::= { ibSmaCompliances 3 }

--**************************************************************** 
-- Units Of Conformance 
--**************************************************************** 

ibSmaNodeGroup  OBJECT-GROUP
   OBJECTS  {
       ibSmaNodeString,
       ibSmaNodeBaseVersion,
       ibSmaNodeClassVersion,
       ibSmaNodeType,
       ibSmaNodeNumPorts,
       ibSmaSystemImageGuid,
       ibSmaNodeGuid,
       ibSmaNodePortGuid,
       ibSmaNodePartitionTableNum,
       ibSmaNodeDeviceId,
       ibSmaNodeRevision,
       ibSmaNodeLocalPortNumOrZero,
       ibSmaNodeVendorId,
       ibSmaNodeLid,
       ibSmaNodePortNum,
       ibSmaNodeMethod,
       ibSmaNodeAttributeId,
       ibSmaNodeAttributeModifier,
       ibSmaNodeKey,
       ibSmaNodeLid2,
       ibSmaNodeServiceLevel,
       ibSmaNodeQueuePair1,
       ibSmaNodeQueuePair2,
       ibSmaNodeGid1,
       ibSmaNodeGid2,
       ibSmaNodeCapMask,
       ibSmaNodeSwitchLid,
       ibSmaNodeDataValid
   }
   STATUS   current
   DESCRIPTION
      "The ibSmaNodeGroup defines the MIB objects that describe
       this InfiniBand subnet node."
   ::= { ibSmaGroups 1 }

ibSmaSwitchGroup  OBJECT-GROUP
   OBJECTS  {
       ibSmaSwLinearFdbTableNum,
       ibSmaSwRandomFdbTableNum,
       ibSmaSwMulticastFdbTableNum,
       ibSmaSwLinearFdbTop,
       ibSmaSwDefaultPort, 
       ibSmaSwDefMcastPriPort,
       ibSmaSwDefMcastNotPriPort,
       ibSmaSwLifeTimeValue,
       ibSmaSwPortStateChange,
       ibSmaSwLidsPerPort,
       ibSmaSwPartitionEnforceNum,
       ibSmaSwInboundEnforceCap,
       ibSmaSwOutboundEnforceCap,
       ibSmaSwFilterRawPktInputCap,
       ibSmaSwFilterRawPktOutputCap,
       ibSmaSwEnhancedPort0
   }
   STATUS   current
   DESCRIPTION
      "The ibSmaSwitchGroup defines the MIB objects that describe
       this InfiniBand switch."
   ::= { ibSmaGroups 2 }

ibSmaGuidGroup  OBJECT-GROUP            
   OBJECTS  {
       ibSmaGuidVal
   }
   STATUS   current
   DESCRIPTION
      "The ibSmaGuidGroup defines the MIB object that describes
       the GUIDs associated with this node."
::= { ibSmaGroups 3 } 

ibSmaMgmtPortGroup  OBJECT-GROUP
   OBJECTS  {
       ibSmaPortMKey,
       ibSmaPortGidPrefix,
       ibSmaPortLid,
       ibSmaPortMasterSmLid,
       ibSmaPortIsSubnetManager,
       ibSmaPortIsNoticeSupported,
       ibSmaPortIsTrapSupported,
       ibSmaPortIsAutoMigrateSupported,
       ibSmaPortIsSlMappingSupported,
       ibSmaPortIsMKeyNvram,
       ibSmaPortIsPKeyNvram,
       ibSmaPortIsLedInfoSupported,
       ibSmaPortIsSmDisabled,
       ibSmaPortIsSysImgGuidSupported,
       ibSmaPortIsPKeyExtPortTrapSup,
       ibSmaPortIsCommManageSupported,
       ibSmaPortIsSnmpTunnelSupported,
       ibSmaPortIsReinitSupported,
       ibSmaPortIsDevManageSupported,
       ibSmaPortIsVendorClassSupported,
       ibSmaPortIsDrNoticeSupported,
       ibSmaPortIsCapMaskNoticSupported,
       ibSmaPortIsBootMgmtSupported,
       ibSmaPortMKeyLeasePeriod,
       ibSmaPortMKeyProtectBits,
       ibSmaPortMasterSmSl,
       ibSmaPortInitTypeLoad,
       ibSmaPortInitTypeContent,
       ibSmaPortInitTypePresence,
       ibSmaPortInitTypeResuscitate,
       ibSmaPortInitNoLoadReply,
       ibSmaPortInitPreserveContReply,
       ibSmaPortInitPreservePresReply,
       ibSmaPortMKeyViolations,
       ibSmaPortPKeyViolations,
       ibSmaPortQKeyViolations,
       ibSmaPortNumGuid,
       ibSmaPortSubnetTimeout,
       ibSmaPortResponseTimeValue
   }
   STATUS   current
   DESCRIPTION
      "The ibSmaMgmtPortGroup defines the MIB objects that describe
       the management port."
   ::= { ibSmaGroups 4 }

ibSmaDataPortGroup  OBJECT-GROUP
   OBJECTS  {
       ibSmaPortLinkWidthEnabled,
       ibSmaPortLinkWidthSupported,
       ibSmaPortLinkWidthActive,
       ibSmaPortLinkSpeedSupported,
       ibSmaPortLinkState,
       ibSmaPortPhysState,
       ibSmaPortLinkDownDefaultState,
       ibSmaPortLidMaskCount,
       ibSmaPortLinkSpeedActive,
       ibSmaPortLinkSpeedEnabled,
       ibSmaPortNeighborMtu,
       ibSmaPortVirtLaneSupport,
       ibSmaPortVlHighPriorityLimit,
       ibSmaPortVlArbHighCapacity,
       ibSmaPortVlArbLowCapacity,
       ibSmaPortMtuCapacity,   
       ibSmaPortVlStallCount,   
       ibSmaPortHeadOfQueueLife, 
       ibSmaPortOperationalVls,   
       ibSmaPortPartEnforceInbound,
       ibSmaPortPartEnforceOutbound,
       ibSmaPortFilterRawPktInbound,
       ibSmaPortFilterRawPktOutbound,
       ibSmaPortLocalPhysErrorThreshold,
       ibSmaPortOverrunErrorThreshold
   }
   STATUS   current
   DESCRIPTION
      "The ibSmaDataPortGroup defines MIB objects for IB data ports."
   ::= { ibSmaGroups 5 }

ibSmaPKeyGroup  OBJECT-GROUP
   OBJECTS  {
       ibSmaPKeyMembership,
       ibSmaPKeyBase
   }
   STATUS   current
   DESCRIPTION
      "The ibSmaPKeyGroup defines the MIB objects that describe the
       Partition Keys."
   ::= { ibSmaGroups 6 }

ibSmaSlToVlMapGroup  OBJECT-GROUP
   OBJECTS  {
       ibSmaVirtualLane
   }
   STATUS   current
   DESCRIPTION
      "The ibSmaSlToVlMapGroup defines the MIB objects that describe
       the Service Level to Virtual Lane mapping."
   ::= { ibSmaGroups 7 } 

ibSmaVLArbitGroup   OBJECT-GROUP
   OBJECTS  {
       ibSmaHiPriVirtLane,
       ibSmaHiPriWeight,
       ibSmaLowPriVirtLane,
       ibSmaLowPriWeight
   }
   STATUS   current
   DESCRIPTION
      "The ibSmaVLArbitGroup defines the MIB objects that describe
       the Virtual Lane High and Low Arbitrations."
   ::= { ibSmaGroups 8 }

ibSmaLFTGroup   OBJECT-GROUP
   OBJECTS  {
       ibSmaLinForwEgressPort
   }
   STATUS   current
   DESCRIPTION
      "The ibSmaLFTGroup defines the MIB objects that describe
       the Linear Forwarding Table."
 ::= { ibSmaGroups 9 } 

ibSmaRFTGroup  OBJECT-GROUP
   OBJECTS  {
       ibSmaRandomDestLID,
       ibSmaRandomForwEgressPort,
       ibSmaRandomLMC,
       ibSmaRandomIsValid
   }
   STATUS   current
   DESCRIPTION
      "The ibSmaRFTGroup defines the MIB objects that describe
       the Random Forwarding Table."
  ::= { ibSmaGroups 10 } 

ibSmaMFTGroup   OBJECT-GROUP
   OBJECTS  {
       ibSmaMulForwMask
   }
   STATUS   current
   DESCRIPTION
      "The ibSmaMFTGroup defines the MIB objects that describe
       the Multicast Forwarding Table."
 ::= { ibSmaGroups 11 } 

ibSmaSMGroup   OBJECT-GROUP
   OBJECTS  {
       ibSmaSmGuid,
       ibSmaSmSmKey,
       ibSmaSmSmpCount,
       ibSmaSmPriority,
       ibSmaSmState
   }
   STATUS   current
   DESCRIPTION
      "The ibSmaSMGroup defines the MIB objects that describe
       the Subnet Manager Information Table."
 ::= { ibSmaGroups 12 } 

ibSmaVendDiagGroup     OBJECT-GROUP
   OBJECTS  {
       ibSmaPortGenericDiagCode,
       ibSmaPortVendorDiagCode,
       ibSmaPortVendorDiagIndexFwd,
       ibSmaPortVendorDiagData
   }
   STATUS   current
   DESCRIPTION
      "The ibSmaVendDiagGroup defines the MIB objects that describe
       the vendor diagnostics table."            
 ::= { ibSmaGroups 13 } 

ibSmaLedGroup   OBJECT-GROUP
   OBJECTS  {
       ibSmaLedState
   }
   STATUS   current
   DESCRIPTION
      "The ibSmaSMGroup defines the MIB objects that describe
       the LED table."
  ::= { ibSmaGroups 14 } 

ibSmaNotificationsGroup  NOTIFICATION-GROUP
   NOTIFICATIONS  {
       ibSmaPortLinkStateChange,
       ibSmaLinkIntegrityThresReached,
       ibSmaExcessBuffOverrunThres,
       ibSmaFlowCntrlUpdateTimerExpire,
       ibSmaCapabilityMaskModified,
       ibSmaSysImageGuidModified,
       ibSmaBadManagementKey,
       ibSmaBadPartitionKey,
       ibSmaBadQueueKey,
       ibSmaBadPKeyAtSwitchPort
   }
   STATUS   current
   DESCRIPTION
      "The notifications that an IPOIB SNMP agent transmits 
       on the behalf of the SMA Trap message implementation."
   ::= { ibSmaGroups 15 }

END 

--  
--    Copyright (C) The Internet Society (2003).  All Rights Reserved.
--  
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
--  
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.            
--      
--
