GUARDIAN-MIB DEFINITIONS ::= BEGIN

--
-- Guardian MIB - Westek Technology Ltd. V1.4
--

IMPORTS
  enterprises    FROM RFC1155-SMI
  OBJECT-TYPE    FROM RFC1155-SMI
  TRAP-TYPE      FROM RFC-1215
  DisplayString  FROM RFC1213-MIB;


-- The Branches

    westek              OBJECT IDENTIFIER ::= { enterprises 3166 }
    guardian            OBJECT IDENTIFIER ::= { westek 1 }

    device              OBJECT IDENTIFIER ::= { guardian 2 }
    masks               OBJECT IDENTIFIER ::= { guardian 4 }
    special             OBJECT IDENTIFIER ::= { guardian 5 }

    devInput            OBJECT IDENTIFIER ::= { device 1 }
    devFan              OBJECT IDENTIFIER ::= { device 2 }
    devTemp             OBJECT IDENTIFIER ::= { device 3 }
    devISA              OBJECT IDENTIFIER ::= { device 4 }
    devDC               OBJECT IDENTIFIER ::= { device 5 }

    devInput1           OBJECT IDENTIFIER ::= { devInput 1 }
    devInput2           OBJECT IDENTIFIER ::= { devInput 2 }
    devInput3           OBJECT IDENTIFIER ::= { devInput 3 }
    devInput4           OBJECT IDENTIFIER ::= { devInput 4 }

    devFan1             OBJECT IDENTIFIER ::= { devFan 1 }
    devFan2             OBJECT IDENTIFIER ::= { devFan 2 }
    devFan3             OBJECT IDENTIFIER ::= { devFan 3 }
    devFan4             OBJECT IDENTIFIER ::= { devFan 4 }

    devTemp1            OBJECT IDENTIFIER ::= { devTemp 1 }
    devTemp2            OBJECT IDENTIFIER ::= { devTemp 2 }
    devTemp3            OBJECT IDENTIFIER ::= { devTemp 3 }
    devTemp4            OBJECT IDENTIFIER ::= { devTemp 4 }
    devTemp5            OBJECT IDENTIFIER ::= { devTemp 5 }
    devTemp6            OBJECT IDENTIFIER ::= { devTemp 6 }
    devTemp7            OBJECT IDENTIFIER ::= { devTemp 7 }
    devTemp8            OBJECT IDENTIFIER ::= { devTemp 8 }

    devISAP12           OBJECT IDENTIFIER ::= { devISA 1 }
    devISAP5            OBJECT IDENTIFIER ::= { devISA 2 }
    devISAN5            OBJECT IDENTIFIER ::= { devISA 3 }
    devISAN12           OBJECT IDENTIFIER ::= { devISA 4 }

    devDCP12            OBJECT IDENTIFIER ::= { devDC 1 }
    devDCP5             OBJECT IDENTIFIER ::= { devDC 2 }


-- The Leaves

    guardianRev OBJECT-TYPE
      SYNTAX  DisplayString
      ACCESS  read-only
      STATUS  mandatory
      DESCRIPTION
	"The name and revision number of Guardian card. Revision 
	 = Major.Minor.Codeversion."
      ::= { guardian 1 }

    control OBJECT-TYPE
      SYNTAX  INTEGER  {
	reset(1),
	updatenvr(2),
	reset2nvr(3),
	reset2fac(4)
	}
      ACCESS  read-write
      STATUS  mandatory
      DESCRIPTION
	"Guardian Control Functions 1=Reset Errors, 2=Write settings to NVRAM, 
	 3=Reset to NVRAM, 4=Reset to factory defaults."
      ::= { guardian 3 }


-- Device Leaves

-- Device Status's

    devInpStat OBJECT-TYPE
      SYNTAX  INTEGER (0..255)
      ACCESS  read-write
      STATUS  mandatory
      DESCRIPTION
	"Status bits for Inputs Bit 0-3 = Inputs 1-4"
      ::= { devInput 10 }

    devFanStat OBJECT-TYPE
      SYNTAX  INTEGER (0..255)
      ACCESS  read-write
      STATUS  mandatory
      DESCRIPTION
	"Status bits for Fans Bit 0-3 = Fans 1-4"
      ::= { devFan 10 }

    devTempStat OBJECT-TYPE
      SYNTAX  INTEGER (0..255)
      ACCESS  read-write
      STATUS  mandatory
      DESCRIPTION
	"Status bits for Temp probes Bit 0-7 = Temps 1-8"
      ::= { devTemp 10 }

    devISAStat OBJECT-TYPE
      SYNTAX  INTEGER (0..255)
      ACCESS  read-write
      STATUS  mandatory
      DESCRIPTION
	"Status bits for ISA Voltages, Bits 0-3 = +12,+5,-5,-12"
      ::= { devISA 10 }

    devDCStat OBJECT-TYPE
      SYNTAX  INTEGER (0..255)
      ACCESS  read-write
      STATUS  mandatory
      DESCRIPTION
	"Status bits for DC Voltages, Bits 0-1 = +12,+5"
      ::= { devDC 10 }


-- Inputs

    devInp1Val OBJECT-TYPE
      SYNTAX  INTEGER (0..1)
      ACCESS  read-write
      STATUS  mandatory
      DESCRIPTION
	"Input Switch 1 current value, 1=Switched"
      ::= { devInput1 1 }

    devInp1Pol OBJECT-TYPE
      SYNTAX  INTEGER (0..1)
      ACCESS  read-write
      STATUS  mandatory
      DESCRIPTION
	"Input Switch 1 Polarity, 1=Inverted"
      ::= { devInput1 2 }

    devInp2Val OBJECT-TYPE
      SYNTAX  INTEGER (0..1)
      ACCESS  read-write
      STATUS  mandatory
      DESCRIPTION
	"Input Switch 2 current value, 1=Switched"
      ::= { devInput2 1 }

    devInp2Pol OBJECT-TYPE
      SYNTAX  INTEGER (0..1)
      ACCESS  read-write
      STATUS  mandatory
      DESCRIPTION
	"Input Switch 2 Polarity, 1=Inverted"
      ::= { devInput2 2 }

    devInp3Val OBJECT-TYPE
      SYNTAX  INTEGER (0..1)
      ACCESS  read-write
      STATUS  mandatory
      DESCRIPTION
	"Input Switch 3 current value, 1=Switched"
      ::= { devInput3 1 }

    devInp3Pol OBJECT-TYPE
      SYNTAX  INTEGER (0..1)
      ACCESS  read-write
      STATUS  mandatory
      DESCRIPTION
	"Input Switch 3 Polarity, 1=Inverted"
      ::= { devInput3 2 }

    devInp4Val OBJECT-TYPE
      SYNTAX  INTEGER (0..1)
      ACCESS  read-write
      STATUS  mandatory
      DESCRIPTION
	"Input Switch 4 current value, 1=Switched"
      ::= { devInput4 1 }

    devInp4Pol OBJECT-TYPE
      SYNTAX  INTEGER (0..1)
      ACCESS  read-write
      STATUS  mandatory
      DESCRIPTION
	"Input Switch 4 Polarity, 1=Inverted"
      ::= { devInput4 2 }

-- Fans

    devFan1Val OBJECT-TYPE
      SYNTAX  INTEGER (0..4000)
      ACCESS  read-only
      STATUS  mandatory
      DESCRIPTION
	"Current Fan 1 Speed in RPM"
      ::= { devFan1 1 }

    devFan1Min OBJECT-TYPE
      SYNTAX  INTEGER (0..4000)
      ACCESS  read-write
      STATUS  mandatory
      DESCRIPTION
	"Fan 1 Minimum Speed in RPM"
      ::= { devFan1 2 }

    devFan1Max OBJECT-TYPE
      SYNTAX  INTEGER (0..4000)
      ACCESS  read-write
      STATUS  mandatory
      DESCRIPTION
	"Fan 1 Maximum Speed in RPM"
      ::= { devFan1 3 }

    devFan2Val OBJECT-TYPE
      SYNTAX  INTEGER (0..4000)
      ACCESS  read-only
      STATUS  mandatory
      DESCRIPTION
	"Current Fan 2 Speed in RPM"
      ::= { devFan2 1 }

    devFan2Min OBJECT-TYPE
      SYNTAX  INTEGER (0..4000)
      ACCESS  read-write
      STATUS  mandatory
      DESCRIPTION
	"Fan 2 Minimum Speed in RPM"
      ::= { devFan2 2 }

    devFan2Max OBJECT-TYPE
      SYNTAX  INTEGER (0..4000)
      ACCESS  read-write
      STATUS  mandatory
      DESCRIPTION
	"Fan 2 Maximum Speed in RPM"
      ::= { devFan2 3 }

    devFan3Val OBJECT-TYPE
      SYNTAX  INTEGER (0..4000)
      ACCESS  read-only
      STATUS  mandatory
      DESCRIPTION
	"Current Fan 3 Speed in RPM"
      ::= { devFan3 1 }

    devFan3Min OBJECT-TYPE
      SYNTAX  INTEGER (0..4000)
      ACCESS  read-write
      STATUS  mandatory
      DESCRIPTION
	"Fan 3 Minimum Speed in RPM"
      ::= { devFan3 2 }

    devFan3Max OBJECT-TYPE
      SYNTAX  INTEGER (0..4000)
      ACCESS  read-write
      STATUS  mandatory
      DESCRIPTION
	"Fan 3 Maximum Speed in RPM"
      ::= { devFan3 3 }

    devFan4Val OBJECT-TYPE
      SYNTAX  INTEGER (0..4000)
      ACCESS  read-only
      STATUS  mandatory
      DESCRIPTION
	"Current Fan 4 Speed in RPM"
      ::= { devFan4 1 }

    devFan4Min OBJECT-TYPE
      SYNTAX  INTEGER (0..4000)
      ACCESS  read-write
      STATUS  mandatory
      DESCRIPTION
	"Fan 4 Minimum Speed in RPM"
      ::= { devFan4 2 }

    devFan4Max OBJECT-TYPE
      SYNTAX  INTEGER (0..4000)
      ACCESS  read-write
      STATUS  mandatory
      DESCRIPTION
	"Fan 4 Maximum Speed in RPM"
      ::= { devFan4 3 }

-- Temps

    devTemp1Val OBJECT-TYPE
      SYNTAX  INTEGER (-23..100)
      ACCESS  read-only
      STATUS  mandatory
      DESCRIPTION
	"Current Probe 1 Temperature"
      ::= { devTemp1 1 }

    devTemp1Min OBJECT-TYPE
      SYNTAX  INTEGER (-23..100)
      ACCESS  read-write
      STATUS  mandatory
      DESCRIPTION
	"Probe 1 Minimum Temperature"
      ::= { devTemp1 2 }

    devTemp1Max OBJECT-TYPE
      SYNTAX  INTEGER (-23..100)
      ACCESS  read-write
      STATUS  mandatory
      DESCRIPTION
	"Probe 1 Maximum Temperature"
      ::= { devTemp1 3 }

    devTemp2Val OBJECT-TYPE
      SYNTAX  INTEGER (-23..100)
      ACCESS  read-only
      STATUS  mandatory
      DESCRIPTION
	"Current Probe 2 Temperature"
      ::= { devTemp2 1 }

    devTemp2Min OBJECT-TYPE
      SYNTAX  INTEGER (-23..100)
      ACCESS  read-write
      STATUS  mandatory
      DESCRIPTION
	"Probe 2 Minimum Temperature"
      ::= { devTemp2 2 }

    devTemp2Max OBJECT-TYPE
      SYNTAX  INTEGER (-23..100)
      ACCESS  read-write
      STATUS  mandatory
      DESCRIPTION
	"Probe 2 Maximum Temperature"
      ::= { devTemp2 3 }

    devTemp3Val OBJECT-TYPE
      SYNTAX  INTEGER (-23..100)
      ACCESS  read-only
      STATUS  mandatory
      DESCRIPTION
	"Current Probe 3 Temperature"
      ::= { devTemp3 1 }

    devTemp3Min OBJECT-TYPE
      SYNTAX  INTEGER (-23..100)
      ACCESS  read-write
      STATUS  mandatory
      DESCRIPTION
	"Probe 3 Minimum Temperature"
      ::= { devTemp3 2 }

    devTemp3Max OBJECT-TYPE
      SYNTAX  INTEGER (-23..100)
      ACCESS  read-write
      STATUS  mandatory
      DESCRIPTION
	"Probe 3 Maximum Temperature"
      ::= { devTemp3 3 }

    devTemp4Val OBJECT-TYPE
      SYNTAX  INTEGER (-23..100)
      ACCESS  read-only
      STATUS  mandatory
      DESCRIPTION
	"Current Probe 4 Temperature"
      ::= { devTemp4 1 }

    devTemp4Min OBJECT-TYPE
      SYNTAX  INTEGER (-23..100)
      ACCESS  read-write
      STATUS  mandatory
      DESCRIPTION
	"Probe 4 Minimum Temperature"
      ::= { devTemp4 2 }

    devTemp4Max OBJECT-TYPE
      SYNTAX  INTEGER (-23..100)
      ACCESS  read-write
      STATUS  mandatory
      DESCRIPTION
	"Probe 4 Maximum Temperature"
      ::= { devTemp4 3 }

    devTemp5Val OBJECT-TYPE
      SYNTAX  INTEGER (-23..100)
      ACCESS  read-only
      STATUS  mandatory
      DESCRIPTION
	"Current Probe 5 Temperature"
      ::= { devTemp5 1 }

    devTemp5Min OBJECT-TYPE
      SYNTAX  INTEGER (-23..100)
      ACCESS  read-write
      STATUS  mandatory
      DESCRIPTION
	"Probe 5 Minimum Temperature"
      ::= { devTemp5 2 }

    devTemp5Max OBJECT-TYPE
      SYNTAX  INTEGER (-23..100)
      ACCESS  read-write
      STATUS  mandatory
      DESCRIPTION
	"Probe 5 Maximum Temperature"
      ::= { devTemp5 3 }

    devTemp6Val OBJECT-TYPE
      SYNTAX  INTEGER (-23..100)
      ACCESS  read-only
      STATUS  mandatory
      DESCRIPTION
	"Current Probe 6 Temperature"
      ::= { devTemp6 1 }

    devTemp6Min OBJECT-TYPE
      SYNTAX  INTEGER (-23..100)
      ACCESS  read-write
      STATUS  mandatory
      DESCRIPTION
	"Probe 6 Minimum Temperature"
      ::= { devTemp6 2 }

    devTemp6Max OBJECT-TYPE
      SYNTAX  INTEGER (-23..100)
      ACCESS  read-write
      STATUS  mandatory
      DESCRIPTION
	"Probe 6 Maximum Temperature"
      ::= { devTemp6 3 }

    devTemp7Val OBJECT-TYPE
      SYNTAX  INTEGER (-23..100)
      ACCESS  read-only
      STATUS  mandatory
      DESCRIPTION
	"Current Probe 7 Temperature"
      ::= { devTemp7 1 }

    devTemp7Min OBJECT-TYPE
      SYNTAX  INTEGER (-23..100)
      ACCESS  read-write
      STATUS  mandatory
      DESCRIPTION
	"Probe 7 Minimum Temperature"
      ::= { devTemp7 2 }

    devTemp7Max OBJECT-TYPE
      SYNTAX  INTEGER (-23..100)
      ACCESS  read-write
      STATUS  mandatory
      DESCRIPTION
	"Probe 7 Maximum Temperature"
      ::= { devTemp7 3 }

    devTemp8Val OBJECT-TYPE
      SYNTAX  INTEGER (-23..100)
      ACCESS  read-only
      STATUS  mandatory
      DESCRIPTION
	"Current Probe 8 Temperature"
      ::= { devTemp8 1 }

    devTemp8Min OBJECT-TYPE
      SYNTAX  INTEGER (-23..100)
      ACCESS  read-write
      STATUS  mandatory
      DESCRIPTION
	"Probe 8 Minimum Temperature"
      ::= { devTemp8 2 }

    devTemp8Max OBJECT-TYPE
      SYNTAX  INTEGER (-23..100)
      ACCESS  read-write
      STATUS  mandatory
      DESCRIPTION
	"Probe 8 Maximum Temperature"
      ::= { devTemp8 3 }

-- ISA Voltages

    devISAP12Val OBJECT-TYPE
      SYNTAX  INTEGER (0..1400)
      ACCESS  read-only
      STATUS  mandatory
      DESCRIPTION
	"Current ISA Bus +12V value (x100)"
      ::= { devISAP12 1 }

    devISAP12Min OBJECT-TYPE
      SYNTAX  INTEGER (0..1400)
      ACCESS  read-write
      STATUS  mandatory
      DESCRIPTION
	"Minimum ISA Bus +12V value (x100)"
      ::= { devISAP12 2 }

    devISAP12Max OBJECT-TYPE
      SYNTAX  INTEGER (0..1400)
      ACCESS  read-write
      STATUS  mandatory
      DESCRIPTION
	"Maximum ISA Bus +12V value (x100)"
      ::= { devISAP12 3 }

    devISAP5Val OBJECT-TYPE
      SYNTAX  INTEGER (0..700)
      ACCESS  read-only
      STATUS  mandatory
      DESCRIPTION
	"Current ISA Bus +5V value (x100)"
      ::= { devISAP5 1 }

    devISAP5Min OBJECT-TYPE
      SYNTAX  INTEGER (0..700)
      ACCESS  read-write
      STATUS  mandatory
      DESCRIPTION
	"Minimum ISA Bus +5V value (x100)"
      ::= { devISAP5 2 }

    devISAP5Max OBJECT-TYPE
      SYNTAX  INTEGER (0..700)
      ACCESS  read-write
      STATUS  mandatory
      DESCRIPTION
	"Maximum ISA Bus +5V value (x100)"
      ::= { devISAP5 3 }

    devISAN5Val OBJECT-TYPE
      SYNTAX  INTEGER (0..700)
      ACCESS  read-only
      STATUS  mandatory
      DESCRIPTION
	"Current ISA Bus -5V value (x100)"
      ::= { devISAN5 1 }

    devISAN5Min OBJECT-TYPE
      SYNTAX  INTEGER (0..700)
      ACCESS  read-write
      STATUS  mandatory
      DESCRIPTION
	"Minimum ISA Bus -5V value (x100)"
      ::= { devISAN5 2 }

    devISAN5Max OBJECT-TYPE
      SYNTAX  INTEGER (0..700)
      ACCESS  read-write
      STATUS  mandatory
      DESCRIPTION
	"Maximum ISA Bus -5V value (x100)"
      ::= { devISAN5 3 }

    devISAN12Val OBJECT-TYPE
      SYNTAX  INTEGER (0..1400)
      ACCESS  read-only
      STATUS  mandatory
      DESCRIPTION
	"Current ISA Bus -12V value (x100)"
      ::= { devISAN12 1 }

    devISAN12Min OBJECT-TYPE
      SYNTAX  INTEGER (0..1400)
      ACCESS  read-write
      STATUS  mandatory
      DESCRIPTION
	"Minimum ISA Bus -12V value (x100)"
      ::= { devISAN12 2 }

    devISAN12Max OBJECT-TYPE
      SYNTAX  INTEGER (0..1400)
      ACCESS  read-write
      STATUS  mandatory
      DESCRIPTION
	"Maximum ISA Bus -12V value (x100)"
      ::= { devISAN12 3 }

-- DC Voltages

    devDCP12Val OBJECT-TYPE
      SYNTAX  INTEGER (0..1400)
      ACCESS  read-only
      STATUS  mandatory
      DESCRIPTION
	"Current Drive Connector +12V value (x100)"
      ::= { devDCP12 1 }

    devDCP12Min OBJECT-TYPE
      SYNTAX  INTEGER (0..1400)
      ACCESS  read-write
      STATUS  mandatory
      DESCRIPTION
	"Minimum Drive Connector +12V value (x100)"
      ::= { devDCP12 2 }

    devDCP12Max OBJECT-TYPE
      SYNTAX  INTEGER (0..1400)
      ACCESS  read-write
      STATUS  mandatory
      DESCRIPTION
	"Maximum Drive Connector +12V value (x100)"
      ::= { devDCP12 3 }

    devDCP5Val OBJECT-TYPE
      SYNTAX  INTEGER (0..700)
      ACCESS  read-only
      STATUS  mandatory
      DESCRIPTION
	"Current Drive Connector +5V value (x100)"
      ::= { devDCP5 1 }

    devDCP5Min OBJECT-TYPE
      SYNTAX  INTEGER (0..700)
      ACCESS  read-write
      STATUS  mandatory
      DESCRIPTION
	"Minimum Drive Connector +5V value (x100)"
      ::= { devDCP5 2 }

    devDCP5Max OBJECT-TYPE
      SYNTAX  INTEGER (0..700)
      ACCESS  read-write
      STATUS  mandatory
      DESCRIPTION
	"Maximum Drive Connector +5V value (x100)"
      ::= { devDCP5 3 }

-- Masks

    fanErrors OBJECT-TYPE
      SYNTAX  INTEGER (0..255)
      ACCESS  read-write
      STATUS  mandatory
      DESCRIPTION
	"BITMASK - Enable Fan Errors, Bit 0=Fan1"
      ::= { masks 1 }

    tempErrors OBJECT-TYPE
      SYNTAX  INTEGER (0..255)
      ACCESS  read-write
      STATUS  mandatory
      DESCRIPTION
	"BITMASK - Enable Temp Errors, Bit 0=Temp1"
      ::= { masks 2 }

    isaErrors OBJECT-TYPE
      SYNTAX  INTEGER (0..255)
      ACCESS  read-write
      STATUS  mandatory
      DESCRIPTION
	"BITMASK - Enable ISA Bus Errors, Bit 0=+12v"
      ::= { masks 3 }

    dcErrors OBJECT-TYPE
      SYNTAX  INTEGER (0..255)
      ACCESS  read-write
      STATUS  mandatory
      DESCRIPTION
	"BITMASK - Enable Drive Connector Bus Errors, Bit 0=+12v, 1=+5v"
      ::= { masks 4 }

    inputPSU OBJECT-TYPE
      SYNTAX  INTEGER (0..255)
      ACCESS  read-write
      STATUS  mandatory
      DESCRIPTION
	"BITMASK - Treat Input switches as PSU Errors, Bit 0-1=Input1=PSU Error"
      ::= { masks 7 }

    inputTamper OBJECT-TYPE
      SYNTAX  INTEGER (0..255)
      ACCESS  read-write
      STATUS  mandatory
      DESCRIPTION
	"BITMASK - Treat Input switches as Tamper Errors, Bit 0-1=Input1=Tamper Error"
      ::= { masks 8 }

    enOutput0 OBJECT-TYPE
      SYNTAX  INTEGER (0..255)
      ACCESS  read-write
      STATUS  mandatory
      DESCRIPTION
	"BITMASK - Enable Outputs/LED's on errors - Bit 0=Power,1=Fan,2=Temp,3=PSU,4=Tamper,5=Watchdog."
      ::= { masks 9 }

    enOutput1 OBJECT-TYPE
      SYNTAX  INTEGER (0..255)
      ACCESS  read-write
      STATUS  mandatory
      DESCRIPTION
	"BITMASK - Enable Outputs/LED's on errors - Bit 0=Power,1=Fan,2=Temp,3=PSU,4=Tamper,5=Watchdog."
      ::= { masks 10 }

    enOutput2 OBJECT-TYPE
      SYNTAX  INTEGER (0..255)
      ACCESS  read-write
      STATUS  mandatory
      DESCRIPTION
	"BITMASK - Enable Outputs/LED's on errors - Bit 0=Power,1=Fan,2=Temp,3=PSU,4=Tamper,5=Watchdog."
      ::= { masks 11 }

    enOutput3 OBJECT-TYPE
      SYNTAX  INTEGER (0..255)
      ACCESS  read-write
      STATUS  mandatory
      DESCRIPTION
	"BITMASK - Enable Outputs/LED's on errors - Bit 0=Power,1=Fan,2=Temp,3=PSU,4=Tamper,5=Watchdog."
      ::= { masks 12 }

    enBeeper OBJECT-TYPE
      SYNTAX  INTEGER (0..255)
      ACCESS  read-write
      STATUS  mandatory
      DESCRIPTION
	"BITMASK - Enable Beeper on errors - Bit 0=Power,1=Fan,2=Temp,3=PSU,4=Tamper,5=Watchdog."
      ::= { masks 13 }

    enRelay OBJECT-TYPE
      SYNTAX  INTEGER (0..255)
      ACCESS  read-write
      STATUS  mandatory
      DESCRIPTION
	"BITMASK - Enable Relay on errors - Bit 0=Power,1=Fan,2=Temp,3=PSU,4=Tamper,5=Watchdog."
      ::= { masks 14 }

    enReset OBJECT-TYPE
      SYNTAX  INTEGER (0..255)
      ACCESS  read-write
      STATUS  mandatory
      DESCRIPTION
	"BITMASK - Enable Reset on errors - Bit 0=Power,1=Fan,2=Temp,3=PSU,4=Tamper,5=Watchdog."
      ::= { masks 15 }


-- Special Stuff

    watchdog OBJECT-TYPE
      SYNTAX  INTEGER (0..255)
      ACCESS  read-write
      STATUS  mandatory
      DESCRIPTION
	"Current Watchdog timeout left in seconds, 0=Disabled"
      ::= { special 1 }


-- Traps

    inputsAlert  TRAP-TYPE
    ENTERPRISE      guardian
--ERROR    VARIABLES       { }
    DESCRIPTION
      "Trap generated if any of the Inputs are activated"
    ::= 0

    fanAlert  TRAP-TYPE
    ENTERPRISE      guardian
--ERROR    VARIABLES       { }
    DESCRIPTION
      "Trap generated if any Fan speeds are outside limits"
    ::= 1

    tempAlert  TRAP-TYPE
    ENTERPRISE      guardian
--ERROR    VARIABLES       { }
    DESCRIPTION
      "Trap generated if temperature exceeds limits"
    ::= 2

    isaAlert  TRAP-TYPE
    ENTERPRISE      guardian
--ERROR    VARIABLES       { }
    DESCRIPTION
      "Trap generated if ISA Bus voltages exceed limits"
    ::= 3

    dcAlert  TRAP-TYPE
    ENTERPRISE      guardian
--ERROR    VARIABLES       { }
    DESCRIPTION
      "Trap generated if disk connector voltages exceed limits"
    ::= 4

END
