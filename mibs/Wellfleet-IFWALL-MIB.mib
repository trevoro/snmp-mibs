Wellfleet-IFWALL-MIB DEFINITIONS ::= BEGIN

-- Created by mdl2asn version 3.1
-- Creation date: Wed May  8 17:23:37 EDT 1996
-- MIB was made obsolete for BayRS 13.20 Firewall Phase 3 by rmehta: 11/25/98

    IMPORTS

      OBJECT-TYPE
        FROM RFC-1212
      DisplayString
        FROM RFC1213-MIB
      wfFwallGroup
        FROM Wellfleet-COMMON-MIB;


    wfIFwallIfTable OBJECT-TYPE
        SYNTAX  SEQUENCE OF WfIFwallIfEntry
        ACCESS  not-accessible
        STATUS  obsolete
        DESCRIPTION
                 "WF_IFWALL_INTERFACE_TABLE - Interface
                 This tabulates the interfaces within an interface firewall
                 group. All interfaces are indexed according to their physical
                 slot and connector designation. "
        ::= { wfFwallGroup 1 }

    wfIFwallIfEntry OBJECT-TYPE
        SYNTAX  WfIFwallIfEntry
        ACCESS  not-accessible
        STATUS  obsolete
        DESCRIPTION
                "Firewall interface entries."
        INDEX   { wfIFwallIfSlot,
                  wfIFwallIfPort }
        ::= { wfIFwallIfTable 1 }

    WfIFwallIfEntry ::= SEQUENCE {
            wfIFwallIfDelete
                INTEGER,
            wfIFwallIfDisable
                INTEGER,
            wfIFwallIfCct
                INTEGER,
            wfIFwallIfSlot
                INTEGER,
            wfIFwallIfPort
                INTEGER,
            wfIFwallIfLineNumber
                INTEGER,
            wfIFwallIfName
                DisplayString
            }

    wfIFwallIfDelete OBJECT-TYPE
        SYNTAX  INTEGER {
                    created(1),
                    deleted(2)
                }
        ACCESS  read-write
        STATUS  obsolete
        DESCRIPTION
                "Creation and deletion flag for this record. When set,
                it will cause this entry to be deleted from the MIB."
        DEFVAL  { created }
        ::= { wfIFwallIfEntry 1 }

    wfIFwallIfDisable OBJECT-TYPE
        SYNTAX  INTEGER {
                    enabled(1),
                    disabled(2)
                }
        ACCESS  read-write
        STATUS  obsolete
        DESCRIPTION
                "Enable/Disable parameter. A disabled interface will never
                be selected as the active interface for a circuit."
        DEFVAL  { enabled }
        ::= { wfIFwallIfEntry 2 }

    wfIFwallIfCct OBJECT-TYPE
        SYNTAX  INTEGER(1..1023)
        ACCESS  read-write
        STATUS  obsolete
        DESCRIPTION
                "The circuit number of the circuit to which the interface
                belongs. This interface will either act as the active
                interface for the circuit or as a hot stand-by."
        ::= { wfIFwallIfEntry 3 }

    wfIFwallIfSlot OBJECT-TYPE
        SYNTAX  INTEGER(1..14)
        ACCESS  read-only
        STATUS  obsolete
        DESCRIPTION
                "Slot ID of the interface, used as instance ID"
        ::= { wfIFwallIfEntry 4 }

    wfIFwallIfPort OBJECT-TYPE
        SYNTAX  INTEGER(1..44)
        ACCESS  read-only
        STATUS  obsolete
        DESCRIPTION
                "Port ID of the interface, used as instance ID"
        ::= { wfIFwallIfEntry 5 }

    wfIFwallIfLineNumber OBJECT-TYPE
        SYNTAX  INTEGER
        ACCESS  read-write
        STATUS  obsolete
        DESCRIPTION
                "The Line number for the port"
        ::= { wfIFwallIfEntry 6 }

    wfIFwallIfName OBJECT-TYPE
        SYNTAX  DisplayString (SIZE(0..32))
        ACCESS  read-write
        STATUS  obsolete
        DESCRIPTION
                "Displayable string that is associated with this instance"
        ::= { wfIFwallIfEntry 7 }


    wfFwallIntfTable OBJECT-TYPE
        SYNTAX  SEQUENCE OF WfFwallIntfEntry
        ACCESS  not-accessible
        STATUS  mandatory
        DESCRIPTION
                "WF_IFWALL_INTERFACE_TABLE - Interface
                 This tabulates the interfaces within an interface firewall
                 group. All interfaces are indexed according to the circuit
                 number."
        ::= { wfFwallGroup 3 }

    wfFwallIntfEntry OBJECT-TYPE
        SYNTAX  WfFwallIntfEntry
        ACCESS  not-accessible
        STATUS  mandatory
        DESCRIPTION
                "Firewall interface entries."
        INDEX   { wfFwallIntfCct }
        ::= { wfFwallIntfTable 1 }

    WfFwallIntfEntry ::= SEQUENCE {
            wfFwallIntfDelete
                INTEGER,
            wfFwallIntfDisable
                INTEGER,
            wfFwallIntfCct
                INTEGER,
            wfFwallIntfName
                DisplayString,
            wfFwallIntfPolicyIndex
                INTEGER
            }

    wfFwallIntfDelete OBJECT-TYPE
        SYNTAX  INTEGER {
                    create(1),
                    delete(2)
                }
        ACCESS  read-write
        STATUS  mandatory
        DESCRIPTION
                "Creation and deletion flag for this record. When set,
                it will cause this entry to be deleted from the MIB."
        DEFVAL  { create }
        ::= { wfFwallIntfEntry 1 }

    wfFwallIntfDisable OBJECT-TYPE
        SYNTAX  INTEGER {
                    enabled(1),
                    disabled(2)
                }
        ACCESS  read-write
        STATUS  mandatory
        DESCRIPTION
                "Enable/Disable parameter. A disabled interface will never
                 be selected as the active interface for a circuit."
        DEFVAL  { enabled }
        ::= { wfFwallIntfEntry 2 }

    wfFwallIntfCct OBJECT-TYPE
        SYNTAX  INTEGER(1..1023)
        ACCESS  read-only
        STATUS  mandatory
        DESCRIPTION
                "The circuit number of the circuit to which the interface
                belongs. This interface will either act as the active
                interface for the circuit or as a hot stand-by."
        ::= { wfFwallIntfEntry 3 }

    wfFwallIntfName OBJECT-TYPE
        SYNTAX  DisplayString (SIZE(0..32))
        ACCESS  read-write
        STATUS  mandatory
        DESCRIPTION
                "Displayable string that is associated with this instance"
        ::= { wfFwallIntfEntry 4 }

    wfFwallIntfPolicyIndex OBJECT-TYPE
        SYNTAX  INTEGER(0..1023)
        ACCESS  read-write
        STATUS  mandatory
        DESCRIPTION
                "Policy Index allows same virtual machine to be used
                 by one or more circuits specified when the same policy
                 index is configured on them. Thus allows scaling."
        ::= { wfFwallIntfEntry 5 }


END  -- Wellfleet-IFWALL-MIB
