ACC-HUB DEFINITIONS ::= BEGIN

    IMPORTS
	 OBJECT-TYPE FROM RFC1155-SMI
               accTrapLogSeqNum FROM ACC-SYSTEM
	accBRG, DisplayString, RowStatus, IfIndex, SmdsAddress
             FROM ACC-MIB;

-- Hub Group
      accEnetHub	OBJECT IDENTIFIER ::= { accBRG 39 }
	accEnetHubStatTable	OBJECT-TYPE
				SYNTAX SEQUENCE OF AccEnetHubStatEntry
				ACCESS  not-accessible
				STATUS mandatory
				DESCRIPTION
				"A List of Ethernet Hub Port statistics."
				::=   { accEnetHub 1 }
	AccEnetHubStatEntry ::=  SEQUENCE {
			accEnetPortIndex		INTEGER,		
			accEnetHubIndex			INTEGER,
			accEnetHubAdStatus		INTEGER,
			accEnetHubOpStatus		INTEGER,
			accEnetHubBitError		INTEGER,
			accEnetHubLinkTest		INTEGER
			}
	accEnetHubStatEntry	OBJECT-TYPE
			SYNTAX  AccEnetHubStatEntry
			ACCESS  not-accessible
			STATUS mandatory
			DESCRIPTION
			" A table entry providing information about Ethernet
			Hub ports."
			INDEX   { accEnetPortIndex, accEnetHubIndex }
			::=  { accEnetHubStatTable	1 }
	accEnetPortIndex	OBJECT-TYPE
			SYNTAX  INTEGER
			ACCESS   read-only
			STATUS mandatory
			DESCRIPTION
			" This is the Ethernet Physical Port starting with 1"
			::=  { accEnetHubStatEntry	1 }
	accEnetHubIndex	OBJECT-TYPE
			SYNTAX  INTEGER
			ACCESS   read-only
			STATUS mandatory
			DESCRIPTION
			" This is the Ethernet Hub Port index 1-8"
			::=  { accEnetHubStatEntry	2 }
	accEnetHubAdStatus	OBJECT-TYPE
			SYNTAX  INTEGER {
			enabled(1),
			disabled(2)
						}
			ACCESS   read-write
			STATUS mandatory
			DESCRIPTION
			"This is the current administrative status of the
			Ethernet Hub Port."
			::=  { accEnetHubStatEntry	3 }
	accEnetHubOpStatus	  OBJECT-TYPE
			SYNTAX  INTEGER {
				connected (1),
				partitioned (2),
				disabled (3)
				}
			ACCESS   read-only
			STATUS mandatory
			DESCRIPTION
			" This shows the Operational State of the Ethernet
			Hub Port"
			::=  { accEnetHubStatEntry	4 }
	accEnetHubBitError	 OBJECT-TYPE
			SYNTAX  INTEGER {
				yes (1),
				no (2)
				}
			ACCESS   read-only
			STATUS mandatory
			DESCRIPTION
			" This shows whether a bit-error has occurred"
			::=  { accEnetHubStatEntry	5 }
	accEnetHubLinkTest	 OBJECT-TYPE
			SYNTAX  INTEGER {
				pass (1),
				fail (2)
				}
			ACCESS   read-only
			STATUS mandatory
			DESCRIPTION
			" This shows whether a link test has occurred"
			::=  { accEnetHubStatEntry	6 }

END
