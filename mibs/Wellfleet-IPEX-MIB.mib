Wellfleet-IPEX-MIB DEFINITIONS ::= BEGIN

-- Created by mdl2asn version 3.1
-- Creation date: Wed Aug 30 16:43:20 EDT 1995


    IMPORTS

      IpAddress 
        FROM RFC1155-SMI
      OBJECT-TYPE
        FROM RFC-1212
      DisplayString
        FROM RFC1213-MIB
      wfIpexGroup
        FROM Wellfleet-COMMON-MIB;


    wfIpex		OBJECT IDENTIFIER ::= { wfIpexGroup 1 }

    wfIpexDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete IPEX."
        DEFVAL	{ created }
        ::= { wfIpex 1 }

    wfIpexDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable IPEX."
        DEFVAL	{ enabled }
        ::= { wfIpex 2 }

    wfIpexState OBJECT-TYPE
        SYNTAX	INTEGER {
    		    up(1),
    		    down(2),
    		    init(3),
    		    notpresent(4)
    		}
        ACCESS	read-only
        STATUS	mandatory
        DESCRIPTION
                "The current state of IPEX."
        DEFVAL	{ down }
        ::= { wfIpex 3 }

    wfIpexMaxMessageSize OBJECT-TYPE
        SYNTAX  INTEGER (16..4096)
        ACCESS  read-write
        STATUS  mandatory
        DESCRIPTION
                "The maximum client message size that IPEX accepts.  The 
                size is in bytes."
        DEFVAL  { 1600 }
        ::= { wfIpex 4 }

  wfIpexInsCalledDte OBJECT-TYPE
        SYNTAX	INTEGER {
    		    enabled(1),
    		    disabled(2)
    		}
        ACCESS	read-write
        STATUS	mandatory
        DESCRIPTION
                "Enable/Disable parameter. Default is disabled.
                Users perform an SNMP SET operation on this
                object in order to enable/disable the support
                for inserting Called DTE address."
        DEFVAL	{ disabled }
        ::= { wfIpex 5 }

    wfIpexInsCallingDte OBJECT-TYPE
        SYNTAX  INTEGER {
                    enabled(1),
                    disabled(2)
                }
        ACCESS  read-write
        STATUS  mandatory
        DESCRIPTION
		        "Enable/disable the support for transmitting the calling
                DTE address over TCP tunnel. This changes the IPEX control
                message header format and hence this attribute should be
                enabled (only for 11.02 or up) on both ends (local & remote
                routers) for proper operation. This attribute applies only
                to End_to_End mode."
        DEFVAL  { disabled }
        ::= { wfIpex 6 }

    wfIpexTcpRequestLimit OBJECT-TYPE
        SYNTAX  INTEGER(0..1000)
        ACCESS  read-write
        STATUS  mandatory
        DESCRIPTION
                "The maximum number of TCP requests IPEX can have pending
                with TCP. Any addition requests will be queued until the
                number of pending requests fall below the limit."
        DEFVAL  { 25 }
        ::= { wfIpex 7 }
 
    wfIpexTcpRequestCheck OBJECT-TYPE
        SYNTAX  INTEGER(0..30000)
        ACCESS  read-write
        STATUS  mandatory
        DESCRIPTION
                "When IPEX has queued TCP requests, the time period (in
                milliseconds) between checking if the number of pending
                TCP requests have fallen below wfIpexTcpRequestLimit."
        DEFVAL  { 1000 }
        ::= { wfIpex 8 }
 
    wfIpexSendResetRequestOnTCPUp OBJECT-TYPE
        SYNTAX	INTEGER
        ACCESS	read-write
        STATUS	mandatory
        DESCRIPTION
                "Default(cause code) is 0x09 and PVC_TCP sends out the Reset
                 Request with the cause code = 0x09 and TCP_PVC Router does not
                 send the Reset Request when TCP is up. If the value is changed
                 from the default cause code(0x09) then IPEX Gateway will send
                 out the Reset Request with this value when network is operational.
                 TCP_PVC will also send the Reset Request with this cause code
                 when TCP connection is up."
        DEFVAL	{ 9 }
        ::= { wfIpex 9 }

    wfIpexTranslateNetworkOutOfOrder OBJECT-TYPE
        SYNTAX	INTEGER
        ACCESS	read-write
        STATUS	mandatory
        DESCRIPTION
                "Default is 0x1d(29): Network out of order. If the value is changed
                 from the default cause code = 0x1d then the IPEX Gateway will
                 send the Reset Request with cause code specified when the network
                 is out of order."
        DEFVAL	{ 29 }
        ::= { wfIpex 10 }
   wfIpexTcpUseIpAddress OBJECT-TYPE
        SYNTAX  INTEGER {
                    enabled(1),
                    disabled(2)
                }
        ACCESS  read-write
        STATUS  mandatory
        DESCRIPTION
                "Enable/Disable parameter. Default is disabled.
                 If set to Enabled, the IP address used for a TCP
                 connection will be the coresponding address for the
                 circuit."
        DEFVAL  { disabled }
        ::= { wfIpex 11 }

    wfIpexBobEnabled OBJECT-TYPE
        SYNTAX INTEGER  {
            disabled(1) ,
            enabled(2)
            }
        ACCESS  read-write
        STATUS  mandatory
        DESCRIPTION
                "This attribute will indicate whether IPEX supports Bank
                 Of Bahrain enhancement. If it is enabled, only calling DTE
                 will be send in ASCII format in user defined area of message
                 header, if header type is full."
        DEFVAL  { disabled }
        ::= {wfIpex 12 }

    wfIpexBobTimeout OBJECT-TYPE
        SYNTAX  INTEGER (0..30000)
        ACCESS  read-write
        STATUS  mandatory
        DESCRIPTION
                "This attribute will indicate the timeout in milliseconds, after
                 which DEVICE UP message is to be send to BOB mainserver
                 from router, as long as this service supports BOB
                 functionality."
        DEFVAL  {15000}
        ::= {wfIpex 13 }

   wfIpexMaxAuditIp OBJECT-TYPE
        SYNTAX	INTEGER
        ACCESS	read-write
        STATUS	mandatory
        DESCRIPTION
                "Default is 25. Specify the maximum of IP address and TCP port
                 pairs that IPEX Audit gate can hold in its internal table when
                 IPEX PVC-TCP Gateway is in TCP Retry Mode. Audit gate puts
                 new ip address and TCP port pair to the internal table when it
                 tries TCP connection. IPEX Audit gate will be re-trying TCP
                 connections until the table is filled up. Once it is full
                 then it won't re-try new TCP connections. Setting zero causes
                 IPEX audit gate to try TCP connections without examining the
                 IP address and TCP port pairs had already tried out or not."
        DEFVAL	{ 25 }
        ::= { wfIpex 14 }

   wfIpexSessionInstanceIdOffsetForSvc OBJECT-TYPE
        SYNTAX	INTEGER
        ACCESS	read-write
        STATUS	mandatory
        DESCRIPTION
                "Default is 0. Specify the offset value for wfIpexSessionEntry
                 when instances for SVC are created. For example, when it is
                 set to 1023, instance ID for wfIpexSessionEntry for SVC
                 connections will be wfIpexSessionEntry.*.3.1024 and the next
                 one will be wfIpexSessionEntry.*.3.1025 and so on.
                 This MIB object is introduced not to assign same instance ID
                 to PVC and SVC when SVCs and PVCs are configured with single
                 circuit. Because wfIpexSessionEntry for PVCs are based on the
                 LCNs and the ones for SVCs are based on the order of each SVC
                 being created, there would be the cases that same instance IDs
                 are assigned to both SVC and PVC and it will cause the router
                 to fault. It needs to be set to the value which is greater
                 than the maximum LCN of the PVC connections when PVCs and SVCs
                 co-exist on a single circuit."
        DEFVAL	{ 0 }
        ::= { wfIpex 15 }

    wfIpexMappingTable OBJECT-TYPE
        SYNTAX	SEQUENCE OF WfIpexMappingEntry
        ACCESS	not-accessible
        STATUS	mandatory
        DESCRIPTION
                "A table which contains the list of mappings between TCP
                connections and X.25 connections.  This is the configuration
                table in which each entry sets up the association between a
                TCP port number and a X.25 DTE address or connection.
                inst_id[] = wfIpexMappingSrcConnCct wfIpexMappingSrcConnType
                wfIpexMappingID"
        ::= { wfIpexGroup 2 }

    wfIpexMappingEntry OBJECT-TYPE
        SYNTAX	WfIpexMappingEntry
        ACCESS	not-accessible
        STATUS	mandatory
        DESCRIPTION
                "An entry in wfIpexMappingTable."
        INDEX	{ wfIpexMappingSrcConnCct,
    		  wfIpexMappingSrcConnType,
    		  wfIpexMappingID1,
    		  wfIpexMappingID2 }
        ::= { wfIpexMappingTable 1 }

    WfIpexMappingEntry ::= SEQUENCE {
    	    wfIpexMappingDelete
    		INTEGER,
    	    wfIpexMappingDisable
    		INTEGER,
    	    wfIpexMappingSrcConnCct
    		INTEGER,
    	    wfIpexMappingSrcConnType
    		INTEGER,
    	    wfIpexMappingID1
    		INTEGER,
    	    wfIpexMappingID2
    		OCTET STRING,
    	    wfIpexMappingDstConnCct
    		INTEGER,
    	    wfIpexMappingDstConnType
    		INTEGER,
    	    wfIpexMappingLocalDTEAddr
    		DisplayString,
    	    wfIpexMappingRemoteDTEAddr
    		DisplayString,
    	    wfIpexMappingPvcLcn
    		INTEGER,
    	    wfIpexMappingRemoteIpAddr
    		IpAddress,
    	    wfIpexMappingRemoteTcpPort
    		INTEGER,
    	    wfIpexMappingQueueSize
    		INTEGER,
    	    wfIpexMappingSlotNumber
    		INTEGER,
    	    wfIpexMappingCtrlMode
    		INTEGER,
    	    wfIpexMappingX25CUDF
	   		OCTET STRING,
		   wfIpexMappingIdleTimer
		INTEGER,
	    wfIpexMappingKeepaliveTimer
		INTEGER,
	    wfIpexMappingKeepaliveRetries
		INTEGER,
	    wfIpexMappingTrace
		INTEGER,
            wfIpexMappingMsgHdrType
                INTEGER,
 	    wfIpexMappingRemoteBackupIp
    		IpAddress,
	    wfIpexMappingXlateCallingX121
                DisplayString,
            wfIpexMappingTcpMaxRetry
                INTEGER,
    	    wfIpexMappingCfgLocalIpAddr
    		IpAddress,
            wfIpexMappingRemoteBackupTcpPort
                INTEGER            
        }

    wfIpexMappingDelete OBJECT-TYPE
        SYNTAX	INTEGER {
    		    created(1),
    		    deleted(2)
    		}
        ACCESS	read-write
        STATUS	mandatory
        DESCRIPTION
                "Create/Delete attribute. Default is created.
                Users perform an SNMP SET operation on this object in
                order to create/delete a translation mapping record."
        DEFVAL	{ created }
        ::= { wfIpexMappingEntry 1 }

    wfIpexMappingDisable OBJECT-TYPE
        SYNTAX	INTEGER {
    		    enabled(1),
    		    disabled(2)
    		}
        ACCESS	read-write
        STATUS	mandatory
        DESCRIPTION
                "Enables or Disables this Mapping entry.
                Setting this attribute to DISABLED will disconnect
                all active Sessions pertaining to this Mapping entry"
        DEFVAL	{ enabled }
        ::= { wfIpexMappingEntry 2 }

    wfIpexMappingSrcConnCct OBJECT-TYPE
        SYNTAX	INTEGER
        ACCESS	read-only
        STATUS	mandatory
        DESCRIPTION
                "The circuit from which the connection attempt is
                received that initiates a translation session."
        ::= { wfIpexMappingEntry 3 }

    wfIpexMappingSrcConnType OBJECT-TYPE
        SYNTAX	INTEGER {
    		    pvc(1),
    		    svc(2),
    		    dcesvc(4),
    		    lapb(8),
    		    tcp(16)
    		}
        ACCESS	read-only
        STATUS	mandatory
        DESCRIPTION
                "Defines the type of original connection attempt.
                Whether it is a PVC, SVC, DCE_SVC, LAPB or TCP"
        ::= { wfIpexMappingEntry 4 }

    wfIpexMappingID1 OBJECT-TYPE
        SYNTAX	INTEGER
        ACCESS	read-only
        STATUS	mandatory
        DESCRIPTION
                "The translation mapping identifier which identifies the
                 remote connection of the translation session.  This is
                 an identifier that is available from the incoming
                 connection attempt.

                 The meaning of this object (wfIpexMappingID1) and the
                 next object (wfIpexMappingID2) is dependent on the
                 value of wfIpexMappingSrcConnType.

                 SrcConnType        ID1          ID2
                ---------------------------------------------------
    		    pvc(1)       LCN value       0 (Null)
    		    svc(2)          0         Called X.121 Address
    		    dcesvc(4)       0            0 (Null)
    		    lapb(8)         0            0 (Null)
    		    tcp(16)      Port Number     0 (Null)
                    
                 "
        ::= { wfIpexMappingEntry 5 }

    wfIpexMappingID2 OBJECT-TYPE
        SYNTAX	OCTET STRING
        ACCESS	read-only
        STATUS	mandatory
        DESCRIPTION
                "(See description for wfIpexMappingID1 above)"
        ::= { wfIpexMappingEntry 6 }

    wfIpexMappingDstConnCct OBJECT-TYPE
        SYNTAX	INTEGER
        ACCESS	read-write
        STATUS	mandatory
        DESCRIPTION
                "The circuit from which the connection to the destination
                is to be established to set up a translation session."
        ::= { wfIpexMappingEntry 7 }

    wfIpexMappingDstConnType OBJECT-TYPE
        SYNTAX	INTEGER {
    		    pvc(1),
    		    svc(2),
    		    dcesvc(4),
    		    lapb(8),
    		    tcp(16)
    		}
        ACCESS	read-write
        STATUS	mandatory
        DESCRIPTION
                "Defines type of connection at the destination end. Whether
                it is a PVC, SVC, DCE_SVC, LAPB or TCP"
        DEFVAL	{ pvc }
        ::= { wfIpexMappingEntry 8 }

    wfIpexMappingLocalDTEAddr OBJECT-TYPE
        SYNTAX	DisplayString
        ACCESS	read-write
        STATUS	mandatory
        DESCRIPTION
                "The Local DTE address (identifies the X.121 address
                of the X.25 interface on the IPEX).  This attribute
                is only used in the case of a SVC connection initiated
                from the IPEX to the terminal"
        ::= { wfIpexMappingEntry 9 }

    wfIpexMappingRemoteDTEAddr OBJECT-TYPE
        SYNTAX	DisplayString
        ACCESS	read-write
        STATUS	mandatory
        DESCRIPTION
                "The Remote DTE address (identifies the X.121 address
                of the X.25 interface on the terminal).  This attribute
                is only used in the case of a SVC connection initiated
                from the IPEX to the terminal"
        ::= { wfIpexMappingEntry 10 }

    wfIpexMappingPvcLcn OBJECT-TYPE
        SYNTAX	INTEGER(1..4095)
        ACCESS	read-write
        STATUS	mandatory
        DESCRIPTION
                "The LCN of the PVC connection from the IPEX to the
                terminal (identifies the channel to be used to reset
                the PVC connection.  This attribute * is only used
                in the case of a PVC connection initiated from the
                IPEX to the terminal"
        DEFVAL	{ 1 }
        ::= { wfIpexMappingEntry 11 }

    wfIpexMappingRemoteIpAddr OBJECT-TYPE
        SYNTAX	IpAddress
        ACCESS	read-write
        STATUS	mandatory
        DESCRIPTION
                "The IP address of the remote host with which
                this translation session is established.  This
                attribute is only used in the case of a TCP
                connection initiated from the IPEX to a host"
        ::= { wfIpexMappingEntry 12 }

    wfIpexMappingRemoteTcpPort OBJECT-TYPE
        SYNTAX	INTEGER
        ACCESS	read-write
        STATUS	mandatory
        DESCRIPTION
                "The remote TCP port number in the host to be used
                to establish a TCP connection from the IPEX to the
                host server.  This attribute is only used in the
                case of a TCP connection initiated from the IPEX
                to a host"
        ::= { wfIpexMappingEntry 13 }

    wfIpexMappingQueueSize OBJECT-TYPE
        SYNTAX  INTEGER(16..8192)
        ACCESS  read-write
        STATUS  mandatory
        DESCRIPTION
                "The size of the IPEX queues used for transfering data
                between TCP and X.25. The size is in bytes."
        DEFVAL  { 8192 }
        ::= { wfIpexMappingEntry 14 }

    wfIpexMappingSlotNumber OBJECT-TYPE
        SYNTAX	INTEGER(1..13)
        ACCESS	read-write
        STATUS	mandatory
        DESCRIPTION
                "The slot of the access (X.25 or LAPB) circuit
                on which the X.25 or LAPB connections will be
                established."
        ::= { wfIpexMappingEntry 15 }

    wfIpexMappingCtrlMode OBJECT-TYPE
        SYNTAX	INTEGER {
			  local(1),
			  end2end(2),
			  gateway(3)
        		}   
        ACCESS	read-write
        STATUS	mandatory
        DESCRIPTION
                "Local mode configuration terminates X.25 at the router 
                interface. The end2end mode configuration allows X.25 
                signalling and data to operate between two remote X.25 
                networks, using the router to translate both call control 
                and data over a TCP/IP network. The gateway mode terminates
                X.25 at the router interface, but allows the user to configure
                3 message header types at the TCP application layer. These 
                header values are described in wfIpexMappingMsgHdrType." 
        DEFVAL	{ end2end }
        ::= { wfIpexMappingEntry 16 }

    wfIpexMappingX25CUDF OBJECT-TYPE
        SYNTAX	OCTET STRING
        ACCESS	read-write
        STATUS	mandatory
        DESCRIPTION
                "The X.25 Call User Data field (CUDF) in a X.25 Call
                Request packet header.  This attribute is only used
                in the case of a SVC connection initiated from the
                IPEX to the terminal.  It is used as the network
                layer protocol identifier of the X.25 connection."
        ::= { wfIpexMappingEntry 17 }

    wfIpexMappingIdleTimer OBJECT-TYPE
        SYNTAX	INTEGER(0..86400)
        ACCESS	read-write
        STATUS	mandatory
        DESCRIPTION
                "Idle session timeout period, in seconds.  If an established
                TCP connection remains inactive for this interval, KEEPALIVE
                messages will be sent to the peer (if the Keepalive Timer is 
                non-zero).  Setting the Idle Timer to zero disables the 
                keepalive feature."
        DEFVAL	{ 120 }
        ::= { wfIpexMappingEntry 18 }

    wfIpexMappingKeepaliveTimer OBJECT-TYPE
        SYNTAX	INTEGER(0..600)
        ACCESS	read-write
        STATUS	mandatory
        DESCRIPTION
                "KEEPALIVE retransmit timeout period, in seconds.  This is
                the interval at which unacknowledged KEEPALIVE messages will
                be retransmitted.  If the Idle Timer is set to zero, this 
                timer ignored.  If the Idle Timer is non-zero and this timer
                IS zero, no KEEPALIVEs are sent and the session is terminated
                upon expiration of the Idle Timer."
        DEFVAL	{ 3 }
        ::= { wfIpexMappingEntry 19 }

    wfIpexMappingKeepaliveRetries OBJECT-TYPE
        SYNTAX	INTEGER(0..99)
        ACCESS	read-write
        STATUS	mandatory
        DESCRIPTION
                "Number of unacknowledged KEEPALIVE messages retransmitted 
                before the TCP session is terminated.  If this count is set
                to zero, only one KEEPALIVE message will be sent."
        DEFVAL	{ 5 }
        ::= { wfIpexMappingEntry 20 }

    wfIpexMappingTrace OBJECT-TYPE
        SYNTAX	INTEGER
        ACCESS	read-write
        STATUS	mandatory
        DESCRIPTION
                "This object is a bitmask, setting the low order bit enables
                 tracing of IPEX internal events. Setting other individual bit
                 postions disable logging of internal IPEX events. Values may
                 be added together to disable multiple message groups.
 
                 Hex     Dec
                Value   Value     Message/Event
                ---------------------------------------------------------
                0x0001     1  Enable IPEX tracing.
                0x0002     2  Data packets from IPEX to X.25.
                0x0004     4  Data packets from X.25 to IPEX.
                0x0008     8  Window updates from X.25.
 
                0x0010    16  Data from TCP to IPEX.
                0x0020    32  Window updates from TCP.
                0x0040    64  Window requests from TCP."
        DEFVAL	{ 0 }
        ::= { wfIpexMappingEntry 21 }

    wfIpexMappingMsgHdrType OBJECT-TYPE
        SYNTAX  INTEGER {
		    none(1),
		    short(2),
		    long(3),
                    full(4)
		}
        ACCESS  read-write
        STATUS  mandatory
        DESCRIPTION
                "This attribute enables the Message Boundary Protocol.
                 When enabled, this bit is used to mark the boundary 
                 of TCP application data that is consistent with 
                 Gateway Operation. The first three message header types
                 are used only with wfIpexMappingCtlMode in gateway mode.
                 The default value is used with wfIpexMappingCtlMode in 
                 the local or end2end mode of operation.
                 NONE  = Msg Boundary Protocol is off, no msg header.
                 SHORT = Msg header condtains a 2-Byte length field.
                 LONG  = Msg header contains a 1-Byte type, 1-Byte
                         version, and a 2-Byte length fields.
                 FULL  = Msg Header contains a 2-Byte length1 field,
                         1-Byte Version field, 1-Byte Type field and,
                         a 1-Byte length2 field"
        DEFVAL   { full }
        ::= { wfIpexMappingEntry 22 }

    wfIpexMappingRemoteBackupIp OBJECT-TYPE
        SYNTAX	IpAddress
        ACCESS	read-write
        STATUS	mandatory
        DESCRIPTION
                "The IP address of the remote host with which
                this translation session is established.  This
                attribute is only used in the case of a TCP
                connection with the primary remote IP address
                (wfIpexMappingRemoteIpAddr) failed."
        ::= { wfIpexMappingEntry 23 }

    wfIpexMappingXlateCallingX121 OBJECT-TYPE
        SYNTAX  DisplayString
        ACCESS  read-write
        STATUS  mandatory
        DESCRIPTION
                "If this attribute is configured then insert this X.121
                 addr as the calling addr in the Call request pkt."
        ::= { wfIpexMappingEntry 24 }

    wfIpexMappingTcpMaxRetry OBJECT-TYPE
        SYNTAX  INTEGER(0..16384)
        ACCESS  read-write
        STATUS  mandatory
        DESCRIPTION
                "The maximum number of attempts that PVC-TCP will make to
                 re-establish the connection to the remote peer. The
                 TCP Retry takes place every 15 seconds hence default
                 setting will perform the TCP Retry forever."
        DEFVAL { 0 }
        ::= { wfIpexMappingEntry 25 }

    wfIpexMappingCfgLocalIpAddr OBJECT-TYPE
        SYNTAX	IpAddress
        ACCESS	read-write
        STATUS	mandatory
        DESCRIPTION
                "The IP address on the router to use as the source of the
                 TCP session.  This attribute is only used in the case of
                 a TCP connection initiated from the IPEX to a host"
        ::= { wfIpexMappingEntry 26 }

    wfIpexMappingRemoteBackupTcpPort OBJECT-TYPE
        SYNTAX	INTEGER
        ACCESS	read-write
        STATUS	mandatory
        DESCRIPTION
                "The TCP port of the remote host with which
                this translation session is established.  This
                attribute is only used in the case of a TCP
                connection with the primary remote IP address
                (wfIpexMappingRemoteIpAddr) failed."
        ::= { wfIpexMappingEntry 27 }       


    wfIpexSessionTable OBJECT-TYPE
        SYNTAX	SEQUENCE OF WfIpexSessionEntry
        ACCESS	not-accessible
        STATUS	mandatory
        DESCRIPTION
                "A table that contains the information about the
                current active IPEX translation sessions.  The
                status and statistics information related to each
                translation session is provided here.
                inst_id[] = wfIpexSessionIndex"
        ::= { wfIpexGroup 3 }

    wfIpexSessionEntry OBJECT-TYPE
        SYNTAX	WfIpexSessionEntry
        ACCESS	not-accessible
        STATUS	mandatory
        DESCRIPTION
                "An entry in wfIpexSession."
        INDEX	{ wfIpexSessionSrcConnCct,
    		  wfIpexSessionIndex }
        ::= { wfIpexSessionTable 1 }


    WfIpexSessionEntry ::= SEQUENCE {
    	    wfIpexSessionState
    		INTEGER,
    	    wfIpexSessionSrcConnCct
    		INTEGER,
    	    wfIpexSessionIndex
    		INTEGER,
    	    wfIpexSessionSrcConnType
    		INTEGER,
    	    wfIpexSessionDstConnCct
    		INTEGER,
    	    wfIpexSessionDstConnType
    		INTEGER,
    	    wfIpexSessionLocalDTEAddr
    		DisplayString,
    	    wfIpexSessionRemoteDTEAddr
    		DisplayString,
    	    wfIpexSessionLCN
    		INTEGER,
    	    wfIpexSessionLocalIpAddr
    		IpAddress,
    	    wfIpexSessionLocalTcpPort
    		INTEGER,
    	    wfIpexSessionRemoteIpAddr
    		IpAddress,
    	    wfIpexSessionRemoteTcpPort
    		INTEGER,
    	    wfIpexSessionQueueSize
    		INTEGER
        }

    wfIpexSessionState OBJECT-TYPE
        SYNTAX	INTEGER {
    		    x25up(1),
    		    tcpup(2),
    		    ccestab(3),
    		    notconn(4),
                    lapbup(5)
    		}
        ACCESS	read-only
        STATUS	mandatory
        DESCRIPTION
                "The IPEX state of this translation session. These are the
                steady states of the IPEX state machine.  Transition
                states are not reflected."
        DEFVAL	{ notconn }
        ::= { wfIpexSessionEntry 1 }

    wfIpexSessionSrcConnCct OBJECT-TYPE
        SYNTAX	INTEGER
        ACCESS	read-only
        STATUS	mandatory
        DESCRIPTION
                "The circuit from which the original connection attempt
                is received that initiated a translation session."
        ::= { wfIpexSessionEntry 2 }

    wfIpexSessionIndex OBJECT-TYPE
        SYNTAX	INTEGER
        ACCESS	read-only
        STATUS	mandatory
        DESCRIPTION
                "The index of this translation session"
        ::= { wfIpexSessionEntry 3 }

    wfIpexSessionSrcConnType OBJECT-TYPE
        SYNTAX	INTEGER {
    		    pvc(1),
    		    svc(2),
    		    dcesvc(4),
    		    lapb(8),
    		    tcp(16)
    		}
        ACCESS	read-only
        STATUS	mandatory
        DESCRIPTION
                "Defines type of original connection attempt. Whether
                it is a PVC, SVC, DCE_SVC, LAPB or TCP"
        ::= { wfIpexSessionEntry 4 }

    wfIpexSessionDstConnCct OBJECT-TYPE
        SYNTAX	INTEGER
        ACCESS	read-only
        STATUS	mandatory
        DESCRIPTION
                "The circuit from which the connection at the destination
                to be established to set up a translation session."
        ::= { wfIpexSessionEntry 5 }

    wfIpexSessionDstConnType OBJECT-TYPE
        SYNTAX	INTEGER {
    		    pvc(1),
    		    svc(2),
    		    dcesvc(4),
    		    lapb(8),
    		    tcp(16)
    		}
        ACCESS	read-only
        STATUS	mandatory
        DESCRIPTION
                "Defines type of connection at the destination end. Whether
                it is a PVC, SVC, DCE_SVC, LAPB or TCP"
        DEFVAL	{ pvc }
        ::= { wfIpexSessionEntry 6 }

    wfIpexSessionLocalDTEAddr OBJECT-TYPE
        SYNTAX	DisplayString
        ACCESS	read-only
        STATUS	mandatory
        DESCRIPTION
                "The Local DTE address (identifies the X.121 address
                of the X.25 interface on the IPEX).  This attribute
                is only used in the case of a SVC connection initiated
                from the IPEX to the terminal"
        ::= { wfIpexSessionEntry 7 }

    wfIpexSessionRemoteDTEAddr OBJECT-TYPE
        SYNTAX	DisplayString
        ACCESS	read-only
        STATUS	mandatory
        DESCRIPTION
                "The Remote DTE address (identifies the X.121 address
                of the X.25 interface on the terminal).  This attribute
                is only used in the case of a SVC connection initiated
                from the IPEX to the terminal"
        ::= { wfIpexSessionEntry 8 }

    wfIpexSessionLCN OBJECT-TYPE
        SYNTAX	INTEGER(1..255)
        ACCESS	read-only
        STATUS	mandatory
        DESCRIPTION
                "The LCN of the PVC (identifies the channel to be used
                to establish a PVC connection from the IPEX to the
                terminal"
        DEFVAL	{ 1 }
        ::= { wfIpexSessionEntry 9 }

    wfIpexSessionLocalIpAddr OBJECT-TYPE
        SYNTAX	IpAddress
        ACCESS	read-only
        STATUS	mandatory
        DESCRIPTION
                "The IP address of an interface on the IPEX to be
                used to establish a TCP connection with the host
                server.  This attribute is only used in the case
                of a TCP connection initiated from the IPEX to a
                host"
        ::= { wfIpexSessionEntry 10 }

    wfIpexSessionLocalTcpPort OBJECT-TYPE
        SYNTAX	INTEGER
        ACCESS	read-only
        STATUS	mandatory
        DESCRIPTION
                "The local TCP port number in the IPEX to be used
                to establish a TCP connection to the host server
                This attribute is only used in the case of a TCP
                connection initiated from the IPEX to a host"
        ::= { wfIpexSessionEntry 11 }

    wfIpexSessionRemoteIpAddr OBJECT-TYPE
        SYNTAX	IpAddress
        ACCESS	read-only
        STATUS	mandatory
        DESCRIPTION
                "The IP address of the remote host with which
                this translation session is established.  This
                attribute is only used in the case of a TCP
                connection initiated from the IPEX to a host"
        ::= { wfIpexSessionEntry 12 }

    wfIpexSessionRemoteTcpPort OBJECT-TYPE
        SYNTAX	INTEGER
        ACCESS	read-only
        STATUS	mandatory
        DESCRIPTION
                "The remote TCP port number in the host to be used
                to establish a TCP connection from the IPEX to the
                host server.  This attribute is only used in the
                case of a TCP connection initiated from the IPEX
                to a host"
        ::= { wfIpexSessionEntry 13 }

    wfIpexSessionQueueSize OBJECT-TYPE
        SYNTAX	INTEGER
        ACCESS	read-only
        STATUS	mandatory
        DESCRIPTION
                "The size of the IPEX queues used for transfering data
                 between IPEX and TCP.  The size is in bytes."
        ::= { wfIpexSessionEntry 14 }

    END  -- Wellfleet-IPEX-MIB
