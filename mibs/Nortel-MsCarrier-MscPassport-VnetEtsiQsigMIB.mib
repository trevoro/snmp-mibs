Nortel-MsCarrier-MscPassport-VnetEtsiQsigMIB
DEFINITIONS ::= BEGIN



IMPORTS

      OBJECT-TYPE
   FROM RFC-1212

      mscPassportMIBs
   FROM Nortel-MsCarrier-MscPassport-UsefulDefinitionsMIB

      DisplayString,
      StorageType,
      RowStatus,
      Unsigned32
   FROM Nortel-MsCarrier-MscPassport-StandardTextualConventionsMIB

      NonReplicated,
      Link
   FROM Nortel-MsCarrier-MscPassport-TextualConventionsMIB

      mscSigChan,
      mscSigChanIndex
   FROM Nortel-MsCarrier-MscPassport-VoiceNetworkingMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     VnetEtsiQsig Enterprise MIB."

vnetEtsiQsigMIB OBJECT IDENTIFIER ::= { mscPassportMIBs 110 }










-- SigChan/n EtsiQsig
-- The EtsiQsig component defines the operational characteristics of 
-- the signalling channel's connection to the external equipment.

mscSigChanEQsig OBJECT IDENTIFIER ::= { mscSigChan 2 }



mscSigChanEQsigRowStatusTable OBJECT-TYPE
   SYNTAX     SEQUENCE OF MscSigChanEQsigRowStatusEntry
   ACCESS     not-accessible
   STATUS     mandatory
   DESCRIPTION
     "This entry controls the addition and deletion of 
      mscSigChanEQsig components."
::= { mscSigChanEQsig 1 }

mscSigChanEQsigRowStatusEntry OBJECT-TYPE
   SYNTAX     MscSigChanEQsigRowStatusEntry
   ACCESS     not-accessible
   STATUS     mandatory
   DESCRIPTION
     "A single entry in the table represents a single 
      mscSigChanEQsig component."
   INDEX {
      mscSigChanIndex,
      mscSigChanEQsigIndex }
::= { mscSigChanEQsigRowStatusTable 1 }

MscSigChanEQsigRowStatusEntry ::= SEQUENCE {
   mscSigChanEQsigRowStatus
      RowStatus,
   mscSigChanEQsigComponentName
      DisplayString,
   mscSigChanEQsigStorageType
      StorageType,
   mscSigChanEQsigIndex
      NonReplicated }

mscSigChanEQsigRowStatus OBJECT-TYPE
   SYNTAX     RowStatus 
   ACCESS     read-write
   STATUS     mandatory
   DESCRIPTION
     "This variable is used as the basis for SNMP naming of
      mscSigChanEQsig components.
      These components can be added and deleted."
::= { mscSigChanEQsigRowStatusEntry 1 }

mscSigChanEQsigComponentName OBJECT-TYPE
   SYNTAX     DisplayString 
   ACCESS     read-only
   STATUS     mandatory
   DESCRIPTION
     "This variable provides the component's string name for
      use with the ASCII Console Interface"
::= { mscSigChanEQsigRowStatusEntry 2 }

mscSigChanEQsigStorageType OBJECT-TYPE
   SYNTAX     StorageType 
   ACCESS     read-only
   STATUS     mandatory
   DESCRIPTION
     "This variable represents the storage type value for the
      mscSigChanEQsig tables."
::= { mscSigChanEQsigRowStatusEntry 4 }

mscSigChanEQsigIndex OBJECT-TYPE
   SYNTAX     NonReplicated 
   ACCESS     not-accessible
   STATUS     mandatory
   DESCRIPTION
     "This variable represents the index for the mscSigChanEQsig tables."
::= { mscSigChanEQsigRowStatusEntry 10 }

mscSigChanEQsigL2Table OBJECT-TYPE
   SYNTAX     SEQUENCE OF MscSigChanEQsigL2Entry
   ACCESS     not-accessible
   STATUS     mandatory
   DESCRIPTION
     "This group specifies the provisionable layer 2 attributes of the 
      Q.931 ITU-T protocol."
::= { mscSigChanEQsig 11 }

mscSigChanEQsigL2Entry OBJECT-TYPE
   SYNTAX     MscSigChanEQsigL2Entry
   ACCESS     not-accessible
   STATUS     mandatory
   DESCRIPTION
     "An entry in the mscSigChanEQsigL2Table."
   INDEX {
      mscSigChanIndex,
      mscSigChanEQsigIndex }
::= { mscSigChanEQsigL2Table 1 }

MscSigChanEQsigL2Entry ::= SEQUENCE {
   mscSigChanEQsigT23
      Unsigned32,
   mscSigChanEQsigT200
      Unsigned32,
   mscSigChanEQsigN200
      Unsigned32,
   mscSigChanEQsigT203
      Unsigned32,
   mscSigChanEQsigCircuitSwitchedK
      Unsigned32 }

mscSigChanEQsigT23 OBJECT-TYPE
   SYNTAX     Unsigned32 (1..15)
   ACCESS     read-write
   STATUS     mandatory
   DESCRIPTION
     "This attribute specifies the layer 2 enable request timer."
   DEFVAL     { 10 }
::= { mscSigChanEQsigL2Entry 1 }

mscSigChanEQsigT200 OBJECT-TYPE
   SYNTAX     Unsigned32 (1..20)
   ACCESS     read-write
   STATUS     mandatory
   DESCRIPTION
     "This attribute specifies the maximum time between a layer 2 frame 
      and its acknowledgment."
   DEFVAL     { 1 }
::= { mscSigChanEQsigL2Entry 2 }

mscSigChanEQsigN200 OBJECT-TYPE
   SYNTAX     Unsigned32 (1..8)
   ACCESS     read-write
   STATUS     mandatory
   DESCRIPTION
     "This attribute specifies the maximum number of re-transmissions of 
      a layer 2 frame."
   DEFVAL     { 3 }
::= { mscSigChanEQsigL2Entry 3 }

mscSigChanEQsigT203 OBJECT-TYPE
   SYNTAX     Unsigned32 (2..40)
   ACCESS     read-write
   STATUS     mandatory
   DESCRIPTION
     "This attribute specifies the maximum time for which layer 2 frames 
      may be absent. Expiry triggers a check on whether the far end is 
      alive."
   DEFVAL     { 10 }
::= { mscSigChanEQsigL2Entry 4 }

mscSigChanEQsigCircuitSwitchedK OBJECT-TYPE
   SYNTAX     Unsigned32 (1..127)
   ACCESS     read-write
   STATUS     mandatory
   DESCRIPTION
     "This attribute specifies the maximum number of sequentially 
      numbered I frames (that is, window size (k)) that may be 
      unacknowledged at any given time for a SAP supporting primary 
      rate (64kbit/sec) signalling."
   DEFVAL     { 7 }
::= { mscSigChanEQsigL2Entry 6 }

mscSigChanEQsigL3Table OBJECT-TYPE
   SYNTAX     SEQUENCE OF MscSigChanEQsigL3Entry
   ACCESS     not-accessible
   STATUS     mandatory
   DESCRIPTION
     "This group represents the provisionable Layer 3 timer attributes of 
      the ETSI Qsig protocol."
::= { mscSigChanEQsig 12 }

mscSigChanEQsigL3Entry OBJECT-TYPE
   SYNTAX     MscSigChanEQsigL3Entry
   ACCESS     not-accessible
   STATUS     mandatory
   DESCRIPTION
     "An entry in the mscSigChanEQsigL3Table."
   INDEX {
      mscSigChanIndex,
      mscSigChanEQsigIndex }
::= { mscSigChanEQsigL3Table 1 }

MscSigChanEQsigL3Entry ::= SEQUENCE {
   mscSigChanEQsigT309
      Unsigned32,
   mscSigChanEQsigT310
      Unsigned32 }

mscSigChanEQsigT309 OBJECT-TYPE
   SYNTAX     Unsigned32 (15..120)
   ACCESS     read-write
   STATUS     mandatory
   DESCRIPTION
     "This attribute specifies the data link failure timer; used to ride out 
      temporary failures."
   DEFVAL     { 90 }
::= { mscSigChanEQsigL3Entry 3 }

mscSigChanEQsigT310 OBJECT-TYPE
   SYNTAX     Unsigned32 (10..120)
   ACCESS     read-write
   STATUS     mandatory
   DESCRIPTION
     "This attribute specifies the call proceeding state timer."
   DEFVAL     { 30 }
::= { mscSigChanEQsigL3Entry 4 }

mscSigChanEQsigProvTable OBJECT-TYPE
   SYNTAX     SEQUENCE OF MscSigChanEQsigProvEntry
   ACCESS     not-accessible
   STATUS     mandatory
   DESCRIPTION
     "This group defines the general options of the D-channel signalling 
      link."
::= { mscSigChanEQsig 13 }

mscSigChanEQsigProvEntry OBJECT-TYPE
   SYNTAX     MscSigChanEQsigProvEntry
   ACCESS     not-accessible
   STATUS     mandatory
   DESCRIPTION
     "An entry in the mscSigChanEQsigProvTable."
   INDEX {
      mscSigChanIndex,
      mscSigChanEQsigIndex }
::= { mscSigChanEQsigProvTable 1 }

MscSigChanEQsigProvEntry ::= SEQUENCE {
   mscSigChanEQsigSide
      INTEGER,
   mscSigChanEQsigMaxNonCallConcurrent
      Unsigned32,
   mscSigChanEQsigOverlapSendingEnabled
      INTEGER,
   mscSigChanEQsigOverlapReceivingEnabled
      INTEGER }

mscSigChanEQsigSide OBJECT-TYPE
   SYNTAX     INTEGER  {
                 network(1),
                 user(2) }
   ACCESS     read-write
   STATUS     mandatory
   DESCRIPTION
     "This attribute specifies whether the interface is the network or user 
      side of the connection. The parameter applies to both the layer 2 
      and layer 3 of the interface. If this attribute is set to network, then 
      the interface is master during channel negotiation. If this attribute is 
      set to user, then the interface is slave during channel negotiation."
   DEFVAL     { network }
::= { mscSigChanEQsigProvEntry 1 }

mscSigChanEQsigMaxNonCallConcurrent OBJECT-TYPE
   SYNTAX     Unsigned32 (1..30)
   ACCESS     read-write
   STATUS     mandatory
   DESCRIPTION
     "This attribute specifies the maximum number of simultaneous active 
      non-call messages that are allowed."
   DEFVAL     { 30 }
::= { mscSigChanEQsigProvEntry 2 }

mscSigChanEQsigOverlapSendingEnabled OBJECT-TYPE
   SYNTAX     INTEGER  {
                 enabled(0),
                 disabled(1) }
   ACCESS     read-write
   STATUS     mandatory
   DESCRIPTION
     "This attribute specifies whether overlap sending to the PBX is 
      enabled."
   DEFVAL     { enabled }
::= { mscSigChanEQsigProvEntry 3 }

mscSigChanEQsigOverlapReceivingEnabled OBJECT-TYPE
   SYNTAX     INTEGER  {
                 enabled(0),
                 disabled(1) }
   ACCESS     read-write
   STATUS     mandatory
   DESCRIPTION
     "This attribute specifies whether overlap receiving from the PBX is 
      enabled."
   DEFVAL     { enabled }
::= { mscSigChanEQsigProvEntry 4 }

mscSigChanEQsigStateTable OBJECT-TYPE
   SYNTAX     SEQUENCE OF MscSigChanEQsigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscSigChanEQsig 14 }

mscSigChanEQsigStateEntry OBJECT-TYPE
   SYNTAX     MscSigChanEQsigStateEntry
   ACCESS     not-accessible
   STATUS     mandatory
   DESCRIPTION
     "An entry in the mscSigChanEQsigStateTable."
   INDEX {
      mscSigChanIndex,
      mscSigChanEQsigIndex }
::= { mscSigChanEQsigStateTable 1 }

MscSigChanEQsigStateEntry ::= SEQUENCE {
   mscSigChanEQsigAdminState
      INTEGER,
   mscSigChanEQsigOperationalState
      INTEGER,
   mscSigChanEQsigUsageState
      INTEGER }

mscSigChanEQsigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscSigChanEQsigStateEntry 1 }

mscSigChanEQsigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscSigChanEQsigStateEntry 2 }

mscSigChanEQsigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscSigChanEQsigStateEntry 3 }

mscSigChanEQsigStatsTable OBJECT-TYPE
   SYNTAX     SEQUENCE OF MscSigChanEQsigStatsEntry
   ACCESS     not-accessible
   STATUS     mandatory
   DESCRIPTION
     "This group provides the operational components for the EtsiQsig 
      component."
::= { mscSigChanEQsig 15 }

mscSigChanEQsigStatsEntry OBJECT-TYPE
   SYNTAX     MscSigChanEQsigStatsEntry
   ACCESS     not-accessible
   STATUS     mandatory
   DESCRIPTION
     "An entry in the mscSigChanEQsigStatsTable."
   INDEX {
      mscSigChanIndex,
      mscSigChanEQsigIndex }
::= { mscSigChanEQsigStatsTable 1 }

MscSigChanEQsigStatsEntry ::= SEQUENCE {
   mscSigChanEQsigTotalCallsToIf
      Unsigned32,
   mscSigChanEQsigTotalCallsFromIf
      Unsigned32,
   mscSigChanEQsigNonCallAssocSessionsToIf
      Unsigned32,
   mscSigChanEQsigNonCallAssocSessionsFromIf
      Unsigned32 }

mscSigChanEQsigTotalCallsToIf OBJECT-TYPE
   SYNTAX     Unsigned32 (0..4294967295)
   ACCESS     read-only
   STATUS     mandatory
   DESCRIPTION
     "This attribute counts the total number of calls that have been made 
      to the interface. The value wraps when it reaches its maximum."
   DEFVAL     { 0 }
::= { mscSigChanEQsigStatsEntry 2 }

mscSigChanEQsigTotalCallsFromIf OBJECT-TYPE
   SYNTAX     Unsigned32 (0..4294967295)
   ACCESS     read-only
   STATUS     mandatory
   DESCRIPTION
     "This attribute counts the total number of calls from the interface. 
      The value wraps when it reaches its maximum."
   DEFVAL     { 0 }
::= { mscSigChanEQsigStatsEntry 3 }

mscSigChanEQsigNonCallAssocSessionsToIf OBJECT-TYPE
   SYNTAX     Unsigned32 (0..4294967295)
   ACCESS     read-only
   STATUS     mandatory
   DESCRIPTION
     "This attribute counts the total number of non-call associated 
      sessions to the interface. The value wraps when it reaches its 
      maximum."
   DEFVAL     { 0 }
::= { mscSigChanEQsigStatsEntry 4 }

mscSigChanEQsigNonCallAssocSessionsFromIf OBJECT-TYPE
   SYNTAX     Unsigned32 (0..4294967295)
   ACCESS     read-only
   STATUS     mandatory
   DESCRIPTION
     "This attribute counts the total number of non-call associated 
      sessions from the interface. The value wraps when it reaches its 
      maximum."
   DEFVAL     { 0 }
::= { mscSigChanEQsigStatsEntry 5 }

mscSigChanEQsigOperTable OBJECT-TYPE
   SYNTAX     SEQUENCE OF MscSigChanEQsigOperEntry
   ACCESS     not-accessible
   STATUS     mandatory
   DESCRIPTION
     "This group provides the operational attributes for the EtsiQsig 
      protocol."
::= { mscSigChanEQsig 16 }

mscSigChanEQsigOperEntry OBJECT-TYPE
   SYNTAX     MscSigChanEQsigOperEntry
   ACCESS     not-accessible
   STATUS     mandatory
   DESCRIPTION
     "An entry in the mscSigChanEQsigOperTable."
   INDEX {
      mscSigChanIndex,
      mscSigChanEQsigIndex }
::= { mscSigChanEQsigOperTable 1 }

MscSigChanEQsigOperEntry ::= SEQUENCE {
   mscSigChanEQsigActiveChannels
      Unsigned32,
   mscSigChanEQsigActiveVoiceChannels
      Unsigned32,
   mscSigChanEQsigActiveDataChannels
      Unsigned32,
   mscSigChanEQsigPeakActiveChannels
      Unsigned32,
   mscSigChanEQsigPeakActiveVoiceChannels
      Unsigned32,
   mscSigChanEQsigPeakActiveDataChannels
      Unsigned32,
   mscSigChanEQsigDChanStatus
      INTEGER }

mscSigChanEQsigActiveChannels OBJECT-TYPE
   SYNTAX     Unsigned32 (0..128)
   ACCESS     read-only
   STATUS     mandatory
   DESCRIPTION
     "This attribute indicates the number of currently active channels. 
      This includes data and voice channels."
   DEFVAL     { 0 }
::= { mscSigChanEQsigOperEntry 1 }

mscSigChanEQsigActiveVoiceChannels OBJECT-TYPE
   SYNTAX     Unsigned32 (0..128)
   ACCESS     read-only
   STATUS     mandatory
   DESCRIPTION
     "This attribute indicates the number of channels that are currently 
      carrying voice."
   DEFVAL     { 0 }
::= { mscSigChanEQsigOperEntry 2 }

mscSigChanEQsigActiveDataChannels OBJECT-TYPE
   SYNTAX     Unsigned32 (0..128)
   ACCESS     read-only
   STATUS     mandatory
   DESCRIPTION
     "This attribute indicates the number of channels that are currently 
      carrying data. This does not include modem data."
   DEFVAL     { 0 }
::= { mscSigChanEQsigOperEntry 3 }

mscSigChanEQsigPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { mscSigChanEQsigOperEntry 4 }

mscSigChanEQsigPeakActiveVoiceChannels OBJECT-TYPE
   SYNTAX     Unsigned32 (0..128)
   ACCESS     read-only
   STATUS     mandatory
   DESCRIPTION
     "This attribute indicates the maximum number of voice channels that 
      have been active on this signalling channel during the last polling 
      period."
   DEFVAL     { 0 }
::= { mscSigChanEQsigOperEntry 5 }

mscSigChanEQsigPeakActiveDataChannels OBJECT-TYPE
   SYNTAX     Unsigned32 (0..128)
   ACCESS     read-only
   STATUS     mandatory
   DESCRIPTION
     "This attribute indicates the maximum number of data channels that 
      have been active on this signalling channel during the last polling 
      period."
   DEFVAL     { 0 }
::= { mscSigChanEQsigOperEntry 6 }

mscSigChanEQsigDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being 
      rei-initialized."
::= { mscSigChanEQsigOperEntry 7 }

mscSigChanEQsigToolsTable OBJECT-TYPE
   SYNTAX     SEQUENCE OF MscSigChanEQsigToolsEntry
   ACCESS     not-accessible
   STATUS     mandatory
   DESCRIPTION
     "This contains a series of operational attributes which turn on and off 
      several kinds of tracing."
::= { mscSigChanEQsig 17 }

mscSigChanEQsigToolsEntry OBJECT-TYPE
   SYNTAX     MscSigChanEQsigToolsEntry
   ACCESS     not-accessible
   STATUS     mandatory
   DESCRIPTION
     "An entry in the mscSigChanEQsigToolsTable."
   INDEX {
      mscSigChanIndex,
      mscSigChanEQsigIndex }
::= { mscSigChanEQsigToolsTable 1 }

MscSigChanEQsigToolsEntry ::= SEQUENCE {
   mscSigChanEQsigTracing
      OCTET STRING }

mscSigChanEQsigTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously.  
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { mscSigChanEQsigToolsEntry 1 }

mscSigChanEQsigEQsigSpecificProvTable OBJECT-TYPE
   SYNTAX     SEQUENCE OF MscSigChanEQsigEQsigSpecificProvEntry
   ACCESS     not-accessible
   STATUS     mandatory
   DESCRIPTION
     "This group provides EtsiQsig protocol specific provisioning."
::= { mscSigChanEQsig 18 }

mscSigChanEQsigEQsigSpecificProvEntry OBJECT-TYPE
   SYNTAX     MscSigChanEQsigEQsigSpecificProvEntry
   ACCESS     not-accessible
   STATUS     mandatory
   DESCRIPTION
     "An entry in the mscSigChanEQsigEQsigSpecificProvTable."
   INDEX {
      mscSigChanIndex,
      mscSigChanEQsigIndex }
::= { mscSigChanEQsigEQsigSpecificProvTable 1 }

MscSigChanEQsigEQsigSpecificProvEntry ::= SEQUENCE {
   mscSigChanEQsigMsgSegmentation
      INTEGER,
   mscSigChanEQsigE1ChannelNumbers
      INTEGER }

mscSigChanEQsigMsgSegmentation OBJECT-TYPE
   SYNTAX     INTEGER  {
                 enabled(0),
                 disabled(1) }
   ACCESS     read-write
   STATUS     mandatory
   DESCRIPTION
     "This attribute allows users to enable/disable the EtsiQsig message 
      segmentation service."
   DEFVAL     { disabled }
::= { mscSigChanEQsigEQsigSpecificProvEntry 1 }

mscSigChanEQsigE1ChannelNumbers OBJECT-TYPE
   SYNTAX     INTEGER  {
                 skip16(1),
                 contiguous(2) }
   ACCESS     read-write
   STATUS     mandatory
   DESCRIPTION
     "This attribute is applicable to E1 interfaces only. It specifies the 
      mapping scheme between channel numbers (identified in Layer 3 
      messages) and timeslot numbers on the E1 link.
      When the attribute value is skip16, channel numbers map directly to 
      actual E1 timeslots; therefore only channel numbers 1 - 15 and 17 - 
      31 are expected.
      When the value is contiguous, channel numbers from 1 - 30 are 
      expected, and the following mapping is used: channels 1 - 15 are 
      mapped to timeslots 1 - 15, and channels 16 - 30 are mapped to 
      timeslots 17 - 31.
      On T1 interfaces, channel numbers are always expected in the range 
      1 - 23."
   DEFVAL     { skip16 }
::= { mscSigChanEQsigEQsigSpecificProvEntry 2 }

mscSigChanEQsigEQsigSpecificOpTable OBJECT-TYPE
   SYNTAX     SEQUENCE OF MscSigChanEQsigEQsigSpecificOpEntry
   ACCESS     not-accessible
   STATUS     mandatory
   DESCRIPTION
     "This group provides specific operational attributes for the Etsi Qsig 
      protocol."
::= { mscSigChanEQsig 19 }

mscSigChanEQsigEQsigSpecificOpEntry OBJECT-TYPE
   SYNTAX     MscSigChanEQsigEQsigSpecificOpEntry
   ACCESS     not-accessible
   STATUS     mandatory
   DESCRIPTION
     "An entry in the mscSigChanEQsigEQsigSpecificOpTable."
   INDEX {
      mscSigChanIndex,
      mscSigChanEQsigIndex }
::= { mscSigChanEQsigEQsigSpecificOpTable 1 }

MscSigChanEQsigEQsigSpecificOpEntry ::= SEQUENCE {
   mscSigChanEQsigSegmentationAccepted
      Unsigned32,
   mscSigChanEQsigSegmentationFailed
      Unsigned32 }

mscSigChanEQsigSegmentationAccepted OBJECT-TYPE
   SYNTAX     Unsigned32 (0..4294967295)
   ACCESS     read-only
   STATUS     mandatory
   DESCRIPTION
     "This attribute counts the total number of times a long Etsi Qsig 
      message has been received from a PBX and forwarded to a Passport 
      subnet. The value wraps when it reaches its maximum."
   DEFVAL     { 0 }
::= { mscSigChanEQsigEQsigSpecificOpEntry 1 }

mscSigChanEQsigSegmentationFailed OBJECT-TYPE
   SYNTAX     Unsigned32 (0..4294967295)
   ACCESS     read-only
   STATUS     mandatory
   DESCRIPTION
     "This attribute counts the total number of times a long Etsi Qsig 
      message has been received from a PBX and could not be forwarded 
      as is to a Passport subnet due to end-to-end incompatibility. The 
      value wraps when it reaches its maximum."
   DEFVAL     { 0 }
::= { mscSigChanEQsigEQsigSpecificOpEntry 2 }


-- SigChan/n EQsig Framer
-- 
-- The Framer component controls link layer framing for application 
-- components sending and receiving data on a link interface. It is also 
-- through Framer, that an application component is associated with a 
-- specific hardware link interface.
-- 
-- The Framer component provides provisionable attributes related to 
-- data path aspects of the hardware interface (such as crc and frame 
-- length). The Framer component also provides a provisionable 
-- attribute which binds the application component to a specific 
-- hardware component.
-- 
-- The Framer component contains operational attributes for link 
-- interface data path statistics (such as frame counts and aborts).
-- 

mscSigChanEQsigFramer OBJECT IDENTIFIER ::= { mscSigChanEQsig 2 }



mscSigChanEQsigFramerRowStatusTable OBJECT-TYPE
   SYNTAX     SEQUENCE OF MscSigChanEQsigFramerRowStatusEntry
   ACCESS     not-accessible
   STATUS     mandatory
   DESCRIPTION
     "This entry controls the addition and deletion of 
      mscSigChanEQsigFramer components."
::= { mscSigChanEQsigFramer 1 }

mscSigChanEQsigFramerRowStatusEntry OBJECT-TYPE
   SYNTAX     MscSigChanEQsigFramerRowStatusEntry
   ACCESS     not-accessible
   STATUS     mandatory
   DESCRIPTION
     "A single entry in the table represents a single 
      mscSigChanEQsigFramer component."
   INDEX {
      mscSigChanIndex,
      mscSigChanEQsigIndex,
      mscSigChanEQsigFramerIndex }
::= { mscSigChanEQsigFramerRowStatusTable 1 }

MscSigChanEQsigFramerRowStatusEntry ::= SEQUENCE {
   mscSigChanEQsigFramerRowStatus
      RowStatus,
   mscSigChanEQsigFramerComponentName
      DisplayString,
   mscSigChanEQsigFramerStorageType
      StorageType,
   mscSigChanEQsigFramerIndex
      NonReplicated }

mscSigChanEQsigFramerRowStatus OBJECT-TYPE
   SYNTAX     RowStatus 
   ACCESS     read-only
   STATUS     mandatory
   DESCRIPTION
     "This variable is used as the basis for SNMP naming of
      mscSigChanEQsigFramer components.
      These components cannot be added nor deleted."
::= { mscSigChanEQsigFramerRowStatusEntry 1 }

mscSigChanEQsigFramerComponentName OBJECT-TYPE
   SYNTAX     DisplayString 
   ACCESS     read-only
   STATUS     mandatory
   DESCRIPTION
     "This variable provides the component's string name for
      use with the ASCII Console Interface"
::= { mscSigChanEQsigFramerRowStatusEntry 2 }

mscSigChanEQsigFramerStorageType OBJECT-TYPE
   SYNTAX     StorageType 
   ACCESS     read-only
   STATUS     mandatory
   DESCRIPTION
     "This variable represents the storage type value for the
      mscSigChanEQsigFramer tables."
::= { mscSigChanEQsigFramerRowStatusEntry 4 }

mscSigChanEQsigFramerIndex OBJECT-TYPE
   SYNTAX     NonReplicated 
   ACCESS     not-accessible
   STATUS     mandatory
   DESCRIPTION
     "This variable represents the index for the mscSigChanEQsigFramer tables."
::= { mscSigChanEQsigFramerRowStatusEntry 10 }

mscSigChanEQsigFramerProvTable OBJECT-TYPE
   SYNTAX     SEQUENCE OF MscSigChanEQsigFramerProvEntry
   ACCESS     not-accessible
   STATUS     mandatory
   DESCRIPTION
     "This group contains the base provisioning data for the Framer 
      component. Application or hardware interface specific provisioning 
      data is contained in other provisionable Framer groups."
::= { mscSigChanEQsigFramer 10 }

mscSigChanEQsigFramerProvEntry OBJECT-TYPE
   SYNTAX     MscSigChanEQsigFramerProvEntry
   ACCESS     not-accessible
   STATUS     mandatory
   DESCRIPTION
     "An entry in the mscSigChanEQsigFramerProvTable."
   INDEX {
      mscSigChanIndex,
      mscSigChanEQsigIndex,
      mscSigChanEQsigFramerIndex }
::= { mscSigChanEQsigFramerProvTable 1 }

MscSigChanEQsigFramerProvEntry ::= SEQUENCE {
   mscSigChanEQsigFramerInterfaceName
      Link }

mscSigChanEQsigFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscSigChanEQsigFramerProvEntry 1 }

mscSigChanEQsigFramerStateTable OBJECT-TYPE
   SYNTAX     SEQUENCE OF MscSigChanEQsigFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscSigChanEQsigFramer 12 }

mscSigChanEQsigFramerStateEntry OBJECT-TYPE
   SYNTAX     MscSigChanEQsigFramerStateEntry
   ACCESS     not-accessible
   STATUS     mandatory
   DESCRIPTION
     "An entry in the mscSigChanEQsigFramerStateTable."
   INDEX {
      mscSigChanIndex,
      mscSigChanEQsigIndex,
      mscSigChanEQsigFramerIndex }
::= { mscSigChanEQsigFramerStateTable 1 }

MscSigChanEQsigFramerStateEntry ::= SEQUENCE {
   mscSigChanEQsigFramerAdminState
      INTEGER,
   mscSigChanEQsigFramerOperationalState
      INTEGER,
   mscSigChanEQsigFramerUsageState
      INTEGER }

mscSigChanEQsigFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscSigChanEQsigFramerStateEntry 1 }

mscSigChanEQsigFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscSigChanEQsigFramerStateEntry 2 }

mscSigChanEQsigFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscSigChanEQsigFramerStateEntry 3 }

mscSigChanEQsigFramerStatsTable OBJECT-TYPE
   SYNTAX     SEQUENCE OF MscSigChanEQsigFramerStatsEntry
   ACCESS     not-accessible
   STATUS     mandatory
   DESCRIPTION
     "This group contains the operational statistics data for a Framer 
      component."
::= { mscSigChanEQsigFramer 13 }

mscSigChanEQsigFramerStatsEntry OBJECT-TYPE
   SYNTAX     MscSigChanEQsigFramerStatsEntry
   ACCESS     not-accessible
   STATUS     mandatory
   DESCRIPTION
     "An entry in the mscSigChanEQsigFramerStatsTable."
   INDEX {
      mscSigChanIndex,
      mscSigChanEQsigIndex,
      mscSigChanEQsigFramerIndex }
::= { mscSigChanEQsigFramerStatsTable 1 }

MscSigChanEQsigFramerStatsEntry ::= SEQUENCE {
   mscSigChanEQsigFramerFrmToIf
      Unsigned32,
   mscSigChanEQsigFramerFrmFromIf
      Unsigned32,
   mscSigChanEQsigFramerOctetFromIf
      Unsigned32,
   mscSigChanEQsigFramerAborts
      Unsigned32,
   mscSigChanEQsigFramerCrcErrors
      Unsigned32,
   mscSigChanEQsigFramerLrcErrors
      Unsigned32,
   mscSigChanEQsigFramerNonOctetErrors
      Unsigned32,
   mscSigChanEQsigFramerOverruns
      Unsigned32,
   mscSigChanEQsigFramerUnderruns
      Unsigned32,
   mscSigChanEQsigFramerLargeFrmErrors
      Unsigned32 }

mscSigChanEQsigFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { mscSigChanEQsigFramerStatsEntry 1 }

mscSigChanEQsigFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { mscSigChanEQsigFramerStatsEntry 2 }

mscSigChanEQsigFramerOctetFromIf OBJECT-TYPE
   SYNTAX     Unsigned32 (0..4294967295)
   ACCESS     read-only
   STATUS     mandatory
   DESCRIPTION
     "The number of bytes received from the link interface by Framer."
   DEFVAL     { 0 }
::= { mscSigChanEQsigFramerStatsEntry 3 }

mscSigChanEQsigFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { mscSigChanEQsigFramerStatsEntry 4 }

mscSigChanEQsigFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { mscSigChanEQsigFramerStatsEntry 5 }

mscSigChanEQsigFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { mscSigChanEQsigFramerStatsEntry 6 }

mscSigChanEQsigFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { mscSigChanEQsigFramerStatsEntry 7 }

mscSigChanEQsigFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { mscSigChanEQsigFramerStatsEntry 8 }

mscSigChanEQsigFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { mscSigChanEQsigFramerStatsEntry 9 }

mscSigChanEQsigFramerLargeFrmErrors OBJECT-TYPE
   SYNTAX     Unsigned32 (0..4294967295)
   ACCESS     read-only
   STATUS     mandatory
   DESCRIPTION
     "This attribute counts the total number of frames received which 
      were too large (longer than 500 bytes).
      This count wraps to zero after reaching its maximum value."
   DEFVAL     { 0 }
::= { mscSigChanEQsigFramerStatsEntry 10 }




-- 
-- Version and Compliance statements
-- 



-- Object-Group Statement:
-- A list of all current accessible leaf objects.

-- OBJECTS { mscSigChanEQsigFramerAdminState,
--           mscSigChanEQsigOverlapSendingEnabled,
--           mscSigChanEQsigFramerStorageType,
--           mscSigChanEQsigFramerLrcErrors,
--           mscSigChanEQsigOverlapReceivingEnabled,
--           mscSigChanEQsigFramerOctetFromIf,
--           mscSigChanEQsigAdminState,
--           mscSigChanEQsigActiveChannels,
--           mscSigChanEQsigActiveVoiceChannels,
--           mscSigChanEQsigT310,
--           mscSigChanEQsigRowStatus,
--           mscSigChanEQsigFramerOverruns,
--           mscSigChanEQsigTotalCallsFromIf,
--           mscSigChanEQsigMaxNonCallConcurrent,
--           mscSigChanEQsigFramerOperationalState,
--           mscSigChanEQsigNonCallAssocSessionsFromIf,
--           mscSigChanEQsigPeakActiveVoiceChannels,
--           mscSigChanEQsigFramerNonOctetErrors,
--           mscSigChanEQsigPeakActiveChannels,
--           mscSigChanEQsigCircuitSwitchedK,
--           mscSigChanEQsigSegmentationFailed,
--           mscSigChanEQsigFramerFrmToIf,
--           mscSigChanEQsigActiveDataChannels,
--           mscSigChanEQsigSegmentationAccepted,
--           mscSigChanEQsigFramerUsageState,
--           mscSigChanEQsigFramerComponentName,
--           mscSigChanEQsigUsageState,
--           mscSigChanEQsigFramerAborts,
--           mscSigChanEQsigN200,
--           mscSigChanEQsigSide,
--           mscSigChanEQsigFramerInterfaceName,
--           mscSigChanEQsigComponentName,
--           mscSigChanEQsigT23,
--           mscSigChanEQsigTotalCallsToIf,
--           mscSigChanEQsigPeakActiveDataChannels,
--           mscSigChanEQsigFramerUnderruns,
--           mscSigChanEQsigFramerCrcErrors,
--           mscSigChanEQsigNonCallAssocSessionsToIf,
--           mscSigChanEQsigFramerRowStatus,
--           mscSigChanEQsigTracing,
--           mscSigChanEQsigT200,
--           mscSigChanEQsigE1ChannelNumbers,
--           mscSigChanEQsigT309,
--           mscSigChanEQsigMsgSegmentation,
--           mscSigChanEQsigOperationalState,
--           mscSigChanEQsigStorageType,
--           mscSigChanEQsigT203,
--           mscSigChanEQsigFramerFrmFromIf,
--           mscSigChanEQsigFramerLargeFrmErrors,
--           mscSigChanEQsigDChanStatus }
-- STATUS  mandatory
-- DESCRIPTION
--   "A list of all current accessible leaf objects."

vnetEtsiQsigGroup OBJECT IDENTIFIER ::= { vnetEtsiQsigMIB 1 }
vnetEtsiQsigGroupCA OBJECT IDENTIFIER ::= { vnetEtsiQsigGroup 1 }
vnetEtsiQsigGroupCA02 OBJECT IDENTIFIER ::= { vnetEtsiQsigGroupCA 3 }
vnetEtsiQsigGroupCA02A OBJECT IDENTIFIER ::= { vnetEtsiQsigGroupCA02 2 }



-- Agent-Capabilities Statement:

-- PRODUCT-RELEASE "MscPassport Release 1.2 VnetEtsiQsig."
-- STATUS          mandatory
-- DESCRIPTION     "Carrier Passport VnetEtsiQsig MIB: MIB Version CA02A,
--                  Software Version CA02S9C."
-- SUPPORTS        Nortel-MsCarrier-MscPassport-VnetEtsiQsigMIB
--    INCLUDES     { vnetEtsiQsigGroupCA02A }

vnetEtsiQsigCapabilities OBJECT IDENTIFIER ::= { vnetEtsiQsigMIB 3 }
vnetEtsiQsigCapabilitiesCA OBJECT IDENTIFIER ::= { vnetEtsiQsigCapabilities 1 }
vnetEtsiQsigCapabilitiesCA02 OBJECT IDENTIFIER ::= { vnetEtsiQsigCapabilitiesCA 3 }
vnetEtsiQsigCapabilitiesCA02A OBJECT IDENTIFIER ::= { vnetEtsiQsigCapabilitiesCA02 2 }





END
