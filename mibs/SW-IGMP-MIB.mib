-- Revision 1.0.0
-- Copyright 1999 D-Link, Inc.
-- All rights reserved.

SW-IGMP-MIB     DEFINITIONS ::= BEGIN
    IMPORTS
        IpAddress       FROM RFC1155-SMI
        OBJECT-TYPE     FROM RFC-1212
        enterprises     FROM RFC1155-SMI;       

    MacAddress  ::= OCTET STRING(SIZE(6))
    PortList    ::= OCTET STRING(SIZE(4))
        
    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }

    marconi-mgmt    OBJECT IDENTIFIER ::= { golfcommon 2 }    

    es2000Mgmt      OBJECT IDENTIFIER ::= { marconi-mgmt 28 }

    swL2Mgmt        OBJECT IDENTIFIER ::= { es2000Mgmt 2 }

    swIGMP          OBJECT IDENTIFIER ::= { swL2Mgmt 7 }

-- *****************************************************************************
--  swIGMPCtrl
-- *****************************************************************************
    swIGMPCtrl      OBJECT IDENTIFIER ::= { swIGMP 1 }

    swIGMPAdminState OBJECT-TYPE
        SYNTAX  INTEGER {
            other(1),
            disabled(2),
            enabled(3)
        }
        ACCESS  read-write
        STATUS  mandatory
        DESCRIPTION
            "This object allows the user to enable/disable the IGMP snooping function.
             The IGMP function provided by the device includes both v1 and v2."
        ::= { swIGMPCtrl 1 }

    swIGMPTimeout OBJECT-TYPE
        SYNTAX  INTEGER
        ACCESS  read-write
        STATUS  mandatory
        DESCRIPTION
            "The timeout value for sending IGMP query packet when no one was
             sent by the multicast router in the lan. The device will actively
             send the query message."
        DEFVAL  { 300 }
        ::= { swIGMPCtrl 2 }

-- *****************************************************************************
--  swIGMPInfoTable
-- *****************************************************************************
    swIGMPInfoTable OBJECT-TYPE
        SYNTAX  SEQUENCE OF SwIGMPInfoEntry
        ACCESS  not-accessible
        STATUS  mandatory
        DESCRIPTION
            "The table contains the number current IGMP query packets which
             is captured by this device, as well as the IGMP query packets
             sent by the device."
        ::= { swIGMP 2 }

    swIGMPInfoEntry OBJECT-TYPE
        SYNTAX  SwIGMPInfoEntry
        ACCESS  not-accessible
        STATUS  mandatory
        DESCRIPTION
            "Information about current IGMP query information, provided that
             swDevIGMPCaptureState and swIGMPCtrlState of associated VLAN
             entry are all enabled."
        INDEX   { swIGMPInfoIndex }
        ::= { swIGMPInfoTable 1 }

    SwIGMPInfoEntry ::=
        SEQUENCE {
            swIGMPInfoIndex
                INTEGER,
            swIGMPInfoVid
                INTEGER,
            swIGMPInfoQueryCount
                INTEGER,
            swIGMPInfoTxQueryCount
                INTEGER
        }

    swIGMPInfoIndex OBJECT-TYPE
        SYNTAX  INTEGER (1..12)
        ACCESS  read-only
        STATUS  mandatory
        DESCRIPTION
            "This object indicates the IGMP query information entry number. It
             could be up to 12 entries, depending on current number of VLAN entries."
        ::= { swIGMPInfoEntry 1 }

    swIGMPInfoVid OBJECT-TYPE
        SYNTAX  INTEGER
        ACCESS  read-only
        STATUS  mandatory
        DESCRIPTION
            "This object indicates the Vid of associated IGMP info table entry.
             It follows swIGMPCtrlVid in the associated entry of IGMP control
             table (swIGMPCtrlTable)."
        ::= { swIGMPInfoEntry 2 }

    swIGMPInfoQueryCount OBJECT-TYPE
        SYNTAX  INTEGER
        ACCESS  read-only
        STATUS  mandatory
        DESCRIPTION
            "This object indicates the number of query packets received since the
             IGMP function enabled, in per-VLAN basis."
        ::= { swIGMPInfoEntry 3 }

    swIGMPInfoTxQueryCount OBJECT-TYPE
        SYNTAX  INTEGER
        ACCESS  read-only
        STATUS  mandatory
        DESCRIPTION
            "This object indicates the send count of IGMP query messages, in
             per-VLAN basis. In case of IGMP timer expiration, the switch sends
             IGMP query packets to related VLAN member ports and increment this
             object by 1."
        ::= { swIGMPInfoEntry 4 }

-- *****************************************************************************
--  swIGMPTable
-- *****************************************************************************
    swIGMPTable OBJECT-TYPE
        SYNTAX  SEQUENCE OF SwIGMPEntry
        ACCESS  not-accessible
        STATUS  mandatory
        DESCRIPTION
            "This table contains information regarding to the IGMP group membership
             report received by each port. The system will use the information
             recorded in this table to forward the multicast packet to those ports
             which have group membership. Since packets will not be forwarded to
             necessary ports, the network bandwith can thus be saved."
        ::= { swIGMP 3 }

    swIGMPEntry OBJECT-TYPE
        SYNTAX  SwIGMPEntry
        ACCESS  not-accessible
        STATUS  mandatory
        DESCRIPTION
            "Each entry describes the ports which are member of a specific group address.
             Note that when a specific multicast address existing in the table also exist in
             the filter table, the filter table has higher priority over this table."
        INDEX   { swIGMPVid, swIGMPGroupIpAddr }
        ::= { swIGMPTable 1 }

    SwIGMPEntry ::=
        SEQUENCE {
            swIGMPVid
                INTEGER,
            swIGMPGroupIpAddr
                IpAddress,
            swIGMPGroupMacAddr
                MacAddress,
            swIGMPPortMap
                PortList,
            swIGMPIpGroupReportCount
                INTEGER
        }

    swIGMPVid OBJECT-TYPE
        SYNTAX  INTEGER
        ACCESS  read-only
        STATUS  mandatory
        DESCRIPTION
            "This object indicates the Vid of individual IGMP table entry.
             It shows the Vid of IGMP report information captured on network."
        ::= { swIGMPEntry 1 }

    swIGMPGroupIpAddr OBJECT-TYPE
        SYNTAX  IpAddress
        ACCESS  read-only
        STATUS  mandatory
        DESCRIPTION
            "A IP multicast group address which has port membership in the underlying network."
        ::= { swIGMPEntry 2 }

    swIGMPGroupMacAddr OBJECT-TYPE
        SYNTAX  MacAddress
        ACCESS  read-only
        STATUS  mandatory
        DESCRIPTION
            "The multicast MAC address corresponds to swIGMPGroupIpAddr."
        ::= { swIGMPEntry 3 }

    swIGMPPortMap OBJECT-TYPE
        SYNTAX  PortList
        ACCESS  read-only
        STATUS  mandatory
        DESCRIPTION
            "Indicates the set of ports which are members of this multicast group.
             These ports are represented by a octet string.The most significant
             bit represents the lowest numbered port, and the least significant
             bit represents the highest numbered port."
        ::= { swIGMPEntry 4 }

    swIGMPIpGroupReportCount OBJECT-TYPE
        SYNTAX  INTEGER
        ACCESS  read-only
        STATUS  mandatory
        DESCRIPTION
            "Indicates the number of group membership report packets received
             by the device corresponding to this multicast group."
        ::= { swIGMPEntry 5 }

-- +updated by Jemy 2000/2/10 02:37PM B14
-- *****************************************************************************
--  swIGMPCtrlTable
-- *****************************************************************************
    swIGMPCtrlTable OBJECT-TYPE
        SYNTAX  SEQUENCE OF SwIGMPCtrlEntry
        ACCESS  not-accessible
        STATUS  mandatory
        DESCRIPTION
            "The table controls the Vlan's IGMP function. Its scale depends on
             current VLAN state (swVlanInfoStatus). If VLAN is disabled or
             in Mac-Base mode, there is only one entry in the table, with
             index 1. If VLAN is in Port-Base or 802.1q mode, the number of
             entries can be up to 12, with index range from 1 to 12."
        ::= { swIGMP 4 }

    swIGMPCtrlEntry OBJECT-TYPE
        SYNTAX  SwIGMPCtrlEntry
        ACCESS  not-accessible
        STATUS  mandatory
        DESCRIPTION
            "The entry in IGMP control table (swIGMPCtrlTable).
             The entry is effective only when IGMP capture switch is enabled."
        INDEX   { swIGMPCtrlIndex }
        ::= { swIGMPCtrlTable 1 }

    SwIGMPCtrlEntry ::=
        SEQUENCE {
            swIGMPCtrlIndex
                INTEGER,
            swIGMPCtrlVid
                INTEGER (1..4094),
            swIGMPCtrlTimer
                INTEGER,
            swIGMPCtrlState
                INTEGER
        }

    swIGMPCtrlIndex OBJECT-TYPE
        SYNTAX  INTEGER (1..12)
        ACCESS  read-only
        STATUS  mandatory
        DESCRIPTION
            "This object indicates the IGMP control entry number.Its scale depends on
             current VLAN state (es400VlanInfoStatus). If VLAN is disabled or in
             Mac-Base mode, there is only one entry in the table, with index 1.
             If VLAN is in Port-Base or 802.1q mode, the number of entries is 12, 
             with index range from 1 to 12."
        ::= { swIGMPCtrlEntry 1 }

    swIGMPCtrlVid OBJECT-TYPE
        SYNTAX  INTEGER (1..4094)
        ACCESS  read-write
        STATUS  mandatory
        DESCRIPTION
            "This object indicates the IGMP control entry's VLAN id. If VLAN is
             disabled or in Mac-Base mode, the Vid is always 0 and cannot be changed
             by management users. If VLAN is in Port-Base mode, the Vid is arranged
             from 1 to 12 , fixed form. If VLAN is in 802.1q mode, the Vid setting 
             can vary from 1 to 4094 by management user, and the Vid in each entry
             must be unique in the IGMP Control Table."
        ::= { swIGMPCtrlEntry 2 }

    swIGMPCtrlTimer OBJECT-TYPE
        SYNTAX  INTEGER  (30..9999)
        ACCESS  read-write
        STATUS  mandatory
        DESCRIPTION
            "The timer value for sending IGMP query packet when none 
             was sent by the multicast router in the LAN. The timer works
             in per-VLAN basis. Our device will be activated to send the query
             message if the timer is expired. Please reference RFC2236-1997.
             And it recommends a default of 125 seconds. The timeout value must 
             be at least 30 seconds."
        DEFVAL  { 300 }
        ::= { swIGMPCtrlEntry 3 }

    swIGMPCtrlState OBJECT-TYPE
        SYNTAX  INTEGER {
            other(1),
            disabled(2),
            enabled(3),
            deleted(4)
        }
        ACCESS  read-write
        STATUS  mandatory
        DESCRIPTION
            "This object indicates the status of this entry.
             other(1) - This entry is currently in use but the conditions under
                        which it will remain so are different from each of the
                        following values.
             disable(2) - IGMP funtion is disabled for this entry.
             enable(3) - IGMP funtion is enabled for this entry.
             deleted(4) - IGMP entry is deleted."
        ::= { swIGMPCtrlEntry 4 }
-- -

END
