FTPEXT-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, IpAddress
			FROM SNMPv2-SMI
		RowStatus, DisplayString
			FROM SNMPv2-TC
		ftpExt
			FROM APENT-MIB;


    ftpExtMib MODULE-IDENTITY
	   LAST-UPDATED "9801282000Z" -- Wed January 28 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for FTP transfer administration records"
      ::= { ftpExt 1}


apFtpTable OBJECT-TYPE
	SYNTAX      SEQUENCE OF ApFtpEntry
	MAX-ACCESS  not-accessible
	STATUS      current
	DESCRIPTION
		"A table of FTP administrative records"
	::= {ftpExt 2}

apFtpEntry OBJECT-TYPE
	SYNTAX      ApFtpEntry
	MAX-ACCESS  not-accessible
	STATUS      current
	DESCRIPTION
	       "ArrowPoint FTP record"
	INDEX  { apFtpRecordName}
	::= {apFtpTable 1}

ApFtpEntry ::=
	SEQUENCE 
	{
	apFtpRecordName				DisplayString,
	apFtpIpAddress				IpAddress,
	apFtpUserName				DisplayString,
	apFtpPassword				DisplayString,
	apFtpEncryptedPassword		DisplayString,
	apFtpBaseDirectory			DisplayString,
	apFtpStatus					RowStatus
	}

apFtpRecordName OBJECT-TYPE
	SYNTAX      DisplayString(SIZE (0..16))
	MAX-ACCESS  read-create
	STATUS      current
	DESCRIPTION
	       "A name which uniquely identifies this record"
	::= {apFtpEntry 1}

apFtpIpAddress OBJECT-TYPE
	SYNTAX      IpAddress
	MAX-ACCESS  read-create
	STATUS      current
	DESCRIPTION
	       "This IP Address of the FTP server"
	::= {apFtpEntry 2}

apFtpUserName OBJECT-TYPE
	SYNTAX      DisplayString(SIZE (0..16))
	MAX-ACCESS  read-create
	STATUS      current
	DESCRIPTION
	       "A username used for login puposes with this FTP record"
	::= {apFtpEntry 3}

apFtpPassword OBJECT-TYPE
	SYNTAX      DisplayString(SIZE (0..16))
	MAX-ACCESS  read-create
	STATUS      current
	DESCRIPTION
	       "A password used for login purposes with this FTP record"
	::= {apFtpEntry 4}

apFtpEncryptedPassword OBJECT-TYPE
	SYNTAX      DisplayString(SIZE (0..64))
	MAX-ACCESS  read-create
	STATUS      current
	DESCRIPTION
	       "An encrypted password used for login purposes with this FTP 
			record"
	::= {apFtpEntry 5}

apFtpBaseDirectory OBJECT-TYPE
	SYNTAX      DisplayString(SIZE (0..64))
	MAX-ACCESS  read-create
	STATUS      current
	DESCRIPTION
	       "A base directory which is used for all access to this FTP daemon"
	::= {apFtpEntry 6}

apFtpStatus OBJECT-TYPE
	SYNTAX      RowStatus
	MAX-ACCESS  read-create
	STATUS      current
	DESCRIPTION
	       "This status object for this row"
	::= {apFtpEntry 7}

END
