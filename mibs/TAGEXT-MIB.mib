TAGEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString, RowStatus
			FROM SNMPv2-TC
		tagExt
			FROM APENT-MIB;

--TAGEXT MIB

    apTagExtMib MODULE-IDENTITY
	   LAST-UPDATED "9012092000Z" -- Thu October 9 20:00:00 EST 1997
	   ORGANIZATION "ArrowPoint Communications Inc."
	   CONTACT-INFO
	   "                      
	   Postal:                ArrowPoint Communications Inc.
				              50 Nagog Park
				              Acton, Massachusetts 01886
	   Tel:                   +1 978 206 3077
	   E-Mail:                mibsupport@arrowpoint.com"
       DESCRIPTION
	  "The MIB module used to describe the ArrowPoint Communications
	   Content Tag Lists"
      ::= { tagExt 1}


apTagListTable OBJECT-TYPE
	SYNTAX          SEQUENCE OF APTagListEntry
	MAX-ACCESS      not-accessible
	STATUS          current
	DESCRIPTION
		"A list of content tag lists"
	::= { tagExt 2 }

apTagListEntry OBJECT-TYPE
	SYNTAX          APTagListEntry
	MAX-ACCESS      not-accessible
	STATUS          current
	DESCRIPTION
		"A group of information uniquely identifying a tag list"
	INDEX   { apTagListName }
	::= { apTagListTable 1 }

APTagListEntry ::= SEQUENCE {
		apTagListName                    DisplayString,
		apTagListDescription             DisplayString,
		apTagListStatus                  RowStatus
        }


apTagListName OBJECT-TYPE
	SYNTAX          DisplayString (SIZE(1..31))
	MAX-ACCESS      read-create
	STATUS          current
	DESCRIPTION     
			"The name of the Tag List"
	::= {apTagListEntry 1}

apTagListDescription OBJECT-TYPE
	SYNTAX          DisplayString (SIZE(0..64))
	MAX-ACCESS      read-create
	STATUS          current
	DESCRIPTION     
			"An Tag List description"
	::= {apTagListEntry 2}

apTagListStatus OBJECT-TYPE
	SYNTAX          RowStatus
	MAX-ACCESS      read-create
	STATUS          current
	DESCRIPTION      
		"Status entry for this row "
	::= {apTagListEntry 3}



apTagInfoTable OBJECT-TYPE
	SYNTAX          SEQUENCE OF APTagInfoEntry
	MAX-ACCESS      not-accessible
	STATUS          current
	DESCRIPTION
		"A list of tag info blocks associated with a tag list"
	::= { tagExt 3 }

apTagInfoEntry OBJECT-TYPE
	SYNTAX          APTagInfoEntry
	MAX-ACCESS      not-accessible
	STATUS          current
	DESCRIPTION
		"Information uniquely identifying a tag within a tag list"
	INDEX   { apTagListName,apTagName }
	::= { apTagInfoTable 1 }

APTagInfoEntry ::= SEQUENCE {
		apTagIndex                      Integer32,
		apTagType                       INTEGER,
		apTagName                       DisplayString,
		apTagDescription                DisplayString,
		apTagOperator                   INTEGER,
		apTagKeyword                    DisplayString,
		apTagKeywordLen                 Integer32,
		apTagKqlName                    DisplayString,
		apTagSearchLen                  Integer32,
		apTagStatus                     RowStatus
        }


apTagIndex OBJECT-TYPE
	SYNTAX          Integer32
	MAX-ACCESS      read-create
	STATUS          current
	DESCRIPTION     
			"The tag's index"
	::= {apTagInfoEntry 1}

apTagType OBJECT-TYPE
        SYNTAX          INTEGER {
                                request-line(0)                           ,
                                user-agent(1)                                        ,
                                language(2)                                             ,
                                host(3)                                  ,
                                pragma(4)                                    ,
                                cache-control(5)                                           ,
                                cookies(6)                            ,
                                connection(7)                                        ,
                                charset(8)                                            ,
                                encoding(9)                                             ,
                                accept(10)                                    ,
                                referer(11)                                     
                                }
        MAX-ACCESS      read-create
        STATUS          current
        DESCRIPTION
                        "The type of the content tag to be processed"
        ::= {apTagInfoEntry 2}

apTagName OBJECT-TYPE
	SYNTAX          DisplayString (SIZE(1..31))
	MAX-ACCESS      read-create
	STATUS          current
	DESCRIPTION     
			"A unique name to identify the tag info entry."
	::= {apTagInfoEntry 3}

apTagDescription OBJECT-TYPE
	SYNTAX          DisplayString (SIZE(1..64))
	MAX-ACCESS      read-create
	STATUS          current
	DESCRIPTION     
			"A description of this tag entry"
	::= {apTagInfoEntry 4}

apTagOperator OBJECT-TYPE
	SYNTAX          INTEGER {
                                contain(1),
                                not-contain(2),
                                equal(3),
                                not-equal(4),
                                exist(5),
                                not-exist(6)
                                }
	MAX-ACCESS      read-create
	STATUS          current
	DESCRIPTION     
			"The operation used by the tag"
	::= {apTagInfoEntry 5}

apTagKeyword OBJECT-TYPE
	SYNTAX          DisplayString (SIZE(1..31))
	MAX-ACCESS      read-create
	STATUS          current
	DESCRIPTION     
			"The keyword used for the tag operation"
	::= {apTagInfoEntry 6}

apTagKeywordLen OBJECT-TYPE
	SYNTAX          Integer32 (0..32)
	MAX-ACCESS      read-create
	STATUS          current
	DESCRIPTION     
			"The length of the keyword being used" 
	::= {apTagInfoEntry 7}

apTagKqlName OBJECT-TYPE
	SYNTAX          DisplayString (SIZE(1..31))
	MAX-ACCESS      read-create
	STATUS          current
	DESCRIPTION     
			"The name of the associated keyword list"
	::= {apTagInfoEntry 8}

apTagSearchLen OBJECT-TYPE
	SYNTAX          Integer32 (0..1024)
	MAX-ACCESS      read-create
	STATUS          current
	DESCRIPTION     
			"The optional length used to search the tag" 
	::= {apTagInfoEntry 9}

apTagStatus OBJECT-TYPE
	SYNTAX          RowStatus
	MAX-ACCESS      read-create
	STATUS          current
	DESCRIPTION      
		"Status entry for this row "
	::= {apTagInfoEntry 10}



apKqlTable OBJECT-TYPE
        SYNTAX          SEQUENCE OF APKqlEntry
        MAX-ACCESS      not-accessible
        STATUS          current
        DESCRIPTION
                "A list of keyword qualifier lists"
        ::= { tagExt 4 }

apKqlEntry OBJECT-TYPE
        SYNTAX          APKqlEntry
        MAX-ACCESS      not-accessible
        STATUS          current
        DESCRIPTION
                "A group of information uniquely identifying an KQL.  One entry
         exists for each KQL"
        INDEX   { apKqlName }
        ::= { apKqlTable 1 }

APKqlEntry ::= SEQUENCE {
                apKqlName                    DisplayString,
                apKqlDescription             DisplayString,
                apKqlStatus                  RowStatus
               }

apKqlName OBJECT-TYPE
        SYNTAX          DisplayString (SIZE(1..31))
        MAX-ACCESS      read-create
        STATUS          current
        DESCRIPTION
                        "The name of the KQL"
        ::= {apKqlEntry 1}

apKqlDescription OBJECT-TYPE
        SYNTAX          DisplayString (SIZE(0..64))
        MAX-ACCESS      read-create
        STATUS          current
        DESCRIPTION
                        "An KQL description"
        ::= {apKqlEntry 2}

apKqlStatus OBJECT-TYPE
        SYNTAX          RowStatus
        MAX-ACCESS      read-create
        STATUS          current
        DESCRIPTION
                "Status entry for this row "
        ::= {apKqlEntry 3}



apKeywordTable OBJECT-TYPE
        SYNTAX          SEQUENCE OF APKeywordEntry
        MAX-ACCESS      not-accessible
        STATUS          current
        DESCRIPTION
                "A list of keywords associated with an KQL"
        ::= { tagExt 5 }

apKeywordEntry OBJECT-TYPE
        SYNTAX          APKeywordEntry
        MAX-ACCESS      not-accessible
        STATUS          current
        DESCRIPTION
                "Information uniquely identifying an extension within a KQL"
        INDEX   { apKqlName,apKeywordStr }
        ::= { apKeywordTable 1 }

APKeywordEntry ::= SEQUENCE {
                apKeywordStr                     DisplayString,
                apKeywordStatus                  RowStatus
               }

apKeywordStr OBJECT-TYPE
        SYNTAX          DisplayString (SIZE(1..31))
        MAX-ACCESS      read-create
        STATUS          current
        DESCRIPTION
                        "The keyword character string"
        ::= {apKeywordEntry 1}

apKeywordStatus OBJECT-TYPE
        SYNTAX          RowStatus
        MAX-ACCESS      read-create
        STATUS          current
        DESCRIPTION
                "Status entry for this row "
        ::= {apKeywordEntry 2}

END
