-- 
--  Copyright 1996, Com21 Inc.  All Rights Reserved.
--
 
COM21-HCXSTUPRXY-MIB DEFINITIONS ::= BEGIN
  IMPORTS
        MODULE-IDENTITY, OBJECT-TYPE, NOTIFICATION-TYPE, Integer32,
        IpAddress, Gauge32, TimeTicks
            FROM SNMPv2-SMI
        DisplayString, MacAddress
            FROM SNMPv2-TC
        com21, com21Hcx
            FROM COM21-HCX-MIB
        com21Stu, com21Traps FROM COM21-HCX-MIB
		  hcxAlmSeverity, hcxEventLogTime
            FROM COM21-HCXALM-MIB;


        com21StuPrxy MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"

                DESCRIPTION
                        "This is the Com21 ComController ComPort Proxy MIB.
                         COM21 Part# 005-0025-00"
                ::= { com21Stu 1 }

        com21StuControlGroup            OBJECT IDENTIFIER ::= {com21Stu 2}
        com21StuPhysicalGroup           OBJECT IDENTIFIER ::= {com21Stu 3}
	com21StuAlarmGroup		OBJECT IDENTIFIER ::= {com21Stu 4}
        com21StuEtherConfigGroup        OBJECT IDENTIFIER ::= {com21Stu 5}
        com21StuEtherTypeGroup		OBJECT IDENTIFIER ::= {com21Stu 6}
        com21StuFiltIpMultiGroup	OBJECT IDENTIFIER ::= {com21Stu 7}
        com21StuEtherMacGroup		OBJECT IDENTIFIER ::= {com21Stu 8}
        com21StuEtherStatsGroup         OBJECT IDENTIFIER ::= {com21Stu 9}
        com21StuStatsGroup              OBJECT IDENTIFIER ::= {com21Stu 10}
        com21StuQStatsGroup             OBJECT IDENTIFIER ::= {com21Stu 11}
	com21StuAlarmSevGroup		OBJECT IDENTIFIER ::= {com21Stu 12}
	com21StuCodeImageGroup		OBJECT IDENTIFIER ::= {com21Stu 13}
	com21StuVoiceChanStatsGroup	OBJECT IDENTIFIER ::= {com21Stu 14}


        FrequencyKhz     ::= INTEGER (0..800000)
	UpstrmFreqKhz	 ::= INTEGER (5000..40000)
        EpochTime        ::= INTEGER (0..2147483647)
        Offset           ::= INTEGER (0..16383)
	AlarmSeverity    ::= INTEGER { clear(1), warning(2), minor(3),
                                       major(4), critical(5) }
	Com21RowStatus	 ::= INTEGER { active(1), create(2), destroy(3),
				       deactive(4) }



        -- -- -- -- -- -- -- -- -- -- -- -- -- -- -- -- -- -- -- -- -- -- -- --
        -- -- -- -- -- -- -- -- -- -- -- -- -- -- -- -- -- -- -- -- -- -- -- --
        --
        -- COM21 ComController Enterprise MIB
        --
        -- This MIB contains SNMP Groups and Attributes definitions for COM21
        -- specific management.
        -- Also supported by the ComController shall be the MIB II for the 
	-- SNMP interface and the MIB II Interfaces Group for both the 
	-- ComController and ComPort Ethernet interfaces.
        -- This Enterprise MIB contains many elements of the ATM UNI 2.1 ILMI
        -- MIB. This full MIB is not presently supported by the COM21 equipment
        -- as there are no external UNI interfaces. When this changes then the
        -- full MIB should be supported and the related Enterprise MIB entries
        -- removed.
        --
        --   com21StuControlGroup       - this group controls the overall 
        --                                ComPort configuration and 
	--				  functionality. This data is held 
	--				  on the ComPort and the
        --                                ComController shall act as proxy.
        --
        --   com21StuPhysicalGroup      - this group provides for the control
        --                                of the physical and MAC layer 
        --                                ComPort interfaces. This data is held
	--				  on the ComPort and the ComController 
	--				  shall act as proxy.
        --
	--   com21StuAlarmGroup		- this group holds all active alarms
	--				  for an ComPort. This data is held on 
	--				  the ComPort and the ComController 
	--				  shall act as proxy.
	--
        --   com21StuEtherConfigGroup   - this group provides for the monitor
        --                                and control of the Ethernet interface
        --                                located on the ComPort. This data is 
	--				  held on the ComPort and the 
	--				  ComController shall act as proxy.
        --
	--   com21StuEtherTypeGroup     - this group holds details of the
	--				  Ethernet Types supported by each 
	--				  ComPort. This data is held on the 
	--				  ComPort and the ComController shall 
	--				  act as proxy.
	--
	--   com21StuFiltIpMultiGroup	- this group contains configuration
	--				  of the IP Multicast Address filtering.
        --                                This data is held on the ComPort 
	--				  and the ComController shall act as 
	--				  proxy.
	--
        --   com21StuEtherStatsGroup    - this group provides for collection
        --                                of the ComPort Ethernet related stats.
        --                                This data is held on the ComPort and 
	--				  the ComController shall act as proxy.
        --
	--   com21StuEtherMacGroup	- this group supports configuration
	--				  of Ethernet MAC address support.
        --                                This data is held on the ComPort and 
	--				  the ComController shall act as proxy.
	--
        --   com21StuStatsGroup         - this group provides for collection
        --                                of the ComPort to ComController link 
	--				  level stats. This data is held on the
	--				  ComPort and the ComController shall
        --                                act as proxy.
        --
        --   com21StuQStatsGroup        - this group provides for collection
        --                                of the ComPort VC statistical data.
        --                                This data is held on the ComPort and 
	--				  the ComController shall act as proxy.
        --
        -- -- -- -- -- -- -- -- -- -- -- -- -- -- -- -- -- -- -- -- -- -- -- --
        -- -- -- -- -- -- -- -- -- -- -- -- -- -- -- -- -- -- -- -- -- -- -- --



        -- -- -- -- -- -- -- -- -- -- -- -- -- -- -- -- -- -- -- -- -- -- -- --
        -- -- -- -- -- -- -- -- -- -- -- -- -- -- -- -- -- -- -- -- -- -- -- --
        --
        -- com21StuControlGroup
        --
        -- defines the attributes related to the management of overall ComPort
        -- functionality. This data is held upon an ComPort and accessed by the
	-- ComController on a proxy basis.
        --
        -- -- -- -- -- -- -- -- -- -- -- -- -- -- -- -- -- -- -- -- -- -- -- --
        -- -- -- -- -- -- -- -- -- -- -- -- -- -- -- -- -- -- -- -- -- -- -- --

        com21StuControlTable OBJECT-TYPE
                SYNTAX SEQUENCE OF StuControlEntry
                MAX-ACCESS not-accessible
                STATUS current
                DESCRIPTION "."
                ::= { com21StuControlGroup 1 }

        com21StuControlEntry OBJECT-TYPE
                SYNTAX StuControlEntry
                MAX-ACCESS not-accessible
                STATUS current
                DESCRIPTION "."
                INDEX { stuCtrlMacAddress }
                ::= { com21StuControlTable 1 }

        StuControlEntry ::= SEQUENCE {
		stuCtrlMacAddress	MacAddress,
		stuUserText		DisplayString,
		stuSerialNumber		DisplayString,
		stuBoardRevision	DisplayString,
		stuUnitRevision		DisplayString,
		stuTunerRevision 	DisplayString,
		stuModelName		DisplayString,
		stuUnitManufacturer	DisplayString,
		stuDesKeySize		INTEGER,
		stuMibRevision		DisplayString,
		stuEpochTime		EpochTime,
        	stuRestartAction	INTEGER,
		stuPrevTestResult	INTEGER,
        	stuPrevTestFailCode	INTEGER,
		stuOperationState	INTEGER,
		stuAimModuleId		INTEGER,
		stuUpstrmTestFreq	UpstrmFreqKhz,
		stuInbPresent		INTEGER,
		stuInbContToneEnable	INTEGER,
		stuLastRestartCause	INTEGER,
		stuUpstrmPingCntrl	INTEGER,
		stuUpstrmTestTimeout	INTEGER,
		stuDnstrmAltFreq	FrequencyKhz,
                stuAsicRevision         INTEGER,
		stuVoiceAimLpBk		INTEGER,
		stuVoiceAimPort1Status  INTEGER,
		stuVoiceAimPort2Status  INTEGER }

        stuCtrlMacAddress OBJECT-TYPE
                SYNTAX MacAddress
                MAX-ACCESS read-only
                STATUS current
                DESCRIPTION "
                        Contains IEEE 802 medium access control address of 
			the ComPort device."
                ::= { com21StuControlEntry 1 }
 
        stuUserText OBJECT-TYPE
                SYNTAX DisplayString (SIZE(32))
                MAX-ACCESS read-write
                STATUS current
                DESCRIPTION "
                        The ComPort User Text is a non-volatile string which is 
			set by the management system with an arbitrary value. 
			This value does not have to be unique. It's purpose 
			is solely to assist the carrier personnel with 
			identifying the ComPort device."
                ::= { com21StuControlEntry 2 }
 
        stuSerialNumber OBJECT-TYPE
                SYNTAX DisplayString (SIZE(16))
                MAX-ACCESS read-only
                STATUS current
                DESCRIPTION "
                        The Serial Number is a 10 character serial number 
			used by COM21 to uniquely identify the device."
                ::= { com21StuControlEntry 3 }

	stuBoardRevision OBJECT-TYPE
                SYNTAX DisplayString (SIZE(16))
                MAX-ACCESS read-only
                STATUS current
                DESCRIPTION "
                        This string defines the hardware revision of the 
			ComPort board."
                ::= { com21StuControlEntry 4 }

	stuUnitRevision OBJECT-TYPE
                SYNTAX DisplayString (SIZE(10))
                MAX-ACCESS read-only
                STATUS current
                DESCRIPTION "
                        This string defines the hardware revision of the 
			complete ComPort unit."
                ::= { com21StuControlEntry 5 }

	stuTunerRevision OBJECT-TYPE
                SYNTAX DisplayString (SIZE(10))
                MAX-ACCESS read-only
                STATUS current
                DESCRIPTION "
                        This string defines the hardware revision of the 
                        RF Tuner."
                ::= { com21StuControlEntry 6 }

        stuModelName OBJECT-TYPE
                SYNTAX DisplayString (SIZE(16))
                MAX-ACCESS read-only
                STATUS current
                DESCRIPTION "
                        This string defines the ComPort Model Type."
                ::= { com21StuControlEntry 7 }
 
	stuUnitManufacturer OBJECT-TYPE
                SYNTAX DisplayString (SIZE(8))
                MAX-ACCESS read-only
                STATUS current
                DESCRIPTION "
                        This string defines the manufacturer of the ComPort.
			Initially COM21 and 3COM."
                ::= { com21StuControlEntry 8 }

	stuDesKeySize OBJECT-TYPE
		SYNTAX INTEGER { bit56key(1), bit40key(2) }
		MAX-ACCESS read-only
		STATUS current
		DESCRIPTION "
			DES encryption key size supported by the ComPort."
                ::= { com21StuControlEntry 9 }

	stuMibRevision OBJECT-TYPE
		SYNTAX DisplayString (SIZE(16))
		MAX-ACCESS read-only
		STATUS current
		DESCRIPTION "
			Indicates the Mib Revision as display string of 
			max. 8 bytes. That includes string terminator."
		::= { com21StuControlEntry 10 }

        stuEpochTime OBJECT-TYPE
                SYNTAX EpochTime
                MAX-ACCESS read-write
                STATUS current
                DESCRIPTION "
                        ComPort time in seconds since 1970."
                ::= { com21StuControlEntry 11 }

        stuRestartAction OBJECT-TYPE
                SYNTAX INTEGER {
                                nil(1),
				restart(2) }
                MAX-ACCESS read-write
                STATUS current
                DESCRIPTION "
                        The Restart Action is an active-value. The 
			setting of this value is idempotent. The setting of 
			this value to restart causes the STU to restart 
			utilizing the present software load."
                ::= { com21StuControlEntry 12 }

	stuPrevTestResult OBJECT-TYPE
                SYNTAX INTEGER { success (1), failure (2) }
                MAX-ACCESS read-only 
                STATUS current
                DESCRIPTION "  
                        Result of previous test. Presently this will
			be warm or cold restart."
                ::= { com21StuControlEntry 13 }

        stuPrevTestFailCode OBJECT-TYPE
                SYNTAX INTEGER (-32768..-1)
                MAX-ACCESS read-only 
                STATUS current
                DESCRIPTION "  
                        Failure result code. Only set if stuPrevTestResult
			is equal to failure."
                ::= { com21StuControlEntry 14 }

        stuOperationState OBJECT-TYPE
                SYNTAX INTEGER {
                                operational(1),
                                deauthorized(2),
                                offline(3),
				upstreamTest(4),
				etherLoopback(5),
				downloading(6),
				failedRanging(7) }
                MAX-ACCESS read-only
                STATUS current
                DESCRIPTION "
                        The ComPort Operational State is controlled either
                        by the stuAdminState or locally detected conditions.
			Note that downloading and failedRanging are 
			ComController helded states."
                ::= { com21StuControlEntry 15 }
 
        stuOperationStateChange NOTIFICATION-TYPE
		OBJECTS { stuAlmSeverity, stuAlmTime,
		            stuCtrlMacAddress, stuOperationState }
                STATUS current
                DESCRIPTION "."
                ::= { com21Traps 110 }

	stuAimModuleId OBJECT-TYPE
                SYNTAX INTEGER { 
				none (1), 
				debugModule (2), 
				teleReturn (3),
				telephony1 (4),
				telephony2 (5),
				wirelessEthernet (6),
				atm (7) }
                MAX-ACCESS read-only
                STATUS current
                DESCRIPTION "  
                        identifies the connected AIM module type. The
		        maceEthernet entry indicates NO AIM inserted."
                ::= { com21StuControlEntry 16 }

	stuMaceFail NOTIFICATION-TYPE
                OBJECTS { stuAlmSeverity, stuAlmTime,
                            stuCtrlMacAddress }
                STATUS current
                DESCRIPTION "
			This trap would be sent after ComPort is completely
                        booted. That is, at least download is completed.
                        Event will be detected during POST (Power On Self 
			Test)"
		::= { com21Traps 119 }

        stuUpstrmTestFreq OBJECT-TYPE
                SYNTAX UpstrmFreqKhz
                MAX-ACCESS read-write
                STATUS current
                DESCRIPTION "
                        Transmit Frequency used by ComPort for Upstream RF
                        test. The default shall be 0 (an invalid freq)."
                ::= { com21StuControlEntry 17 }

        stuInbPresent OBJECT-TYPE
                SYNTAX INTEGER { inbInstalled(1), noInbSupport(2), inbReady(3) }
                MAX-ACCESS read-only
                STATUS current
                DESCRIPTION "
                        Indicates if the INB is present on the ComPORT.
			This is a future item not supported by present
			ComPORT hardware."
                ::= { com21StuControlEntry 19 }

        stuInbContToneEnable OBJECT-TYPE
                SYNTAX INTEGER { disable(1), enable(2) }
                MAX-ACCESS read-write
                STATUS current
                DESCRIPTION "
                        Controls the activation of a continuous pilot
			tone. This does not effect the standard tone
			sent before data (which is controlled by a 
			hardware switch). This value is not stored
			in NVRAM. Default is disable."
                ::= { com21StuControlEntry 20 }

        stuLastRestartCause OBJECT-TYPE
                SYNTAX INTEGER { 
				unknown(1), 
				hcxDirected(2), 
				pingFail(3),
				imageRefresh(4),
				lof(5),
				fault(6) }
                MAX-ACCESS read-only
                STATUS current
                DESCRIPTION "
                        specifies the reason for the last ComPort reset."
                ::= { com21StuControlEntry 21 }

	stuUpstrmPingCntrl OBJECT-TYPE
                SYNTAX INTEGER { disable(1), enable(2) }
                MAX-ACCESS read-write
                STATUS current
                DESCRIPTION "
                        used to control the upstream ping. Default is
			enable."
                ::= { com21StuControlEntry 22 }

        stuUpstrmTestTimeout OBJECT-TYPE
                SYNTAX INTEGER (0..86400)
                MAX-ACCESS read-write
                STATUS current
                DESCRIPTION "
                        timeout used by ComPort for Upstream RF test. If
			the ComController does not terminate the test
			in this period - defined in seconds - then the
			ComPort will automatically reset, thus terminating
			the test. 0 means no timeout. Default is 0."
                ::= { com21StuControlEntry 23 }

        stuDnstrmAltFreq OBJECT-TYPE
                SYNTAX FrequencyKhz
                MAX-ACCESS read-write
                STATUS current
                DESCRIPTION "
                        Defines an alternate downstream frequency for the
			ComPort. This value is non-voltile. Default is
                        0 (an invalid freq). IMPORTANT - this is a tbd
			feature not available in 2.3 release."
                ::= { com21StuControlEntry 24 }

        stuAsicRevision OBJECT-TYPE
                SYNTAX INTEGER (1..255)
                MAX-ACCESS read-only
                STATUS current
                DESCRIPTION "
                        defines the revision of the ASIC. Presently
                        values 1-255 are supported."
                ::= { com21StuControlEntry 25 }

        stuVoiceAimLpBk OBJECT-TYPE
                SYNTAX INTEGER { nil (1), stuLpBk (2) }
                MAX-ACCESS read-write
                STATUS current
                DESCRIPTION "
			If a voiceAim Module is configured on the
			stu, setting the Aim Module to stuLpBk will
			configure the Aim Module to loopback from
			one voice port to the other.
			default: nil" 
                ::= { com21StuControlEntry 26 }

        stuVoiceAimPort1Status OBJECT-TYPE
                SYNTAX INTEGER { onHook (1), offHook (2) }
                MAX-ACCESS read-only
                STATUS current
                DESCRIPTION "
			Describes whether the AimPort is onhook
			or offhook.
                        default: nil"
                ::= { com21StuControlEntry 27 }

        stuVoiceAimPort2Status OBJECT-TYPE
                SYNTAX INTEGER { onHook (1), offHook (2) }
                MAX-ACCESS read-only
                STATUS current
                DESCRIPTION "
                        Describes whether the AimPort is onhook
                        or offhook.
                        default: nil"
                ::= { com21StuControlEntry 28 }






        -- -- -- -- -- -- -- -- -- -- -- -- -- -- -- -- -- -- -- -- -- -- -- --
        -- -- -- -- -- -- -- -- -- -- -- -- -- -- -- -- -- -- -- -- -- -- -- --
        --
        -- com21StuPhysicalGroup
        --
        -- defines the attributes related to the management of the Physical 
	-- (RF) and MAC layer. This data is held by the ComPort and accessed by
	-- the ComController on a proxy basis.
        --
        -- -- -- -- -- -- -- -- -- -- -- -- -- -- -- -- -- -- -- -- -- -- -- --
        -- -- -- -- -- -- -- -- -- -- -- -- -- -- -- -- -- -- -- -- -- -- -- --

        com21StuPhysicalTable OBJECT-TYPE
                SYNTAX SEQUENCE OF StuPhysicalEntry
                MAX-ACCESS not-accessible
                STATUS current
                DESCRIPTION "."
                ::= { com21StuPhysicalGroup 1 }

        com21StuPhysicalEntry OBJECT-TYPE
                SYNTAX StuPhysicalEntry
                MAX-ACCESS not-accessible
                STATUS current
                DESCRIPTION "."
                INDEX { stuPhyMacAddress }
                ::= { com21StuPhysicalTable 1 }

        StuPhysicalEntry ::= SEQUENCE {
		stuPhyMacAddress	MacAddress,
		stuXmitFrequency	UpstrmFreqKhz,
		stuRecvFrequency	FrequencyKhz,
		stuRecvRfSrEstimate	Integer32,
		stuRecvRfSigLevel	Integer32,
		stuXmitOffset		Offset,
		stuXmitDacVRef		INTEGER,
		stuRecvFreqDrift	INTEGER }

        stuPhyMacAddress OBJECT-TYPE
                SYNTAX MacAddress
                MAX-ACCESS read-only
                STATUS current
                DESCRIPTION "
                        Contains IEEE 802 medium access control address of the 
			ComPort device."
                ::= { com21StuPhysicalEntry 1 }
 
        stuXmitFrequency OBJECT-TYPE
                SYNTAX UpstrmFreqKhz
                MAX-ACCESS read-write
                STATUS current
                DESCRIPTION "
                        Contains the transmit frequency of the ComPort RF board 
			in KHz. A change in this value shall result in the 
			ComPort being hopped to a differing RX card. The Common
			Controller shall ensure the sanity of a change to this 
			attribute and shall perform the necessary interface to 
			the RX cards. The actual set of this attribute on the 
			ComPort shall be performed by a GO_SET message."
                ::= { com21StuPhysicalEntry 2 }

        stuXmitFeqChange NOTIFICATION-TYPE
		OBJECTS { stuAlmSeverity, stuAlmTime,
		            stuPhyMacAddress, stuXmitFrequency }
                STATUS current
                DESCRIPTION "
			This trap is generated whenever an ComPort is hopped. It
			will not be generated at initial acquisition."
                ::= { com21Traps 111 }
 
        stuRecvFrequency OBJECT-TYPE
                SYNTAX FrequencyKhz
                MAX-ACCESS read-write
                STATUS current
                DESCRIPTION "
                        Contains the receive frequency in KHz. This attribute 
			will match the downstream frequency of the 
			ComController. The ONLY time when this should be change
			is when the NMAPS wishes hop the ComPort to a different 
			ComController."
                ::= { com21StuPhysicalEntry 3 }
 
	stuRecvRfSrEstimate OBJECT-TYPE
                SYNTAX Integer32
                MAX-ACCESS read-only
                STATUS current
                DESCRIPTION "
			Received Signal S/R estimate in dB on Rf Downstream.
			This value is an approximation in dB. Received value 
			should be divided by 10 to get a fixed point
             		representation. e.g., value 185 means 18.5 dB."
		::= { com21StuPhysicalEntry 4 }

	stuRecvRfSigLevel OBJECT-TYPE
                SYNTAX Integer32
                MAX-ACCESS read-only 
                STATUS current 
                DESCRIPTION "
			Received Signal Level in dBmv on Rf Downstream."
                ::= { com21StuPhysicalEntry 5 }

        stuOutOfSpecRFCond NOTIFICATION-TYPE
                OBJECTS { stuAlmSeverity, stuAlmTime,
                            stuPhyMacAddress, stuRecvRfSigLevel }
                STATUS current
                DESCRIPTION "
                        This trap is generated whenever an ComPort is acquired
			with out of spec signal quality condition. The trap
			trap is issued after the GO-SET-DONE message."
                ::= { com21Traps 117 }

        stuXmitOffset OBJECT-TYPE
                SYNTAX Offset
                MAX-ACCESS read-only
                STATUS current
                DESCRIPTION "
                        Specifies the transmit offset of the ComPort."
                ::= { com21StuPhysicalEntry 6 }

	stuXmitDacVRef OBJECT-TYPE               
                SYNTAX INTEGER (0..4294967295)
		MAX-ACCESS read-only
                STATUS current
                DESCRIPTION "
			Specifies the upstream RF DAC Voltage Reference. This
 			value is set only via a GO_SET message under the
			control of the RX card."
		::= { com21StuPhysicalEntry 7 } 

	stuRecvFreqDrift OBJECT-TYPE              
                SYNTAX INTEGER (-250..250)
                MAX-ACCESS read-only
                STATUS current
                DESCRIPTION "
			Frequency shift (+/- 250Khz) from Downstream 
			Frequency."
                ::= { com21StuPhysicalEntry 8 }


 
        -- -- -- -- -- -- -- -- -- -- -- -- -- -- -- -- -- -- -- -- -- -- -- --
        -- -- -- -- -- -- -- -- -- -- -- -- -- -- -- -- -- -- -- -- -- -- -- --
        --
        -- com21StuAlarmGroup
        --
        -- defines the attributes related to the ComPort alarm log.
        --
        -- -- -- -- -- -- -- -- -- -- -- -- -- -- -- -- -- -- -- -- -- -- -- --
        -- -- -- -- -- -- -- -- -- -- -- -- -- -- -- -- -- -- -- -- -- -- -- --
 
        com21StuAlarmTable OBJECT-TYPE
                SYNTAX SEQUENCE OF StuAlarmEntry
                MAX-ACCESS not-accessible
                STATUS current
                DESCRIPTION "."
                ::= { com21StuAlarmGroup 1 }
 
        com21StuAlarmEntry OBJECT-TYPE
                SYNTAX StuAlarmEntry
                MAX-ACCESS not-accessible
                STATUS current
                DESCRIPTION "."
                INDEX { stuAlmMacAddress, stuAlmTime }
                ::= { com21StuAlarmTable 1 }
 
        StuAlarmEntry ::= SEQUENCE {
		stuAlmMacAddress	MacAddress,
		stuAlmTime		EpochTime,
		stuAlmTrapId		INTEGER,
		stuAlmSeverity		AlarmSeverity }

	stuAlmMacAddress OBJECT-TYPE
                SYNTAX MacAddress
                MAX-ACCESS read-only
                STATUS current
                DESCRIPTION "
                        Contains IEEE 802 medium access control address of
                        the ComPort device."
                ::= { com21StuAlarmEntry 1 }

        stuAlmTime OBJECT-TYPE 
                SYNTAX EpochTime
                MAX-ACCESS read-only    
                STATUS current  
                DESCRIPTION "   
                        Specifies the time the alarm condition was detected."
                ::= { com21StuAlarmEntry 2 } 

	stuAlmTrapId OBJECT-TYPE 
                SYNTAX INTEGER (100..200)
                MAX-ACCESS read-only
                STATUS current
                DESCRIPTION "
                        Specifies the trap number."
                ::= { com21StuAlarmEntry 3 }

	stuAlmSeverity OBJECT-TYPE 
                SYNTAX AlarmSeverity
                MAX-ACCESS read-only
                STATUS current
                DESCRIPTION "
                        Specifies the alarm severity."
                ::= { com21StuAlarmEntry 4 }



        -- -- -- -- -- -- -- -- -- -- -- -- -- -- -- -- -- -- -- -- -- -- -- --
        -- -- -- -- -- -- -- -- -- -- -- -- -- -- -- -- -- -- -- -- -- -- -- --
        --
        -- com21StuAlarmSevGroup
        --
        -- defines the attributes related to the ComPort alarm 
        --
        -- -- -- -- -- -- -- -- -- -- -- -- -- -- -- -- -- -- -- -- -- -- -- --
        -- -- -- -- -- -- -- -- -- -- -- -- -- -- -- -- -- -- -- -- -- -- -- --

        com21StuAlarmSevTable OBJECT-TYPE
                SYNTAX SEQUENCE OF StuAlarmSevEntry
                MAX-ACCESS not-accessible
                STATUS current
                DESCRIPTION "."
                ::= { com21StuAlarmSevGroup 1 }

        com21StuAlarmSevEntry OBJECT-TYPE
                SYNTAX StuAlarmSevEntry
                MAX-ACCESS not-accessible
                STATUS current
                DESCRIPTION "."
                INDEX { stuAlmSevMacAddress }
                ::= { com21StuAlarmSevTable 1 } 

        StuAlarmSevEntry ::= SEQUENCE {
                stuAlmSevMacAddress     MacAddress,
		stuAlmSevCrcThres	INTEGER,
		stuAlmSevTeiThres	INTEGER,
		stuAlmSevHecThres	INTEGER,
		stuAlmSevEsThres	INTEGER,
		stuAlmSevFecThres	INTEGER }

        stuAlmSevMacAddress OBJECT-TYPE
                SYNTAX MacAddress  
                MAX-ACCESS read-only
                STATUS current
                DESCRIPTION "  
                        Contains IEEE 802 medium access control address of
                        the ComPort device."
                ::= { com21StuAlarmSevEntry 1 }

        stuAlmSevCrcThres OBJECT-TYPE
                SYNTAX AlarmSeverity
                MAX-ACCESS read-write
                STATUS current
                DESCRIPTION "  
                        Specifies the CRC Error Threshold alarm severity.
			Default Minor."
                ::= { com21StuAlarmSevEntry 2 }

        stuAlmSevTeiThres OBJECT-TYPE
                SYNTAX AlarmSeverity
                MAX-ACCESS read-write
                STATUS current
                DESCRIPTION "  
                        Specifies the TEI Threshold alarm severity. Default
			Minor."
                ::= { com21StuAlarmSevEntry 3 }

        stuAlmSevHecThres OBJECT-TYPE
                SYNTAX AlarmSeverity
                MAX-ACCESS read-write
                STATUS current
                DESCRIPTION "  
                        Specifies the HEC Error Threshold alarm severity.
			Default Minor."
                ::= { com21StuAlarmSevEntry 4 }

        stuAlmSevEsThres OBJECT-TYPE
                SYNTAX AlarmSeverity
                MAX-ACCESS read-write
                STATUS current
                DESCRIPTION "  
                        Specifies the Errored Seconds Threshold alarm severity.
			Default Minor."
                ::= { com21StuAlarmSevEntry 5 }

        stuAlmSevFecThres OBJECT-TYPE
                SYNTAX AlarmSeverity
                MAX-ACCESS read-write
                STATUS current
                DESCRIPTION "  
                        Specifies the Corrected FEC Threshold alarm severity.
			Default Minor."
                ::= { com21StuAlarmSevEntry 6 }


 
        -- -- -- -- -- -- -- -- -- -- -- -- -- -- -- -- -- -- -- -- -- -- -- --
        -- -- -- -- -- -- -- -- -- -- -- -- -- -- -- -- -- -- -- -- -- -- -- --
        --
        -- com21StuEtherConfigGroup
        -- 
        -- defines the attributes related to the management, configuration
        -- and status of the ComPort ethernet interface. This data is held by 
	-- the ComPort and accessed by the ComController on a proxy basis.
        --
        -- -- -- -- -- -- -- -- -- -- -- -- -- -- -- -- -- -- -- -- -- -- -- --
        -- -- -- -- -- -- -- -- -- -- -- -- -- -- -- -- -- -- -- -- -- -- -- --
 
        com21StuEtherConfigTable OBJECT-TYPE
                SYNTAX  SEQUENCE OF StuEtherConfigEntry
                MAX-ACCESS  not-accessible
                STATUS  current
                DESCRIPTION "."
                ::= { com21StuEtherConfigGroup 1 }
 
        com21StuEtherConfigEntry OBJECT-TYPE
                SYNTAX  StuEtherConfigEntry
                MAX-ACCESS  not-accessible
                STATUS  current
                DESCRIPTION "."
                INDEX { stuEthMacAddress }
                ::= { com21StuEtherConfigTable 1 }
 
        StuEtherConfigEntry ::= SEQUENCE {
		stuEthMacAddress	MacAddress,
		stuEtherFiltFlushAction	INTEGER,
		stuEtherForwArpOnly	INTEGER,
		stuEtherMacFiltAge	INTEGER,
		stuEtherBCastRateEn	INTEGER,
		stuEtherBCastRateCo	INTEGER,
		stuEtherStickyBitCtrl	INTEGER,
		stuEther8021QEnable	INTEGER,
		stuEtherNonSnapRej	INTEGER,
		stuEtherIgmpEnable	INTEGER,
		stuEtherNonIpMultiEn	INTEGER,
                stuEtherBcmpOnly        INTEGER,
                stuEtherIgmpSnoopEnable INTEGER }

        stuEthMacAddress OBJECT-TYPE
                SYNTAX MacAddress
                MAX-ACCESS read-only
                STATUS current
                DESCRIPTION "
                        Contains IEEE 802 medium access control address of
                        the ComPort device. Held on ComController."
                ::= { com21StuEtherConfigEntry 1 }

	stuEtherFiltFlushAction OBJECT-TYPE
                SYNTAX	INTEGER {
			none (1),
			flushMac (2),
			flushEtherType (3),
			flushIp (4) }
                MAX-ACCESS read-write
                STATUS current
                DESCRIPTION "
                        Controls the flush operations."
		::= { com21StuEtherConfigEntry 2 }

	stuEtherForwArpOnly OBJECT-TYPE
		SYNTAX	INTEGER { disable (1), enable (2) }
                MAX-ACCESS read-write
                STATUS current
                DESCRIPTION "
			If enable state then only ARP broadcast packets
			are forwarded upstream. Default is disable."
                ::= { com21StuEtherConfigEntry 3 }

	stuEtherMacFiltAge OBJECT-TYPE
                SYNTAX	INTEGER (0..4095)
                MAX-ACCESS read-write
		STATUS current
                DESCRIPTION "
			Specifies the number of seconds that a learned
			MAC Address entry survives since last learning."
                ::= { com21StuEtherConfigEntry 4 }
			
	stuEtherBCastRateEn OBJECT-TYPE
                SYNTAX	INTEGER { disable (1), enable (2) }
                MAX-ACCESS read-write
                STATUS current
                DESCRIPTION "
			Enable rate control. Default is disabled."
                ::= { com21StuEtherConfigEntry 5 }
		
	stuEtherBCastRateCo OBJECT-TYPE
                SYNTAX	INTEGER (1..255)
                MAX-ACCESS read-write
                STATUS current
                DESCRIPTION "
                        Limit of maximum number of broadcast packets per
			second allowed upstream." 
                ::= { com21StuEtherConfigEntry 6 }

        stuEtherStickyBitCtrl OBJECT-TYPE
                SYNTAX  INTEGER { disable (1), enable (2) }
                MAX-ACCESS read-write
                STATUS current
                DESCRIPTION "
                        When the Sticky Bit control is enabled, a MAC
			table entry will not be replaced by another MAC
			address for at least one aging period. Default 
			disable."
                ::= { com21StuEtherConfigEntry 7 }

        stuEther8021QEnable OBJECT-TYPE
                SYNTAX  INTEGER { disable (1), enable (2) }
                MAX-ACCESS read-write
                STATUS current
                DESCRIPTION "
                        Enables both 802.1Q priority queuing and the filter
			of 802.1Q format packets. Default disable."
                ::= { com21StuEtherConfigEntry 8 }

        stuEtherNonSnapRej OBJECT-TYPE 
                SYNTAX  INTEGER { disable (1), enable (2) } 
                MAX-ACCESS read-write 
                STATUS current 
                DESCRIPTION " 
                        This attribute controls the filtering of 802.2 non-
			SNAP encoded packets. Ethernet type filtering must
			be enabled to activate this feature. Default disable."
                ::= { com21StuEtherConfigEntry 9 } 

        stuEtherIgmpEnable OBJECT-TYPE
                SYNTAX  INTEGER { disable (1), enable (2) }
                MAX-ACCESS read-write
                STATUS current
                DESCRIPTION "
                        This attribute controls the forwarding of IGMP
			multicast traffic upstream. This attribute will
			override any other multicast filtering in the case
			of IGMP packets. Default is enable."
                ::= { com21StuEtherConfigEntry 10 }

        stuEtherNonIpMultiEn OBJECT-TYPE 
                SYNTAX  INTEGER { disable (1), enable (2) } 
                MAX-ACCESS read-write
                STATUS current 
                DESCRIPTION " 
                        This attribute controls the forwarding of non-IP
                        multicast traffic upstream. This attribute will 
                        override any other multicast filtering in the case 
                        of non-IP multicast packets. Default is enable."
                ::= { com21StuEtherConfigEntry 11 } 

	stuEtherBcmpOnly OBJECT-TYPE 
                SYNTAX  INTEGER { disable (1), enable (2) }
                MAX-ACCESS read-write
                STATUS current
                DESCRIPTION "   
                        When this attribute is enabled, all non-BCMP
			traffic will be rejected in both the upstream
			and downstream. This attribute is utilized in a
			Spannong Tree implementation. Default is disable."
                ::= { com21StuEtherConfigEntry 12 }

        stuEtherIgmpSnoopEnable OBJECT-TYPE
                SYNTAX  INTEGER { disable (1), enable (2) }
                MAX-ACCESS read-write
                STATUS current
                DESCRIPTION "
                        This attribute controls the snooping of IGMP
                        multicast traffic upstream. Default is disable."
                ::= { com21StuEtherConfigEntry 13 }



        -- -- -- -- -- -- -- -- -- -- -- -- -- -- -- -- -- -- -- -- -- -- -- --
        -- -- -- -- -- -- -- -- -- -- -- -- -- -- -- -- -- -- -- -- -- -- -- --
        --
        -- com21StuEtherTypeGroup
        -- 
        -- defines the attributes related to the management of supported
        -- Ethernet Types. This data is held by the ComPort and accessed by the 
	-- ComController on a proxy basis.
        --
        -- -- -- -- -- -- -- -- -- -- -- -- -- -- -- -- -- -- -- -- -- -- -- --
        -- -- -- -- -- -- -- -- -- -- -- -- -- -- -- -- -- -- -- -- -- -- -- --
 
        com21StuEtherTypeTable OBJECT-TYPE
                SYNTAX  SEQUENCE OF StuFiltEthTypeEntry
                MAX-ACCESS not-accessible
                STATUS current
                DESCRIPTION "."
                ::= { com21StuEtherTypeGroup 1 }
 
	com21StuFiltEthTypeEntry OBJECT-TYPE
                SYNTAX  StuFiltEthTypeEntry
		MAX-ACCESS not-accessible
                STATUS current
                DESCRIPTION "
			Holds Ethernet Types codes that are to be passed
			upstream. Maximum of 6 entries."
                INDEX { stuFiltEtherMacAddr, stuFiltEtherType }
		::= { com21StuEtherTypeTable 1 }

	StuFiltEthTypeEntry ::= SEQUENCE {
		stuFiltEtherMacAddr	MacAddress,
		stuFiltEtherType	INTEGER,
		stuFiltEtherStatus	Com21RowStatus }

        stuFiltEtherMacAddr OBJECT-TYPE
                SYNTAX MacAddress
                MAX-ACCESS read-only
                STATUS current
                DESCRIPTION "
                        Contains IEEE 802 medium access control address of
                        the ComPort device. Held on ComController."
                ::= { com21StuFiltEthTypeEntry 1 }

	stuFiltEtherType OBJECT-TYPE
                SYNTAX INTEGER (1..65535)
                MAX-ACCESS read-only
                STATUS current
                DESCRIPTION " 
                        Holds Ethernet Type codes that is to be passed 
                        upstream. Held on ComPort. "
                ::= { com21StuFiltEthTypeEntry 2 }

	stuFiltEtherStatus OBJECT-TYPE
                SYNTAX Com21RowStatus
                MAX-ACCESS read-create
                STATUS current
                DESCRIPTION "
			This attribute is used to create or delete Ethernet
			Type entry."
		::= { com21StuFiltEthTypeEntry 3 }



        -- -- -- -- -- -- -- -- -- -- -- -- -- -- -- -- -- -- -- -- -- -- -- --
        -- -- -- -- -- -- -- -- -- -- -- -- -- -- -- -- -- -- -- -- -- -- -- --
        --
        -- com21StuFiltIpMultiGroup
        -- 
        -- defines the attributes related to the management of IP Multicast
        -- Address Types. This data is held by the ComPort and accessed by the 
	-- ComController on a proxy basis.
        --
        -- -- -- -- -- -- -- -- -- -- -- -- -- -- -- -- -- -- -- -- -- -- -- --
        -- -- -- -- -- -- -- -- -- -- -- -- -- -- -- -- -- -- -- -- -- -- -- --
 
        com21StuFiltIpMultiTable OBJECT-TYPE
                SYNTAX SEQUENCE OF StuFiltIpMultiEntry
                MAX-ACCESS not-accessible
                STATUS current
                DESCRIPTION "."
                ::= { com21StuFiltIpMultiGroup 1 }
 
        com21StuFiltIpMultiEntry OBJECT-TYPE
                SYNTAX  StuFiltIpMultiEntry
                MAX-ACCESS not-accessible 
                STATUS current
                DESCRIPTION " 
                        Holds IP Multicast Addresses that are to be allowed
                        in either upstream, or downstream, or both directions. 
			Maximum of 16 entries." 
                INDEX { stuFiltIpMacAddr, stuFiltIpMultiAddr }
                ::= { com21StuFiltIpMultiTable 1 }
 
        StuFiltIpMultiEntry ::= SEQUENCE {
		stuFiltIpMacAddr	MacAddress,
                stuFiltIpMultiAddr      MacAddress,
		stuFiltIpMultiStatus	Com21RowStatus,
		stuFiltIpDirectCntrl	INTEGER }

        stuFiltIpMacAddr OBJECT-TYPE
                SYNTAX MacAddress
                MAX-ACCESS read-only
                STATUS current
                DESCRIPTION "
                        Contains IEEE 802 medium access control address of
                        the ComPort device. Held on ComController."
                ::= { com21StuFiltIpMultiEntry 1 }

        stuFiltIpMultiAddr OBJECT-TYPE
                SYNTAX MacAddress
                MAX-ACCESS read-only
                STATUS current
                DESCRIPTION "
                        Holds Multicast Address. Held on ComPort. 
			Valid values are within the range of MAC addresses 
			of 01.00.5E.00.00.00 to 01.00.5E.7F.FF.FF"
                ::= { com21StuFiltIpMultiEntry 2 }

	stuFiltIpMultiStatus OBJECT-TYPE
                SYNTAX Com21RowStatus
                MAX-ACCESS read-create
                STATUS current
                DESCRIPTION "
			Used to delete or create an entry."
		::= { com21StuFiltIpMultiEntry 3 }

        stuFiltIpDirectCntrl OBJECT-TYPE
                SYNTAX INTEGER { 
				upstreamOnly(1), 
				downstreamOnly(2), 
				bothDirections(3) }
                MAX-ACCESS read-write
                STATUS current
                DESCRIPTION "
                        Used to control the filter direction. Default
			is bothDirections."
                ::= { com21StuFiltIpMultiEntry 4 }
 


        -- -- -- -- -- -- -- -- -- -- -- -- -- -- -- -- -- -- -- -- -- -- -- --
        -- -- -- -- -- -- -- -- -- -- -- -- -- -- -- -- -- -- -- -- -- -- -- --
        --
        -- com21StuEtherMacGroup
        -- 
        -- defines the attributes related to the management of supported
        -- Ethernet MAC addresses. This data is held by the ComPort and accessed 
	-- by the ComController on a proxy basis.
        --
        -- -- -- -- -- -- -- -- -- -- -- -- -- -- -- -- -- -- -- -- -- -- -- --
        -- -- -- -- -- -- -- -- -- -- -- -- -- -- -- -- -- -- -- -- -- -- -- --

        com21StuEtherMacTable OBJECT-TYPE
                SYNTAX SEQUENCE OF StuEtherMacEntry
                MAX-ACCESS not-accessible
                STATUS current
                DESCRIPTION "."
                ::= { com21StuEtherMacGroup 1 }
 
        com21StuEtherMacEntry OBJECT-TYPE
                SYNTAX  StuEtherMacEntry
                MAX-ACCESS not-accessible 
                STATUS current
                DESCRIPTION " 
                        Holds Ethernet MAC address that are to be
			processed as specified. Maximum of 8 entries."
		INDEX { stuEtherStuMac, stuEtherMacAddr }
                ::= { com21StuEtherMacTable 1 } 
 
        StuEtherMacEntry ::= SEQUENCE {
                stuEtherStuMac		MacAddress,
                stuEtherMacAddr		MacAddress,
		stuEtherMacType		INTEGER,
		stuEtherMacStatus	Com21RowStatus }
 
        stuEtherStuMac OBJECT-TYPE
                SYNTAX MacAddress
                MAX-ACCESS read-only
                STATUS current
                DESCRIPTION "
                        Contains IEEE 802 medium access control address of
                        the ComPort device. Held on ComController."
                ::= { com21StuEtherMacEntry 1 }

        stuEtherMacAddr OBJECT-TYPE
                SYNTAX MacAddress
                MAX-ACCESS read-only
                STATUS current
                DESCRIPTION "
                        Holds MAC address. Held on ComPort."
                ::= { com21StuEtherMacEntry 2 }

        stuEtherMacType OBJECT-TYPE
                SYNTAX INTEGER {
			learned (1),
			processor (2),
			upstream (3),
			reject (4) }
                MAX-ACCESS read-write
                STATUS current
                DESCRIPTION "
                        Holds action to be performed upon packets of
			the specified MAC address. In the case of the
			learned MAC address, this entry becomes read
			only. Held on ComPort."
                ::= { com21StuEtherMacEntry 3 }

	stuEtherMacStatus OBJECT-TYPE
                SYNTAX Com21RowStatus
		MAX-ACCESS read-create
                STATUS current
                DESCRIPTION "
                        Used to create or delete an entry."
                ::= { com21StuEtherMacEntry 4 }



        -- -- -- -- -- -- -- -- -- -- -- -- -- -- -- -- -- -- -- -- -- -- -- --
        -- -- -- -- -- -- -- -- -- -- -- -- -- -- -- -- -- -- -- -- -- -- -- --
        --
        -- com21StuEtherStatsGroup
        -- 
        -- defines the attributes related to the statistical monitoring
        -- of the ComPort ethernet interface. Much of this data is collected
	-- and held by the ComPort and accessed by the ComController on a proxy 
	-- basis.
        --
        --
        -- -- -- -- -- -- -- -- -- -- -- -- -- -- -- -- -- -- -- -- -- -- -- --
        -- -- -- -- -- -- -- -- -- -- -- -- -- -- -- -- -- -- -- -- -- -- -- --
 
        com21StuEtherStatsTable OBJECT-TYPE
                SYNTAX  SEQUENCE OF StuEtherStatsEntry
                MAX-ACCESS  not-accessible
                STATUS  current
                DESCRIPTION "."
                ::= { com21StuEtherStatsGroup 1 }
 
        com21StuEtherStatsEntry OBJECT-TYPE
                SYNTAX  StuEtherStatsEntry
                MAX-ACCESS  not-accessible
                STATUS  current
                DESCRIPTION "."
                INDEX { stuEthStatsMacAddr }
                ::= { com21StuEtherStatsTable 1 }
 
        StuEtherStatsEntry ::= SEQUENCE {
		stuEthStatsMacAddr	MacAddress,
		stuCurrEtherRunts	Gauge32,
		stuCurrEtherCollitns	Gauge32,
		stuCurrEtherFramErrs	Gauge32,
		stuCurrEtherCrcErrs	Gauge32,
		stuCurrEtherCrcThres	Integer32,
		stuCurrEtherTxUnder	Gauge32,
		stuCurrEtherRxOver	Gauge32,
		stuCurrEtherDropFrms	Gauge32,
		stuPrevEtherRunts       Gauge32,
                stuPrevEtherCollitns    Gauge32,
                stuPrevEtherFramErrs    Gauge32,
                stuPrevEtherCrcErrs     Gauge32,
		stuPrevEtherTxUnder	Gauge32,
		stuPrevEtherRxOver	Gauge32,
		stuPrevEtherDropFrms	Gauge32,
		stuEtherConnState	INTEGER,
		stuEtherClearStats	INTEGER }

        stuEthStatsMacAddr OBJECT-TYPE
                SYNTAX MacAddress
                MAX-ACCESS read-only
                STATUS current
                DESCRIPTION "
                        Contains IEEE 802 medium access control address of
                        the ComPort device. Held on ComController."
                ::= { com21StuEtherStatsEntry 1 }

	stuCurrEtherRunts OBJECT-TYPE
                SYNTAX Gauge32
                MAX-ACCESS read-only
                STATUS current
		DESCRIPTION "
			Contains number of runt packets received by the
			ComPort in the current 15minute period. This data is
			held on the ComPort."
                ::= { com21StuEtherStatsEntry 2 }

        stuCurrEtherCollitns OBJECT-TYPE
                SYNTAX Gauge32
                MAX-ACCESS read-only
                STATUS current
                DESCRIPTION "  
                        Contains number of collisions detected by the
                        ComPort in the current 15minute period. This data is 
                        held on the ComPort."
                ::= { com21StuEtherStatsEntry 3 }

        stuCurrEtherFramErrs OBJECT-TYPE
                SYNTAX Gauge32
                MAX-ACCESS read-only
                STATUS current
                DESCRIPTION "  
                        Contains number of Ethernet Packets with Framing
                        Errors detected by the ComPort in the current 15minute
			period. This data is held on the ComPort."
                ::= { com21StuEtherStatsEntry 4 }

        stuCurrEtherCrcErrs OBJECT-TYPE
                SYNTAX Gauge32
                MAX-ACCESS read-only
                STATUS current
                DESCRIPTION "
                        Contains number of Ethernet Packets with CRC
                        Errors detected by the ComPort in the current 15minute
                        period. This data is held on the ComPort."
                ::= { com21StuEtherStatsEntry 5 }

        stuCurrEtherCrcThres OBJECT-TYPE       
                SYNTAX Integer32
                MAX-ACCESS read-write
                STATUS current
                DESCRIPTION "
                        contains 15minute error level at which a threshold
                        trap shall be generated. This is mapped to theComPort 
			alarm severity entry stuThresholdLevel. Default is
			0 - threshold disabled."
                ::= { com21StuEtherStatsEntry 6 }
                 
        stuEtherCrcThres NOTIFICATION-TYPE
                OBJECTS { stuAlmSeverity, stuAlmTime,
                            stuEthStatsMacAddr, stuCurrEtherCrcErrs,
                            stuCurrEtherCrcThres }
                STATUS current
                DESCRIPTION "."
                ::= { com21Traps 112 }

	stuCurrEtherTxUnder OBJECT-TYPE
                SYNTAX Gauge32
                MAX-ACCESS read-only
                STATUS current
                DESCRIPTION "
                        Contains number of times Ethernet TX FIFO Underflow
			occurred on transmit queue in the current 15minute
			period."
                ::= { com21StuEtherStatsEntry 7 }

	stuCurrEtherRxOver OBJECT-TYPE 
                SYNTAX Gauge32
                MAX-ACCESS read-only 
                STATUS current
                DESCRIPTION " 
                        Contains number of times Ethernet RX FIFO Overflow
			occurred on a receive queue in the current 15minute
			period."
                ::= { com21StuEtherStatsEntry 8 }

	stuCurrEtherDropFrms OBJECT-TYPE 
                SYNTAX Gauge32
                MAX-ACCESS read-only 
                STATUS current
                DESCRIPTION " 
                        Contains number of receive frames dropped by MACE
			controller in the current 15minute period."
                ::= { com21StuEtherStatsEntry 9 }

	stuPrevEtherRunts OBJECT-TYPE
                SYNTAX Gauge32
                MAX-ACCESS read-only
                STATUS current
		DESCRIPTION "
			Contains number of runt packets received by the
			ComPort in the previous 15minute period. This data is
			held on the ComPort."
                ::= { com21StuEtherStatsEntry 10 }

        stuPrevEtherCollitns OBJECT-TYPE
                SYNTAX Gauge32
                MAX-ACCESS read-only
                STATUS current
                DESCRIPTION "  
                        Contains number of collisions detected by the
                        ComPort in the previous 15minute period. This data is 
                        held on the ComPort."
                ::= { com21StuEtherStatsEntry 11 }

        stuPrevEtherFramErrs OBJECT-TYPE
                SYNTAX Gauge32
                MAX-ACCESS read-only
                STATUS current
                DESCRIPTION "  
                        Contains number of Ethernet Packets with Framing
                        Errors detected by the ComPort in the previous 15minute
			period. This data is held on the ComPort."
                ::= { com21StuEtherStatsEntry 12 }

        stuPrevEtherCrcErrs OBJECT-TYPE
                SYNTAX Gauge32
                MAX-ACCESS read-only
                STATUS current
                DESCRIPTION "
                        Contains number of Ethernet Packets with CRC
                        Errors detected by the ComPort in the previous 15minute
                        period. This data is held on the ComPort."
                ::= { com21StuEtherStatsEntry 13 }

        stuPrevEtherTxUnder OBJECT-TYPE
                SYNTAX Gauge32
                MAX-ACCESS read-only
                STATUS current
                DESCRIPTION "
                        Contains number of times Ethernet TX FIFO Underflow
                        occurred on transmit queue in the previous 15minute
                        period."
                ::= { com21StuEtherStatsEntry 14 }
 
        stuPrevEtherRxOver OBJECT-TYPE 
                SYNTAX Gauge32
                MAX-ACCESS read-only 
                STATUS current
                DESCRIPTION " 
                        Contains number of times Ethernet RX FIFO Overflow
                        occurred on a receive queue in the previous 15minute
                        period."
                ::= { com21StuEtherStatsEntry 15 }

        stuPrevEtherDropFrms OBJECT-TYPE 
                SYNTAX Gauge32
                MAX-ACCESS read-only 
                STATUS current
                DESCRIPTION " 
                        Contains number of receive frames dropped by MACE
                        controller in the previous 15minute period."
                ::= { com21StuEtherStatsEntry 16 }

	stuEtherConnState OBJECT-TYPE
                SYNTAX INTEGER { unint(1), is(2), oos(3) }
		MAX-ACCESS read-only
		STATUS current
		DESCRIPTION "
			Contains state of Ethernet connection."
		::= { com21StuEtherStatsEntry 17 }

	stuEtherClearStats OBJECT-TYPE
                SYNTAX INTEGER { nil(1), clear(2) }
		MAX-ACCESS read-write
		STATUS current
		DESCRIPTION "
			This attribute is used to clear all Ethernet
			statistics counters in this group. This operation
			is only possible if the hcxStatsControl attribute
			is set to wrapCurr."
		::= { com21StuEtherStatsEntry 18 }



        -- -- -- -- -- -- -- -- -- -- -- -- -- -- -- -- -- -- -- -- -- -- -- --
        -- -- -- -- -- -- -- -- -- -- -- -- -- -- -- -- -- -- -- -- -- -- -- --
        --
        -- com21StuStatsGroup
        -- 
        -- defines the attributes related to the statistics monitoring of an
	-- ComController<->ComPort link. This data is collected and held by 
	-- the ComPort and retrieved by the ComController on a proxy basis.
        --
        -- -- -- -- -- -- -- -- -- -- -- -- -- -- -- -- -- -- -- -- -- -- -- --
        -- -- -- -- -- -- -- -- -- -- -- -- -- -- -- -- -- -- -- -- -- -- -- --

        com21StuStatsTable OBJECT-TYPE
                SYNTAX  SEQUENCE OF StuStatsEntry
                MAX-ACCESS  not-accessible
                STATUS  current
                DESCRIPTION "."
                ::= { com21StuStatsGroup 1 }
 
        com21StuStatsEntry OBJECT-TYPE
                SYNTAX  StuStatsEntry
                MAX-ACCESS  not-accessible
                STATUS  current
                DESCRIPTION "."
                INDEX { stuStatsMacAddress }
                ::= { com21StuStatsTable 1 }

        StuStatsEntry ::= SEQUENCE {
		stuStatsMacAddress	MacAddress,
		stuStatsCurrAtmTei	Gauge32,
        	stuAtmTeiThreshold	Integer32,
		stuStatsCurrAtmHec	Gauge32,
        	stuAtmHecThreshold	Integer32,
		stuStatsCurrESMin	Gauge32,
		stuESMinThreshold	Integer32,
		stuStatsCurrFecCorrect	Gauge32,
		stuFecCorrectThreshold  Integer32,
		stuStatsCurrUASMin	Gauge32,
		stuStatsPrevAtmTei	Gauge32,
		stuStatsPrevAtmHec	Gauge32,
		stuStatsPrevESMin	Gauge32,
		stuStatsPrevFecCorrect	Gauge32,
		stuStatsPrevUASMin	Gauge32,
		stuStatsClearStats	INTEGER }
                 
        stuStatsMacAddress OBJECT-TYPE
                SYNTAX MacAddress
                MAX-ACCESS read-only
                STATUS current
                DESCRIPTION "
                        Contains IEEE 802 medium access control address of
                        the ComPort device. Held on ComController."
                ::= { com21StuStatsEntry 1 }

	stuStatsCurrAtmTei OBJECT-TYPE        
                SYNTAX Gauge32
                MAX-ACCESS read-only
                STATUS current
                DESCRIPTION "
			Number of cells received with transport errors -
			uncorrectable FEC or HEC errors - in the current 
			15minute period."
                ::= { com21StuStatsEntry 2 }
 
        stuAtmTeiThreshold OBJECT-TYPE
                SYNTAX Integer32
                MAX-ACCESS read-write
                STATUS current
                DESCRIPTION "
                        contains 15minute transport error level at which
                        a threshold trap shall be generated. Default is
                        0 - threshold disabled."
                ::= { com21StuStatsEntry 3 }

        stuAtmTeiThres NOTIFICATION-TYPE
		OBJECTS { stuAlmSeverity, stuAlmTime,
		            stuStatsMacAddress, stuStatsCurrAtmTei,
		            stuAtmTeiThreshold }
                STATUS current
                DESCRIPTION "."
                ::= { com21Traps 113 }

	stuStatsCurrAtmHec OBJECT-TYPE        
                SYNTAX Gauge32
                MAX-ACCESS read-only
                STATUS current
                DESCRIPTION "
			Number of cells received with HEC or Encryption errors
			in the current 15minute period."
                ::= { com21StuStatsEntry 4 }

        stuAtmHecThreshold OBJECT-TYPE
                SYNTAX Integer32
                MAX-ACCESS read-write
                STATUS current
                DESCRIPTION "
                        contains 15minute HEC error level at which
                        a threshold trap shall be generated. Default is
                        0 - threshold disabled."
                ::= { com21StuStatsEntry 5 }

        stuAtmHecThres NOTIFICATION-TYPE
		OBJECTS { stuAlmSeverity, stuAlmTime,
		            stuStatsMacAddress, stuStatsCurrAtmHec,
		            stuAtmHecThreshold }
                STATUS current
                DESCRIPTION "."
                ::= { com21Traps 114 }
  
        stuStatsCurrESMin OBJECT-TYPE
                SYNTAX Gauge32
                MAX-ACCESS read-only
                STATUS current
                DESCRIPTION "
                        Represents the number of errored seconds in 
			the current 15 minute period."
                ::= { com21StuStatsEntry 6 }
 
        stuESMinThreshold OBJECT-TYPE
                SYNTAX Integer32
                MAX-ACCESS read-write
                STATUS current
                DESCRIPTION "
                        contains 15minute errored seconds level at which
                        a threshold trap shall be generated. Default is
                        0 - threshold disabled."
                ::= { com21StuStatsEntry 7 }

        stuESMinThres NOTIFICATION-TYPE
		OBJECTS { stuAlmSeverity, stuAlmTime,
		            stuStatsMacAddress, stuStatsCurrESMin,
		            stuESMinThreshold }
                STATUS current
                DESCRIPTION "."
                ::= { com21Traps 115 }

	stuStatsCurrFecCorrect OBJECT-TYPE
		SYNTAX Gauge32
		MAX-ACCESS read-only
		STATUS current
		DESCRIPTION "
			Fecs corrected by Demodulator on Downstream
			in the current 15 minute period."
                ::= { com21StuStatsEntry 8 }

        stuFecCorrectThreshold OBJECT-TYPE
                SYNTAX Integer32
                MAX-ACCESS read-write
                STATUS current
                DESCRIPTION "  
                        contains 15minute Fecs corrected level at which
                        a threshold trap shall be generated. Default is
                        0 - threshold disabled."
                ::= { com21StuStatsEntry 9 }
 
        stuFecCorrectThres NOTIFICATION-TYPE
                OBJECTS { stuAlmSeverity, stuAlmTime,
                            stuStatsMacAddress, stuStatsCurrFecCorrect,
                            stuFecCorrectThreshold }
                STATUS current
                DESCRIPTION "."    
                ::= { com21Traps 116 }
 
        stuStatsCurrUASMin OBJECT-TYPE 
                SYNTAX Gauge32
                MAX-ACCESS read-only 
                STATUS current 
                DESCRIPTION " 
                        Represents the number of unavailable seconds
                        in the current 15 minute period." 
                ::= { com21StuStatsEntry 10 } 
 
        stuStatsPrevAtmTei OBJECT-TYPE
                SYNTAX Gauge32
                MAX-ACCESS read-only
                STATUS current
                DESCRIPTION "
                        Number of cells received with transport errors -
			HEC or uncorrectable FEC errors - in the previous 
			15minute period."
                ::= { com21StuStatsEntry 11 }

        stuStatsPrevAtmHec OBJECT-TYPE
                SYNTAX Gauge32
                MAX-ACCESS read-only
                STATUS current
                DESCRIPTION "
                        Number of cells received with HEC or Encryption errors
                        in the previous 15minute period."
                ::= { com21StuStatsEntry 12 }
 
        stuStatsPrevESMin OBJECT-TYPE
                SYNTAX Gauge32
                MAX-ACCESS read-only
                STATUS current
                DESCRIPTION "
                        Represents the number of errored seconds in 
			the previous 15 minute period."
                ::= { com21StuStatsEntry 13 }

        stuStatsPrevFecCorrect OBJECT-TYPE
                SYNTAX Gauge32
                MAX-ACCESS read-only
                STATUS current
                DESCRIPTION "
                        Fecs corrected by Demodulator on Downstream in
			the previous 15 minute period."
                ::= { com21StuStatsEntry 14 }
 
	stuStatsPrevUASMin OBJECT-TYPE
                SYNTAX Gauge32
                MAX-ACCESS read-only
                STATUS current
                DESCRIPTION "
                        Represents the number of unavailable seconds
                        in the previous 15 minute period."
                ::= { com21StuStatsEntry 15 }

        stuStatsClearStats OBJECT-TYPE
                SYNTAX INTEGER { nil(1), clear(2) }
                MAX-ACCESS read-write
                STATUS current
                DESCRIPTION "
                        This attribute is used to clear the all ComPort
                        statistics counters in this group. This operation
                        is only possible if the hcxStatsControl attribute
                        is set to wrapCurr."
                ::= { com21StuStatsEntry 16 }



        -- -- -- -- -- -- -- -- -- -- -- -- -- -- -- -- -- -- -- -- -- -- -- --
        -- -- -- -- -- -- -- -- -- -- -- -- -- -- -- -- -- -- -- -- -- -- -- --
        --
        -- com21StuQStatsGroup
        -- 
        -- defines the attributes related to the statistics monitoring of a
	-- single Mongoose queue. This group is based very closely on the
	-- ATM 2.1 ILMI atmfAtmStatsTable. Any future aboption of a differing
	-- standarized ATM MIB would most likely replace this group.
	-- This data is collected and held by the ComPort and accessed by the
	-- ComController on a proxy basis.
        --
        -- -- -- -- -- -- -- -- -- -- -- -- -- -- -- -- -- -- -- -- -- -- -- --
        -- -- -- -- -- -- -- -- -- -- -- -- -- -- -- -- -- -- -- -- -- -- -- --

        com21StuQStatsTable OBJECT-TYPE
                SYNTAX  SEQUENCE OF StuQStatsEntry
                MAX-ACCESS  not-accessible
                STATUS  current
                DESCRIPTION "."
                ::= { com21StuQStatsGroup 1 }
 
        com21StuQStatsEntry OBJECT-TYPE
                SYNTAX  StuQStatsEntry
                MAX-ACCESS  not-accessible
                STATUS  current
                DESCRIPTION "."
                INDEX { stuAtmStuMacAddr, stuAtmStuQNo }
                ::= { com21StuQStatsTable 1 }
 
        StuQStatsEntry ::= SEQUENCE {
		stuAtmStuMacAddr		MacAddress,
		stuAtmStuQNo			Integer32,
		stuAtmStatsCurrMinRx		Gauge32,
		stuAtmStatsCurrMinRxDropped	Gauge32,
		stuAtmStatsCurrMinCRCErrors	Gauge32,
		stuAtmStatsPrevMinRx		Gauge32,
                stuAtmStatsPrevMinRxDropped	Gauge32,
                stuAtmStatsPrevMinCRCErrors     Gauge32,
		stuAtmStatsClearStats	INTEGER }

	stuAtmStuMacAddr OBJECT-TYPE 
                SYNTAX  MacAddress
                MAX-ACCESS  read-only
                STATUS  current
                DESCRIPTION "
                        Contains IEEE 802 medium access control address of
                        the ComPort device. Held on ComController."
		::= { com21StuQStatsEntry 1 }

	stuAtmStuQNo OBJECT-TYPE 
                SYNTAX  Integer32
                MAX-ACCESS  read-only
                STATUS  current
                DESCRIPTION "
                        This index consists of a number representing a
			Mongoose queue. For initial phase this number
			shall equal the associated VCI number. i.e.
			Ethernet or Telephony VCIs. This VCI number 
			shall be mapped to a Mongoose queue id by the
			ComController. For 3.0 there is only a single
			Ethernet queue - queue 5."
		::= { com21StuQStatsEntry 2 }

        stuAtmStatsCurrMinRx OBJECT-TYPE
                SYNTAX Gauge32
                MAX-ACCESS read-only
                STATUS current
                DESCRIPTION "
                        Represents the number of cells or frames successfully 
			received in the current 15 minute period."
                ::= { com21StuQStatsEntry 3 }
 
        stuAtmStatsCurrMinRxDropped OBJECT-TYPE
                SYNTAX Gauge32
                MAX-ACCESS read-only
                STATUS current
                DESCRIPTION "
                        Represents the number of cells or frames dropped in 
			the current 15 minute period."
                ::= { com21StuQStatsEntry 4 }
 
        stuAtmStatsCurrMinCRCErrors OBJECT-TYPE
                SYNTAX Gauge32
                MAX-ACCESS read-only
                STATUS current
                DESCRIPTION "
                        Represents the number of cells or frames received with 
			CRC errors in the current 15 minute period."
                ::= { com21StuQStatsEntry 5 }

        stuAtmStatsPrevMinRx OBJECT-TYPE
                SYNTAX Gauge32
                MAX-ACCESS read-only
                STATUS current
                DESCRIPTION "
                        Represents the number of cells or frames successfully 
			received in the previous 15 minute period."
                ::= { com21StuQStatsEntry 6 }
 
        stuAtmStatsPrevMinRxDropped OBJECT-TYPE
                SYNTAX Gauge32
                MAX-ACCESS read-only
                STATUS current
                DESCRIPTION "
                        Represents the number of cells or frames dropped in 
			the previous 15 minute period."
                ::= { com21StuQStatsEntry 7 }
 
        stuAtmStatsPrevMinCRCErrors OBJECT-TYPE
                SYNTAX Gauge32
                MAX-ACCESS read-only
                STATUS current
                DESCRIPTION "
                        Represents the number of cells or frames received with 
			CRC errors in the previous 15 minute period."
                ::= { com21StuQStatsEntry 8 }

        stuAtmStatsClearStats OBJECT-TYPE
                SYNTAX INTEGER { nil(1), clear(2) }
                MAX-ACCESS read-write
                STATUS current
                DESCRIPTION "
                        This attribute is used to clear the ComPort
                        queue statistics counters in this group. This 
			operation is only possible if the hcxStatsControl 
			attribute is set to wrapCurr."
                ::= { com21StuQStatsEntry 9 }



        -- -- -- -- -- -- -- -- -- -- -- -- -- -- -- -- -- -- -- -- -- -- -- --
        -- -- -- -- -- -- -- -- -- -- -- -- -- -- -- -- -- -- -- -- -- -- -- --
        --
        -- com21StuImageTable
        --
        -- defines the attributes associated with each of the component
	-- ComPort images.
        --
        -- -- -- -- -- -- -- -- -- -- -- -- -- -- -- -- -- -- -- -- -- -- -- --
        -- -- -- -- -- -- -- -- -- -- -- -- -- -- -- -- -- -- -- -- -- -- -- --

        com21StuCodeImageTable OBJECT-TYPE
                SYNTAX  SEQUENCE OF StuCodeImageEntry
                MAX-ACCESS  not-accessible
                STATUS  current
                DESCRIPTION "."
                ::= { com21StuCodeImageGroup 1 }
 
        com21StuCodeImageEntry OBJECT-TYPE
                SYNTAX  StuCodeImageEntry
                MAX-ACCESS  not-accessible
                STATUS  current
                DESCRIPTION "."
                INDEX { stuCodeStuMacAddr, stuCodeImageIndex }
                ::= { com21StuCodeImageTable 1 }
 
        StuCodeImageEntry ::= SEQUENCE {
		stuCodeStuMacAddr	   MacAddress,
		stuCodeImageIndex	   INTEGER,
		stuCodeImageType           INTEGER,
		stuCodeImageVersion        DisplayString,
		stuCodeImageBuildDir       DisplayString,
		stuCodeImageDate           DisplayString,
		stuCodeImageTime           DisplayString }

        stuCodeStuMacAddr OBJECT-TYPE 
                SYNTAX MacAddress
                MAX-ACCESS read-only
                STATUS current
                DESCRIPTION "
                        Contains IEEE 802 medium access control address of
                        the ComPort device. Held on ComController."
                ::= { com21StuCodeImageEntry 1 }

	stuCodeImageIndex OBJECT-TYPE
		SYNTAX INTEGER { 
				vxWorksImage(1), 
			  	applicationStu(2), 
				downloadImage(3) }
		MAX-ACCESS read-only
		STATUS current
		DESCRIPTION "
			Index to receive information about various images;
		        VxWorks        - operating system.
		        ApplicationStu - Image comprising Stu Application,
		        DownloadImage  - Image downloaded into DRAM."
		::= { com21StuCodeImageEntry 2 }


        stuCodeImageType OBJECT-TYPE 
                SYNTAX INTEGER { 
                                stuBoot(1), 
                                reserved1(2), 
                                stuNewapp(3),
                                stuDnld(4),
                                updateApp(5),
                                reserved2(6), 
                                reserved3(7), 
                                reserved4(8), 
                                updateBoth(9),
                                reserved5(10),
                                vxWorks(11) }
                MAX-ACCESS read-only
                STATUS current
                DESCRIPTION "
			Code image identifier.
                	vxWorks    - boot code and OS, boot memory resident,
                  	stuBoot    - backup application image, boot memory 
			             resident,
                 	stuNewapp  - primary application image, app memory 
			             resident,
                  	stuDnld    - downloaded application supplement 
			             (optional),
                  	updateApp  - downloaded flash update, updates app flash,
                  	updateBoth - downloaded flash update, updates boot+app 
			             flash."
                ::= { com21StuCodeImageEntry 3 }

	stuCodeImageVersion OBJECT-TYPE
		SYNTAX DisplayString (SIZE(40))
		MAX-ACCESS read-only
                STATUS current 
                DESCRIPTION "
			 Version Description for the Code Image."
                ::= { com21StuCodeImageEntry 4 }    
 
	stuCodeImageBuildDir OBJECT-TYPE 
                SYNTAX DisplayString (SIZE(80))
		MAX-ACCESS read-only
		STATUS current
		DESCRIPTION "
			Directory name where image was built."
                ::= { com21StuCodeImageEntry 5 }

	stuCodeImageDate OBJECT-TYPE
		SYNTAX DisplayString (SIZE(12))
		MAX-ACCESS read-only
		STATUS current
		DESCRIPTION "
			Date when the image is built."
                ::= { com21StuCodeImageEntry 6 }

	stuCodeImageTime OBJECT-TYPE 
                SYNTAX DisplayString (SIZE(9))
                MAX-ACCESS read-only 
                STATUS current 
                DESCRIPTION " 
                        Time when the image is built." 
                ::= { com21StuCodeImageEntry 7 } 



        -- -- -- -- -- -- -- -- -- -- -- -- -- -- -- -- -- -- -- -- -- -- -- --
        -- -- -- -- -- -- -- -- -- -- -- -- -- -- -- -- -- -- -- -- -- -- -- --
        --
        -- com21StuVoiceChanStatsGroup
        --
        -- This group defines the Voice Channel Statistics on each Comport 
	-- device
        --
        -- -- -- -- -- -- -- -- -- -- -- -- -- -- -- -- -- -- -- -- -- -- -- --
        -- -- -- -- -- -- -- -- -- -- -- -- -- -- -- -- -- -- -- -- -- -- -- --
 
        com21StuVoiceChanStatsTable OBJECT-TYPE
                SYNTAX SEQUENCE OF StuVoiceChanStatsEntry
                MAX-ACCESS not-accessible
                STATUS current
                DESCRIPTION "."
                ::= { com21StuVoiceChanStatsGroup 1 }
 
        com21StuVoiceChanStatsEntry OBJECT-TYPE
                SYNTAX StuVoiceChanStatsEntry
                MAX-ACCESS not-accessible
                STATUS current
                DESCRIPTION "."
                INDEX { stuVoiceChanStatsMacAddr, stuVoiceChanStatsNum }
                ::= { com21StuVoiceChanStatsTable 1 }
 
        StuVoiceChanStatsEntry ::= SEQUENCE {
                stuVoiceChanStatsMacAddr                MacAddress,
                stuVoiceChanStatsNum                    INTEGER,
                stuVoiceChanStatsCurrLostCellCnt        Gauge32,
                stuVoiceChanStatsCurrDrpdCellCnt        Gauge32,
                stuVoiceChanStatsCurrCrc3ErrCnt         Gauge32,
                stuVoiceChanStatsCurrSetUpFailCnt       Gauge32,
                stuVoiceChanStatsCurrTxVoiceCellCnt     Gauge32,
                stuVoiceChanStatsCurrRxVoiceCellCnt     Gauge32,
                stuVoiceChanStatsCurrTxOamCellCnt       Gauge32,
                stuVoiceChanStatsCurrRxOamCellCnt       Gauge32,
                stuVoiceChanStatsPrevLostCellCnt        Gauge32,
                stuVoiceChanStatsPrevDrpdCellCnt        Gauge32,
                stuVoiceChanStatsPrevCrc3ErrCnt         Gauge32,
                stuVoiceChanStatsPrevSetUpFailCnt       Gauge32,
                stuVoiceChanStatsPrevTxVoiceCellCnt     Gauge32,
                stuVoiceChanStatsPrevRxVoiceCellCnt     Gauge32,
                stuVoiceChanStatsPrevTxOamCellCnt       Gauge32,
                stuVoiceChanStatsPrevRxOamCellCnt       Gauge32,
                stuVoiceChanStatsClear                  INTEGER }
 
        stuVoiceChanStatsMacAddr OBJECT-TYPE
                SYNTAX MacAddress
                MAX-ACCESS read-only
                STATUS current
                DESCRIPTION "
                        Contains IEEE 802 medium access control address
                        of the ComPort device."
                ::= { com21StuVoiceChanStatsEntry 1 }
 
 
        stuVoiceChanStatsNum OBJECT-TYPE
                SYNTAX INTEGER ( 1..2 )
                MAX-ACCESS read-only
                STATUS current
                DESCRIPTION "
                        Defines the voice port on the Comport device used
                        for Voice. "
                ::= { com21StuVoiceChanStatsEntry 2 }
 
        stuVoiceChanStatsCurrLostCellCnt OBJECT-TYPE
                SYNTAX Integer32
                MAX-ACCESS read-only
                STATUS current
                DESCRIPTION "
                        Defines the number of times the Comport's voice port
                        received Cells out of sequence in the current
                        15-min period."
                ::= { com21StuVoiceChanStatsEntry 3 }

        stuVoiceChanStatsCurrDrpdCellCnt OBJECT-TYPE
                SYNTAX Integer32
                MAX-ACCESS read-only
                STATUS current
                DESCRIPTION "
                        Defines the number of times the Comport's voice port
                        dropped cells due to Queue Full in the current
                        15-min period."
                ::= { com21StuVoiceChanStatsEntry 4 }
 
        stuVoiceChanStatsCurrCrc3ErrCnt OBJECT-TYPE
                SYNTAX Integer32
                MAX-ACCESS read-only
                STATUS current
                DESCRIPTION "
                        Defines the number of cells  Comport's voice port
                        received with CRC3 Errors in the current 15-min period."
                ::= { com21StuVoiceChanStatsEntry 5 }
 
        stuVoiceChanStatsCurrSetUpFailCnt OBJECT-TYPE
                SYNTAX Integer32
                MAX-ACCESS read-only
                STATUS current
                DESCRIPTION "
                        Defines the number of times the Comport's voice port
                        had to drop the calls due to Call Setup Failure in the current
                        15-min period."
                ::= { com21StuVoiceChanStatsEntry 6 }
 
        stuVoiceChanStatsCurrTxVoiceCellCnt OBJECT-TYPE
                SYNTAX Integer32
                MAX-ACCESS read-only
                STATUS current
                DESCRIPTION "
                        Defines the number of Voice cells Comport's voice port
                        Queued to Transmit in the current 15-min period."
                ::= { com21StuVoiceChanStatsEntry 7 }
 
        stuVoiceChanStatsCurrRxVoiceCellCnt OBJECT-TYPE
                SYNTAX Integer32
                MAX-ACCESS read-only
                STATUS current
                DESCRIPTION "
                        Defines the number of Voice cells the Comport's voice port
                        received in the current 15-min period."
                ::= { com21StuVoiceChanStatsEntry 8 }
 
        stuVoiceChanStatsCurrTxOamCellCnt OBJECT-TYPE
                SYNTAX Integer32
                MAX-ACCESS read-only
                STATUS current
                DESCRIPTION "
                        Defines the number of OAM cells Comport's voice port
                        Queued to Transmit in the current 15-min period."
                ::= { com21StuVoiceChanStatsEntry 9 }
 
        stuVoiceChanStatsCurrRxOamCellCnt OBJECT-TYPE
                SYNTAX Integer32
                MAX-ACCESS read-only
                STATUS current
                DESCRIPTION "
                        Defines the number of OAM cells the Comport's voice port
                        received in the current 15-min period."
                ::= { com21StuVoiceChanStatsEntry 10 }
 
        stuVoiceChanStatsPrevLostCellCnt OBJECT-TYPE
                SYNTAX Integer32
                MAX-ACCESS read-only
                STATUS current
                DESCRIPTION "
                        Defines the number of times the Comport's voice port
                        received Cells out of sequence in the previous
                        15-min period."
                ::= { com21StuVoiceChanStatsEntry 11 }
 
        stuVoiceChanStatsPrevDrpdCellCnt OBJECT-TYPE
                SYNTAX Integer32
                MAX-ACCESS read-only
                STATUS current
                DESCRIPTION "
                        Defines the number of times the Comport's voice port
                        dropped cells due to Queue Full in the previous
                        15-min period."
                ::= { com21StuVoiceChanStatsEntry 12 }
 
        stuVoiceChanStatsPrevCrc3ErrCnt OBJECT-TYPE
                SYNTAX Integer32
                MAX-ACCESS read-only
                STATUS current
                DESCRIPTION "
                        Defines the number of cells  Comport's voice port
                        received with CRC3 Errors in the previous 15-min period."
                ::= { com21StuVoiceChanStatsEntry 13 }
 
        stuVoiceChanStatsPrevSetUpFailCnt OBJECT-TYPE
                SYNTAX Integer32
                MAX-ACCESS read-only
                STATUS current
                DESCRIPTION "
                        Defines the number of times the Comport's voice port
                        had to drop the calls due to Call Setup Failure in the previous
                        15-min period."
                ::= { com21StuVoiceChanStatsEntry 14 }
 
        stuVoiceChanStatsPrevTxVoiceCellCnt OBJECT-TYPE
                SYNTAX Integer32
                MAX-ACCESS read-only
                STATUS current
                DESCRIPTION "
                        Defines the number of Voice cells Comport's voice port
                        Tranmitted in the previous 15-min period"
                ::= { com21StuVoiceChanStatsEntry 15 }
 
        stuVoiceChanStatsPrevRxVoiceCellCnt OBJECT-TYPE
                SYNTAX Integer32
                MAX-ACCESS read-only
                STATUS current
                DESCRIPTION "
                        Defines the number of times the Comport's voice port
                        received Cells out of sequence in the previous
                        15-min period."
                ::= { com21StuVoiceChanStatsEntry 16 }
 
        stuVoiceChanStatsPrevTxOamCellCnt OBJECT-TYPE
                SYNTAX Integer32
                MAX-ACCESS read-only
                STATUS current
                DESCRIPTION "
                        Defines the number of times the Comport's voice port
                        received Cells out of sequence in the previous
                        15-min period."
                ::= { com21StuVoiceChanStatsEntry 17 }
 
        stuVoiceChanStatsPrevRxOamCellCnt OBJECT-TYPE
                SYNTAX Integer32
                MAX-ACCESS read-only
                STATUS current
                DESCRIPTION "
                        Defines the number of times the Comport's voice port
                        received Cells out of sequence in the previous
                        15-min period."
                ::= { com21StuVoiceChanStatsEntry 18 }
 
        stuVoiceChanStatsClear OBJECT-TYPE
                SYNTAX INTEGER { nil (1), clear (2) }
                MAX-ACCESS read-write
                STATUS current
                DESCRIPTION "
                        Provides the capability to clear the statistics.
                        Clearing of statistics allowed only if hcxStatsControl
                        attribute is set to wrapCurr."
                ::= { com21StuVoiceChanStatsEntry 19 }

END
