-- 
--  Copyright 1996, Com21 Inc.  All Rights Reserved.
--
 
COM21-HCXETH-MIB DEFINITIONS ::= BEGIN
        IMPORTS
        MODULE-IDENTITY, OBJECT-TYPE, NOTIFICATION-TYPE, Integer32,
        IpAddress, Gauge32
        FROM SNMPv2-SMI
        MacAddress, DisplayString
        FROM SNMPv2-TC
        com21, com21Hcx
        FROM COM21-HCX-MIB
        com21Traps FROM COM21-HCX-MIB
		  hcxAlmSeverity, hcxEventLogTime
        FROM COM21-HCXALM-MIB;


        com21HcxEth MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"

                DESCRIPTION
                        "This is the Com21 ComController Ethernet 
			   MIB module. COM21 Part# 005-0025-00"
                ::= { com21Hcx 40 }

        com21HcxEtherUnitGroup          OBJECT IDENTIFIER ::= {com21Hcx 41}
        com21HcxEtherPortGroup          OBJECT IDENTIFIER ::= {com21Hcx 42}
	com21HcxEtherStatsGroup		OBJECT IDENTIFIER ::= {com21Hcx 43}
	com21HcxEtherIpAddrGroup	OBJECT IDENTIFIER ::= {com21Hcx 44}
	com21HcxEtherStuStatsGroup	OBJECT IDENTIFIER ::= {com21Hcx 45}
        com21HcxServGrpAssocGroup       OBJECT IDENTIFIER ::= {com21Hcx 46}

        PrimServiceState ::= INTEGER { is(1), oos(2) }
        Com21RowStatus   ::= INTEGER { active(1), 
				       create(2), 
				       destroy(3),
				       deactive(4) }


        -- -- -- -- -- -- -- -- -- -- -- -- -- -- -- -- -- -- -- -- -- -- -- --
        -- -- -- -- -- -- -- -- -- -- -- -- -- -- -- -- -- -- -- -- -- -- -- --
        --
        -- COM21 ComController Enterprise MIB
        --
        -- This MIB contains SNMP Groups and Attributes definitions for COM21
        -- specific management.
        -- Also supported by the ComController shall be the MIB II for the 
	-- SNMP interface and the MIB II Interfaces Group for both the 
	-- ComController and ComPort Ethernet interfaces.
        -- This Enterprise MIB contains many elements of the ATM UNI 2.1 ILMI
        -- MIB. This full MIB is not presently supported by the COM21 equipment
        -- as there are no external UNI interfaces. When this changes then the
        -- full MIB should be supported and the related Enterprise MIB entries
        -- removed.
        --
        --   com21HcxEtherUnitGroup      - this group provides for the
        --                                 management of Ethernet card level
        --                                 functionality.
        --
        --   com21HcxEtherPortGroup      - this group provides for the control
        --                                 of the port level (VLAN) Ethernet
        --                                 configuration.
	--
	--   com21HcxEtherStatsGroup     - defines port level statistics.
	--
	--   com21HcxEtherStuStatsGroup  - defines ComPort level statistics.
        --
        --   com21HcxServGrpAssocGroup   - details the Services Groups
        --                                 active on an WAN port.
        --
        -- -- -- -- -- -- -- -- -- -- -- -- -- -- -- -- -- -- -- -- -- -- -- --
        -- -- -- -- -- -- -- -- -- -- -- -- -- -- -- -- -- -- -- -- -- -- -- --



        -- -- -- -- -- -- -- -- -- -- -- -- -- -- -- -- -- -- -- -- -- -- -- --
        -- -- -- -- -- -- -- -- -- -- -- -- -- -- -- -- -- -- -- -- -- -- -- --
        --
        -- com21HcxEtherUnitGroup
        --
        -- defines the attributes related to the management of the Ethernet
	-- Unit. For the purposes of this MIB, all ethernet card types shall 
	-- be managed by this group. The exact type and number of ports shall
	-- be defined within the group.
        --
        -- -- -- -- -- -- -- -- -- -- -- -- -- -- -- -- -- -- -- -- -- -- -- --
        -- -- -- -- -- -- -- -- -- -- -- -- -- -- -- -- -- -- -- -- -- -- -- --

        com21HcxEtherUnitTable OBJECT-TYPE
                SYNTAX  SEQUENCE OF HcxEtherUnitEntry
                MAX-ACCESS  not-accessible
                STATUS  current
                DESCRIPTION "."
                ::= { com21HcxEtherUnitGroup 1 }
 
        com21HcxEtherUnitEntry OBJECT-TYPE
                SYNTAX  HcxEtherUnitEntry
                MAX-ACCESS  not-accessible
                STATUS  current
                DESCRIPTION "."
                INDEX { hcxEtherShelfId, hcxEtherSlotId }
                ::= { com21HcxEtherUnitTable 1 }

        HcxEtherUnitEntry ::= SEQUENCE { 
		hcxEtherShelfId			INTEGER,
		hcxEtherSlotId			Integer32,
		hcxEtherCardType		INTEGER,
		hcxEtherNoPorts			INTEGER,
		hcxEtherHardwareVersion		DisplayString,
		hcxEtherBootVersion		DisplayString,
		hcxEtherUnitPrimServState	PrimServiceState,
		hcxEtherUnitSecServState	DisplayString,
		hcxEtherRestartAction		INTEGER,
		hcxEtherTestStatusLed		INTEGER,
		hcxEtherFaultStatusLed          INTEGER,
		hcxEtherSerialNumber		DisplayString }

        hcxEtherShelfId OBJECT-TYPE
                SYNTAX INTEGER (1..2)
                MAX-ACCESS read-only
                STATUS current
                DESCRIPTION "
                        contains the associated shelf id."
                ::= { com21HcxEtherUnitEntry 1 }

        hcxEtherSlotId OBJECT-TYPE
                SYNTAX Integer32
                MAX-ACCESS read-only
                STATUS current
                DESCRIPTION "
                        contains associated slot id."
                ::= { com21HcxEtherUnitEntry 2 }

        hcxEtherCardType OBJECT-TYPE
                SYNTAX INTEGER {
			tenBaseT (1),
			onehundredBaseT (2) }
                MAX-ACCESS read-only
                STATUS current
                DESCRIPTION "
                        contains Ethernet card type."
                ::= { com21HcxEtherUnitEntry 3 }

        hcxEtherNoPorts OBJECT-TYPE
                SYNTAX INTEGER (1..4)
                MAX-ACCESS read-only
                STATUS current
                DESCRIPTION "
                        contains the number of ports supported by the
			Ethernet card."
                ::= { com21HcxEtherUnitEntry 4 }

        hcxEtherHardwareVersion OBJECT-TYPE
                SYNTAX DisplayString (SIZE (16))
                MAX-ACCESS read-only
                STATUS current
                DESCRIPTION "
                        contains the hardware version of the Ethernet
                        card. Will contain empty string if card has not
			been inserted in the slot."
                ::= { com21HcxEtherUnitEntry 5 }

        hcxEtherBootVersion OBJECT-TYPE
                SYNTAX DisplayString (SIZE (16))
                MAX-ACCESS read-only
                STATUS current
                DESCRIPTION "
                        contains the version of the Ethernet card boot ROM.
			Will contain empty string if card has not been 
			inserted in the slot."
                ::= { com21HcxEtherUnitEntry 6 }

        hcxEtherUnitPrimServState OBJECT-TYPE
                SYNTAX PrimServiceState
                MAX-ACCESS read-only
                STATUS current
                DESCRIPTION "
                        contains primary service state of the Ethernet
                        Unit."
                ::= { com21HcxEtherUnitEntry 7 }

        hcxEtherUnitPrimStateChange NOTIFICATION-TYPE
                OBJECTS { hcxAlmSeverity, hcxEventLogTime,
                            hcxEtherShelfId, hcxEtherSlotId, 
			    hcxEtherUnitPrimServState }
                STATUS current
                DESCRIPTION "
			This trap is generated whenever a change in the
			the hcxEtherUnitPrimServState occurs. This an event 
			with no clear condition. Only severity is WARNING."
                ::= { com21Traps 20 }

        hcxEtherUnitSecServState OBJECT-TYPE
                SYNTAX DisplayString (SIZE (16))
                MAX-ACCESS read-only
                STATUS current
                DESCRIPTION "
                        contains a string defining the secondary service states
                        of the Ethernet Unit. The substrings supported by 
			the Ethernet Unit shall be: UNEQ - unequipped."
                ::= { com21HcxEtherUnitEntry 8 }

        hcxEtherUnitSecStateChange NOTIFICATION-TYPE
                OBJECTS { hcxAlmSeverity, hcxEventLogTime,
                            hcxEtherShelfId, hcxEtherSlotId, 
			    hcxEtherUnitSecServState }
                STATUS current
                DESCRIPTION "
			This trap is generated whenever a change in the
			the hcxEtherUnitSecServState occurs. This an event 
                        with no clear condition. Only severity is WARNING."
                ::= { com21Traps 21 }

	hcxEtherRestartAction OBJECT-TYPE
		SYNTAX INTEGER {
				nil(1),
				restart(2) }
                MAX-ACCESS read-write
                STATUS current
                DESCRIPTION "
                        The Ethernet Unit Restart Action is an active-value.
			The setting of this attribute to restart(2) causes
			the Ethernet card to reset and download a new image."
                ::= { com21HcxEtherUnitEntry 9 }

        hcxEtherTestStatusLed OBJECT-TYPE
                SYNTAX INTEGER { on (1), off (2) }
                MAX-ACCESS read-only
                STATUS current
                DESCRIPTION "
                        The Ethernet Test Status LED is a read-only 
			attribute which describes the condition of the 
			Ethernet Test Status light emitting diode 
			located on the Ethernet board. A value of on(1) 
			indicates that a service effecting test is in 
			progress and that the LED is illuminated. Will
			be off if no card present."
                ::= { com21HcxEtherUnitEntry 10 }

        hcxEtherTestStatusLedChange NOTIFICATION-TYPE
                OBJECTS { hcxAlmSeverity, hcxEventLogTime,
                            hcxEtherShelfId, hcxEtherSlotId, 
                            hcxEtherTestStatusLed }
                STATUS current
                DESCRIPTION "
                        generated whenever there is a change in test LED
                        status. This an event with no clear condition.
                        Only severity is WARNING."
                ::= { com21Traps 22 }

        hcxEtherFaultStatusLed OBJECT-TYPE
                SYNTAX INTEGER { on (1), off (2) }
                MAX-ACCESS read-only
                STATUS current
                DESCRIPTION "
                        The Ethernet Fault Status LED is a read-only 
			attribute which describes the condition of the 
			Ethernet Fault Status light emitting diode 
			located on the Ethernet board. A value of on(1) 
			indicates that an fault condition has been detected 
			(for which a trap will have been issued) and the 
			LED is illuminated. Will be off if no card present."
                ::= { com21HcxEtherUnitEntry 11 }
 
        hcxEtherFaultStatusLedChange NOTIFICATION-TYPE
                OBJECTS { hcxAlmSeverity, hcxEventLogTime,
                            hcxEtherShelfId, hcxEtherSlotId, 
                            hcxEtherFaultStatusLed }
                STATUS current
                DESCRIPTION "
                        generated whenever there is a change in the Fault
                        LED status. This an event with no clear condition.
                        Only severity is WARNING."
                ::= { com21Traps 23 }

        hcxEtherSerialNumber OBJECT-TYPE
                SYNTAX DisplayString (SIZE (16))
                MAX-ACCESS read-only
                STATUS current
                DESCRIPTION "
                        contains the serial number of the Ethernet card.
                        Will contain empty string if card has not been
                        inserted in the slot."
                ::= { com21HcxEtherUnitEntry 12 }
 


        -- -- -- -- -- -- -- -- -- -- -- -- -- -- -- -- -- -- -- -- -- -- -- --
        -- -- -- -- -- -- -- -- -- -- -- -- -- -- -- -- -- -- -- -- -- -- -- --
        --
        -- com21HcxEtherPortGroup
        --
        -- defines the attributes related to the management of a single
	-- Ethernet port. 
        --
        -- -- -- -- -- -- -- -- -- -- -- -- -- -- -- -- -- -- -- -- -- -- -- --
        -- -- -- -- -- -- -- -- -- -- -- -- -- -- -- -- -- -- -- -- -- -- -- --

        com21HcxEtherPortTable OBJECT-TYPE
                SYNTAX  SEQUENCE OF HcxEtherPortEntry
                MAX-ACCESS  not-accessible
                STATUS  current
                DESCRIPTION "."
                ::= { com21HcxEtherPortGroup 1 }
 
        com21HcxEtherPortEntry OBJECT-TYPE
                SYNTAX  HcxEtherPortEntry
                MAX-ACCESS  not-accessible
                STATUS  current
                DESCRIPTION "."
                INDEX { hcxEtherPortShelfId, hcxEtherPortSlotId, hcxEtherPortId }
                ::= { com21HcxEtherPortTable 1 }

        HcxEtherPortEntry ::= SEQUENCE { 
		hcxEtherPortShelfId		INTEGER,
		hcxEtherPortSlotId		Integer32,
		hcxEtherPortId			INTEGER,
		hcxEtherPortType		INTEGER,
		hcxEtherPortService		DisplayString,
		hcxEtherPortPrimServState	PrimServiceState,
		hcxEtherPortSecServState	DisplayString,
		hcxEtherMaxBandwidth		INTEGER,
		hcxEtherAggrDnStrmCbrRate	Integer32,
		hcxEtherAggrDnStrmPcrRate	Integer32,
		hcxEtherAggrUpStrmCbrRate	Integer32,
		hcxEtherAggrUpStrmMinRate	Integer32,
		hcxEtherAggrUpStrmMaxRate	Integer32,
		hcxEtherAgeTime			Integer32,
		hcxEtherPortConfigState		INTEGER,
		hcxEtherPortRestartAction	INTEGER,
		hcxEtherPortDiagTestAction	INTEGER,
		hcxEtherPortDiagTestResult	INTEGER,
		hcxEtherPortLinkStatusLed	INTEGER,
		hcxEtherPortArpFiltRate		INTEGER,
		hcxEtherAggrActDnStrmCbrRate	Integer32,
		hcxEtherAggrActDnStrmPcrRate	Integer32,
		hcxEtherAggrActUpStrmCbrRate	Integer32,
		hcxEtherAggrActUpStrmMinRate	Integer32,
		hcxEtherAggrActUpStrmMaxRate	Integer32,
		hcxEtherPortIpAddr		IpAddress,
                hcxEtherPortIpMask     		IpAddress,
		hcxEtherPortMacAddr		MacAddress,
		hcxEtherPortAutoNegEnable	INTEGER,
		hcxEtherPortSpeedSelect		INTEGER,
		hcxEtherCurrPortState		INTEGER }

        hcxEtherPortShelfId OBJECT-TYPE
                SYNTAX INTEGER (1..2)
                MAX-ACCESS read-only
                STATUS current
                DESCRIPTION "
                        contains shelf in which this Ethernet port is
			located."
                ::= { com21HcxEtherPortEntry 1 }

        hcxEtherPortSlotId OBJECT-TYPE
                SYNTAX Integer32
                MAX-ACCESS read-only
                STATUS current
                DESCRIPTION "
                        contains slot in which this Ethernet port is
			located."
                ::= { com21HcxEtherPortEntry 2 }

        hcxEtherPortId OBJECT-TYPE
                SYNTAX INTEGER (1..4)
                MAX-ACCESS read-only
                STATUS current
                DESCRIPTION "
                        contains Ethernet port id. Represents the port
			number on the card. In the case of single 10baseT
			or 100baseT, this value will always be 1. In the
			case of a quad 10baseT card, this value is in the
			range 1-4."
                ::= { com21HcxEtherPortEntry 3 }

        hcxEtherPortType OBJECT-TYPE
                SYNTAX INTEGER {
			tenBaseT (1),
                        onehundredBaseT (2) }
                MAX-ACCESS read-only
                STATUS current
                DESCRIPTION "
                        contains type of Ethernet port."
                ::= { com21HcxEtherPortEntry 4 }

	hcxEtherPortService OBJECT-TYPE
                SYNTAX DisplayString (SIZE(32))
                MAX-ACCESS read-write
                STATUS current
                DESCRIPTION "  
                        contains string defining the service provided by
			the Ethernet port (VLAN). Set by NMAPS. Default
			null string. CC most ensure uniqueness." 
                ::= { com21HcxEtherPortEntry 5 }
 
        hcxEtherPortPrimServState OBJECT-TYPE
                SYNTAX PrimServiceState
                MAX-ACCESS read-only
                STATUS current
                DESCRIPTION "
                        contains primary service state of the Ethernet
                        Unit. This state shall be effected by the
			hcxEtherPortState attribute."
                ::= { com21HcxEtherPortEntry 6 }

        hcxEtherPortPrimStateChange NOTIFICATION-TYPE
                OBJECTS { hcxAlmSeverity, hcxEventLogTime,
		            hcxEtherPortShelfId, hcxEtherPortSlotId,
			    hcxEtherPortId, hcxEtherPortPrimServState }
                STATUS current
                DESCRIPTION "
			This trap is generated whenever a change in the
			the hcxEtherPortPrimServState occurs. This an event
                        with no clear condition. Only severity is WARNING."
                ::= { com21Traps 24 }

        hcxEtherPortSecServState OBJECT-TYPE
                SYNTAX DisplayString (SIZE (16))
                MAX-ACCESS read-only
                STATUS current
                DESCRIPTION "
                        contains a string defining the secondary service states
                        of the Ethernet Unit. The substrings supported by 
			the Ethernet Unit shall be: MT - offline, set by
                        hcxEthernetUnitState, FAULT - hardware failure, TEST
			- test, UNEQ - unequipped."
                ::= { com21HcxEtherPortEntry 7 }

        hcxEtherPortSecStateChange NOTIFICATION-TYPE
                OBJECTS { hcxAlmSeverity, hcxEventLogTime,
		            hcxEtherPortShelfId, hcxEtherPortSlotId,
		            hcxEtherPortId, hcxEtherPortSecServState }
                STATUS current
                DESCRIPTION "
			This trap is generated whenever a change in the
			the hcxEtherPortSecServState occurs. This an event
                        with no clear condition. Only severity is WARNING."
                ::= { com21Traps 25 }

        -- -- -- -- -- -- -- -- -- -- -- -- -- -- -- -- -- -- -- -- -- -- -- --
        -- -- -- 1 Attribute Deprecated
        -- -- -- -- -- -- -- -- -- -- -- -- -- -- -- -- -- -- -- -- -- -- -- --

        hcxEtherMaxBandwidth OBJECT-TYPE
                SYNTAX INTEGER (0..22222)
                MAX-ACCESS read-write
                STATUS current
                DESCRIPTION "
                        This attribute defines the maximum output payload
			bandwidth associated with the Ethernet port. Defined 
			in thousands of bps. From 0 to 22222. This value shall
			be checked by the CC which shall ensure that
			the aggregate of the hcxEtherMaxBandwidth attributes
			for each of the Ethernet ports does not exceed
			the system maximum. Note max for 10bT port is 11560.
			Default: 7000."
                ::= { com21HcxEtherPortEntry 9 }

        -- -- -- -- -- -- -- -- -- -- -- -- -- -- -- -- -- -- -- -- -- -- -- --
        -- -- -- 2 Attribute Deprecated
        -- -- -- -- -- -- -- -- -- -- -- -- -- -- -- -- -- -- -- -- -- -- -- --

 
	hcxEtherAggrDnStrmCbrRate OBJECT-TYPE
                SYNTAX Integer32
                MAX-ACCESS read-only
                STATUS current
                DESCRIPTION "
                        This attribute specifies the aggregate of all ComPort
                        downstream CBR rates configured on the Ethernet port 
			(VLAN). This includes both acquired and unacquired
			ComPorts. Defined in Kbps."
                ::= { com21HcxEtherPortEntry 12 }

	hcxEtherAggrDnStrmPcrRate OBJECT-TYPE
                SYNTAX Integer32
                MAX-ACCESS read-only
                STATUS current
                DESCRIPTION "
                        This attribute specifies the aggregate of all ComPort
                        downstream PCR rates configured on the Ethernet port 
			(VLAN). This includes both acquired and unacquired 
			ComPorts. Defined in Kbps."
                ::= { com21HcxEtherPortEntry 13 }

	hcxEtherAggrUpStrmCbrRate OBJECT-TYPE
                SYNTAX Integer32
                MAX-ACCESS read-only
                STATUS current
                DESCRIPTION "
                        This attribute specifies the aggregate of all ComPort
                        upstream CBR rates configured on the Ethernet port 
			(VLAN). This includes both acquired and unacquired 
			ComPorts. Defined in Kbps."
                ::= { com21HcxEtherPortEntry 14 }

	hcxEtherAggrUpStrmMinRate OBJECT-TYPE
                SYNTAX Integer32
                MAX-ACCESS read-only
                STATUS current
                DESCRIPTION "
                        This attribute specifies the aggregate of all ComPort
                        upstream minimum PCR rates on the Ethernet port (VLAN). 
			This includes both acquired and unacquired ComPorts.
			Defined in Kbps."
                ::= { com21HcxEtherPortEntry 15 }

	hcxEtherAggrUpStrmMaxRate OBJECT-TYPE
                SYNTAX Integer32
                MAX-ACCESS read-only
                STATUS current
                DESCRIPTION "
                        This attribute specifies the aggregate of all ComPort
                        upstream maximum cell rates on the Ethernet port 
			(VLAN). This includes both acquired and unacquired 
			ComPorts. Defined in Kbps."
                ::= { com21HcxEtherPortEntry 16 }

        hcxEtherAgeTime OBJECT-TYPE
                SYNTAX Integer32
                MAX-ACCESS read-write
                STATUS current
                DESCRIPTION "
                        This attribute defines, in seconds, the aging time
			for non-accessed entries in the Bridge mapping table.
			The default shall be 300secs. If this set to 0, then
			aging is disabled."
                ::= { com21HcxEtherPortEntry 17 }

        hcxEtherPortConfigState OBJECT-TYPE
                SYNTAX INTEGER { 
			offline(2000), 
			online(2001),
			test(2002) }
                MAX-ACCESS read-write
                STATUS current
                DESCRIPTION "
                        The Ethernet Port State is an active-value. The
			Ethernet port will default to offline, in which
			case no traffic shall be passed. Default offline."
                ::= { com21HcxEtherPortEntry 18 }

	hcxEtherPortRestartAction OBJECT-TYPE
		SYNTAX INTEGER {
				nil(1),
				restart(2) }
                MAX-ACCESS read-write
                STATUS current
                DESCRIPTION "
                        The Ethernet Port Restart Action is an active-value.
			The setting of this attribute to restart(2) causes
			the Ethernet port to reset and download a new image."
                ::= { com21HcxEtherPortEntry 19 }

        hcxEtherPortDiagTestAction OBJECT-TYPE
                SYNTAX INTEGER { nil(1), execute(2) }
                MAX-ACCESS read-write
                STATUS current
                DESCRIPTION "
                        This attribute is used to invoke the internal
                        Ethernet card diagnostic test. In order to activate
                        this test, the card must be placed in the test state."
                ::= { com21HcxEtherPortEntry 20 }
 
        hcxEtherPortDiagTestComplete NOTIFICATION-TYPE
                OBJECTS { hcxAlmSeverity, hcxEventLogTime,
                            hcxEtherPortShelfId, hcxEtherPortSlotId,
                            hcxEtherPortId, hcxEtherPortDiagTestResult }
                STATUS current
                DESCRIPTION "
                        This notification is generated whenever the Ethernet
                        port internal diagnostic tests are completed. Event
                        only, no clear. Only severity allowed is WARNING."
                ::= { com21Traps 26 }
                                 
        hcxEtherPortDiagTestResult OBJECT-TYPE
                SYNTAX INTEGER { 
                                inprogress(1),
                                success(2), 
                                failure(3),
				invalidState(4) }
                MAX-ACCESS read-only
                STATUS current
                DESCRIPTION "
                        This attribute contains the result of the last
                        Ethernet port diagnostic test."
                ::= { com21HcxEtherPortEntry 21 }

        hcxEtherOperationFailure NOTIFICATION-TYPE
                OBJECTS { hcxAlmSeverity, hcxEventLogTime,
                            hcxEtherPortShelfId, hcxEtherPortSlotId,
			    hcxEtherPortId }
                STATUS current
                DESCRIPTION "
                        This notification is generated by the CC whenever
                        an Ethernet port fails to respond correctly to a
                        request. This failure could indicate either a
                        resource problem or software failure. Note that
                        if an Ethernet card failures to respond completely
                        to a CC request, then a hcxInsertChange trap shall
                        be generated. This is an event without a
                        corresponding clear. Only severity allowed is
                        WARNING."
                ::= { com21Traps 27 }

        hcxEtherPortLinkStatusLed OBJECT-TYPE
                SYNTAX INTEGER { on (1), off (2) }
                MAX-ACCESS read-only
                STATUS current
                DESCRIPTION "
                        The Ethernet Link Status LED is a read-only
                        attribute which describes the condition of the
                        Ethernet Link Status light emitting diode
                        located on the Ethernet board. A value of on(1)
                        indicates that the link is up and active, and 
			that the LED is illuminated. Will be off if no 
			card present."
                ::= { com21HcxEtherPortEntry 22 }

        hcxEtherPortLinkStatusLedChange NOTIFICATION-TYPE
                OBJECTS { hcxAlmSeverity, hcxEventLogTime,
                            hcxEtherPortShelfId, hcxEtherPortSlotId,
                            hcxEtherPortId, hcxEtherPortLinkStatusLed }
                STATUS current
                DESCRIPTION "
                        generated whenever there is a change in link LED
                        status. This an event with no clear condition.
                        Only severity is WARNING."
                ::= { com21Traps 28 }

        -- -- -- -- -- -- -- -- -- -- -- -- -- -- -- -- -- -- -- -- -- -- -- --
        -- -- -- 1 Attribute Deprecated
        -- -- -- -- -- -- -- -- -- -- -- -- -- -- -- -- -- -- -- -- -- -- -- --


        hcxEtherPortArpFiltRate OBJECT-TYPE
                SYNTAX INTEGER (10000..150000)
                MAX-ACCESS read-write
                STATUS deprecated
                DESCRIPTION "
                        No longer supported"
                ::= { com21HcxEtherPortEntry 24 }

	hcxEtherAggrActDnStrmCbrRate OBJECT-TYPE
                SYNTAX Integer32
                MAX-ACCESS read-only
                STATUS current
                DESCRIPTION "
                        This attribute specifies the aggregate of all ComPort
                        downstream CBR rates active on the Ethernet port
                        (VLAN). This includes only acquired ComPorts. Defined 
			in Kbps."
                ::= { com21HcxEtherPortEntry 25 }
 
        hcxEtherAggrActDnStrmPcrRate OBJECT-TYPE
                SYNTAX Integer32
                MAX-ACCESS read-only
                STATUS current
                DESCRIPTION "  
                        This attribute specifies the aggregate of all ComPort
                        downstream PCR rates active on the Ethernet port (VLAN).
                        This includes only acquired ComPorts. Defined in Kbps."
                ::= { com21HcxEtherPortEntry 26 }  
 
        hcxEtherAggrActUpStrmCbrRate OBJECT-TYPE
                SYNTAX Integer32
                MAX-ACCESS read-only
                STATUS current
                DESCRIPTION "  
                        This attribute specifies the aggregate of all ComPort
                        upstream CBR rates active on the Ethernet port (VLAN).    
                        This includes only acquired ComPorts. Defined in Kbps."
                ::= { com21HcxEtherPortEntry 27 }  
 
        hcxEtherAggrActUpStrmMinRate OBJECT-TYPE
                SYNTAX Integer32
                MAX-ACCESS read-only
                STATUS current
                DESCRIPTION "  
                        This attribute specifies the aggregate of all ComPort
                        upstream minimum PCR rates active on the Ethernet port 
			(VLAN). This includes only acquired ComPorts. Defined 
			in Kbps."
                ::= { com21HcxEtherPortEntry 28 }
 
        hcxEtherAggrActUpStrmMaxRate OBJECT-TYPE
                SYNTAX Integer32
                MAX-ACCESS read-only
                STATUS current
                DESCRIPTION "
                        This attribute specifies the aggregate of all ComPort
                        upstream maximum cell rates active on the Ethernet port 
			(VLAN). This includes only acquired ComPorts. Defined 
			in Kbps."
                ::= { com21HcxEtherPortEntry 29 }
 
        hcxEtherPortIpAddr OBJECT-TYPE           
                SYNTAX IpAddress
                MAX-ACCESS read-write
                STATUS current
                DESCRIPTION "
                        IP Address associated with this ethernet port. This
			is a future item for telephone return support."
                ::= { com21HcxEtherPortEntry 30 }

        hcxEtherPortIpMask OBJECT-TYPE           
                SYNTAX IpAddress
                MAX-ACCESS read-write
                STATUS current
                DESCRIPTION "
                        IP mask associated with port. Default is ff.ff.ff.ff.
			This is a future item for telephone return support."
                ::= { com21HcxEtherPortEntry 31 }

        hcxEtherPortMacAddr OBJECT-TYPE            
                SYNTAX MacAddress 
                MAX-ACCESS read-only
                STATUS current 
                DESCRIPTION "  
                        MAC address associated with port."
                ::= { com21HcxEtherPortEntry 32 }

        hcxEtherPortAutoNegEnable OBJECT-TYPE
                SYNTAX  INTEGER { on (1), off(2) }
                MAX-ACCESS  read-write
                STATUS  current
                DESCRIPTION "
                        This attribute is used for 100BaseT ports ONLY, to
                	enable/disable Auto Negotiation Feature. Default is
                	Auto Negotiation Enable. For 10bT ports this
			attribute will be read-only with a value of off."
                ::= { com21HcxEtherPortEntry 33 }

        hcxEtherPortSpeedSelect OBJECT-TYPE
                SYNTAX  INTEGER { tenMbpsHalfDuplex (1),
                                  tenMbpsFullDuplex (2),
                                  hundredMbpsHalfDulplex (3),
                                  hundredMbpsFullDuplex(4) }
                MAX-ACCESS  read-write
                STATUS  current
                DESCRIPTION "
                        If 'hcxEtherPortAutoNegEnble' is set to 'off' then
                	the Media speed of the port is set to the value in
                	this attribute.  This attribute is valid only for
                	100BaseT ports - for 10bT ports this attribute
			shall be read-only with a value of tenMbpsHalfDuplex.
			Default for 100bT ports is 'hundredMbps'. An error 
			will be returned if PortSpeed is set to 'tenMbps' 
			and 'hcxEtherMaxBandwidth' is greater than 10 Mbps"
                ::= { com21HcxEtherPortEntry 34 }

        hcxEtherCurrPortState OBJECT-TYPE         
                SYNTAX  INTEGER  { linkFail (1),
                                   autoNegPending (2),
                                   autoNegFailure (3),
                                   tenMbpsHalfDuplex (4),
                                   tenMbpsFullDuplex (5),
                                   hundredMbpsHalfDulplex (6),
                                   hundredMbpsFullDuplex(7) }
                MAX-ACCESS  read-only
                STATUS  current
                DESCRIPTION "
                        specifies the Media speed of the port."
                ::= { com21HcxEtherPortEntry 35 }



        -- -- -- -- -- -- -- -- -- -- -- -- -- -- -- -- -- -- -- -- -- -- -- --
        -- -- -- -- -- -- -- -- -- -- -- -- -- -- -- -- -- -- -- -- -- -- -- --
        --
        -- com21HcxEtherStatsGroup
        --
        -- defines the statistical attributes related to a single Ethernet
	-- port. This group is applicable to both 10bT and 100bT cards.
        --
        -- -- -- -- -- -- -- -- -- -- -- -- -- -- -- -- -- -- -- -- -- -- -- --
        -- -- -- -- -- -- -- -- -- -- -- -- -- -- -- -- -- -- -- -- -- -- -- --

        com21HcxEtherStatsTable OBJECT-TYPE
                SYNTAX  SEQUENCE OF HcxEtherStatsEntry
                MAX-ACCESS  not-accessible
                STATUS  current
                DESCRIPTION "."
                ::= { com21HcxEtherStatsGroup 1 }
 
        com21HcxEtherStatsEntry OBJECT-TYPE
                SYNTAX  HcxEtherStatsEntry
                MAX-ACCESS  not-accessible
                STATUS  current
                DESCRIPTION "."
                INDEX { hcxEtherStatsShelfId, hcxEtherStatsSlotId, hcxEtherStatsPortId }
                ::= { com21HcxEtherStatsTable 1 }

        HcxEtherStatsEntry ::= SEQUENCE { 
		hcxEtherStatsShelfId		INTEGER,
		hcxEtherStatsSlotId		Integer32,
		hcxEtherStatsPortId		INTEGER,
		hcxEtherCurrCollisions		Gauge32,
		hcxEtherCurrRunts		Gauge32,
		hcxEtherCurrGrunts		Gauge32,
		hcxEtherCurrCrcPkts		Gauge32,
		hcxEtherCurrTxPkts		Gauge32,
		hcxEtherCurrRxPkts		Gauge32,
		hcxEtherPrevCollisions		Gauge32,
		hcxEtherPrevRunts		Gauge32,
		hcxEtherPrevGrunts		Gauge32,
		hcxEtherPrevCrcPkts		Gauge32,
		hcxEtherPrevTxPkts		Gauge32,
		hcxEtherPrevRxPkts		Gauge32,
		hcxEtherClearStats		INTEGER }

        hcxEtherStatsShelfId OBJECT-TYPE
                SYNTAX INTEGER (1..2)
                MAX-ACCESS read-only
                STATUS current
                DESCRIPTION "
                        contains shelf in which the associated Ethernet 
			port is located."
                ::= { com21HcxEtherStatsEntry 1 }

        hcxEtherStatsSlotId OBJECT-TYPE
                SYNTAX Integer32
                MAX-ACCESS read-only
                STATUS current
                DESCRIPTION "
                        contains slot in which the associated Ethernet 
			port is located."
                ::= { com21HcxEtherStatsEntry 2 }

        hcxEtherStatsPortId OBJECT-TYPE
                SYNTAX INTEGER (1..4)
                MAX-ACCESS read-only
                STATUS current
                DESCRIPTION "
                        contains the associated Ethernet port id."
                ::= { com21HcxEtherStatsEntry 3 }

        hcxEtherCurrCollisions OBJECT-TYPE
                SYNTAX Gauge32
                MAX-ACCESS read-only    
                STATUS current
                DESCRIPTION "  
                        contains the number of detected collisions
			in the current 15 minute period."
                ::= { com21HcxEtherStatsEntry 4 }
	
        hcxEtherCurrRunts OBJECT-TYPE
                SYNTAX Gauge32
                MAX-ACCESS read-only    
                STATUS current
                DESCRIPTION "  
                        contains the number of receive runt packets
			in the current 15 minute period."
                ::= { com21HcxEtherStatsEntry 5 }
	
        hcxEtherCurrGrunts OBJECT-TYPE
                SYNTAX Gauge32
                MAX-ACCESS read-only    
                STATUS current
                DESCRIPTION "  
                        contains the number of received grunt packets
			in the current 15 minute period."
                ::= { com21HcxEtherStatsEntry 6 }
	
        hcxEtherCurrCrcPkts OBJECT-TYPE
                SYNTAX Gauge32
                MAX-ACCESS read-only    
                STATUS current
                DESCRIPTION "  
                        contains the number of ethernet packets with
			CRC errors received in the current 15 minute 
			period."
                ::= { com21HcxEtherStatsEntry 7 }
	
        hcxEtherCurrTxPkts OBJECT-TYPE
                SYNTAX Gauge32
                MAX-ACCESS read-only    
                STATUS current
                DESCRIPTION "  
                        contains the number of ethernet packets transmitted
			in the current 15 minute period."
                ::= { com21HcxEtherStatsEntry 8 }
	
        hcxEtherCurrRxPkts OBJECT-TYPE
                SYNTAX Gauge32
                MAX-ACCESS read-only    
                STATUS current
                DESCRIPTION "  
                        contains the number of ethernet packets received
			in the current 15 minute period."
                ::= { com21HcxEtherStatsEntry 9 }

        hcxEtherPrevCollisions OBJECT-TYPE
                SYNTAX Gauge32
                MAX-ACCESS read-only    
                STATUS current
                DESCRIPTION "  
                        contains the number of detected collisions
			in the previous 15 minute period."
                ::= { com21HcxEtherStatsEntry 10 }
	
        hcxEtherPrevRunts OBJECT-TYPE
                SYNTAX Gauge32
                MAX-ACCESS read-only    
                STATUS current
                DESCRIPTION "  
                        contains the number of received runt packets
			in the previous 15 minute period."
                ::= { com21HcxEtherStatsEntry 11 }
	
        hcxEtherPrevGrunts OBJECT-TYPE
                SYNTAX Gauge32
                MAX-ACCESS read-only    
                STATUS current
                DESCRIPTION "  
                        contains the number of received grunt packets
			in the previous 15 minute period."
                ::= { com21HcxEtherStatsEntry 12 }
	
        hcxEtherPrevCrcPkts OBJECT-TYPE
                SYNTAX Gauge32
                MAX-ACCESS read-only    
                STATUS current
                DESCRIPTION "  
                        contains the number of ethernet packets received
			with CRC errors in the previous 15 minute period."
                ::= { com21HcxEtherStatsEntry 13 }
	
        hcxEtherPrevTxPkts OBJECT-TYPE
                SYNTAX Gauge32
                MAX-ACCESS read-only    
                STATUS current
                DESCRIPTION "  
                        contains the number of ethernet packets transmitted
			in the previous 15 minute period."
                ::= { com21HcxEtherStatsEntry 14 }
	
        hcxEtherPrevRxPkts OBJECT-TYPE
                SYNTAX Gauge32
                MAX-ACCESS read-only    
                STATUS current
                DESCRIPTION "  
                        contains the number of ethernet packets received
			in the previous 15 minute period."
                ::= { com21HcxEtherStatsEntry 15 }

        hcxEtherClearStats OBJECT-TYPE
                SYNTAX INTEGER { nil(1), clear(2) }
                MAX-ACCESS read-write
                STATUS current
                DESCRIPTION "
                        This attribute is used to clear all Ethernet
                        statistics counters in this group. This operation
                        is only possible if the hcxStatsControl attribute
                        is set to wrapCurr."
                ::= { com21HcxEtherStatsEntry 16 }


        -- -- -- -- -- -- -- -- -- -- -- -- -- -- -- -- -- -- -- -- -- -- -- --
        -- -- -- -- -- -- -- -- -- -- -- -- -- -- -- -- -- -- -- -- -- -- -- --
        --
        -- com21HcxEtherStuStatsGroup
        --
        -- this table defines the per ComPort statistics collected by the
	-- ComController ethernet card (10bT or 100bT).
        --
        -- -- -- -- -- -- -- -- -- -- -- -- -- -- -- -- -- -- -- -- -- -- -- --
        -- -- -- -- -- -- -- -- -- -- -- -- -- -- -- -- -- -- -- -- -- -- -- --
 
        com21HcxEtherStuStatsTable OBJECT-TYPE
                SYNTAX  SEQUENCE OF HcxEtherStuStatsEntry
                MAX-ACCESS  not-accessible
                STATUS  current
                DESCRIPTION "."
                ::= { com21HcxEtherStuStatsGroup 1 }

        com21HcxEtherStuStatsEntry OBJECT-TYPE       
                SYNTAX  HcxEtherStuStatsEntry
                MAX-ACCESS  not-accessible
                STATUS  current
                DESCRIPTION "."
                INDEX { hcxEtherStuStatsMacAddr }
                ::= { com21HcxEtherStuStatsTable 1 }
 
        HcxEtherStuStatsEntry ::= SEQUENCE {
                hcxEtherStuStatsMacAddr          MacAddress,
                hcxEtherStuCurrDnstrmBytes       Gauge32,
		hcxEtherStuCurrUpstrmBytes	 Gauge32,
		hcxEtherStuCurrUpstrmAal5CrcErrs Gauge32,
		hcxEtherStuCurrDnstrmDropPkts	 Gauge32,
                hcxEtherStuPrevDnstrmBytes       Gauge32,
		hcxEtherStuPrevUpstrmBytes	 Gauge32,
		hcxEtherStuPrevUpstrmAal5CrcErrs Gauge32,
		hcxEtherStuPrevDnstrmDropPkts	 Gauge32,
		hcxEtherStuClearStats		 INTEGER }

        hcxEtherStuStatsMacAddr OBJECT-TYPE
                SYNTAX MacAddress
                MAX-ACCESS read-only
                STATUS current
                DESCRIPTION "
                        Contains IEEE 802 medium access control address
                        of the ComPort device."
                ::= { com21HcxEtherStuStatsEntry 1 }
 
        hcxEtherStuCurrDnstrmBytes OBJECT-TYPE
                SYNTAX Gauge32
                MAX-ACCESS read-only
                STATUS current
                DESCRIPTION "
                        Contains the number of unicast bytes transmitted 
			downstream to this ComPort in the current 15
			minute collection period."
                ::= { com21HcxEtherStuStatsEntry 2 }

        hcxEtherStuCurrUpstrmBytes OBJECT-TYPE
                SYNTAX Gauge32
                MAX-ACCESS read-only
                STATUS current
                DESCRIPTION "
                        Contains the number of bytes received upstream
                        from this ComPort in the current 15 minute 
			collection period."
                ::= { com21HcxEtherStuStatsEntry 3 }

        hcxEtherStuCurrUpstrmAal5CrcErrs OBJECT-TYPE
                SYNTAX Gauge32
                MAX-ACCESS read-only
                STATUS current
                DESCRIPTION "
                        Contains the number of AAL5 CRC errors related to
                        upstream traffic from the ComPort in the current 15
                        minute collection period. Each of these errors
			indicates a dropped Ethernet frame."
                ::= { com21HcxEtherStuStatsEntry 4 } 

        hcxEtherStuCurrDnstrmDropPkts OBJECT-TYPE
                SYNTAX Gauge32
                MAX-ACCESS read-only
                STATUS current
                DESCRIPTION "
                        Contains the number of dropped Ethernet frames in 
			the downstream direction in the current 15min period.
			These frames are generally dropped due to policing."
                ::= { com21HcxEtherStuStatsEntry 5 } 

        hcxEtherStuPrevDnstrmBytes OBJECT-TYPE
                SYNTAX Gauge32
                MAX-ACCESS read-only
                STATUS current
                DESCRIPTION "
                        Contains the number of unicast bytes transmitted 
                        downstream to this ComPort in the last 15 minute 
			collection period."
                ::= { com21HcxEtherStuStatsEntry 6 }
 
        hcxEtherStuPrevUpstrmBytes OBJECT-TYPE 
                SYNTAX Gauge32 
                MAX-ACCESS read-only 
                STATUS current
                DESCRIPTION "
                        Contains the number of bytes received upstream
                        from this ComPort in the last 15 minute collection 
			period."
                ::= { com21HcxEtherStuStatsEntry 7 } 
 
        hcxEtherStuPrevUpstrmAal5CrcErrs OBJECT-TYPE 
                SYNTAX Gauge32 
                MAX-ACCESS read-only 
                STATUS current 
                DESCRIPTION "  
                        Contains the number of AAL5 CRC errors related to
                        upstream traffic from the ComPort in the last 15
                        minute collection period. Each of these errors
                        indicates a dropped Ethernet frame." 
                ::= { com21HcxEtherStuStatsEntry 8 } 
 
        hcxEtherStuPrevDnstrmDropPkts OBJECT-TYPE
                SYNTAX Gauge32
                MAX-ACCESS read-only
                STATUS current
                DESCRIPTION "
                        Contains the number of dropped RX frames in the
                        upstream direction in the previous 15min period."
                ::= { com21HcxEtherStuStatsEntry 9 }

	hcxEtherStuClearStats OBJECT-TYPE
                SYNTAX INTEGER { nil(1), clear(2) }
                MAX-ACCESS read-write
                STATUS current
                DESCRIPTION "
                        This attribute is used to clear all ComPort
                        statistics counters in this group. This operation
                        is only possible if the hcxStatsControl attribute
                        is set to wrapCurr."
                ::= { com21HcxEtherStuStatsEntry 10 }


        -- -- -- -- -- -- -- -- -- -- -- -- -- -- -- -- -- -- -- -- -- -- -- --
        -- -- -- -- -- -- -- -- -- -- -- -- -- -- -- -- -- -- -- -- -- -- -- --
        -- 
        -- com21EtherIpAddrGroup 
        -- 
        -- defines gateway and server IP addresses supported by the 
        -- the ethernet interface. The ARP Authentication feature shall
	-- prevent ComPorts from using these addresses as source addresses
	-- in ARP messages. Limit is 8 per interface. ARP filter is
	-- controlled by the hcxEtherPortArpFiltEnable attribute.
        -- 
        -- -- -- -- -- -- -- -- -- -- -- -- -- -- -- -- -- -- -- -- -- -- -- --
        -- -- -- -- -- -- -- -- -- -- -- -- -- -- -- -- -- -- -- -- -- -- -- --   
        com21HcxEtherIpAddrTable OBJECT-TYPE 
                SYNTAX  SEQUENCE OF HcxEtherIpAddrListEntry 
                MAX-ACCESS  not-accessible
                STATUS  current 
                DESCRIPTION 
                        "TBD." 
                ::= { com21HcxEtherIpAddrGroup 1 } 
 
        com21HcxEtherIpAddrEntry OBJECT-TYPE 
                SYNTAX  HcxEtherIpAddrListEntry 
                MAX-ACCESS  not-accessible
                STATUS  current 
                DESCRIPTION "." 
                INDEX { hcxEtherIpAddrShelfId, hcxEtherIpAddrSlotId, hcxEtherIpAddrPortId, hcxEtherIpAddrIPAddr } 
                ::= { com21HcxEtherIpAddrTable 1 } 
 
        HcxEtherIpAddrListEntry ::= SEQUENCE { 
		hcxEtherIpAddrShelfId	 INTEGER,
		hcxEtherIpAddrSlotId     Integer32,
		hcxEtherIpAddrPortId	 INTEGER,
                hcxEtherIpAddrIPAddr     IpAddress,
                hcxEtherIpAddrIPMask     IpAddress,
                hcxEtherIpAddrIPStatus   Com21RowStatus }
 
        hcxEtherIpAddrShelfId OBJECT-TYPE
                SYNTAX INTEGER (1..2)
                MAX-ACCESS read-only
                STATUS current
                DESCRIPTION "
                        contains shelf in which the associated Ethernet
                        port is located."
                ::= { com21HcxEtherIpAddrEntry 1 }
 
        hcxEtherIpAddrSlotId OBJECT-TYPE
                SYNTAX Integer32
                MAX-ACCESS read-only
                STATUS current
                DESCRIPTION "
                        contains slot in which the associated Ethernet
                        port is located."
                ::= { com21HcxEtherIpAddrEntry 2 }
 
        hcxEtherIpAddrPortId OBJECT-TYPE
                SYNTAX INTEGER (1..4)
                MAX-ACCESS read-only
                STATUS current
                DESCRIPTION "
                        contains the associated Ethernet port id."
                ::= { com21HcxEtherIpAddrEntry 3 }
  
        hcxEtherIpAddrIPAddr OBJECT-TYPE
                SYNTAX IpAddress
                MAX-ACCESS read-only
                STATUS current
                DESCRIPTION "
                        target IP Address. No ComPort will be able to use
			this IP address in an ARP response."
                ::= { com21HcxEtherIpAddrEntry 4 }
 
        hcxEtherIpAddrIPMask OBJECT-TYPE
                SYNTAX IpAddress
                MAX-ACCESS read-write
                STATUS current
                DESCRIPTION "
                        IP mask. Default is ff.ff.ff.ff."
                ::= { com21HcxEtherIpAddrEntry 5 }
 
        hcxEtherIpAddrIPStatus OBJECT-TYPE
                SYNTAX Com21RowStatus
                MAX-ACCESS read-create
                STATUS current
                DESCRIPTION "
                        Used to delete or create an entry."
                ::= { com21HcxEtherIpAddrEntry 6 }



        -- -- -- -- -- -- -- -- -- -- -- -- -- -- -- -- -- -- -- -- -- -- -- --
        -- -- -- -- -- -- -- -- -- -- -- -- -- -- -- -- -- -- -- -- -- -- -- --
        --
        -- com21HcxServGrpAssocGroup
        --
        -- defines the number of VLANS/STUS associated with a given
        -- WAN port.
        --
        -- -- -- -- -- -- -- -- -- -- -- -- -- -- -- -- -- -- -- -- -- -- -- --
        -- -- -- -- -- -- -- -- -- -- -- -- -- -- -- -- -- -- -- -- -- -- -- --
 
        com21HcxServGrpAssocTable OBJECT-TYPE
                SYNTAX  SEQUENCE OF HcxServGrpAssocEntry
                MAX-ACCESS  not-accessible
                STATUS  current
                DESCRIPTION "."
                ::= { com21HcxServGrpAssocGroup 1 }
 
        com21HcxServGrpAssocEntry OBJECT-TYPE
                SYNTAX  HcxServGrpAssocEntry
                MAX-ACCESS  not-accessible
                STATUS  current
                DESCRIPTION "."
                INDEX { hcxServGrpAssocShelfId, hcxServGrpAssocSlotId, hcxServGrpAssocCardType, 
                        hcxServGrpAssocPortId, hcxServGrpAssocEntryId }
                ::= { com21HcxServGrpAssocTable 1 }
 
        HcxServGrpAssocEntry ::= SEQUENCE {
                hcxServGrpAssocShelfId             INTEGER,
                hcxServGrpAssocSlotId              INTEGER,
                hcxServGrpAssocCardType            INTEGER,
                hcxServGrpAssocPortId              Integer32,
                hcxServGrpAssocEntryId             Integer32,
                hcxServGrpAssocRate                Integer32,
                hcxServGrpAssocType                INTEGER,
                hcxServGrpAssocNumOfVlans          Integer32,
                hcxServGrpAssocNumOfStus           Integer32}
 
        hcxServGrpAssocShelfId OBJECT-TYPE
                SYNTAX INTEGER (1..2)
                MAX-ACCESS read-only
                STATUS current
                DESCRIPTION "
                        defines shelfId to index into this entry.
                        It is the ShelfId where this Service Group
                        has an entry"
                ::= { com21HcxServGrpAssocEntry 1 }
 
        hcxServGrpAssocSlotId OBJECT-TYPE
                SYNTAX INTEGER (1..2)
                MAX-ACCESS read-only
                STATUS current
                DESCRIPTION "
                        defines SlotId to index into this entry.
                        It is the slot where this Service Group
                        has an entry"
                ::= { com21HcxServGrpAssocEntry 2 }
 
        hcxServGrpAssocCardType OBJECT-TYPE
                SYNTAX INTEGER { tenBaseT (1), onehundredBaseT (2), oc3 (3) }
                MAX-ACCESS read-only
                STATUS current
                DESCRIPTION "
                        defines cardType to index into this entry.
                        It is the card Type where this Service Group
                        has an entry"
                ::= { com21HcxServGrpAssocEntry 3 }
 
        hcxServGrpAssocPortId OBJECT-TYPE
                SYNTAX Integer32
                MAX-ACCESS read-only
                STATUS current
                DESCRIPTION "
                        defines portId to index into this entry.
                        It is the port number where this Service Group
                        has an entry"
                ::= { com21HcxServGrpAssocEntry 4 }
 
        hcxServGrpAssocEntryId OBJECT-TYPE
                SYNTAX Integer32
                MAX-ACCESS read-only
                STATUS current
                DESCRIPTION "
                        defines entryId to index into this entry.
                        it is the entry number assigned to this service
                        group"
                ::= { com21HcxServGrpAssocEntry 5 }
 
        hcxServGrpAssocRate OBJECT-TYPE
                SYNTAX Integer32
                MAX-ACCESS read-only
                STATUS current
                DESCRIPTION "
                        contains Rate associated with this Entry."
                ::= { com21HcxServGrpAssocEntry 6 }
 
        hcxServGrpAssocType OBJECT-TYPE
                SYNTAX INTEGER { cbr (1), ondemand (2) }
                MAX-ACCESS read-only
                STATUS current
                DESCRIPTION "
                        contains Type associated with this Entry."
                ::= { com21HcxServGrpAssocEntry 7 }
 
        hcxServGrpAssocNumOfVlans OBJECT-TYPE
                SYNTAX Integer32
                MAX-ACCESS read-only
                STATUS current
                DESCRIPTION "
                        contains number of Vlans associated with this
                        Service Group "
                ::= { com21HcxServGrpAssocEntry 8 }
 
        hcxServGrpAssocNumOfStus OBJECT-TYPE
                SYNTAX Integer32
                MAX-ACCESS read-only
                STATUS current
                DESCRIPTION "
                        contains number of Stus associated with this
                        Service Group "
                ::= { com21HcxServGrpAssocEntry 9 }
 
 
END
