Nortel-MsCarrier-MscPassport-SoftwareMIB
DEFINITIONS ::= BEGIN



IMPORTS

      OBJECT-TYPE
   FROM RFC-1212

      mscPassportMIBs,
      mscComponents
   FROM Nortel-MsCarrier-MscPassport-UsefulDefinitionsMIB

      DisplayString,
      StorageType,
      RowStatus,
      Unsigned32
   FROM Nortel-MsCarrier-MscPassport-StandardTextualConventionsMIB

      AsciiString,
      NonReplicated,
      Link,
      AsciiStringIndex
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Software Enterprise MIB."

softwareMIB OBJECT IDENTIFIER ::= { mscPassportMIBs 17 }










-- SW
-- The SW component is the top-level component of all software 
-- configuration components.

mscSw OBJECT IDENTIFIER ::= { mscComponents 14 }



mscSwRowStatusTable OBJECT-TYPE
   SYNTAX     SEQUENCE OF MscSwRowStatusEntry
   ACCESS     not-accessible
   STATUS     mandatory
   DESCRIPTION
     "This entry controls the addition and deletion of 
      mscSw components."
::= { mscSw 1 }

mscSwRowStatusEntry OBJECT-TYPE
   SYNTAX     MscSwRowStatusEntry
   ACCESS     not-accessible
   STATUS     mandatory
   DESCRIPTION
     "A single entry in the table represents a single 
      mscSw component."
   INDEX {
      mscSwIndex }
::= { mscSwRowStatusTable 1 }

MscSwRowStatusEntry ::= SEQUENCE {
   mscSwRowStatus
      RowStatus,
   mscSwComponentName
      DisplayString,
   mscSwStorageType
      StorageType,
   mscSwIndex
      NonReplicated }

mscSwRowStatus OBJECT-TYPE
   SYNTAX     RowStatus 
   ACCESS     read-only
   STATUS     mandatory
   DESCRIPTION
     "This variable is used as the basis for SNMP naming of
      mscSw components.
      These components cannot be added nor deleted."
::= { mscSwRowStatusEntry 1 }

mscSwComponentName OBJECT-TYPE
   SYNTAX     DisplayString 
   ACCESS     read-only
   STATUS     mandatory
   DESCRIPTION
     "This variable provides the component's string name for
      use with the ASCII Console Interface"
::= { mscSwRowStatusEntry 2 }

mscSwStorageType OBJECT-TYPE
   SYNTAX     StorageType 
   ACCESS     read-only
   STATUS     mandatory
   DESCRIPTION
     "This variable represents the storage type value for the
      mscSw tables."
::= { mscSwRowStatusEntry 4 }

mscSwIndex OBJECT-TYPE
   SYNTAX     NonReplicated 
   ACCESS     not-accessible
   STATUS     mandatory
   DESCRIPTION
     "This variable represents the index for the mscSw tables."
::= { mscSwRowStatusEntry 10 }

mscSwOperTable OBJECT-TYPE
   SYNTAX     SEQUENCE OF MscSwOperEntry
   ACCESS     not-accessible
   STATUS     mandatory
   DESCRIPTION
     "This group contain the operational attributes for the SW component."
::= { mscSw 11 }

mscSwOperEntry OBJECT-TYPE
   SYNTAX     MscSwOperEntry
   ACCESS     not-accessible
   STATUS     mandatory
   DESCRIPTION
     "An entry in the mscSwOperTable."
   INDEX {
      mscSwIndex }
::= { mscSwOperTable 1 }

MscSwOperEntry ::= SEQUENCE {
   mscSwTidyStatus
      INTEGER,
   mscSwAvBeingTidied
      AsciiString }

mscSwTidyStatus OBJECT-TYPE
   SYNTAX     INTEGER  {
                 inactive(0),
                 inProgress(1),
                 querying(2) }
   ACCESS     read-only
   STATUS     mandatory
   DESCRIPTION
     "This attribute indicates the tidy or remove status. If the value is 
      inactive, no tidy or remove is in progress. If the value is inProgress 
      or querying, the tidy or remove process has begun and therefore no 
      further Tidy Sw or Remove sw/<avName> command is allowed 
      until status returns to inactive."
::= { mscSwOperEntry 1 }

mscSwAvBeingTidied OBJECT-TYPE
   SYNTAX     AsciiString (SIZE (1..30))
   ACCESS     read-only
   STATUS     mandatory
   DESCRIPTION
     "This attribute indicates the name of the AV currently being tidied or 
      removed. An empty string indicates there is no AV being tidied."
::= { mscSwOperEntry 421 }

mscSwAvlTable OBJECT-TYPE
   SYNTAX     SEQUENCE OF MscSwAvlEntry
   ACCESS     not-accessible
   STATUS     mandatory
   DESCRIPTION
     "This attribute specifies, for each application, which version of its 
      Features and the associated software will be loaded when any of its 
      Features are selected in an LPT.
      A version of the 'base' application must be specified.
      All names specified by the user must actually be AV names.
      All AVs specified must be compatible with each other.
      No more than one version of a single application can be specified"
::= { mscSw 256 }

mscSwAvlEntry OBJECT-TYPE
   SYNTAX     MscSwAvlEntry
   ACCESS     not-accessible
   STATUS     mandatory
   DESCRIPTION
     "An entry in the mscSwAvlTable."
   INDEX {
      mscSwIndex,
      mscSwAvlValue }
::= { mscSwAvlTable 1 }

MscSwAvlEntry ::= SEQUENCE {
   mscSwAvlValue
      AsciiString,
   mscSwAvlRowStatus
      RowStatus }

mscSwAvlValue OBJECT-TYPE
   SYNTAX     AsciiString (SIZE (1..30))
   ACCESS     read-write
   STATUS     mandatory
   DESCRIPTION
     "This variable represents both the value and the index for the
      mscSwAvlTable."
::= { mscSwAvlEntry 1 }

mscSwAvlRowStatus OBJECT-TYPE
   SYNTAX     RowStatus 
   ACCESS     write-only
   STATUS     mandatory
   DESCRIPTION
     "This variable is used to control the addition and deletion 
      of individual values of the mscSwAvlTable."
::= { mscSwAvlEntry 2 }

mscSwAvListToTidyTable OBJECT-TYPE
   SYNTAX     SEQUENCE OF MscSwAvListToTidyEntry
   ACCESS     not-accessible
   STATUS     mandatory
   DESCRIPTION
     "This attribute holds the list of names of AVs to be tidied or 
      removed. As AVs are successfully cleaned, they are removed from 
      this list and added to avListTidied."
::= { mscSw 422 }

mscSwAvListToTidyEntry OBJECT-TYPE
   SYNTAX     MscSwAvListToTidyEntry
   ACCESS     not-accessible
   STATUS     mandatory
   DESCRIPTION
     "An entry in the mscSwAvListToTidyTable."
   INDEX {
      mscSwIndex,
      mscSwAvListToTidyValue }
::= { mscSwAvListToTidyTable 1 }

MscSwAvListToTidyEntry ::= SEQUENCE {
   mscSwAvListToTidyValue
      AsciiString }

mscSwAvListToTidyValue OBJECT-TYPE
   SYNTAX     AsciiString (SIZE (1..30))
   ACCESS     read-only
   STATUS     mandatory
   DESCRIPTION
     "This variable represents both the value and the index for the
      mscSwAvListToTidyTable."
::= { mscSwAvListToTidyEntry 1 }

mscSwAvListTidiedTable OBJECT-TYPE
   SYNTAX     SEQUENCE OF MscSwAvListTidiedEntry
   ACCESS     not-accessible
   STATUS     mandatory
   DESCRIPTION
     "This attribute holds the list of names of AVs which have been 
      successfully tidied or removed as a result of the last Tidy Sw or 
      Remove Sw av/<avName> command. It is cleared each time a new 
      Tidy Sw or Remove Sw av/<avName> command is issued."
::= { mscSw 423 }

mscSwAvListTidiedEntry OBJECT-TYPE
   SYNTAX     MscSwAvListTidiedEntry
   ACCESS     not-accessible
   STATUS     mandatory
   DESCRIPTION
     "An entry in the mscSwAvListTidiedTable."
   INDEX {
      mscSwIndex,
      mscSwAvListTidiedValue }
::= { mscSwAvListTidiedTable 1 }

MscSwAvListTidiedEntry ::= SEQUENCE {
   mscSwAvListTidiedValue
      AsciiString }

mscSwAvListTidiedValue OBJECT-TYPE
   SYNTAX     AsciiString (SIZE (1..30))
   ACCESS     read-only
   STATUS     mandatory
   DESCRIPTION
     "This variable represents both the value and the index for the
      mscSwAvListTidiedTable."
::= { mscSwAvListTidiedEntry 1 }

mscSwPatlTable OBJECT-TYPE
   SYNTAX     SEQUENCE OF MscSwPatlEntry
   ACCESS     not-accessible
   STATUS     mandatory
   DESCRIPTION
     "This attribute specifies which patches are to be loaded and enabled.
      Only patches for Av's that appear in the AvList may be specified.
      Only patches appearing as instances of Sw Av Patch may be 
      specified.
      Patch names are case insensitive. Except for case, patch names must 
      be typed as they appear as instances of Sw Av Patch.
      All patches specified must be compatible with one another.
      Any prerequisite patches for specified patches, must themselves be 
      specified.
      A patch must be specified only once in the list."
::= { mscSw 436 }

mscSwPatlEntry OBJECT-TYPE
   SYNTAX     MscSwPatlEntry
   ACCESS     not-accessible
   STATUS     mandatory
   DESCRIPTION
     "An entry in the mscSwPatlTable."
   INDEX {
      mscSwIndex,
      mscSwPatlValue }
::= { mscSwPatlTable 1 }

MscSwPatlEntry ::= SEQUENCE {
   mscSwPatlValue
      AsciiString,
   mscSwPatlRowStatus
      RowStatus }

mscSwPatlValue OBJECT-TYPE
   SYNTAX     AsciiString (SIZE (1..30))
   ACCESS     read-write
   STATUS     mandatory
   DESCRIPTION
     "This variable represents both the value and the index for the
      mscSwPatlTable."
::= { mscSwPatlEntry 1 }

mscSwPatlRowStatus OBJECT-TYPE
   SYNTAX     RowStatus 
   ACCESS     write-only
   STATUS     mandatory
   DESCRIPTION
     "This variable is used to control the addition and deletion 
      of individual values of the mscSwPatlTable."
::= { mscSwPatlEntry 2 }


-- Sw Dld
-- The Download component manages the retrieval of software from 
-- the Software Distribution Site (SDS). The module initiates the 
-- connection to the SDS and retrieves the files it wants according to 
-- the AVs specified by the user in avListToDownload.

mscSwDld OBJECT IDENTIFIER ::= { mscSw 2 }



mscSwDldRowStatusTable OBJECT-TYPE
   SYNTAX     SEQUENCE OF MscSwDldRowStatusEntry
   ACCESS     not-accessible
   STATUS     mandatory
   DESCRIPTION
     "This entry controls the addition and deletion of 
      mscSwDld components."
::= { mscSwDld 1 }

mscSwDldRowStatusEntry OBJECT-TYPE
   SYNTAX     MscSwDldRowStatusEntry
   ACCESS     not-accessible
   STATUS     mandatory
   DESCRIPTION
     "A single entry in the table represents a single 
      mscSwDld component."
   INDEX {
      mscSwIndex,
      mscSwDldIndex }
::= { mscSwDldRowStatusTable 1 }

MscSwDldRowStatusEntry ::= SEQUENCE {
   mscSwDldRowStatus
      RowStatus,
   mscSwDldComponentName
      DisplayString,
   mscSwDldStorageType
      StorageType,
   mscSwDldIndex
      NonReplicated }

mscSwDldRowStatus OBJECT-TYPE
   SYNTAX     RowStatus 
   ACCESS     read-only
   STATUS     mandatory
   DESCRIPTION
     "This variable is used as the basis for SNMP naming of
      mscSwDld components.
      These components cannot be added nor deleted."
::= { mscSwDldRowStatusEntry 1 }

mscSwDldComponentName OBJECT-TYPE
   SYNTAX     DisplayString 
   ACCESS     read-only
   STATUS     mandatory
   DESCRIPTION
     "This variable provides the component's string name for
      use with the ASCII Console Interface"
::= { mscSwDldRowStatusEntry 2 }

mscSwDldStorageType OBJECT-TYPE
   SYNTAX     StorageType 
   ACCESS     read-only
   STATUS     mandatory
   DESCRIPTION
     "This variable represents the storage type value for the
      mscSwDld tables."
::= { mscSwDldRowStatusEntry 4 }

mscSwDldIndex OBJECT-TYPE
   SYNTAX     NonReplicated 
   ACCESS     not-accessible
   STATUS     mandatory
   DESCRIPTION
     "This variable represents the index for the mscSwDld tables."
::= { mscSwDldRowStatusEntry 10 }

mscSwDldOperTable OBJECT-TYPE
   SYNTAX     SEQUENCE OF MscSwDldOperEntry
   ACCESS     not-accessible
   STATUS     mandatory
   DESCRIPTION
     "This group contains the operational attributes for the Download 
      component."
::= { mscSwDld 10 }

mscSwDldOperEntry OBJECT-TYPE
   SYNTAX     MscSwDldOperEntry
   ACCESS     not-accessible
   STATUS     mandatory
   DESCRIPTION
     "An entry in the mscSwDldOperTable."
   INDEX {
      mscSwIndex,
      mscSwDldIndex }
::= { mscSwDldOperTable 1 }

MscSwDldOperEntry ::= SEQUENCE {
   mscSwDldAvBeingDownloaded
      AsciiString,
   mscSwDldStatus
      INTEGER,
   mscSwDldFilesToTransfer
      Unsigned32,
   mscSwDldProcessorTargets
      OCTET STRING }

mscSwDldAvBeingDownloaded OBJECT-TYPE
   SYNTAX     AsciiString (SIZE (0..30))
   ACCESS     read-only
   STATUS     mandatory
   DESCRIPTION
     "This attribute indicates the name of the AV currently being 
      downloaded. If the download is inProgress, this attribute will 
      indicate the same as the first AV in the list of AV's to be 
      downloaded. If there is no AV being downloaded, this attribute will 
      indicate an empty string."
::= { mscSwDldOperEntry 1 }

mscSwDldStatus OBJECT-TYPE
   SYNTAX     INTEGER  {
                 inactive(0),
                 inProgress(1),
                 stopping(2) }
   ACCESS     read-only
   STATUS     mandatory
   DESCRIPTION
     "This attribute indicates the download status.
      If the value is inactive, no download is in progress. This is the value 
      required in order to issue a Start command.
      If the value is inProgress, the download procedure has begun. This 
      process starts from the time a Software Distribution Site (SDS) 
      login is attempted and continues through the time during which files 
      are actually being transferred.
      If the value is stopping, a user has requested a stoppage but the 
      connections have not yet been completely torn down."
::= { mscSwDldOperEntry 2 }

mscSwDldFilesToTransfer OBJECT-TYPE
   SYNTAX     Unsigned32 (0..1000)
   ACCESS     read-only
   STATUS     mandatory
   DESCRIPTION
     "This attribute indicates the number of files which are still left to 
      transfer for the AV currently being downloaded. It is cleared each 
      time a new AV is processed from the avListToDownload. Note that 
      for each AV, the value of this attribute will be 0 until the actual 
      number of files to transfer has been computed."
::= { mscSwDldOperEntry 3 }

mscSwDldProcessorTargets OBJECT-TYPE
   SYNTAX     OCTET STRING (SIZE (1))
   ACCESS     read-write
   STATUS     mandatory
   DESCRIPTION
     "This attribute indicated the processor based object file to download 
      on switch.

      Description of bits:
      i960(0)
      ppc(1)"
::= { mscSwDldOperEntry 4 }

mscSwDldDldListTable OBJECT-TYPE
   SYNTAX     SEQUENCE OF MscSwDldDldListEntry
   ACCESS     not-accessible
   STATUS     mandatory
   DESCRIPTION
     "This attribute holds the list of names of AVs to be downloaded. If a 
      download is in progress, the first one in the list is the one currently 
      being downloaded. As AVs are successfully downloaded, they are 
      removed from this list and added to the downloadedAvList.
      The user cannot specify an AV which already exists on disk. It must 
      first be removed before re-downloading it (see the Tidy and Remove 
      commands)."
::= { mscSwDld 260 }

mscSwDldDldListEntry OBJECT-TYPE
   SYNTAX     MscSwDldDldListEntry
   ACCESS     not-accessible
   STATUS     mandatory
   DESCRIPTION
     "An entry in the mscSwDldDldListTable."
   INDEX {
      mscSwIndex,
      mscSwDldIndex,
      mscSwDldDldListValue }
::= { mscSwDldDldListTable 1 }

MscSwDldDldListEntry ::= SEQUENCE {
   mscSwDldDldListValue
      AsciiString,
   mscSwDldDldListRowStatus
      RowStatus }

mscSwDldDldListValue OBJECT-TYPE
   SYNTAX     AsciiString (SIZE (1..30))
   ACCESS     read-write
   STATUS     mandatory
   DESCRIPTION
     "This variable represents both the value and the index for the
      mscSwDldDldListTable."
::= { mscSwDldDldListEntry 1 }

mscSwDldDldListRowStatus OBJECT-TYPE
   SYNTAX     RowStatus 
   ACCESS     write-only
   STATUS     mandatory
   DESCRIPTION
     "This variable is used to control the addition and deletion 
      of individual values of the mscSwDldDldListTable."
::= { mscSwDldDldListEntry 2 }

mscSwDldDownloadedAvListTable OBJECT-TYPE
   SYNTAX     SEQUENCE OF MscSwDldDownloadedAvListEntry
   ACCESS     not-accessible
   STATUS     mandatory
   DESCRIPTION
     "This attribute holds the list of names of AVs which have been 
      successfully downloaded as a result of the last Start command. It is 
      cleared each time the Start command is issued."
::= { mscSwDld 261 }

mscSwDldDownloadedAvListEntry OBJECT-TYPE
   SYNTAX     MscSwDldDownloadedAvListEntry
   ACCESS     not-accessible
   STATUS     mandatory
   DESCRIPTION
     "An entry in the mscSwDldDownloadedAvListTable."
   INDEX {
      mscSwIndex,
      mscSwDldIndex,
      mscSwDldDownloadedAvListValue }
::= { mscSwDldDownloadedAvListTable 1 }

MscSwDldDownloadedAvListEntry ::= SEQUENCE {
   mscSwDldDownloadedAvListValue
      AsciiString }

mscSwDldDownloadedAvListValue OBJECT-TYPE
   SYNTAX     AsciiString (SIZE (1..30))
   ACCESS     read-only
   STATUS     mandatory
   DESCRIPTION
     "This variable represents both the value and the index for the
      mscSwDldDownloadedAvListTable."
::= { mscSwDldDownloadedAvListEntry 1 }

-- 
-- *** THIS SUBTREE CURRENTLY NOT IMPLEMENTED ***
-- 

-- Sw Av/<name>
-- This component represents a particular version of an application 
-- that is available to use in the AVL. They can only be created by 
-- downloading and can only be deleted by using the Tidy or Remove 
-- commands.
-- An AV has one or more Feature subcomponents which belong to it.

mscSwAv OBJECT IDENTIFIER ::= { mscSw 3 }



mscSwAvRowStatusTable OBJECT-TYPE
   SYNTAX     SEQUENCE OF MscSwAvRowStatusEntry
   ACCESS     not-accessible
   STATUS     mandatory
   DESCRIPTION
     "*** THIS TABLE CURRENTLY NOT IMPLEMENTED ***

      This entry controls the addition and deletion of 
      mscSwAv components."
::= { mscSwAv 1 }

mscSwAvRowStatusEntry OBJECT-TYPE
   SYNTAX     MscSwAvRowStatusEntry
   ACCESS     not-accessible
   STATUS     mandatory
   DESCRIPTION
     "A single entry in the table represents a single 
      mscSwAv component."
   INDEX {
      mscSwIndex,
      mscSwAvIndex }
::= { mscSwAvRowStatusTable 1 }

MscSwAvRowStatusEntry ::= SEQUENCE {
   mscSwAvRowStatus
      RowStatus,
   mscSwAvComponentName
      DisplayString,
   mscSwAvStorageType
      StorageType,
   mscSwAvIndex
      AsciiStringIndex }

mscSwAvRowStatus OBJECT-TYPE
   SYNTAX     RowStatus 
   ACCESS     read-only
   STATUS     mandatory
   DESCRIPTION
     "This variable is used as the basis for SNMP naming of
      mscSwAv components.
      These components cannot be added nor deleted."
::= { mscSwAvRowStatusEntry 1 }

mscSwAvComponentName OBJECT-TYPE
   SYNTAX     DisplayString 
   ACCESS     read-only
   STATUS     mandatory
   DESCRIPTION
     "This variable provides the component's string name for
      use with the ASCII Console Interface"
::= { mscSwAvRowStatusEntry 2 }

mscSwAvStorageType OBJECT-TYPE
   SYNTAX     StorageType 
   ACCESS     read-only
   STATUS     mandatory
   DESCRIPTION
     "This variable represents the storage type value for the
      mscSwAv tables."
::= { mscSwAvRowStatusEntry 4 }

mscSwAvIndex OBJECT-TYPE
   SYNTAX     AsciiStringIndex (SIZE (1..30))
   ACCESS     not-accessible
   STATUS     mandatory
   DESCRIPTION
     "This variable represents the index for the mscSwAv tables."
::= { mscSwAvRowStatusEntry 10 }

mscSwAvOperTable OBJECT-TYPE
   SYNTAX     SEQUENCE OF MscSwAvOperEntry
   ACCESS     not-accessible
   STATUS     mandatory
   DESCRIPTION
     "*** THIS TABLE CURRENTLY NOT IMPLEMENTED ***

      This group contains the operational attributes for an AV component."
::= { mscSwAv 10 }

mscSwAvOperEntry OBJECT-TYPE
   SYNTAX     MscSwAvOperEntry
   ACCESS     not-accessible
   STATUS     mandatory
   DESCRIPTION
     "An entry in the mscSwAvOperTable."
   INDEX {
      mscSwIndex,
      mscSwAvIndex }
::= { mscSwAvOperTable 1 }

MscSwAvOperEntry ::= SEQUENCE {
   mscSwAvProcessorTargets
      OCTET STRING }

mscSwAvProcessorTargets OBJECT-TYPE
   SYNTAX     OCTET STRING (SIZE (1))
   ACCESS     read-only
   STATUS     mandatory
   DESCRIPTION
     "This is a list of the processor based object file types which exist on 
      disk for a given AV. Semantic check will validate that the object 
      files needed for a provisioned card type are present as part of an 
      application.

      Description of bits:
      i960(0)
      ppc(1)"
::= { mscSwAvOperEntry 1 }

mscSwAvCompatibleAvListTable OBJECT-TYPE
   SYNTAX     SEQUENCE OF MscSwAvCompatibleAvListEntry
   ACCESS     not-accessible
   STATUS     mandatory
   DESCRIPTION
     "*** THIS TABLE CURRENTLY NOT IMPLEMENTED ***

      This is a list of the AV names which specify the minimum version 
      of all other applications that can be used in conjunction with this AV 
      in an AVL. Semantic checks will validate that AVs within the AVL 
      are indeed compatible."
::= { mscSwAv 259 }

mscSwAvCompatibleAvListEntry OBJECT-TYPE
   SYNTAX     MscSwAvCompatibleAvListEntry
   ACCESS     not-accessible
   STATUS     mandatory
   DESCRIPTION
     "An entry in the mscSwAvCompatibleAvListTable."
   INDEX {
      mscSwIndex,
      mscSwAvIndex,
      mscSwAvCompatibleAvListValue }
::= { mscSwAvCompatibleAvListTable 1 }

MscSwAvCompatibleAvListEntry ::= SEQUENCE {
   mscSwAvCompatibleAvListValue
      AsciiString }

mscSwAvCompatibleAvListValue OBJECT-TYPE
   SYNTAX     AsciiString (SIZE (1..30))
   ACCESS     read-only
   STATUS     mandatory
   DESCRIPTION
     "This variable represents both the value and the index for the
      mscSwAvCompatibleAvListTable."
::= { mscSwAvCompatibleAvListEntry 1 }

-- 
-- *** THIS SUBTREE CURRENTLY NOT IMPLEMENTED ***
-- 

-- Sw Av/<name> Feat/<name>
-- There is one of these components for each provisionable feature of 
-- the parent AV component. Each feature's name can be used in an 
-- Lpt's feature list attribute. A feature component does not have any 
-- attributes of its own.

mscSwAvFeat OBJECT IDENTIFIER ::= { mscSwAv 2 }



mscSwAvFeatRowStatusTable OBJECT-TYPE
   SYNTAX     SEQUENCE OF MscSwAvFeatRowStatusEntry
   ACCESS     not-accessible
   STATUS     mandatory
   DESCRIPTION
     "*** THIS TABLE CURRENTLY NOT IMPLEMENTED ***

      This entry controls the addition and deletion of 
      mscSwAvFeat components."
::= { mscSwAvFeat 1 }

mscSwAvFeatRowStatusEntry OBJECT-TYPE
   SYNTAX     MscSwAvFeatRowStatusEntry
   ACCESS     not-accessible
   STATUS     mandatory
   DESCRIPTION
     "A single entry in the table represents a single 
      mscSwAvFeat component."
   INDEX {
      mscSwIndex,
      mscSwAvIndex,
      mscSwAvFeatIndex }
::= { mscSwAvFeatRowStatusTable 1 }

MscSwAvFeatRowStatusEntry ::= SEQUENCE {
   mscSwAvFeatRowStatus
      RowStatus,
   mscSwAvFeatComponentName
      DisplayString,
   mscSwAvFeatStorageType
      StorageType,
   mscSwAvFeatIndex
      AsciiStringIndex }

mscSwAvFeatRowStatus OBJECT-TYPE
   SYNTAX     RowStatus 
   ACCESS     read-only
   STATUS     mandatory
   DESCRIPTION
     "This variable is used as the basis for SNMP naming of
      mscSwAvFeat components.
      These components cannot be added nor deleted."
::= { mscSwAvFeatRowStatusEntry 1 }

mscSwAvFeatComponentName OBJECT-TYPE
   SYNTAX     DisplayString 
   ACCESS     read-only
   STATUS     mandatory
   DESCRIPTION
     "This variable provides the component's string name for
      use with the ASCII Console Interface"
::= { mscSwAvFeatRowStatusEntry 2 }

mscSwAvFeatStorageType OBJECT-TYPE
   SYNTAX     StorageType 
   ACCESS     read-only
   STATUS     mandatory
   DESCRIPTION
     "This variable represents the storage type value for the
      mscSwAvFeat tables."
::= { mscSwAvFeatRowStatusEntry 4 }

mscSwAvFeatIndex OBJECT-TYPE
   SYNTAX     AsciiStringIndex (SIZE (1..25))
   ACCESS     not-accessible
   STATUS     mandatory
   DESCRIPTION
     "This variable represents the index for the mscSwAvFeat tables."
::= { mscSwAvFeatRowStatusEntry 10 }

-- 
-- *** THIS SUBTREE CURRENTLY NOT IMPLEMENTED ***
-- 

-- Sw Av/<name> Patch/<name>
-- There is one of these components for each patch of the parent AV 
-- component that has been downloaded to the switch.

mscSwAvPatch OBJECT IDENTIFIER ::= { mscSwAv 3 }



mscSwAvPatchRowStatusTable OBJECT-TYPE
   SYNTAX     SEQUENCE OF MscSwAvPatchRowStatusEntry
   ACCESS     not-accessible
   STATUS     mandatory
   DESCRIPTION
     "*** THIS TABLE CURRENTLY NOT IMPLEMENTED ***

      This entry controls the addition and deletion of 
      mscSwAvPatch components."
::= { mscSwAvPatch 1 }

mscSwAvPatchRowStatusEntry OBJECT-TYPE
   SYNTAX     MscSwAvPatchRowStatusEntry
   ACCESS     not-accessible
   STATUS     mandatory
   DESCRIPTION
     "A single entry in the table represents a single 
      mscSwAvPatch component."
   INDEX {
      mscSwIndex,
      mscSwAvIndex,
      mscSwAvPatchIndex }
::= { mscSwAvPatchRowStatusTable 1 }

MscSwAvPatchRowStatusEntry ::= SEQUENCE {
   mscSwAvPatchRowStatus
      RowStatus,
   mscSwAvPatchComponentName
      DisplayString,
   mscSwAvPatchStorageType
      StorageType,
   mscSwAvPatchIndex
      AsciiStringIndex }

mscSwAvPatchRowStatus OBJECT-TYPE
   SYNTAX     RowStatus 
   ACCESS     read-only
   STATUS     mandatory
   DESCRIPTION
     "This variable is used as the basis for SNMP naming of
      mscSwAvPatch components.
      These components cannot be added nor deleted."
::= { mscSwAvPatchRowStatusEntry 1 }

mscSwAvPatchComponentName OBJECT-TYPE
   SYNTAX     DisplayString 
   ACCESS     read-only
   STATUS     mandatory
   DESCRIPTION
     "This variable provides the component's string name for
      use with the ASCII Console Interface"
::= { mscSwAvPatchRowStatusEntry 2 }

mscSwAvPatchStorageType OBJECT-TYPE
   SYNTAX     StorageType 
   ACCESS     read-only
   STATUS     mandatory
   DESCRIPTION
     "This variable represents the storage type value for the
      mscSwAvPatch tables."
::= { mscSwAvPatchRowStatusEntry 4 }

mscSwAvPatchIndex OBJECT-TYPE
   SYNTAX     AsciiStringIndex (SIZE (1..30))
   ACCESS     not-accessible
   STATUS     mandatory
   DESCRIPTION
     "This variable represents the index for the mscSwAvPatch tables."
::= { mscSwAvPatchRowStatusEntry 10 }

mscSwAvPatchOperTable OBJECT-TYPE
   SYNTAX     SEQUENCE OF MscSwAvPatchOperEntry
   ACCESS     not-accessible
   STATUS     mandatory
   DESCRIPTION
     "*** THIS TABLE CURRENTLY NOT IMPLEMENTED ***

      This group contains the operational attributes for the Patch 
      component."
::= { mscSwAvPatch 10 }

mscSwAvPatchOperEntry OBJECT-TYPE
   SYNTAX     MscSwAvPatchOperEntry
   ACCESS     not-accessible
   STATUS     mandatory
   DESCRIPTION
     "An entry in the mscSwAvPatchOperTable."
   INDEX {
      mscSwIndex,
      mscSwAvIndex,
      mscSwAvPatchIndex }
::= { mscSwAvPatchOperTable 1 }

MscSwAvPatchOperEntry ::= SEQUENCE {
   mscSwAvPatchDescription
      AsciiString }

mscSwAvPatchDescription OBJECT-TYPE
   SYNTAX     AsciiString (SIZE (0..512))
   ACCESS     read-only
   STATUS     mandatory
   DESCRIPTION
     "This attribute indicates the new behavior that the patch provides. 
      The availability of this description is dependent on the disk being 
      available."
::= { mscSwAvPatchOperEntry 1 }


-- Sw Lpt/<name>
-- This component is the Logical Processor Type, specifying 
-- characteristics of the software to be loaded on a card. Minimally, 
-- LPT/CP is required to exist. If it is deleted, semantic checks will 
-- fail.

mscSwLpt OBJECT IDENTIFIER ::= { mscSw 4 }



mscSwLptRowStatusTable OBJECT-TYPE
   SYNTAX     SEQUENCE OF MscSwLptRowStatusEntry
   ACCESS     not-accessible
   STATUS     mandatory
   DESCRIPTION
     "This entry controls the addition and deletion of 
      mscSwLpt components."
::= { mscSwLpt 1 }

mscSwLptRowStatusEntry OBJECT-TYPE
   SYNTAX     MscSwLptRowStatusEntry
   ACCESS     not-accessible
   STATUS     mandatory
   DESCRIPTION
     "A single entry in the table represents a single 
      mscSwLpt component."
   INDEX {
      mscSwIndex,
      mscSwLptIndex }
::= { mscSwLptRowStatusTable 1 }

MscSwLptRowStatusEntry ::= SEQUENCE {
   mscSwLptRowStatus
      RowStatus,
   mscSwLptComponentName
      DisplayString,
   mscSwLptStorageType
      StorageType,
   mscSwLptIndex
      AsciiStringIndex }

mscSwLptRowStatus OBJECT-TYPE
   SYNTAX     RowStatus 
   ACCESS     read-write
   STATUS     mandatory
   DESCRIPTION
     "This variable is used as the basis for SNMP naming of
      mscSwLpt components.
      These components can be added and deleted."
::= { mscSwLptRowStatusEntry 1 }

mscSwLptComponentName OBJECT-TYPE
   SYNTAX     DisplayString 
   ACCESS     read-only
   STATUS     mandatory
   DESCRIPTION
     "This variable provides the component's string name for
      use with the ASCII Console Interface"
::= { mscSwLptRowStatusEntry 2 }

mscSwLptStorageType OBJECT-TYPE
   SYNTAX     StorageType 
   ACCESS     read-only
   STATUS     mandatory
   DESCRIPTION
     "This variable represents the storage type value for the
      mscSwLpt tables."
::= { mscSwLptRowStatusEntry 4 }

mscSwLptIndex OBJECT-TYPE
   SYNTAX     AsciiStringIndex (SIZE (1..25))
   ACCESS     not-accessible
   STATUS     mandatory
   DESCRIPTION
     "This variable represents the index for the mscSwLpt tables."
::= { mscSwLptRowStatusEntry 10 }

mscSwLptProvTable OBJECT-TYPE
   SYNTAX     SEQUENCE OF MscSwLptProvEntry
   ACCESS     not-accessible
   STATUS     mandatory
   DESCRIPTION
     "This group contains the provisionable attributes for the LPT 
      component."
::= { mscSwLpt 10 }

mscSwLptProvEntry OBJECT-TYPE
   SYNTAX     MscSwLptProvEntry
   ACCESS     not-accessible
   STATUS     mandatory
   DESCRIPTION
     "An entry in the mscSwLptProvTable."
   INDEX {
      mscSwIndex,
      mscSwLptIndex }
::= { mscSwLptProvTable 1 }

MscSwLptProvEntry ::= SEQUENCE {
   mscSwLptCommentText
      AsciiString,
   mscSwLptSystemConfig
      INTEGER }

mscSwLptCommentText OBJECT-TYPE
   SYNTAX     AsciiString (SIZE (0..80))
   ACCESS     read-write
   STATUS     mandatory
   DESCRIPTION
     "An arbitrary string used to enter a comment about an LPT."
::= { mscSwLptProvEntry 1 }

mscSwLptSystemConfig OBJECT-TYPE
   SYNTAX     INTEGER  {
                 default(0) }
   ACCESS     read-write
   STATUS     mandatory
   DESCRIPTION
     "This attribute specifies which set of preconfigured system 
      parameters to use for the set of Features selected in featureList."
   DEFVAL     { default }
::= { mscSwLptProvEntry 2 }

mscSwLptFlTable OBJECT-TYPE
   SYNTAX     SEQUENCE OF MscSwLptFlEntry
   ACCESS     not-accessible
   STATUS     mandatory
   DESCRIPTION
     "This attribute specifies a list of names of Features that define a 
      particular configuration of application functionality that the user 
      wants to load on a single processor. 
      The combination of Features selected must be compatible (for 
      example, none can be mutually exclusive with another in the list).
      All Features must belong to an AV specified in the AVL.
      All Features must be able to be loaded on any of the Cards which 
      are linked to LPs which are linked to this LPT.
      All prerequisite Features of the ones in this list will also be loaded."
::= { mscSwLpt 257 }

mscSwLptFlEntry OBJECT-TYPE
   SYNTAX     MscSwLptFlEntry
   ACCESS     not-accessible
   STATUS     mandatory
   DESCRIPTION
     "An entry in the mscSwLptFlTable."
   INDEX {
      mscSwIndex,
      mscSwLptIndex,
      mscSwLptFlValue }
::= { mscSwLptFlTable 1 }

MscSwLptFlEntry ::= SEQUENCE {
   mscSwLptFlValue
      AsciiString,
   mscSwLptFlRowStatus
      RowStatus }

mscSwLptFlValue OBJECT-TYPE
   SYNTAX     AsciiString (SIZE (1..25))
   ACCESS     read-write
   STATUS     mandatory
   DESCRIPTION
     "This variable represents both the value and the index for the
      mscSwLptFlTable."
::= { mscSwLptFlEntry 1 }

mscSwLptFlRowStatus OBJECT-TYPE
   SYNTAX     RowStatus 
   ACCESS     write-only
   STATUS     mandatory
   DESCRIPTION
     "This variable is used to control the addition and deletion 
      of individual values of the mscSwLptFlTable."
::= { mscSwLptFlEntry 2 }

mscSwLptLogicalProcessorsTable OBJECT-TYPE
   SYNTAX     SEQUENCE OF MscSwLptLogicalProcessorsEntry
   ACCESS     not-accessible
   STATUS     mandatory
   DESCRIPTION
     "This attribute shows which LPs are configured to load the Feature 
      files associated with this LPT. It is the opposite side of the LP 
      component's logicalProcessorType link attribute."
::= { mscSwLpt 258 }

mscSwLptLogicalProcessorsEntry OBJECT-TYPE
   SYNTAX     MscSwLptLogicalProcessorsEntry
   ACCESS     not-accessible
   STATUS     mandatory
   DESCRIPTION
     "An entry in the mscSwLptLogicalProcessorsTable."
   INDEX {
      mscSwIndex,
      mscSwLptIndex,
      mscSwLptLogicalProcessorsValue }
::= { mscSwLptLogicalProcessorsTable 1 }

MscSwLptLogicalProcessorsEntry ::= SEQUENCE {
   mscSwLptLogicalProcessorsValue
      Link }

mscSwLptLogicalProcessorsValue OBJECT-TYPE
   SYNTAX     Link 
   ACCESS     read-only
   STATUS     mandatory
   DESCRIPTION
     "This variable represents both the value and the index for the
      mscSwLptLogicalProcessorsTable."
::= { mscSwLptLogicalProcessorsEntry 1 }




-- 
-- Version and Compliance statements
-- 



-- Object-Group Statement:
-- A list of all current accessible leaf objects.

-- OBJECTS { mscSwAvRowStatus,
--           mscSwAvPatchDescription,
--           mscSwAvCompatibleAvListValue,
--           mscSwAvProcessorTargets,
--           mscSwLptSystemConfig,
--           mscSwAvPatchComponentName,
--           mscSwDldDldListRowStatus,
--           mscSwDldStorageType,
--           mscSwAvBeingTidied,
--           mscSwComponentName,
--           mscSwDldProcessorTargets,
--           mscSwTidyStatus,
--           mscSwAvListTidiedValue,
--           mscSwDldComponentName,
--           mscSwPatlRowStatus,
--           mscSwLptFlRowStatus,
--           mscSwStorageType,
--           mscSwDldDldListValue,
--           mscSwAvComponentName,
--           mscSwLptFlValue,
--           mscSwAvlRowStatus,
--           mscSwAvStorageType,
--           mscSwPatlValue,
--           mscSwDldStatus,
--           mscSwLptRowStatus,
--           mscSwDldAvBeingDownloaded,
--           mscSwLptCommentText,
--           mscSwLptLogicalProcessorsValue,
--           mscSwAvlValue,
--           mscSwDldDownloadedAvListValue,
--           mscSwDldFilesToTransfer,
--           mscSwAvPatchRowStatus,
--           mscSwAvFeatRowStatus,
--           mscSwAvListToTidyValue,
--           mscSwRowStatus,
--           mscSwAvPatchStorageType,
--           mscSwAvFeatComponentName,
--           mscSwDldRowStatus,
--           mscSwLptStorageType,
--           mscSwLptComponentName,
--           mscSwAvFeatStorageType }
-- STATUS  mandatory
-- DESCRIPTION
--   "A list of all current accessible leaf objects."

softwareGroup OBJECT IDENTIFIER ::= { softwareMIB 1 }
softwareGroupCA OBJECT IDENTIFIER ::= { softwareGroup 1 }
softwareGroupCA02 OBJECT IDENTIFIER ::= { softwareGroupCA 3 }
softwareGroupCA02A OBJECT IDENTIFIER ::= { softwareGroupCA02 2 }



-- Agent-Capabilities Statement:

-- PRODUCT-RELEASE "MscPassport Release 1.2 Software."
-- STATUS          mandatory
-- DESCRIPTION     "Carrier Passport Software MIB: MIB Version CA02A,
--                  Software Version CA02S9C."
-- SUPPORTS        Nortel-MsCarrier-MscPassport-SoftwareMIB
--    INCLUDES     { softwareGroupCA02A }

softwareCapabilities OBJECT IDENTIFIER ::= { softwareMIB 3 }
softwareCapabilitiesCA OBJECT IDENTIFIER ::= { softwareCapabilities 1 }
softwareCapabilitiesCA02 OBJECT IDENTIFIER ::= { softwareCapabilitiesCA 3 }
softwareCapabilitiesCA02A OBJECT IDENTIFIER ::= { softwareCapabilitiesCA02 2 }





END
