ELFIQ-MODULE-LB-MIB DEFINITIONS ::= BEGIN

	IMPORTS
      MODULE-IDENTITY, OBJECT-TYPE, Integer32, Counter64, Unsigned32,
      IpAddress, NOTIFICATION-TYPE				FROM SNMPv2-SMI
		TEXTUAL-CONVENTION, DisplayString		FROM SNMPv2-TC
		MODULE-COMPLIANCE, OBJECT-GROUP,
		NOTIFICATION-GROUP							FROM SNMPv2-CONF
		snmpTraps										FROM SNMPv2-MIB
		linkBalancer, linkBalancerConformance	FROM ELFIQ-INC-MIB;

--
-- A brief description and update information about this mib.
--
linkBalancerComponent                     MODULE-IDENTITY
    LAST-UPDATED "200904190000Z"            -- 11 Nov 2008, midnight
    ORGANIZATION "Elfiq Inc."
    CONTACT-INFO "
              Author:     Elfiq Network
              postal:     Montreal, QC H3B3A7
                                     CANADA
              email:      support@elfiq.com
              phone:      +1-514-667-0611
                        "
    DESCRIPTION  "This is the standard component of the link balancer"
    ::= { linkBalancer 1 }

--
-- 3) This is the part for the component vfi
--


vfiInfo	OBJECT IDENTIFIER ::= { linkBalancerComponent 1 }

VfiIndex ::= TEXTUAL-CONVENTION
	DISPLAY-HINT	"d"
	STATUS 			current
	DESCRIPTION 
				" A unique value, greater than zero, for
					each vfi in the llb "
	SYNTAX		Integer32 (0..5)

vfiNumber			OBJECT-TYPE
	SYNTAX      Integer32 (0..10)
	MAX-ACCESS  read-only
	STATUS      current
	DESCRIPTION
           "The number of virtual forwarder interfaces configured in the system"
	::= { vfiInfo 1 }

-- the vfi table which contains information about its component details

vfiTable 		OBJECT-TYPE
	SYNTAX 		SEQUENCE OF VfiEntry
	MAX-ACCESS	not-accessible
	STATUS		current
	DESCRIPTION	
				"This is a list of vfi entries. The number of vfi is 
				given by the value of vfiNumber."
	::= { vfiInfo 2 }

vfiEntry		OBJECT-TYPE
	SYNTAX		VfiEntry
	MAX-ACCESS	not-accessible
	STATUS 		current
	DESCRIPTION	
				" An entry containing vfi sub-component."
	INDEX	{ vfiIndex }
	::= { vfiTable 1 }
	
VfiEntry ::=
	SEQUENCE {
			vfiIndex				VfiIndex,
	 		vfiDescr				DisplayString,
			vfiActivated			INTEGER,
	 		vfiStatus				INTEGER,
			totThroughputIn			Counter64,
			totThroughputOut		Counter64,
			topTotThroughputIn		Counter64,
			topTotThroughputOut		Counter64,
			numPackReceivedOut		Counter64,
			numBytesReceivedOut		Counter64,
			numPackReceivedIn		Counter64,
			numBytesReceivedIn		Counter64,
			numL2Dropped			Unsigned32,
			numIPDroppedShun		Unsigned32,
			numIPDroppedAll			Unsigned32,
			numIPFragNat			Unsigned32,
			numTCPMSSModif			Unsigned32,
			numTCPCheckError		Unsigned32,
			numUDPCheckError		Unsigned32,
			totNumDropProbe			Unsigned32,
			totNumDropProbePerSec	Unsigned32,
			lastPacketTimeTraver	Unsigned32,
			topPacketTimeTraver		Unsigned32,
			numLiveSessIn			Unsigned32,
			topNumLiveSessIn		Unsigned32,
			samplingIntervalIn		Unsigned32,
			numNewSessPerSecIn		Unsigned32,
			numEndSessPerSecIn		Unsigned32,
			numHandledSessIn		Counter64,
			numLiveSessOut			Unsigned32,
			topNumLiveSessOut		Unsigned32,
			samplingIntervalOut		Unsigned32,
			numNewSessPerSecOut		Unsigned32,
			numEndSessPerSecOut		Unsigned32,
			numHandledSessOut		Counter64,
			numDNSReqPerSecOut		Unsigned32,
			topNumDNSReqPerSecOut	Unsigned32,
			numHandledDNSReqOut		Counter64,
			numDNSReqPerSecIn		Unsigned32,
			topNumDNSReqPerSecIn	Unsigned32,
			numHandledDNSReqIn		Counter64
	}
	
vfiIndex			OBJECT-TYPE
	SYNTAX      VfiIndex
	MAX-ACCESS  read-only
	STATUS      current
	DESCRIPTION
           "The vfi index 0 - 4"
	::= { vfiEntry 1 }

vfiDescr		OBJECT-TYPE
	SYNTAX		DisplayString (SIZE (0..64))
	MAX-ACCESS	read-only
	STATUS		current
	DESCRIPTION
				"A textual string containing a description about 
				the vfi "
	::= { vfiEntry 2 }

vfiActivated		OBJECT-TYPE
	SYNTAX INTEGER { 
						activated(1),
						desactivated(2)
			}
	MAX-ACCESS	read-only
	STATUS		current
	DESCRIPTION
				"Inform if this vfi has been activated at startup"
	::= { vfiEntry 3 }	
	
vfiStatus		OBJECT-TYPE
	SYNTAX INTEGER { 
						resume(1),
						pause(2)
			}
	MAX-ACCESS	read-only
	STATUS		current
	DESCRIPTION
				"The current status of the vfi"
	::= { vfiEntry 4 }	

totThroughputIn		OBJECT-TYPE
	SYNTAX				Counter64
	MAX-ACCESS			read-only
	STATUS				current
	DESCRIPTION
			"This is the total incoming throughput for this vfi (all gmacs) in kb/s"
	::= { vfiEntry 5 }

totThroughputOut		OBJECT-TYPE
	SYNTAX				Counter64
	MAX-ACCESS			read-only
	STATUS				current
	DESCRIPTION
			"This is the total outgoing throughput for this vfi (all gmacs) in kb/s"
	::= { vfiEntry 6 }

topTotThroughputIn	OBJECT-TYPE
	SYNTAX				Counter64
	MAX-ACCESS			read-only
	STATUS				current
	DESCRIPTION
			"This is the top total incoming throughput for this vfi (all gmacs) in kb/s"
	::= { vfiEntry 7 }

topTotThroughputOut	OBJECT-TYPE
	SYNTAX				Counter64
	MAX-ACCESS			read-only
	STATUS				current
	DESCRIPTION
			"This is the top total outgoing throughput for this vfi (all gmacs) in kb/s"
	::= { vfiEntry 8 }

numPackReceivedOut	OBJECT-TYPE
	SYNTAX				Counter64
	MAX-ACCESS			read-only
	STATUS				current
	DESCRIPTION
			"This is the total number of packets received outside"
	::= { vfiEntry 9 }

numBytesReceivedOut	OBJECT-TYPE
	SYNTAX				Counter64
	MAX-ACCESS			read-only
	STATUS				current
	DESCRIPTION
			"This is the total number of bytes received outside"
	::= { vfiEntry 10 }

numPackReceivedIn	OBJECT-TYPE
	SYNTAX				Counter64
	MAX-ACCESS			read-only
	STATUS				current
	DESCRIPTION
			"This is the total number of packets received inside"
	::= { vfiEntry 11 }

numBytesReceivedIn	OBJECT-TYPE
	SYNTAX				Counter64
	MAX-ACCESS			read-only
	STATUS				current
	DESCRIPTION
			"This is the total number of bytes received inside"
	::= { vfiEntry 12 }

numL2Dropped			OBJECT-TYPE
	SYNTAX				Unsigned32
	MAX-ACCESS			read-only
	STATUS				current
	DESCRIPTION
			"This is the total number of L2 dropped packets"
	::= { vfiEntry 13 }

numIPDroppedShun		OBJECT-TYPE
	SYNTAX				Unsigned32
	MAX-ACCESS			read-only
	STATUS				current
	DESCRIPTION
			"This is the total number of IP dropped packets (shun)"
	::= { vfiEntry 14 }

numIPDroppedAll		OBJECT-TYPE
	SYNTAX				Unsigned32
	MAX-ACCESS			read-only
	STATUS				current
	DESCRIPTION
			"This is the total number of IP dropped packets (all)"
	::= { vfiEntry 15 }

numIPFragNat			OBJECT-TYPE
	SYNTAX				Unsigned32
	MAX-ACCESS			read-only
	STATUS				current
	DESCRIPTION
			"This is the total number of IP fragmented ( Nat ) packets"
	::= { vfiEntry 16 }

numTCPMSSModif			OBJECT-TYPE
	SYNTAX				Unsigned32
	MAX-ACCESS			read-only
	STATUS				current
	DESCRIPTION
			"This is the total number of TCP MSS modified"
	::= { vfiEntry 17 }

numTCPCheckError		OBJECT-TYPE
	SYNTAX				Unsigned32
	MAX-ACCESS			read-only
	STATUS				current
	DESCRIPTION
			"This is the total number of TCP checksum error (Nat) packets"
	::= { vfiEntry 18 }

numUDPCheckError		OBJECT-TYPE
	SYNTAX				Unsigned32
	MAX-ACCESS			read-only
	STATUS				current
	DESCRIPTION
			"This is the total number of UDP checksum error (Nat) packets"
	::= { vfiEntry 19 }

totNumDropProbe			OBJECT-TYPE
	SYNTAX				Unsigned32
	MAX-ACCESS			read-only
	STATUS				current
	DESCRIPTION
			"This is the total number of dropped packets (probe)"
	::= { vfiEntry 20 }

totNumDropProbePerSec	OBJECT-TYPE
	SYNTAX				Unsigned32
	MAX-ACCESS			read-only
	STATUS				current
	DESCRIPTION
			"This is the total number of dropped packets/sec (probe)"
	::= { vfiEntry 21 }

lastPacketTimeTraver	OBJECT-TYPE
	SYNTAX				Unsigned32
	MAX-ACCESS			read-only
	STATUS				current
	DESCRIPTION
			"This is the last vfi packet time traversal"
	::= { vfiEntry 22 }

topPacketTimeTraver	OBJECT-TYPE
	SYNTAX				Unsigned32
	MAX-ACCESS			read-only
	STATUS				current
	DESCRIPTION
			"This is the top vfi packet time traversal"
	::= { vfiEntry 23 }

numLiveSessIn			OBJECT-TYPE
	SYNTAX				Unsigned32
	MAX-ACCESS			read-only
	STATUS				current
	DESCRIPTION
			"This is the dnat inside total number of live sessions "
	::= { vfiEntry 24 }

topNumLiveSessIn		OBJECT-TYPE
	SYNTAX				Unsigned32
	MAX-ACCESS			read-only
	STATUS				current
	DESCRIPTION
			"This is the dnat inside top total number of live sessions "
	::= { vfiEntry 25 }

samplingIntervalIn	OBJECT-TYPE
	SYNTAX				Unsigned32
	MAX-ACCESS			read-only
	STATUS				current
	DESCRIPTION
			"This is the dnat inside sampling interval "
	::= { vfiEntry 26 }

numNewSessPerSecIn		OBJECT-TYPE
	SYNTAX				Unsigned32
	MAX-ACCESS			read-only
	STATUS				current
	DESCRIPTION
			"This is the dnat inside total number of new sessions/sec"
	::= { vfiEntry 27 }

numEndSessPerSecIn		OBJECT-TYPE
	SYNTAX				Unsigned32
	MAX-ACCESS			read-only
	STATUS				current
	DESCRIPTION
			"This is the dnat inside total number of ending sessions/sec"
	::= { vfiEntry 28 }

numHandledSessIn		OBJECT-TYPE
	SYNTAX				Counter64
	MAX-ACCESS			read-only
	STATUS				current
	DESCRIPTION
			"This is the dnat inside total number of handled sessions"
	::= { vfiEntry 29 }

numLiveSessOut			OBJECT-TYPE
	SYNTAX				Unsigned32
	MAX-ACCESS			read-only
	STATUS				current
	DESCRIPTION
			"This is the dnat outside total number of live sessions "
	::= { vfiEntry 30 }

topNumLiveSessOut		OBJECT-TYPE
	SYNTAX				Unsigned32
	MAX-ACCESS			read-only
	STATUS				current
	DESCRIPTION
			"This is the dnat Outside top total number of live sessions "
	::= { vfiEntry 31 }

samplingIntervalOut	OBJECT-TYPE
	SYNTAX				Unsigned32
	MAX-ACCESS			read-only
	STATUS				current
	DESCRIPTION
			"This is the dnat Outside sampling interval "
	::= { vfiEntry 32 }

numNewSessPerSecOut		OBJECT-TYPE
	SYNTAX				Unsigned32
	MAX-ACCESS			read-only
	STATUS				current
	DESCRIPTION
			"This is the dnat Outside total number of new sessions/sec"
	::= { vfiEntry 33 }

numEndSessPerSecOut		OBJECT-TYPE
	SYNTAX				Unsigned32
	MAX-ACCESS			read-only
	STATUS				current
	DESCRIPTION
			"This is the dnat Outside total number of ending sessions/sec"
	::= { vfiEntry 34 }

numHandledSessOut		OBJECT-TYPE
	SYNTAX				Counter64
	MAX-ACCESS			read-only
	STATUS				current
	DESCRIPTION
			"This is the dnat Outside total number of handled sessions"
	::= { vfiEntry 35 }

numDNSReqPerSecOut		OBJECT-TYPE
	SYNTAX				Unsigned32
	MAX-ACCESS			read-only
	STATUS				current
	DESCRIPTION
			"This is the total outside number of dns requests/sec"
	::= { vfiEntry 36 }

topNumDNSReqPerSecOut	OBJECT-TYPE
	SYNTAX				Unsigned32
	MAX-ACCESS			read-only
	STATUS				current
	DESCRIPTION
			"This is the top total outside number of dns requests/sec"
	::= { vfiEntry 37 }

numHandledDNSReqOut	OBJECT-TYPE
	SYNTAX				Counter64
	MAX-ACCESS			read-only
	STATUS				current
	DESCRIPTION
			"This is the total outside number of handled dns requests"
	::= { vfiEntry 38 }

numDNSReqPerSecIn		OBJECT-TYPE
	SYNTAX				Unsigned32
	MAX-ACCESS			read-only
	STATUS				current
	DESCRIPTION
			"This is the total inside number of dns requests/sec"
	::= { vfiEntry 39 }

topNumDNSReqPerSecIn	OBJECT-TYPE
	SYNTAX				Unsigned32
	MAX-ACCESS			read-only
	STATUS				current
	DESCRIPTION
			"This is the top total inside number of dns requests/sec"
	::= { vfiEntry 40 }

numHandledDNSReqIn	OBJECT-TYPE
	SYNTAX				Counter64
	MAX-ACCESS			read-only
	STATUS				current
	DESCRIPTION
			"This is the total inside number of handled dns requests"
	::= { vfiEntry 41 }

--
-- 4) This is the part for the gmac information
--

gmacInfo	OBJECT IDENTIFIER ::= { linkBalancerComponent 2 }


-- GmacIndex contains the semantics of gmacIndex and should be used 
-- for any objects defined in other MIB modules 

GmacIndex ::= TEXTUAL-CONVENTION
	DISPLAY-HINT	"d"
	STATUS 			current
	DESCRIPTION 
				" A unique value, equal or greater than zero, for
				each gmac in the vfi. "
	SYNTAX		Integer32 (0..2147483647)


gmacNumber			OBJECT-TYPE
	SYNTAX      Integer32
	MAX-ACCESS  read-only
	STATUS      current
	DESCRIPTION
           "The number of gmac configured on this system"
	::= { gmacInfo 1 }

-- the gmac table which contains information about link status

gmacTable 			OBJECT-TYPE
	SYNTAX 		SEQUENCE OF GmacEntry
	MAX-ACCESS	not-accessible
	STATUS		current
	DESCRIPTION	
				"This is a list of gmac entries. The number of gmac is 
				given by the value of gmacNumber."
	::= { gmacInfo 2 }
	 
gmacEntry		OBJECT-TYPE
	SYNTAX		GmacEntry
	MAX-ACCESS	not-accessible
	STATUS 		current
	DESCRIPTION	
				" An entry containing gmac information."
	INDEX	{ gmacIndex }
	::= { gmacTable 1 }
	
GmacEntry ::=
	SEQUENCE {
			gmacVfiNumber			INTEGER,
			gmacIndex				GmacIndex,
	 		gmacName				DisplayString,
	 		gmacDescr				DisplayString,
	 		gmacStatus				INTEGER,
	 		gmacMessage				DisplayString,
	 		gmacMode				DisplayString,
			gmacType				DisplayString,
	 		gmacIPAddress			IpAddress,
	 		gmacNetmask				IpAddress,
			gmacPrimaryNetwork		IpAddress,
	 		gmacMtu					Unsigned32,
	 		gmacProbeSource			IpAddress,
	 		gmacProbeSourceType		DisplayString,
	 		gmacProbeDest			IpAddress,
	 		gmacProbeDestInt		Unsigned32,
	 		gmacProbeFailThres		Unsigned32,
	 		gmacProbeFailTimeout	Unsigned32,
	 		gmacProbeSynSeq			Unsigned32,
	 		gmacProbeFail			Unsigned32,
	 		gmacRTT					Unsigned32,
	 		gmacWeight				Unsigned32,
	 		gmacInThreshold			Unsigned32,
	 		gmacOutThreshold		Unsigned32,
	 		gmacSpeedIn				Unsigned32,
	 		gmacSpeedOut			Unsigned32,
	 		gmacSampleInter			Unsigned32,
	 		gmacSampleCount			Unsigned32,
	 		gmacL2No				Unsigned32,
	 		gmacTotalIn				Unsigned32,
	 		gmacTotalOut			Unsigned32,
	 		gmacAvgIn				Unsigned32,
	 		gmacAvgOut				Unsigned32,
	 		gmacUsageIn				Unsigned32,
	 		gmacUsageOut			Unsigned32,
	 		gmacUsageInPercent		Unsigned32,
	 		gmacUsageOutPercent		Unsigned32,
	 		gmacTopSpeedIn			Unsigned32,
	 		gmacTopSpeedOut			Unsigned32,
	 		gmacQosActivated		INTEGER,
	 		gmacBeforeQosUsageIn	Unsigned32,
	 		gmacBeforeQosUsageOut	Unsigned32	
	}

gmacVfiNumber	OBJECT-TYPE
	SYNTAX	INTEGER {
						vfi0(0),
						vfi1(1),
						vfi2(2),
						vfi3(3),
						vfi4(4)
					} 
	MAX-ACCESS	read-only
	STATUS		current
	DESCRIPTION
				"This is vfi number containing this gmac"
	::= { gmacEntry 1 }

gmacIndex	OBJECT-TYPE
	SYNTAX		GmacIndex
	MAX-ACCESS	read-only	
	STATUS		current
	DESCRIPTION
				" A unique value, equal or greater than zero, for
				each gmac in the vfi. "
	::= { gmacEntry 2 }
	
gmacName		OBJECT-TYPE
	SYNTAX		DisplayString (SIZE (0..16))
	MAX-ACCESS	read-only
	STATUS		current
	DESCRIPTION
				"A textual string containing the gmac name"
	::= { gmacEntry 3 }
	
gmacDescr		OBJECT-TYPE
	SYNTAX		DisplayString (SIZE (0..64))
	MAX-ACCESS	read-only
	STATUS		current
	DESCRIPTION
				"A textual string containing a description about 
				the gmac "
	::= { gmacEntry 4 }
	
gmacStatus		OBJECT-TYPE
	SYNTAX INTEGER { 
						enable(1),
						shutdown(2),
						disable(3),
						disableLinkFlap(4),
						failure(5),
						incomplete(6),
						up(7),
						down(8)
			}
	MAX-ACCESS	read-only
	STATUS		current
	DESCRIPTION
				"The desired state of a gmac; up and down states are used for notifications"
	::= { gmacEntry 5 }

gmacMessage		OBJECT-TYPE
	SYNTAX		DisplayString (SIZE (0..128))
	MAX-ACCESS	read-only
	STATUS		current
	DESCRIPTION
				"This is the general information string provided by a gmac"
	::= { gmacEntry 6 }

gmacMode			OBJECT-TYPE
	SYNTAX		DisplayString (SIZE (0..32))
	MAX-ACCESS	read-only
	STATUS		current
	DESCRIPTION
				"This is the mode of the gmac: monomode or multimode"
	::= { gmacEntry 7 }

gmacType			OBJECT-TYPE
	SYNTAX		DisplayString (SIZE (0..32))
	MAX-ACCESS	read-only
	STATUS		current
	DESCRIPTION
				"This is the type of the gmac: monomode or multimode"
	::= { gmacEntry 8 }

gmacIPAddress	OBJECT-TYPE
	SYNTAX		IpAddress
	MAX-ACCESS	read-only
	STATUS		current
	DESCRIPTION
				"This is the IP address of the gmac"
	::= { gmacEntry 9 }
	
gmacNetmask		OBJECT-TYPE
	SYNTAX		IpAddress
	MAX-ACCESS	read-only
	STATUS		current
	DESCRIPTION
				"This is the network mask of the gmac"
	::= { gmacEntry 10 }

gmacPrimaryNetwork	OBJECT-TYPE
	SYNTAX				IpAddress
	MAX-ACCESS			read-only
	STATUS				current
	DESCRIPTION
			"This is the gmac primary network"
	::= { gmacEntry 11 }

gmacMtu			OBJECT-TYPE
	SYNTAX		Unsigned32 
	MAX-ACCESS	read-only
	STATUS		current
	DESCRIPTION
				"This is the mtu size"
	::= { gmacEntry 12 }

gmacProbeSource	OBJECT-TYPE
	SYNTAX			IpAddress 
	MAX-ACCESS		read-only
	STATUS			current
	DESCRIPTION
				"Future Use: This is the gmac probe source ip address"
	::= { gmacEntry 13 }

gmacProbeSourceType	OBJECT-TYPE
	SYNTAX			DisplayString (SIZE (0..255))
	MAX-ACCESS		read-only
	STATUS			current
	DESCRIPTION
				"Future Use: This is the gmac probe source type"
	::= { gmacEntry 14 }

gmacProbeDest			OBJECT-TYPE
	SYNTAX				IpAddress
	MAX-ACCESS			read-only
	STATUS				current
	DESCRIPTION
				"Future Use: This is the gmac probe destination address"
	::= { gmacEntry 15 }

gmacProbeDestInt		OBJECT-TYPE
	SYNTAX				Unsigned32
	MAX-ACCESS			read-only
	STATUS				current
	DESCRIPTION
				"Future Use: This is the gmac probe intervalle"
	::= { gmacEntry 16 }
	
gmacProbeFailThres	OBJECT-TYPE
	SYNTAX				Unsigned32
	MAX-ACCESS			read-only
	STATUS				current
	DESCRIPTION
				"Future Use: This is the gmac probe failure threshold"
	::= { gmacEntry 17 }	

gmacProbeFailTimeout	OBJECT-TYPE
	SYNTAX				Unsigned32
	MAX-ACCESS			read-only
	STATUS				current
	DESCRIPTION
				"Future Use: This is the gmac probe failure timeout"
	::= { gmacEntry 18 }	

gmacProbeSynSeq		OBJECT-TYPE
	SYNTAX				Unsigned32
	MAX-ACCESS			read-only
	STATUS				current
	DESCRIPTION
				"Future Use: This is the gmac number of syn sequence sent"
	::= { gmacEntry 19 }	
	
gmacProbeFail			OBJECT-TYPE
	SYNTAX				Unsigned32
	MAX-ACCESS			read-only
	STATUS				current
	DESCRIPTION
				"Future Use: This is the gmac probe failure"
	::= { gmacEntry 20 }	
	
gmacRTT					OBJECT-TYPE
	SYNTAX				Unsigned32
	MAX-ACCESS			read-only
	STATUS				current
	DESCRIPTION
				"This is the gmac probe round-time-trip"
	::= { gmacEntry 21 }	
	
gmacWeight				OBJECT-TYPE
	SYNTAX				Unsigned32
	MAX-ACCESS			read-only
	STATUS				current
	DESCRIPTION
				"This is the gmac weigth"
	::= { gmacEntry 22 }	

gmacInThreshold		OBJECT-TYPE
	SYNTAX				Unsigned32
	MAX-ACCESS			read-only
	STATUS				current
	DESCRIPTION
				"This is the gmac weigth"
	::= { gmacEntry 23 }	

gmacOutThreshold		OBJECT-TYPE
	SYNTAX				Unsigned32
	MAX-ACCESS			read-only
	STATUS				current
	DESCRIPTION
				"This is the gmac out threshold"
	::= { gmacEntry 24 }

gmacSpeedIn				OBJECT-TYPE
	SYNTAX				Unsigned32
	MAX-ACCESS			read-only
	STATUS				current
	DESCRIPTION
				"This is the gmac speed in"
	::= { gmacEntry 25 }

gmacSpeedOut			OBJECT-TYPE
	SYNTAX				Unsigned32
	MAX-ACCESS			read-only
	STATUS				current
	DESCRIPTION
				"This is the gmac speed out"
	::= { gmacEntry 26 }

gmacSampleInter		OBJECT-TYPE
	SYNTAX				Unsigned32
	MAX-ACCESS			read-only
	STATUS				current
	DESCRIPTION
				"Future Use: This is the gmac sample interval"
	::= { gmacEntry 27 }

gmacSampleCount		OBJECT-TYPE
	SYNTAX				Unsigned32
	MAX-ACCESS			read-only
	STATUS				current
	DESCRIPTION
				"Future Use: This is the gmac sample count"
	::= { gmacEntry 28 }
	
gmacL2No					OBJECT-TYPE
	SYNTAX				Unsigned32
	MAX-ACCESS			read-only
	STATUS				current
	DESCRIPTION
				"Future Use: This is the gmac L2 information"
	::= { gmacEntry 29 }
	
gmacTotalIn			OBJECT-TYPE
	SYNTAX				Unsigned32
	MAX-ACCESS			read-only
	STATUS				current
	DESCRIPTION
			"This is the gmac total In"
	::= { gmacEntry 30 }

gmacTotalOut		OBJECT-TYPE
	SYNTAX				Unsigned32
	MAX-ACCESS			read-only
	STATUS				current
	DESCRIPTION
			"This is the gmac total Out"
	::= { gmacEntry 31 }

gmacAvgIn			OBJECT-TYPE
	SYNTAX				Unsigned32
	MAX-ACCESS			read-only
	STATUS				current
	DESCRIPTION
			"This is the gmac average in"
	::= { gmacEntry 32 }

gmacAvgOut			OBJECT-TYPE
	SYNTAX				Unsigned32
	MAX-ACCESS			read-only
	STATUS				current
	DESCRIPTION
			"This is the gmac average out"
	::= { gmacEntry 33 }
	
gmacUsageIn			OBJECT-TYPE
	SYNTAX				Unsigned32
	MAX-ACCESS			read-only
	STATUS				current
	DESCRIPTION
			"This is the gmac usage in"
	::= { gmacEntry 34 }
	
gmacUsageOut			OBJECT-TYPE
	SYNTAX				Unsigned32
	MAX-ACCESS			read-only
	STATUS				current
	DESCRIPTION
			"This is the gmac usage out"
	::= { gmacEntry 35 }
	
gmacUsageInPercent	OBJECT-TYPE
	SYNTAX				Unsigned32
	MAX-ACCESS			read-only
	STATUS				current
	DESCRIPTION
			"This is the gmac usage in percent"
	::= { gmacEntry 36 }
	
gmacUsageOutPercent	OBJECT-TYPE
	SYNTAX				Unsigned32
	MAX-ACCESS			read-only
	STATUS				current
	DESCRIPTION
			"This is the gmac usage in out percent"
	::= { gmacEntry 37 }
	
gmacTopSpeedIn			OBJECT-TYPE
	SYNTAX				Unsigned32
	MAX-ACCESS			read-only
	STATUS				current
	DESCRIPTION
			"This is the gmac top speed in"
	::= { gmacEntry 38 }
	
gmacTopSpeedOut		OBJECT-TYPE
	SYNTAX				Unsigned32
	MAX-ACCESS			read-only
	STATUS				current
	DESCRIPTION
			"This is the gmac top speed out"
	::= { gmacEntry 39 }
	
gmacQosActivated		OBJECT-TYPE
	SYNTAX				INTEGER {
						desactivated(0),
						activated(1)
						}
	MAX-ACCESS			read-only
	STATUS				current
	DESCRIPTION
			"This is the gmac QOS activation"
	::= { gmacEntry 40 }
	
gmacBeforeQosUsageIn	OBJECT-TYPE
	SYNTAX				Unsigned32
	MAX-ACCESS			read-only
	STATUS				current
	DESCRIPTION
			"This is the gmac QOS usage in"
	::= { gmacEntry 41 }
	
gmacBeforeQosUsageOut		OBJECT-TYPE
	SYNTAX				Unsigned32
	MAX-ACCESS			read-only
	STATUS				current
	DESCRIPTION
			"This is the gmac QOS usage out"
	::= { gmacEntry 42 }

	
---
--- ARP Info ( arp actually just provides notification and arp tables is not accessible )
---

arpInfo		OBJECT IDENTIFIER ::= { linkBalancerComponent 3 }


ArpIndex ::= TEXTUAL-CONVENTION
	DISPLAY-HINT	"d"
	STATUS 			current
	DESCRIPTION 
				" A unique value, equal or greater than zero, for
				each arp entry in the vfi. "
	SYNTAX		Integer32 (0..2147483647)


arpNumber			OBJECT-TYPE
	SYNTAX      Integer32
	MAX-ACCESS  not-accessible
	STATUS      current
	DESCRIPTION
           "The number of arp entries in this system"
	::= { arpInfo 1 }

-- the arp table which contains information about link status

arpTable 		OBJECT-TYPE
	SYNTAX 		SEQUENCE OF ArpEntry
	MAX-ACCESS	not-accessible
	STATUS		current
	DESCRIPTION	
				"This is a list of arp entries. The number of arp is 
				given by the value of arpNumber."
	::= { arpInfo 2 }
	 
arpEntry		OBJECT-TYPE
	SYNTAX		ArpEntry
	MAX-ACCESS	not-accessible
	STATUS 		current
	DESCRIPTION	
				" An entry containing arp information."
	INDEX	{ arpIndex }
	::= { arpTable 1 }

	
ArpEntry ::=
	SEQUENCE {
		arpVfiNumber			INTEGER,
		arpIndex				ArpIndex,
		arpMessage				DisplayString
	}
			

arpVfiNumber	OBJECT-TYPE
	SYNTAX	INTEGER {
						vfi0(0),
						vfi1(1),
						vfi2(2),
						vfi3(3),
						vfi4(4)
					} 
	MAX-ACCESS	read-only
	STATUS		current
	DESCRIPTION
				"For future use : This is vfi number which poll arp devices"
	::= { arpEntry 1 }

arpIndex	OBJECT-TYPE
	SYNTAX		ArpIndex
	MAX-ACCESS	read-only
	STATUS		current
	DESCRIPTION
				"For future use : A unique value, equal or greater than zero, for
				each arp entries in the vfi. "
	::= { arpEntry 2 }

arpMessage		OBJECT-TYPE
	SYNTAX		DisplayString (SIZE (0..128))
	MAX-ACCESS	read-only
	STATUS		current
	DESCRIPTION
				"Used by notification, but not yet implemented in the mib tree:  This is the general information string provided by a arp"
	::= { arpEntry 3 }


---
--- Notification event
---

linkBalancerNotification			OBJECT IDENTIFIER ::= { linkBalancer 2 }

--

gmacNotification			OBJECT IDENTIFIER ::= { linkBalancerNotification 1 }

--

gmacStatusNotInitialiazed	NOTIFICATION-TYPE
    OBJECTS 		{ 	gmacName,
							gmacVfiNumber,
						  	gmacStatus,
						  	gmacMessage }
    STATUS    		current
    DESCRIPTION
        "This notification is sent when you load balancer is unable to initiate gmac X"
    ::= { gmacNotification 1 }

gmacStatusChanged			NOTIFICATION-TYPE
    OBJECTS 		{ 	gmacName,
							gmacVfiNumber,
						  	gmacStatus,
						  	gmacMessage }
    STATUS    		current
    DESCRIPTION
        "This notification is sent when the status of your gmac has changed"
    ::= { gmacNotification 2 }

gmacInSaturated	NOTIFICATION-TYPE
    OBJECTS 		{ 	gmacName,
							gmacVfiNumber,
							gmacUsageInPercent
						  	 }
    STATUS    		current
    DESCRIPTION
        "This notification is sent when a significant consumption of incoming bandwidth was maintained 
			for the last 300 seconds"
    ::= { gmacNotification 3 }

gmacOutSaturated	NOTIFICATION-TYPE
    OBJECTS 		{ 	gmacName,
							gmacVfiNumber,
							gmacUsageOutPercent
						  	 }
    STATUS    		current
    DESCRIPTION
        "This notification is sent when a significant consumption of outgoing bandwidth was maintained 
			for the last 300 seconds"
    ::= { gmacNotification 4 }


--

vfiNotification			OBJECT IDENTIFIER ::= { linkBalancerNotification 2 }

--

arpNotification			OBJECT IDENTIFIER ::= { linkBalancerNotification 3 }

--

arpDeviceNotResponding	NOTIFICATION-TYPE
    OBJECTS 		{ 	arpVfiNumber,
						  	arpMessage }
    STATUS    		current
    DESCRIPTION
        "This notification is sent when Device IP X stopped responding arp request"
    ::= { arpNotification 1 }



-- Define object group conformance

vfiGroups	OBJECT IDENTIFIER ::= { linkBalancerConformance 2 }
gmacGroups 	OBJECT IDENTIFIER ::= { linkBalancerConformance 3 }
arpGroups 	OBJECT IDENTIFIER ::= { linkBalancerConformance 4 }

	 vfiStatsGroup    OBJECT-GROUP
          OBJECTS {
			vfiNumber, vfiIndex, vfiDescr,vfiActivated,	vfiStatus, totThroughputIn, totThroughputOut, topTotThroughputIn,
			topTotThroughputOut,	numPackReceivedOut, numBytesReceivedOut, numPackReceivedIn,	numBytesReceivedIn, numL2Dropped,
			numIPDroppedShun,	numIPDroppedAll, numIPFragNat, numTCPMSSModif, numTCPCheckError, numUDPCheckError, totNumDropProbe,
			totNumDropProbePerSec ,	lastPacketTimeTraver, topPacketTimeTraver, numLiveSessIn, topNumLiveSessIn, samplingIntervalIn,
			numNewSessPerSecIn	,numEndSessPerSecIn,	numHandledSessIn,	numLiveSessOut, topNumLiveSessOut, samplingIntervalOut,
			numNewSessPerSecOut	,numEndSessPerSecOut, numHandledSessOut, numDNSReqPerSecOut, topNumDNSReqPerSecOut,	numHandledDNSReqOut,
			numDNSReqPerSecIn		,topNumDNSReqPerSecIn, numHandledDNSReqIn
       }
          STATUS     current
          DESCRIPTION
              "A collection of objects providing the vfi statistic information"
      ::= { vfiGroups 1 }


	 gmacNetworkGroup    OBJECT-GROUP
          OBJECTS {
             gmacNumber, gmacVfiNumber, gmacIndex,	gmacName, gmacDescr,	gmacStatus,
	 		gmacMessage, gmacMode, gmacIPAddress, gmacNetmask, gmacType,
	 		gmacMtu,	gmacProbeSource, gmacProbeSourceType, gmacProbeDest, gmacProbeDestInt, gmacProbeFailThres, gmacProbeFailTimeout,
	 		gmacProbeSynSeq, gmacProbeFail, gmacRTT, gmacWeight, gmacInThreshold, gmacOutThreshold, gmacSpeedIn, gmacSpeedOut, gmacSampleInter,
	 		gmacSampleCount, gmacL2No, gmacTotalIn, gmacTotalOut,	gmacAvgIn, gmacAvgOut, gmacUsageIn, gmacUsageOut, gmacUsageInPercent,
	 		gmacUsageOutPercent,	gmacTopSpeedIn, gmacTopSpeedOut,	gmacQosActivated, gmacBeforeQosUsageIn,	gmacBeforeQosUsageOut, gmacPrimaryNetwork
       }
          STATUS     current
          DESCRIPTION
              "A collection of objects providing network information"
      ::= { gmacGroups 1 }


		gmacNotificationGroup    NOTIFICATION-GROUP
          NOTIFICATIONS {
             gmacStatusNotInitialiazed, gmacStatusChanged, gmacInSaturated, gmacOutSaturated
       }
          STATUS     current
          DESCRIPTION
              "A collection of objects notification corresponding to gmac changes"
      ::= { gmacGroups 2 }

	
	arpNetworkGroup    OBJECT-GROUP
         OBJECTS { arpVfiNumber, arpIndex, arpMessage
		}
		STATUS     current
        DESCRIPTION
             "A collection of objects providing arp information"
     ::= { arpGroups 1 }

	arpNotificationGroup    NOTIFICATION-GROUP
          NOTIFICATIONS {
             arpDeviceNotResponding
       }
          STATUS     current
          DESCRIPTION
              "A collection of objects notification corresponding to arp changes"
      ::= { arpGroups 2 }


END
