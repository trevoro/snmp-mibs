-- *****************************************************************************
-- Unisphere-Data-Subscriber-CONF
--
-- SNMP Agent Capabilities definitions for the Subscriber MIB.
--
-- Copyright (c) 2001, 2002 Unisphere Networks, Inc.  All rights reserved.
-- *****************************************************************************

Unisphere-Data-Subscriber-CONF DEFINITIONS ::= BEGIN

IMPORTS
    MODULE-IDENTITY
        FROM SNMPv2-SMI
    AGENT-CAPABILITIES
        FROM SNMPv2-CONF
    usDataAgents
        FROM Unisphere-Data-Agents
    usdSubscriberLocalGroup, usdSubscriberLocalGroup2
        FROM Unisphere-Data-SUBSCRIBER-MIB;

usdSubscriberAgent MODULE-IDENTITY
    LAST-UPDATED "200205102017Z"  -- 10-May-02 04:17 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Subscriber component of the
        SNMP agent in the Unisphere Data Routing Switch family of products."
    -- Revision History
    REVISION    "200205102017Z"  -- 10-May-02 04:17 PM EDT  - RX 4.0
    DESCRIPTION
        "Added local authentication support."
    REVISION    "200103301525Z"  -- 30-Mar-01 10:25 AM EST  - RX 3.2
    DESCRIPTION
        "The initial release of this management information module."
    ::= { usDataAgents 45 }


usdSubscriberAgentV1 AGENT-CAPABILITIES
    PRODUCT-RELEASE
        "Version 1 of the Subscriber component of the Unisphere Routing Switch
        SNMP agent.  This version of the Subscriber component was supported in
        the Unisphere RX 3.x system releases."
    STATUS      obsolete
    DESCRIPTION
        "The MIB supported by the SNMP agent for subscriber capabilities in the
        Unisphere Routing Switch.  These capabilities became obsolete when local
        authentication support was added."
    SUPPORTS    Unisphere-Data-SUBSCRIBER-MIB
        INCLUDES  {
           usdSubscriberLocalGroup }
    ::= { usdSubscriberAgent 1 }

usdSubscriberAgentV2 AGENT-CAPABILITIES
    PRODUCT-RELEASE
        "Version 2 of the Subscriber component of the Unisphere Routing Switch
        SNMP agent.  This version of the Subscriber component is supported in
        the Unisphere RX 4.0 and subsequent system releases."
    STATUS      current
    DESCRIPTION
        "The MIB supported by the SNMP agent for subscriber capabilities in the
        Unisphere Routing Switch."
    SUPPORTS    Unisphere-Data-SUBSCRIBER-MIB
        INCLUDES  {
            usdSubscriberLocalGroup2 }
    ::= { usdSubscriberAgent 2 }

END
